Wellfleet-WFMPS-MIB DEFINITIONS ::= BEGIN

-- Created by mdl2asn version 3.1
-- Creation date:


    IMPORTS

      Counter, TimeTicks
        FROM RFC1155-SMI
      OBJECT-TYPE
        FROM RFC-1212
      DisplayString
        FROM RFC1213-MIB
      wfmpsObjects
        FROM Wellfleet-COMMON-MIB;

    --
    --  MPOA Server Objects
    --

    wfmpsEntryTable OBJECT-TYPE
        SYNTAX SEQUENCE OF WfmpsEntry
        ACCESS not-accessible
        STATUS mandatory
        DESCRIPTION
                "MPS base entry table.
                "
        ::= {wfmpsObjects 1}

    wfmpsEntry OBJECT-TYPE
                SYNTAX  WfmpsEntry
                ACCESS  not-accessible
                STATUS  mandatory
                DESCRIPTION
                "An MPS base entry description"
        INDEX   { wfmpsSlot}
	::= { wfmpsEntryTable 1 }

    WfmpsEntry ::= SEQUENCE {
	        wfmpsDelete		INTEGER,
		wfmpsDisable		INTEGER,
		wfmpsSlot		INTEGER,
		wfmpsCct		INTEGER,
		wfmpsCacheIpOverRide    INTEGER,
		wfmpsCacheReverifyTimer	INTEGER,
		wfmpsAddrGenerateMode   INTEGER			
    	}

    wfmpsDelete  OBJECT-TYPE
	        SYNTAX  INTEGER {
                    created(1),
                    deleted(2)
                }
        ACCESS  read-write
        STATUS  mandatory
        DESCRIPTION
                "Indication to create or delete an MPS base Entry
                from the MIB "
        DEFVAL  { created }
        ::= { wfmpsEntry 1 }

    wfmpsDisable OBJECT-TYPE
        SYNTAX  INTEGER {
		enabled(1),
                disabled(2)
        }
	ACCESS  read-write
	STATUS  mandatory
	DESCRIPTION
	"Enables or Disables MPS Subsystem."
	DEFVAL  { enabled }
	::= { wfmpsEntry 2 }

    wfmpsSlot OBJECT-TYPE
        SYNTAX  INTEGER
        ACCESS  read-only
        STATUS      mandatory
        DESCRIPTION
            "The Slot number of the slot on which this MPS is instantiated."
        ::= { wfmpsEntry 3 }

    wfmpsCct	OBJECT-TYPE
        SYNTAX  INTEGER
        ACCESS  read-write
        STATUS  mandatory
        DESCRIPTION
	"This corresponds to the circuit number associated with the
	 ATM Driver "
	::= { wfmpsEntry 4 }   
 

    wfmpsCacheIpOverRide OBJECT-TYPE
	SYNTAX  INTEGER {
		  on(1),
		  off(2)
	        }
        ACCESS  read-write
        STATUS  mandatory
        DESCRIPTION
	" Indicates whether the wfmps defined MPS Egress Cache reverification 
          timer over rides the timer defined by the wfIpInterfaceHostCache.i
	  If on, overide and use the timer defined by wfmpsCacheReverifyTimer
          if off, use the timer defined by wfIpInterfaceHostCache. "
	DEFVAL	{ off }
	::= { wfmpsEntry 5 }

    wfmpsCacheReverifyTimer OBJECT-TYPE
	SYNTAX  INTEGER {
		  timeroff(1),
		  timer120(120),
		  timer180(180),
		  timer240(240),
		  timer300(300),
		  timer600(600),
		  timer900(900),
		  timer1200(1200)
		}
        ACCESS  read-write
        STATUS  mandatory
        DESCRIPTION
	" A range of values to specify the timer value for MPS Egress
	  Cache reverification. This value is of significance, only when
	  wfmpsCacheIpOverRide is turned on."
	DEFVAL { timer120 }
	::= { wfmpsEntry 6 }

   wfmpsAddrGenerateMode OBJECT-TYPE
        SYNTAX      INTEGER {
                        automatic(1),
                        manual(2)
                    }
        ACCESS  read-write
        STATUS      mandatory
        DESCRIPTION
                "Indicates whether this MPS's address should
		 be generated automatically or manually."
	DEFVAL { automatic }
	::= { wfmpsEntry 7 } 


    --
    --  MPOA Server configuration group
    --

    wfmpsConfigTable OBJECT-TYPE
        SYNTAX       SEQUENCE OF WfmpsConfigEntry
        ACCESS   not-accessible
        STATUS       mandatory
        DESCRIPTION
             "The MPOA Server Configuration Table.
              This table represents the configuration information for
              all MPOA Servers which this agent manages."
        ::= { wfmpsObjects 2 }

    wfmpsConfigEntry OBJECT-TYPE
        SYNTAX       WfmpsConfigEntry
        ACCESS   not-accessible
        STATUS       mandatory
        DESCRIPTION
                "MPOA Server Configuration Entry.
                 Each entry contains configuration information
                 for one MPOA Server Control."
        INDEX   { wfmpsCnfSlot,
	          wfmpsCnfIndex }
        ::= { wfmpsConfigTable 1 }

    WfmpsConfigEntry ::=
        SEQUENCE {

            --
            -- Primary config info: Index, mode and address information
            --
            wfmpsCnfDelete		  INTEGER,
	    wfmpsRowStatus                INTEGER,
            wfmpsCnfIndex                 INTEGER,
            wfmpsConfigMode               INTEGER,
            wfmpsCtrlAtmAddr              OCTET STRING,
            -- 
            -- MPS parameters that can be obtained from
            -- the LECS.
            --
            wfmpsKeepAliveTime            INTEGER,     -- MPS-p1
            wfmpsKeepAliveLifeTime        INTEGER,     -- MPS-p2
            -- The Flow-detection Protocols (denoted with MPS-p3)     
            -- are represented in the mpcProtocolsTable.
            wfmpsInitialRetryTime         INTEGER,     -- MPS-p4
            wfmpsRetryTimeMaximum         INTEGER,     -- MPS-p5
            wfmpsGiveupTime               INTEGER,     -- MPS-p6
            wfmpsDefaultHoldingTime       INTEGER,     -- MPS-p7
	    --
	    -- Enterprise specific
	    --
	    wfmpsCnfSlot		  INTEGER,
            wfmpsInitialCacheSize         INTEGER,
	    wfmpsMaxCacheSize		  INTEGER,
	    wfmpsLECSAddress              OCTET STRING,
	    wfmpsDebugMsgLevel		  INTEGER,    
	    wfmpsConfigMpsName		  DisplayString
        }

    wfmpsCnfDelete OBJECT-TYPE
        SYNTAX  INTEGER {
                    created(1),
                    deleted(2)
                }
        ACCESS  read-write
        STATUS  mandatory
        DESCRIPTION
                "Indication to create or delete an MPS Config Entry
                from the MIB "
        DEFVAL  { created }
        ::= { wfmpsConfigEntry 1 }

    wfmpsRowStatus OBJECT-TYPE
        SYNTAX      INTEGER {
                        enabled(1),
                        disabled(2)
                    }
        ACCESS  read-write
        STATUS      mandatory
        DESCRIPTION
                "This object allows creation and deletion of
                 MPOA Servers.

                 Within each conceptual wfmpsConfigTable row,
                 objects which are writable may be modified regardless
                 of the value of wfmpsRowStatus.  It is not
                 necessary to set a row's status to 'notInService'
                 first.

                 A row cannot be created, unless the wfmpsAtmCtrlAddress
                 in this table is unique.

                 When an MPOA Server is created via this object,
                 it will initially have

                     'wfmpsOperStatus' = 'initialState'"
        DEFVAL  { enabled }
        ::= { wfmpsConfigEntry 2 }

    
    wfmpsCnfIndex OBJECT-TYPE
        SYNTAX      INTEGER
        ACCESS      read-only
        STATUS      mandatory
        DESCRIPTION
                "A value which uniquely identifies this conceptual
                 row in the wfmpsConfigTable.  The 'wfmpsNextIndex' object
                 needs to be used to determine the value of this object.

                 A row cannot be added, unless wfmpsCtrlAtmAddr
                 is unique.

                 In the event of an MPS re-initialization, the value
                 of this wfmpsIndex must remain the same.  However, in
                 the event of an agent re-initialization, this value
                 does not need to be preserved."
        ::= { wfmpsConfigEntry 3 }


    wfmpsConfigMode OBJECT-TYPE
        SYNTAX      INTEGER {
                        automatic(1),
                        manual(2)
                    }
        ACCESS  read-write
        STATUS      mandatory
        DESCRIPTION
                "Indicates whether this MPS should auto-configure
                 the next time it is (re-)initialized.
 
                 In automatic(1) mode the LECS is contacted and
                 requests are made for the MPS-p* parameters as
                 indicated by wfmpsConfigMask.
 
                 In manual(2) mode, the values of the configuration 
                 parameters are obtained from the wfmpsConfigTable
                 and the wfmpsProtocolTable."
        DEFVAL { automatic }
        ::= { wfmpsConfigEntry 4 }


   wfmpsCtrlAtmAddr OBJECT-TYPE
        SYNTAX      OCTET STRING (SIZE (20))
        ACCESS  read-write
        STATUS      mandatory
        DESCRIPTION
                "The MPS's Control ATM Address.  There exists one 
                 Control ATM Address per MPS, therefore, the value
                 of this entry is unique within the table."
        ::= { wfmpsConfigEntry 5 }


    wfmpsKeepAliveTime OBJECT-TYPE
        SYNTAX      INTEGER (1..300)
        ACCESS  read-write
        STATUS      mandatory
        DESCRIPTION
                "MPS-p1 Keep-alive time is max interval between
                 the MPS sending MPOA Keep-Alives in seconds."
        DEFVAL { 10 }
        ::= { wfmpsConfigEntry 6 }


    wfmpsKeepAliveLifeTime OBJECT-TYPE
        SYNTAX      INTEGER (3..1000)
        ACCESS  read-write
        STATUS      mandatory
        DESCRIPTION
                "MPS-p2 Keep-Alive Lifetime
                 The length of time an MPC may consider a Keep-Alive 
                 valid in seconds.  This value must be at least 
                 three times the wfmpsKeepAliveTime (MPS-p1)."
        DEFVAL  { 35 }
        ::= { wfmpsConfigEntry 7 }

    wfmpsInitialRetryTime OBJECT-TYPE
        SYNTAX      INTEGER (1..300)
        ACCESS  read-write
        STATUS      mandatory
        DESCRIPTION
                "MPS-p4 is initial value in seconds for the 
                MPOA retry mechanism."
        DEFVAL { 5 }
        ::= { wfmpsConfigEntry 8 }

    wfmpsRetryTimeMaximum OBJECT-TYPE
        SYNTAX      INTEGER (10..300)
        ACCESS  read-write
        STATUS      mandatory
        DESCRIPTION
                "MPS-p5 cumulative max value in seconds 
                for Retry Time (MPS-p4)."
        REFERENCE "Multiprotocol Over ATM.  AF-MPOA-0087.000.
                   Section 4.3 MPOA Retry Mechanism"
        DEFVAL  { 40 }
        ::= { wfmpsConfigEntry 9 }


    wfmpsGiveupTime OBJECT-TYPE
        SYNTAX      INTEGER (5..300)
        ACCESS  read-write
        STATUS      mandatory
        DESCRIPTION
                "MPS-p6 Give Up Time.

                 Minimum time in seconds to wait before giving up on a
                 pending resolution request."
        DEFVAL  { 40 }
        ::= { wfmpsConfigEntry 10 }


    wfmpsDefaultHoldingTime  OBJECT-TYPE
        SYNTAX      INTEGER (1..120)
        ACCESS  read-write
        STATUS      mandatory
        DESCRIPTION
                "MPS-p7 Default Holding Time in minutes.

                 The default Holding Time used in NHRP Resolution Replies.
                 An egress MPS may use local information to determine a
                 more appropriate Holding Time."
        DEFVAL  { 20 }
        ::= { wfmpsConfigEntry 11 }

    wfmpsCnfSlot OBJECT-TYPE
        SYNTAX  INTEGER
        ACCESS  read-only
        STATUS      mandatory
        DESCRIPTION
            "The Slot number of the slot on which this MPS is instantiated."
        ::= { wfmpsConfigEntry 12 }

    wfmpsInitialCacheSize  OBJECT-TYPE
        SYNTAX	    INTEGER (50..500)
        ACCESS  read-write
        STATUS      mandatory
        DESCRIPTION
		"Indicates the amount of memory to allocate 
		 initially to accomadate the cache entries. "
	DEFVAL  { 100 }
        ::= { wfmpsConfigEntry 13 }

    wfmpsMaxCacheSize OBJECT-TYPE
        SYNTAX      INTEGER(100..2000)
        ACCESS  read-write
        STATUS      mandatory
        DESCRIPTION
                "Maximum number of Ingress/Egress cache entries allowed "
        DEFVAL  { 500 }
        ::= { wfmpsConfigEntry 14 }

    wfmpsLECSAddress OBJECT-TYPE
        SYNTAX  OCTET STRING (SIZE (20))
        ACCESS  read-write
        STATUS  mandatory
        DESCRIPTION
        "The LE Config Server Address to be used. If left(or set) to
         NULL_VAL the well-known LECS ATM address will be used."
        ::= { wfmpsConfigEntry 15 }

    wfmpsDebugMsgLevel OBJECT-TYPE
        SYNTAX	INTEGER (0..32)
        ACCESS  read-write
        STATUS      mandatory
        DESCRIPTION
                "Debug Levels - This attribute is used to assign the 
                level of DEBUG message to be logged for each MPS."
			
        DEFVAL	{ 0 }
        ::= { wfmpsConfigEntry 16 }

    wfmpsConfigMpsName OBJECT-TYPE
        SYNTAX  DisplayString
        ACCESS  read-write
        STATUS  mandatory
        DESCRIPTION
                "User name for the MPS"
        ::= { wfmpsConfigEntry 17 }

    --
    --  MPOA Server Actual group
    --

    wfmpsActualTable OBJECT-TYPE
        SYNTAX       SEQUENCE OF WfmpsActualEntry
        ACCESS   not-accessible
        STATUS       mandatory
        DESCRIPTION
                "A read-only table containing identification, status,
                 and operational information about the MPOA
                 Servers this agent manages."
        ::= { wfmpsObjects 3 }

    wfmpsActualEntry OBJECT-TYPE
        SYNTAX       WfmpsActualEntry
        ACCESS   not-accessible
        STATUS       mandatory
        DESCRIPTION
                "An entry in the MPS Actual Table.
                 An entry represents a specific MPOA Server's
                 status and operation information."
        INDEX   { wfmpsActSlot,
		  wfmpsActIndex }
        ::= { wfmpsActualTable 1 }

    WfmpsActualEntry ::=
        SEQUENCE { 
            wfmpsActIndex                       INTEGER,
            wfmpsActualState                    INTEGER,
            wfmpsDiscontinuityTime              TimeTicks,
           
            -- 
            -- Actual values of parameters
            --
            wfmpsActualConfigMode               INTEGER,
           
            wfmpsActualKeepAlive                INTEGER,   -- MPS-p1
            wfmpsActualKeepAliveLifeTime        INTEGER,   -- MPS-p2
            -- The Internetwork-layer Protocols for MPS-p3 are 
            -- represented in the wfmpsProtocolTable.  There is no
            -- status counterpart for them.
            wfmpsActualInitialRetryTime         INTEGER,   -- MPS-p4
            wfmpsActualRetryTimeMaximum         INTEGER,   -- MPS-p5
            wfmpsActualGiveupTime               INTEGER,   -- MPS-p6
            wfmpsActualDefaultHoldingTime       INTEGER,   -- MPS-p7
	          wfmpsActSlot			INTEGER,
            wfmpsActualCtrlAtmAddr              OCTET STRING

        }

    wfmpsActIndex OBJECT-TYPE
        SYNTAX      INTEGER
        ACCESS      read-only
        STATUS      mandatory
        DESCRIPTION
                " This is the mps index "
    ::= { wfmpsActualEntry 1 }


    wfmpsActualState OBJECT-TYPE
        SYNTAX      INTEGER {
                        up(1),	
                        initialState(2),
                        unknown(3),
                        down(4)
                    }
        ACCESS  read-only
        STATUS      mandatory
        DESCRIPTION
                "This object indicates the current operational status
                 of the MPOA Server."
        ::= { wfmpsActualEntry 2 }

    wfmpsDiscontinuityTime OBJECT-TYPE
        SYNTAX      TimeTicks
        ACCESS  read-only
        STATUS      mandatory
        DESCRIPTION
                "The value of sysUpTime on the most recent occasion at
                 which any one or more of this MPS's counters 
                 experienced a discontinuity.  The relevant counters
                 are the specific instances associated with this
                 MPS.  If discontinuities have not occurred since the
                 last re-initialization of the local management subsystem,
                 then this object contains a zero value."
        ::= { wfmpsActualEntry 3 }

    wfmpsActualConfigMode OBJECT-TYPE
        SYNTAX      INTEGER {
                        automatic(1),
                        manual(2)
                            }
        ACCESS  read-only
        STATUS      mandatory
        DESCRIPTION
                "Indicates whether this MPS auto-configured 
                 when it started was last (re-)initialized.
                 In automatic(1) mode the LECS was contacted and
                 all the MPS-p* parameters were downloaded.

                 In manual(2) mode, either the LECS could not be
                 contacted (if wfmpsConfigMode is automatic) or 
                 local over rides are being used (wfmpsConfigMode 
                 is manual).
                         
                 if wfmpsConfigMode is automatic and
                 wfmpsActualConfigMode is manual, then the initial
                 values are the MIB defaults.  As always, any
                 values can be set, however, if wfmpsConfigMode is
                 automatic, those changes will be lost on the 
                 next restart."
                ::= { wfmpsActualEntry 4 }


    wfmpsActualKeepAlive OBJECT-TYPE
        SYNTAX      INTEGER
        ACCESS  read-only
        STATUS      mandatory
        DESCRIPTION
                "The maximum amount of time in seconds this MPS waits 
                between sending MPOA Keep-Alives."
        ::= { wfmpsActualEntry 5 }

    wfmpsActualKeepAliveLifeTime OBJECT-TYPE
        SYNTAX      INTEGER
        ACCESS  read-only
        STATUS      mandatory
        DESCRIPTION
                "The length of time in seconds this MPS 
                considers a Keep-Alive valid."
        ::= { wfmpsActualEntry 6 }

    wfmpsActualInitialRetryTime OBJECT-TYPE
        SYNTAX      INTEGER (1..300)
        ACCESS  read-only
        STATUS      mandatory
        DESCRIPTION
                "The actual initial value in seconds for the MPOA 
                retry mechanism."
        DEFVAL { 5 }
        ::= { wfmpsActualEntry 7 }

    wfmpsActualRetryTimeMaximum OBJECT-TYPE
        SYNTAX      INTEGER (30..300)
        ACCESS  read-only
        STATUS      mandatory
        DESCRIPTION
                "The actual cumulative max value in seconds for Retry Time."
        REFERENCE "Multiprotocol Over ATM.  AF-MPOA-0087.000.
                   Section 4.3 MPOA Retry Mechanism"
        DEFVAL  { 40 }
        ::= { wfmpsActualEntry 8 }

    wfmpsActualGiveupTime OBJECT-TYPE
        SYNTAX      INTEGER (5..300)
        ACCESS  read-only
        STATUS      mandatory
        DESCRIPTION
                "Minimum time in seconds that this MPS waits
                 before giving up on a pending resolution request."
        DEFVAL  { 40 }
        ::= { wfmpsActualEntry 9 }

    wfmpsActualDefaultHoldingTime OBJECT-TYPE
        SYNTAX      INTEGER (1..120)
        ACCESS  read-only
        STATUS      mandatory
        DESCRIPTION
                "The actual Holding Time in minutes used in 
                 NHRP Resolution Replies."
        ::= { wfmpsActualEntry 10 }

    wfmpsActSlot OBJECT-TYPE
        SYNTAX  INTEGER
        ACCESS  read-only
        STATUS      mandatory
        DESCRIPTION
            "The Slot number of the slot on which this MPS is instantiated."
        ::= { wfmpsActualEntry 11 }

   wfmpsActualCtrlAtmAddr OBJECT-TYPE
        SYNTAX      OCTET STRING (SIZE (20))
        ACCESS  read-only
        STATUS      mandatory
        DESCRIPTION
                "The Actual MPS's Control ATM Address. There exists one 
                 Control ATM Address per MPS, therefore, the value
                 of this entry is unique within the table."
        ::= { wfmpsActualEntry 12 }



    --
    --  MPOA Server statistics group
    --

    wfmpsStatisticsTable OBJECT-TYPE
        SYNTAX       SEQUENCE OF WfmpsStatisticsEntry
        ACCESS   not-accessible
        STATUS       mandatory
        DESCRIPTION
                "This table represents the statistical information
                 for the MPSs, which this agent manages."
        ::= { wfmpsObjects 4 }

    wfmpsStatisticsEntry OBJECT-TYPE
        SYNTAX       WfmpsStatisticsEntry
        ACCESS   not-accessible
        STATUS       mandatory
        DESCRIPTION
                "Each row in this table contains statistics
                 for one MPOA server."
        INDEX   { wfmpsStatSlot,wfmpsStatIndex }
        ::= { wfmpsStatisticsTable 1 }

    WfmpsStatisticsEntry ::=
        SEQUENCE {
            wfmpsStatIndex                                  INTEGER,
            wfmpsStatRxMpoaResolveRequests                  Counter,
            wfmpsStatTxMpoaResolveReplyAcks                 Counter,
            wfmpsStatTxMpoaResolveReplyInsufECResources     Counter,
            wfmpsStatTxMpoaResolveReplyInsufSCResources     Counter,
            wfmpsStatTxMpoaResolveReplyInsufEitherResources Counter,
            wfmpsStatTxMpoaResolveReplyUnsupportedInetProt  Counter,
            wfmpsStatTxMpoaResolveReplyUnsupportedMacEncaps Counter,
            wfmpsStatTxMpoaResolveReplyUnspecifiedOther     Counter,
            wfmpsStatTxMpoaResolveReplyOther                Counter,
	    wfmpsStatGiveupTimeExpireds                     Counter,
            wfmpsStatTxMpoaImpRequests                      Counter,
            wfmpsStatRxMpoaImpReplyAcks                     Counter,
            wfmpsStatRxMpoaImpReplyInsufECResources         Counter,
            wfmpsStatRxMpoaImpReplyInsufSCResources         Counter,
            wfmpsStatRxMpoaImpReplyInsufEitherResources     Counter,
            wfmpsStatRxMpoaImpReplyUnsupportedInetProt      Counter,
            wfmpsStatRxMpoaImpReplyUnsupportedMacEncaps     Counter,
            wfmpsStatRxMpoaImpReplyUnspecifiedOther         Counter,
            wfmpsStatRxMpoaImpReplyOther                    Counter,
            wfmpsStatRxMpoaEgressCachePurgeRequests         Counter,
            wfmpsStatTxMpoaEgressCachePurgeReplies          Counter,
            wfmpsStatTxMpoaTriggers                         Counter,
            wfmpsStatTxNhrpResolveRequests                  Counter,
	    wfmpsStatRxNhrpResolveReplies 		    Counter,
	    wfmpsStatRxNhrpResolveRequests                  Counter, 
	    wfmpsStatTxNhrpResolveReplies                   Counter,
	    wfmpsStatSlot				    INTEGER
        }

    wfmpsStatIndex OBJECT-TYPE
        SYNTAX      INTEGER
        ACCESS      read-only
        STATUS      mandatory
        DESCRIPTION
                " This is the mps index "
    ::= { wfmpsStatisticsEntry 1 }

    wfmpsStatRxMpoaResolveRequests OBJECT-TYPE
        SYNTAX      Counter
        ACCESS  read-only
        STATUS      mandatory
        DESCRIPTION
                "The number of MPOA Resolve Requests received
                 by this MPS which are translated to NHRP 
                 resolve requests.
                 Discontinuities in the value of this counter can occur
                 at re-initialization of the management system, and/or 
                 re-initialization of the MPS, and at other times, 
                 as indicated by the value of wfmpsDiscontinuityTime."
        ::= { wfmpsStatisticsEntry 2 }


     wfmpsStatTxMpoaResolveReplyAcks   OBJECT-TYPE
         SYNTAX      Counter
         ACCESS  read-only
         STATUS      mandatory
         DESCRIPTION
                 "The number of MPOA Resolve Replies transmitted by this MPS
                  which contain the MPOA CIE Code of 0x00 - Success.
                  Discontinuities in the value of this counter can occur
                  at re-initialization of the management system, and/or
                  re-initialization of the MPS, and at other times,
                  as indicated by the value of mpsDiscontinuityTime."
     REFERENCE "Multiprotocol Over ATM.  AF-MPOA-0087.000. Page 62."
        ::= { wfmpsStatisticsEntry 3 }

    wfmpsStatTxMpoaResolveReplyInsufECResources  OBJECT-TYPE
    SYNTAX      Counter
    ACCESS  read-only
    STATUS      mandatory
    DESCRIPTION
       "The number of MPOA Resolve Replies transmitted by this MPS
        which contain the MPOA CIE Code of 0x81 - Insufficient
        resources to accept egress cache entry.
        Discontinuities in the value of this counter can occur
        at re-initialization of the management system, and/or
        re-initialization of the MPS, and at other times,
        as indicated by the value of mpsDiscontinuityTime."
     REFERENCE "Multiprotocol Over ATM.  AF-MPOA-0087.000. Page 62."
     ::= { wfmpsStatisticsEntry 4 }

    wfmpsStatTxMpoaResolveReplyInsufSCResources   OBJECT-TYPE
    SYNTAX      Counter
    ACCESS  read-only
    STATUS      mandatory
    DESCRIPTION
       "The number of MPOA Resolve Replies transmitted by this MPS
        which contain the MPOA CIE Code of 0x82 - Insufficent resources
        to accept shortcut.
        Discontinuities in the value of this counter can occur
        at re-initialization of the management system, and/or
        re-initialization of the MPS, and at other times,
        as indicated by the value of mpsDiscontinuityTime."
     REFERENCE "Multiprotocol Over ATM.  AF-MPOA-0087.000. Page 62."
     ::= { wfmpsStatisticsEntry 5 }


   wfmpsStatTxMpoaResolveReplyInsufEitherResources   OBJECT-TYPE
   SYNTAX     Counter
   ACCESS  read-only
   STATUS      mandatory
   DESCRIPTION
      "The number of MPOA Resolve Replies transmitted by this MPS
       which contain the MPOA CIE CODE of 0x83 - Insufficient resources
       to accept either shortcut or egress cache entry.
       Discontinuities in the value of this counter can occur
       at re-initialization of the management system, and/or
       re-initialization of the MPS, and at other times,
       as indicated by the value of mpsDiscontinuityTime."
     REFERENCE "Multiprotocol Over ATM.  AF-MPOA-0087.000. Page 62."
     ::= { wfmpsStatisticsEntry 6 }

   wfmpsStatTxMpoaResolveReplyUnsupportedInetProt   OBJECT-TYPE
   SYNTAX     Counter
   ACCESS  read-only
   STATUS      mandatory
   DESCRIPTION
      "The number of MPOA Resolve Replies transmitted by this MPS
       which contain the MPOA CIE CODE of 0x84 - Unsupported Internetwork
       Layer protocol.
       Discontinuities in the value of this counter can occur
       at re-initialization of the management system, and/or
       re-initialization of the MPS, and at other times,
       as indicated by the value of mpsDiscontinuityTime."
     REFERENCE "Multiprotocol Over ATM.  AF-MPOA-0087.000. Page 62."
     ::= { wfmpsStatisticsEntry 7 }

   wfmpsStatTxMpoaResolveReplyUnsupportedMacEncaps   OBJECT-TYPE
   SYNTAX     Counter
   ACCESS  read-only
   STATUS      mandatory
   DESCRIPTION
      "The number of MPOA Resolve Replies transmitted by this MPS
       which contain the MPOA CIE CODE of 0x85 - Unsupported MAC
       layer encapsulation.
       Discontinuities in the value of this counter can occur
       at re-initialization of the management system, and/or
       re-initialization of the MPS, and at other times,
       as indicated by the value of mpsDiscontinuityTime."
     REFERENCE "Multiprotocol Over ATM.  AF-MPOA-0087.000. Page 62."
     ::= { wfmpsStatisticsEntry 8 }

   wfmpsStatTxMpoaResolveReplyUnspecifiedOther   OBJECT-TYPE
   SYNTAX     Counter
   ACCESS  read-only
   STATUS      mandatory
   DESCRIPTION
      "The number of MPOA Resolve Replies transmitted by this MPS
       which contain the MPOA CIE CODE of 0x88 - Unspecified/Other.
       Discontinuities in the value of this counter can occur
       at re-initialization of the management system, and/or
       re-initialization of the MPS, and at other times,
       as indicated by the value of mpsDiscontinuityTime."
     REFERENCE "Multiprotocol Over ATM.  AF-MPOA-0087.000. Page 62."
     ::= { wfmpsStatisticsEntry 9 }

   wfmpsStatTxMpoaResolveReplyOther   OBJECT-TYPE
   SYNTAX     Counter
   ACCESS  read-only
   STATUS      mandatory
   DESCRIPTION
      "The number of MPOA Resolve Replies transmitted by this MPS
       which are not counted above.  NOTE - this would include
       NHRP errors.
       Discontinuities in the value of this counter can occur
       at re-initialization of the management system, and/or
       re-initialization of the MPS, and at other times,
       as indicated by the value of mpsDiscontinuityTime."
     REFERENCE "Multiprotocol Over ATM.  AF-MPOA-0087.000. Page 62."
     ::= { wfmpsStatisticsEntry 10 }

    wfmpsStatGiveupTimeExpireds OBJECT-TYPE
        SYNTAX      Counter
        ACCESS  read-only
        STATUS      mandatory
        DESCRIPTION
                "The number of times the MPS Give up Time (MPS-p6)
                 has expired while waiting for a reply from a
                 re-originated MPOA resolution request, i.e. a
                 reply for a translated NHRP resolution request.

                 Discontinuities in the value of this counter can occur
                 at re-initialization of the management system, and/or
                 re-initialization of the MPS, and at other times,
                 as indicated by the value of mpsDiscontinuityTime."
        ::= { wfmpsStatisticsEntry 11 }

    wfmpsStatTxMpoaImpRequests OBJECT-TYPE
        SYNTAX      Counter
        ACCESS  read-only
        STATUS      mandatory
        DESCRIPTION
                "The number of MPOA Cache Imposition Requests
                 transmitted by this MPS.

                 Discontinuities in the value of this counter can occur
                 at re-initialization of the management system, and/or
                 re-initialization of the MPS, and at other times,
                 as indicated by the value of mpsDiscontinuityTime."
        ::= { wfmpsStatisticsEntry 12 }

    wfmpsStatRxMpoaImpReplyAcks OBJECT-TYPE
        SYNTAX      Counter
        ACCESS  read-only
        STATUS      mandatory
        DESCRIPTION
                "The number of successful MPOA Cache Imposition Replies
                 received by this MPS which contain an MPOA CIE Code of 0x00,
                 Success.

                 Discontinuities in the value of this counter can occur
                 at re-initialization of the management system, and/or
                 re-initialization of the MPS, and at other times,
                 as indicated by the value of mpsDiscontinuityTime."
        ::= { wfmpsStatisticsEntry 13 }

     wfmpsStatRxMpoaImpReplyInsufECResources   OBJECT-TYPE
       SYNTAX      Counter
       ACCESS  read-only
       STATUS      mandatory
       DESCRIPTION
          "The number of MPOA Cache Imposition Replies received by this
           MPS which contain the MPOA CIE Code of 0x81, Insufficient
           resources to accept egress cache entry.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 14 }


     wfmpsStatRxMpoaImpReplyInsufSCResources   OBJECT-TYPE
       SYNTAX      Counter
       ACCESS  read-only
       STATUS      mandatory
       DESCRIPTION
          "The number of MPOA Cache Imposition Replies received by this
           MPS which contain the MPOA CIE Code of 0x82 - Insufficient
           resources to accept shortcut.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 15 }

     wfmpsStatRxMpoaImpReplyInsufEitherResources   OBJECT-TYPE
       SYNTAX      Counter
       ACCESS  read-only
       STATUS      mandatory
       DESCRIPTION
          "The number of MPOA Cache Imposition Replies received by this
           MPS which contain the MPOA CIE Code of 0x83 - Insufficient
           resources to accept either shortcut or egress cache entry.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 16 }


     wfmpsStatRxMpoaImpReplyUnsupportedInetProt   OBJECT-TYPE
       SYNTAX      Counter
       ACCESS  read-only
       STATUS      mandatory
       DESCRIPTION
          "The number of MPOA Cache Imposition Replies received by this
           MPS which contain the MPOA CIE Code of 0x84 - Unsupported
           Internetwork Layer protocol.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 17 }

     wfmpsStatRxMpoaImpReplyUnsupportedMacEncaps   OBJECT-TYPE
       SYNTAX      Counter
       ACCESS  read-only
       STATUS      mandatory
       DESCRIPTION
          "The number of MPOA Cache Imposition Replies received by this
           MPS which contain the MPOA CIE Code of 0x85 - Unsupported
           MAC layer encapsulation.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 18 }

     wfmpsStatRxMpoaImpReplyUnspecifiedOther   OBJECT-TYPE
       SYNTAX      Counter
       ACCESS  read-only
       STATUS      mandatory
       DESCRIPTION
          "The number of MPOA Cache Imposition Replies received by this
           MPS which contain the MPOA CIE Code of 0x88 - Unspecified/Other.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 19 }

    wfmpsStatRxMpoaImpReplyOther   OBJECT-TYPE
       SYNTAX      Counter
       ACCESS  read-only
       STATUS      mandatory
       DESCRIPTION
          "The number of MPOA Cache Imposition Replies received by this
           MPS which are not counted previously.  NOTE - this would
           include NHRP errors.
           Discontinuities in the value of this counter can occur
           at re-initialization of the management system, and/or
           re-initialization of the MPS, and at other times,
           as indicated by the value of mpsDiscontinuityTime."
       REFERENCE "Multiprotocol Over ATM. AF-MPOA-0087.000. Page 62."
       ::= { wfmpsStatisticsEntry 20 }

    wfmpsStatRxMpoaEgressCachePurgeRequests OBJECT-TYPE
        SYNTAX      Counter
        ACCESS  read-only
        STATUS      mandatory
        DESCRIPTION
                "The number of MPOA Egress Cache Purges Requests
                 received by this MPS.
                 Discontinuities in the value of this counter can occur
                 at re-initialization of the management system, and/or
                 re-initialization of the MPS, and at other times,
                 as indicated by the value of mpsDiscontinuityTime."
         ::= { wfmpsStatisticsEntry 21 }

    wfmpsStatTxMpoaEgressCachePurgeReplies OBJECT-TYPE
        SYNTAX      Counter
        ACCESS  read-only
        STATUS      mandatory
        DESCRIPTION
                "The number of MPOA Egress Cache Purge Replies
                 transmitted by this MPS.
                 Discontinuities in the value of this counter can occur
                 at re-initialization of the management system, and/or
                 re-initialization of the MPS, and at other times,
                 as indicated by the value of mpsDiscontinuityTime."
         ::= { wfmpsStatisticsEntry 22 }

    wfmpsStatTxMpoaTriggers OBJECT-TYPE
        SYNTAX      Counter
        ACCESS  read-only
        STATUS      mandatory
        DESCRIPTION
                "The number of MPOA Trigger messages transmitted by this MPS.
                 Discontinuities in the value of this counter can occur
                 at re-initialization of the management system, and/or
                 re-initialization of the MPS, and at other times,
                 as indicated by the value of mpsDiscontinuityTime."
        REFERENCE "Multiprotocol Over ATM.  AF-MPOA-0087.000.
                   Section 4.7.2.1 MPOA Trigger"
         ::= { wfmpsStatisticsEntry 23 }

    wfmpsStatTxNhrpResolveRequests OBJECT-TYPE
        SYNTAX      Counter
        ACCESS  read-only
        STATUS      mandatory
        DESCRIPTION
		"Total count of MPOA Resolution Requests received by the Ingress
		 MPS which were translated to NHRP Resolution Requests and 
		transmitted to the NHS. Discontinuities in the value of this 
		counter can occur at re-initialization of the management 
		system, and/or re-initialization of the MPS, and at other 
		times, as indicated by the value of mpsDiscontinuityTime."
        REFERENCE "Multiprotocol Over ATM.  AF-MPOA-0087.000.
                   Section 4.7.2.1 MPOA Trigger"
         ::= { wfmpsStatisticsEntry 24 }


    wfmpsStatRxNhrpResolveReplies OBJECT-TYPE
        SYNTAX      Counter
        ACCESS  read-only
        STATUS      mandatory
        DESCRIPTION
		"Total count of NHRP Resolution Replies received by the Ingress.
		 Discontinuities in the value of this counter can occur 
		 at re-initialization of the management system, and/or 
		 re-initialization of the MPS, and at other times, as indicated
		 by the value of mpsDiscontinuityTime."		
        REFERENCE "Multiprotocol Over ATM.  AF-MPOA-0087.000.
                   Section 4.7.2.1 MPOA Trigger"
         ::= { wfmpsStatisticsEntry 25 }


    wfmpsStatRxNhrpResolveRequests OBJECT-TYPE
        SYNTAX      Counter
        ACCESS  read-only
        STATUS      mandatory
        DESCRIPTION

	"Total count of NHRP Resolution Requests received by the Egress MPS 
	 from the NHS. Discontinuities in the value of this counter can occur
	 at re-initialization of the management system, and/or re-initialization
	 of the MPS, and at other times, as indicated by the value of 
	 mpsDiscontinuityTime."
        REFERENCE "Multiprotocol Over ATM.  AF-MPOA-0087.000.
                   Section 4.7.2.1 MPOA Trigger"
         ::= { wfmpsStatisticsEntry 26 }

    wfmpsStatTxNhrpResolveReplies OBJECT-TYPE
        SYNTAX      Counter
        ACCESS  read-only
        STATUS      mandatory
        DESCRIPTION
	"Total count of NHRP Resolution Replies transmitted by the Egress MPS
	 to the NHS. Discontinuities in the value of this counter can occur 
	 at re-initialization of the management system, and/or re-initialization
	 of the MPS, and at other times, as indicated by the value of
	 mpsDiscontinuityTime."
        REFERENCE "Multiprotocol Over ATM.  AF-MPOA-0087.000.
                   Section 4.7.2.1 MPOA Trigger"
         ::= { wfmpsStatisticsEntry 27 }



    wfmpsStatSlot OBJECT-TYPE
        SYNTAX  INTEGER
        ACCESS  read-only
        STATUS      mandatory
        DESCRIPTION
            "The Slot number of the slot on which this MPS is instantiated."
         ::= { wfmpsStatisticsEntry 28 }


    --  MPOA Server Protocol support group
    --

    wfmpsProtocolTable OBJECT-TYPE
        SYNTAX      SEQUENCE OF WfmpsProtocolEntry
        ACCESS  not-accessible
        STATUS      mandatory
        DESCRIPTION
                "List of protocols, per MPS, for which 
                 MPOA resolution is enabled."
        REFERENCE "Multiprotocol Over ATM Version 1.0 (Letter Ballot),
                   Section 4.1.1.1 MPS Parameters"
        ::= { wfmpsObjects 5 }
    
    wfmpsProtocolEntry OBJECT-TYPE
        SYNTAX      WfmpsProtocolEntry
        ACCESS  not-accessible
        STATUS      mandatory
        DESCRIPTION
                "Each row indicates one protocol for which an MPS
                 will perform MPOA resolution.

                 If the corresponding MPS entry in wfmpsStatusTable has
                 wfmpsActualConfigMode set to automatic, and the appropriate 
                 bit in wfmpsActualConfigMask (MPS-p3, bit 3) is set to 1,
                 then values retrieved from the LECS are reflected in 
                 this table and the wfmpsLECSValue object will be (1) true.

                 Also, the user can create rows which 
                 appropriately correspond to the MPS denoted by wfmpsIndex, 
                 and the wfmpsLECSValue object will be set to (2) false.  
                 NOTE - if the LECS does not return information for 
                 the MPS-p3 parameter, or if in manual mode, the user 
                 should create at least one entry for the corresponding MPS.
          
                 Both, LECS and user-created rows may exist in this Table.
                 This means that if the MPS was last re-initialized in
                 in automatic mode (see wfmpsActualConfigMode), the set of 
                 rows is a union of values retreived from the LECS and
                 manually configured."
        INDEX { wfmpsProtSlot,wfmpsProtIndex, wfmpsInternetworkLayerProtocol }
        ::= {wfmpsProtocolTable 1 }
    
    
    WfmpsProtocolEntry ::= SEQUENCE {
	    wfmpsProtocolDelete		     INTEGER,
            wfmpsProtocolRowStatus           INTEGER,
            wfmpsProtIndex                   INTEGER,
            wfmpsInternetworkLayerProtocol   OCTET STRING,  -- MPS-p3
            wfmpsLECSValue                   INTEGER,
	    wfmpsProtSlot		     INTEGER
    }

    wfmpsProtocolDelete OBJECT-TYPE
        SYNTAX  INTEGER {
                    created(1),
                    deleted(2)
                }
        ACCESS  read-write
        STATUS  mandatory
        DESCRIPTION
                "Indication to create or delete an MPS Protocol Entry
                from the MIB "
        DEFVAL  { created }
        ::= { wfmpsProtocolEntry 1 }

    wfmpsProtocolRowStatus OBJECT-TYPE
        SYNTAX      INTEGER {
                        enabled(1),
                        disabled(2)
                    }
        ACCESS  read-write
        STATUS      mandatory
        DESCRIPTION
                "This object allows network managers to enable
                 resolution for the 'wfmpsInternetworkLayerProtocol'."
        DEFVAL  { enabled }
        ::= { wfmpsProtocolEntry 2 }

    wfmpsProtIndex OBJECT-TYPE
        SYNTAX      INTEGER
        ACCESS      read-only
        STATUS      mandatory
        DESCRIPTION
                " This is the mps index "
        ::= { wfmpsProtocolEntry 3 }
    
    wfmpsInternetworkLayerProtocol       OBJECT-TYPE
        SYNTAX      OCTET STRING
        ACCESS      read-only
        STATUS      mandatory
        DESCRIPTION
                "MPS-p3 A protocol on which to perform MPOA resolution."
        ::= { wfmpsProtocolEntry 4 }
    
    wfmpsLECSValue OBJECT-TYPE
        SYNTAX      INTEGER
        ACCESS      read-only
        STATUS      mandatory
        DESCRIPTION
                "This object reflects if the current entry is due to 
                a retrieval from the LECS or not.  If this entry is 
                due to the LECS, then true(1) is the value for this object,
                otherwise, false (2)."
        ::= { wfmpsProtocolEntry 5 }

    wfmpsProtSlot OBJECT-TYPE
        SYNTAX  INTEGER
        ACCESS  read-only
        STATUS      mandatory
        DESCRIPTION
            "The Slot number of the slot on which this MPS is instantiated."
	::= { wfmpsProtocolEntry 6 }

    --
    -- MPOA Server LEC Mapping group
    --

    wfmpsMappingTable        OBJECT-TYPE
        SYNTAX SEQUENCE OF WfmpsMappingEntry
        ACCESS  not-accessible
        STATUS      mandatory
        DESCRIPTION
                "A table mapping the 'lecIndex' values of 
                LANE Clients to the 'wfmpsIndex' values of 
                corresponding MPOA Servers."
        ::= { wfmpsObjects 6 }
    
    wfmpsMappingEntry        OBJECT-TYPE
        SYNTAX  WfmpsMappingEntry
        ACCESS  not-accessible
        STATUS      mandatory
        DESCRIPTION
                "Each row defines one lecIndex --> wfmpsIndex mapping.
                The wfmpsIndex that a lecIndex maps to is not
                necessarily unique. In other words, there can be
                multiple LECs associated with one MPS."
        REFERENCE
            "LAN Emulation Client Management Specification.  
             af-lane-0044-000."
        INDEX { wfmpslecIndex }
            ::= { wfmpsMappingTable 1 }
    
    WfmpsMappingEntry  ::= SEQUENCE {
	wfmpsMappingDelete      INTEGER,
        wfmpsMappingRowStatus   INTEGER,
        wfmpslecIndex           INTEGER,
        wfmpsMapIndex           INTEGER,
	wfmpsMapSlot            INTEGER
    }

    wfmpsMappingDelete OBJECT-TYPE
        SYNTAX  INTEGER {
                    created(1),
                    deleted(2)
                }
        ACCESS  read-write
        STATUS  mandatory
        DESCRIPTION
                "Indication to create or delete an MPS Mapping Entry
                from the MIB "
        DEFVAL  { created }
        ::= { wfmpsMappingEntry 1 }

    wfmpsMappingRowStatus  OBJECT-TYPE
       SYNTAX      INTEGER {
                        enabled(1),
                        disabled(2)
                    }

       ACCESS  read-write
       STATUS      mandatory
       DESCRIPTION
          "Allows creation, enabling/disabling of this row."
	DEFVAL  { enabled }
       ::= { wfmpsMappingEntry 2 }

    wfmpslecIndex OBJECT-TYPE
       SYNTAX      INTEGER
       ACCESS      read-only
       STATUS      mandatory
       DESCRIPTION
          "Mapped lec index. "
       ::= { wfmpsMappingEntry 3 }
    
    wfmpsMapIndex OBJECT-TYPE
        SYNTAX  INTEGER
        ACCESS  read-write
        STATUS      mandatory
        DESCRIPTION
            "The wfmpsMapIndex of the MPOA Server that is associated with
            this LEC.  The wfmpsMapIndex corresponds to the wfmpsIndex."
        ::= { wfmpsMappingEntry 4 }
    
    wfmpsMapSlot OBJECT-TYPE
	SYNTAX  INTEGER
        ACCESS  read-write
        STATUS      mandatory
        DESCRIPTION
	    "The Slot number of the slot on which this MPS is instantiated."
	::= { wfmpsMappingEntry 5 }


    --
    --  MPOA Server Ingress Cache (Address Resolution) group
    --

    wfmpsIngressCacheTable OBJECT-TYPE
        SYNTAX       SEQUENCE OF WfmpsIngressCacheEntry
        ACCESS   not-accessible
        STATUS       mandatory
        DESCRIPTION
              "This table tracks all the Ingress Cache information 
               of the MPSs which this agents manages."
        ::= { wfmpsObjects 7 }


    wfmpsIngressCacheEntry OBJECT-TYPE
        SYNTAX       WfmpsIngressCacheEntry
        ACCESS   not-accessible
        STATUS       mandatory
        DESCRIPTION
             "A entry contains parameters and state variables 
              for a row in a MPS's Ingress Cache."
        INDEX   { wfmpsIngressSlot,	 
		  wfmpsIngressIndex,
		  wfmpsIngressMpcIndex,
                  wfmpsIngressCacheDestInternetworkAddrType,
                  wfmpsIngressCacheDestAddr
                }
        ::= { wfmpsIngressCacheTable 1 }

    WfmpsIngressCacheEntry ::=
        SEQUENCE {
            wfmpsIngressIndex				INTEGER,
            wfmpsIngressMpcIndex			INTEGER,
            wfmpsIngressCacheDestInternetworkAddrType   INTEGER,
            wfmpsIngressCacheDestAddr                 	OCTET STRING,
            wfmpsIngressCachePrefixLen                  INTEGER,
            wfmpsIngressCacheState			INTEGER,
            wfmpsIngressCacheSrcInternetworkAddrType   	INTEGER,
            wfmpsIngressCacheSrcAddr                 	OCTET STRING,
            wfmpsIngressCacheSourceMpcAtmAddr           OCTET STRING,
	    wfmpsIngressCacheResolvedAtmAddr            OCTET STRING,
            wfmpsIngressCacheHoldTime                   INTEGER,
            wfmpsIngressCacheMpoaRequestId              INTEGER, 
            wfmpsIngressCacheNhrpRequestId              INTEGER,
            wfmpsIngressCacheServiceCategory            INTEGER,
	    wfmpsIngressSlot				INTEGER 
        }

    wfmpsIngressIndex OBJECT-TYPE
        SYNTAX      INTEGER
        ACCESS      read-only
        STATUS      mandatory
        DESCRIPTION
                " This is the mps index "
	::= { wfmpsIngressCacheEntry 1 }

    wfmpsIngressMpcIndex OBJECT-TYPE
        SYNTAX      INTEGER
        ACCESS      read-only
        STATUS      mandatory
        DESCRIPTION
                " This is the mpc index "
	::= { wfmpsIngressCacheEntry 2 }


    wfmpsIngressCacheDestInternetworkAddrType OBJECT-TYPE
        SYNTAX      INTEGER
        ACCESS  read-only
        STATUS      mandatory
        DESCRIPTION
                "The type of internetwork layer address of the 
                 Destination Address."

        ::= { wfmpsIngressCacheEntry 3 }

    wfmpsIngressCacheDestAddr OBJECT-TYPE
        SYNTAX      OCTET STRING (SIZE (4))
        ACCESS  read-only
        STATUS      mandatory
        DESCRIPTION
                "The Ingress MPS Destination Internetwork Layer Address."
        ::= { wfmpsIngressCacheEntry 4 }

    wfmpsIngressCachePrefixLen OBJECT-TYPE
        SYNTAX      INTEGER
        ACCESS  read-only
        STATUS      mandatory
        DESCRIPTION
                "The Prefix Length of the wfmpsIngressCacheDestAddr."
        ::= { wfmpsIngressCacheEntry 5 }

    wfmpsIngressCacheState OBJECT-TYPE
        SYNTAX      INTEGER {
                     -- TBD
                     active(1),
                     inActive(2)
                    }
        ACCESS  read-only
        STATUS      mandatory
        DESCRIPTION
                "The state of this entry."
        ::= { wfmpsIngressCacheEntry 6 }

    wfmpsIngressCacheSrcInternetworkAddrType OBJECT-TYPE
        SYNTAX      INTEGER
        ACCESS  read-only
        STATUS      mandatory
        DESCRIPTION
                "The type of internetwork layer address of the 
                 Source Address."

        ::= { wfmpsIngressCacheEntry 7 }

    wfmpsIngressCacheSrcAddr OBJECT-TYPE
        SYNTAX      OCTET STRING
        ACCESS  read-only
        STATUS      mandatory
        DESCRIPTION
                "The Ingress MPS Source Internetwork Layer Address."
        ::= { wfmpsIngressCacheEntry 8 }

    wfmpsIngressCacheSourceMpcAtmAddr OBJECT-TYPE
        SYNTAX      OCTET STRING
        ACCESS  read-only
        STATUS      mandatory
        DESCRIPTION
                "The ATM Adress from the source of this MPOA request.  
                 In other words, the Ingress MPC's Control Atm Address."
        ::= { wfmpsIngressCacheEntry 9 }

    wfmpsIngressCacheResolvedAtmAddr OBJECT-TYPE
        SYNTAX      OCTET STRING
        ACCESS  read-only
        STATUS      mandatory
        DESCRIPTION
                "The ATM Adress which has been resolved by an Egress MPC."
        ::= { wfmpsIngressCacheEntry 10 }

    wfmpsIngressCacheHoldTime OBJECT-TYPE
        SYNTAX      INTEGER
        ACCESS  read-only
        STATUS      mandatory
        DESCRIPTION
                "Time interval that this value is valid."
        ::= { wfmpsIngressCacheEntry 11 }

    wfmpsIngressCacheMpoaRequestId OBJECT-TYPE
        SYNTAX      INTEGER
        ACCESS  read-only
        STATUS      mandatory
        DESCRIPTION
                "The request ID contained in the MPOA resolution request
                 from the local Ingress MPC."
        ::= { wfmpsIngressCacheEntry 12 }

    wfmpsIngressCacheNhrpRequestId OBJECT-TYPE
        SYNTAX      INTEGER
        ACCESS  read-only
        STATUS      mandatory
        DESCRIPTION
                "The request ID which this MPS generates to identify the 
                 NHRP resolution request."
        ::= { wfmpsIngressCacheEntry 13 }


    wfmpsIngressCacheServiceCategory OBJECT-TYPE
        SYNTAX      INTEGER
        ACCESS  read-only
        STATUS      mandatory
        DESCRIPTION
                "The request ID which this MPS generates to identify the 
                 NHRP resolution request."
        ::= { wfmpsIngressCacheEntry 14 }


    wfmpsIngressSlot OBJECT-TYPE
        SYNTAX  INTEGER
        ACCESS  read-only
        STATUS      mandatory
        DESCRIPTION
            "The Slot number of the slot on which this MPS is instantiated."
        ::= { wfmpsIngressCacheEntry 15 }

    --
    --  MPOA Server Egress Cache (Impositions) group
    --

    wfmpsEgressCacheTable OBJECT-TYPE
        SYNTAX       SEQUENCE OF WfmpsEgressCacheEntry
        ACCESS   not-accessible
        STATUS       mandatory
        DESCRIPTION
              "This table contains information regarding the
               Egress MPOA Server Cache Table."
        ::= { wfmpsObjects 8 }

    wfmpsEgressCacheEntry OBJECT-TYPE
        SYNTAX       WfmpsEgressCacheEntry
        ACCESS   not-accessible
        STATUS       mandatory
        DESCRIPTION
              "An entry represents an entry in the MPS's Egress
               cache Table which keeps track of the state of the
               impositions."
        INDEX   { wfmpsEgressSlot,
		  wfmpsEgressIndex,
                  wfmpsEgressMpcIndex,
                  wfmpsEgressCacheId
                }
        ::= { wfmpsEgressCacheTable 1 }

    WfmpsEgressCacheEntry ::=
        SEQUENCE {
	    wfmpsEgressIndex			 INTEGER,
            wfmpsEgressMpcIndex			 INTEGER,
            wfmpsEgressCacheId                   INTEGER,
            wfmpsEgressCacheHoldTime             INTEGER,
            wfmpsEgressCacheState                INTEGER, 
            wfmpsEgressCacheDataLinkHeader       OCTET STRING,
            wfmpsEgressCacheElanId               INTEGER,
            wfmpsEgressCacheSourceClientAtmAddr  OCTET STRING,
            wfmpsEgressCacheNhrpRequestId        INTEGER, 
            wfmpsEgressCacheMpoaRequestId        INTEGER,
            wfmpsEgressCacheServiceCategory      INTEGER,
	    wfmpsEgressCacheNextHopInternetworkAddrType  INTEGER,
	    wfmpsEgressCacheNextHopAddr		 OCTET STRING,
	    wfmpsEgressSlot		         INTEGER
        }

    wfmpsEgressIndex OBJECT-TYPE
        SYNTAX      INTEGER
        ACCESS      read-only
        STATUS      mandatory
        DESCRIPTION
                " This is the mps index "
        ::= { wfmpsEgressCacheEntry 1 }

    wfmpsEgressMpcIndex OBJECT-TYPE
        SYNTAX      INTEGER
        ACCESS      read-only
        STATUS      mandatory
        DESCRIPTION
                " This is the mpc index "
        ::= { wfmpsEgressCacheEntry 2 }

    wfmpsEgressCacheId OBJECT-TYPE
        SYNTAX      INTEGER
        ACCESS  read-only
        STATUS      mandatory
        DESCRIPTION
                "The id which identifies this cache entry."
        ::= { wfmpsEgressCacheEntry 3 }

    wfmpsEgressCacheHoldTime OBJECT-TYPE
        SYNTAX      INTEGER
        ACCESS  read-only
        STATUS      mandatory
        DESCRIPTION
                "Time interval that this value is valid."
        ::= { wfmpsEgressCacheEntry 4 }

    wfmpsEgressCacheState OBJECT-TYPE
        SYNTAX      INTEGER {
                    -- TBD
                    active(1),
                    inActive(2)
                    }
        ACCESS  read-only
        STATUS      mandatory
        DESCRIPTION
                "The state of the entry."
        REFERENCE "Multiprotocol Over ATM.  AF-MPOA-0087.000.
                   Appendix I.4 Egress MPS Control State MAchine."
        ::= { wfmpsEgressCacheEntry 5 }

    wfmpsEgressCacheDataLinkHeader OBJECT-TYPE
        SYNTAX      OCTET STRING
        ACCESS  read-only
        STATUS      mandatory
        DESCRIPTION
                "Data-Link Layer Header."
        ::= { wfmpsEgressCacheEntry 6 }


    wfmpsEgressCacheElanId OBJECT-TYPE
        SYNTAX      INTEGER
        ACCESS  read-only
        STATUS      mandatory
        DESCRIPTION
                "The  elan id that this Cache Imposition is sent on"
        ::= { wfmpsEgressCacheEntry 7 }


    wfmpsEgressCacheSourceClientAtmAddr OBJECT-TYPE
        SYNTAX      OCTET STRING
        ACCESS  read-only
        STATUS      mandatory
        DESCRIPTION
		"The Ingress NHC's Atm Address used in the original 
		cache imposition."
	REFERENCE "Multiprotocol Over ATM. AF-MPOA-0087.000. Page 45."
        ::= { wfmpsEgressCacheEntry 8 }

    wfmpsEgressCacheNhrpRequestId OBJECT-TYPE
        SYNTAX      INTEGER
        ACCESS  read-only
        STATUS      mandatory
        DESCRIPTION
                "The request id from the original NHRP Resolution Request, 
                 may be only useful in the Resolving State."
        ::= { wfmpsEgressCacheEntry 9 }

    wfmpsEgressCacheMpoaRequestId OBJECT-TYPE
        SYNTAX      INTEGER
        ACCESS  read-only
        STATUS      mandatory
        DESCRIPTION
                "The new request id which is generated for this imposition's
                 request, may be only useful in the Resolving State."
        ::= { wfmpsEgressCacheEntry 10 }

    wfmpsEgressCacheServiceCategory OBJECT-TYPE
        SYNTAX      INTEGER
        ACCESS  read-only
        STATUS      mandatory
        DESCRIPTION
	"The service categories supported for this shortcut" 
	REFERENCE "Lane V2 LUNI TLVs"
        ::= { wfmpsEgressCacheEntry 11 }

    wfmpsEgressCacheNextHopInternetworkAddrType OBJECT-TYPE
        SYNTAX      INTEGER
        ACCESS  read-only
        STATUS      mandatory
        DESCRIPTION
		"The NextHop protocol address type."
        ::= { wfmpsEgressCacheEntry 12 }

    wfmpsEgressCacheNextHopAddr OBJECT-TYPE
        SYNTAX      OCTET STRING
        ACCESS  read-only
        STATUS      mandatory
        DESCRIPTION
		"The NextHop protocol address."
        ::= { wfmpsEgressCacheEntry 13 }


    wfmpsEgressSlot OBJECT-TYPE
        SYNTAX      INTEGER
        ACCESS  read-only
        STATUS      mandatory
        DESCRIPTION
            "The Slot number of the slot on which this MPS is instantiated."
        ::= { wfmpsEgressCacheEntry 14 }


    --
    -- MPOA Server MPC Information  group
    --

    wfmpsMpcTable        OBJECT-TYPE
        SYNTAX SEQUENCE OF WfmpsMpcEntry
        ACCESS  not-accessible
        STATUS      mandatory
        DESCRIPTION
                "A table contains information about the MPCs that 
		 these MPSs know about."
        ::= { wfmpsObjects 9 }
    
    wfmpsMpcEntry        OBJECT-TYPE
        SYNTAX  WfmpsMpcEntry
        ACCESS  not-accessible
        STATUS      mandatory
        DESCRIPTION
                "Each row defines one MPC identified by an index 
		and its control ATM address."
        INDEX   { wfmpsMpcSlot,
		  wfmpsMpsIndex,
                  wfmpsMpcIndex
                }
        ::= { wfmpsMpcTable 1 }
	
    WfmpsMpcEntry ::=
        SEQUENCE {
        wfmpsMpsIndex           INTEGER,
        wfmpsMpcIndex           INTEGER,
        wfmpsMpcCtrlAtmAddr     OCTET STRING,
	wfmpsMpcSlot            INTEGER
    }

    wfmpsMpsIndex OBJECT-TYPE
       SYNTAX      INTEGER
       ACCESS      read-only
       STATUS      mandatory
       DESCRIPTION
          "Local Index (instance )of the Mps. "
       ::= { wfmpsMpcEntry 1 }
    
    wfmpsMpcIndex OBJECT-TYPE
        SYNTAX  INTEGER
        ACCESS  read-write
        STATUS      mandatory
        DESCRIPTION
           "The local index for the mpc represented by this entry"
         ::= { wfmpsMpcEntry 2 }

    wfmpsMpcCtrlAtmAddr OBJECT-TYPE
        SYNTAX  OCTET STRING
        ACCESS  read-write
        STATUS      mandatory
        DESCRIPTION
           "MPC control ATM address."
         ::= { wfmpsMpcEntry 3 }
    
    wfmpsMpcSlot OBJECT-TYPE
	SYNTAX  INTEGER
        ACCESS  read-write
        STATUS      mandatory
        DESCRIPTION
	    "The Slot number of the slot on which this MPS is instantiated."
	::= { wfmpsMpcEntry 4 }



    --
    --  MPOA Server Debug Message Creation and dispatch method----
    --

  wfmpsDebugTable OBJECT-TYPE
        SYNTAX       SEQUENCE OF WfmpsDebugEntry
        ACCESS   not-accessible
        STATUS       mandatory
        DESCRIPTION
             "The MPOA Server Debug Message Creation Table.
              This table represents the attributes necessary to send a message to
	      the approprieate MPS gates for debug purpose."
        ::= { wfmpsObjects 10 }

    wfmpsDebugEntry OBJECT-TYPE
        SYNTAX       WfmpsDebugEntry
        ACCESS   not-accessible
        STATUS       mandatory
        DESCRIPTION
                "MPOA Server Debugd Entry.
                 Each entry contains identity of the MPS being Debugged."
        INDEX   { wfmpsDebugSlot}
        ::= { wfmpsDebugTable 1 }

    WfmpsDebugEntry ::=
        SEQUENCE {

            --
            -- Primary config info: Index, mode and address information
            --
            wfmpsDebugSlot		  INTEGER,
	    wfmpsDebugIndex               INTEGER,
            wfmpsDebugDestGid             INTEGER,
            wfmpsDebugMsg	          OCTET STRING,
            wfmpsDebugSendEnable          INTEGER,
            wfmpsDebugSignalNum           INTEGER,
            wfmpsDebugSignalSendEnable    INTEGER
        }

  
    wfmpsDebugSlot OBJECT-TYPE
        SYNTAX  INTEGER
        ACCESS  read-only
        STATUS      mandatory
        DESCRIPTION
            "The Slot number of the slot on which this MPS is ainstantiated."
        ::= { wfmpsDebugEntry 1 }



    wfmpsDebugIndex OBJECT-TYPE
        SYNTAX      INTEGER
        ACCESS      read-write
        STATUS      mandatory
        DESCRIPTION
                "A value which uniquely identifies an mps being debugged."
        ::= { wfmpsDebugEntry 2 }

    wfmpsDebugDestGid  OBJECT-TYPE
	SYNTAX  INTEGER {
		  mpsProc(1),
		  mpsCtrl(2),
		  mpsVCC(3),
		  mpsMstr(4)
		}
        ACCESS  read-write
    
    STATUS  mandatory
        DESCRIPTION
	" Send the message to the gate specified."
	DEFVAL { mpsProc}
	::= { wfmpsDebugEntry 3 }


    wfmpsDebugMsg OBJECT-TYPE
	SYNTAX  OCTET STRING
        ACCESS  read-write
        STATUS  mandatory
        DESCRIPTION
        "Send the gived message to DestId."
	::= { wfmpsDebugEntry 4 }


    wfmpsDebugSendEnable  OBJECT-TYPE
	SYNTAX  INTEGER {
		enabled(1),
                disabled(2)
		}
        ACCESS  read-write
        STATUS  mandatory
        DESCRIPTION
	"Send the message if enabled."
	DEFVAL { disabled}
	::= { wfmpsDebugEntry 5 }


    wfmpsDebugSignalNum OBJECT-TYPE
	SYNTAX  INTEGER
        ACCESS  read-write
        STATUS  mandatory
        DESCRIPTION
        "Send the given signal to DestId."
	::= { wfmpsDebugEntry 6 }

    wfmpsDebugSignalSendEnable  OBJECT-TYPE
	SYNTAX  INTEGER {
		enabled(1),
                disabled(2)
		}
        ACCESS  read-write
        STATUS  mandatory
        DESCRIPTION
	"Send the Signal if enabled."
	DEFVAL { disabled}
	::= { wfmpsDebugEntry 7 }


END
