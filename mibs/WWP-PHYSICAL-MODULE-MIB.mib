--
 -- WWP-PHYSICAL-MODULE-MIB.my
 --
 --

 WWP-PHYSICAL-MODULE-MIB DEFINITIONS ::= BEGIN

 IMPORTS 		
   IpAddress, Integer32, Unsigned32, OBJECT-TYPE, MODULE-IDENTITY		
	    FROM SNMPv2-SMI			
   DisplayString, MacAddress, DateAndTime, TEXTUAL-CONVENTION			
	    FROM SNMPv2-TC						
   wwpModules			
	    FROM WWP-SMI;
	
	
 wwpPhyModuleMIB MODULE-IDENTITY
	    LAST-UPDATED "200104031700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "The MIB module for the WWP Physical Module specific information. This MIB 
                    provide the attributes such as Serial Number, App Ver etc for the physical module."                  
	    REVISION    "200104031700Z"
	    DESCRIPTION
		    "Initial creation."
	    ::= { wwpModules 3 }

 --
 -- Node definitions
 --
	
 wwpPhyModuleMIBObjects OBJECT IDENTIFIER ::= { wwpPhyModuleMIB 1 }
 

 -- Module Info
 --
 wwpPhyModuleInfo OBJECT IDENTIFIER ::= { wwpPhyModuleMIBObjects 1 }

 -- Module Reboot Attr
 --
 wwpPhyModuleRebootAttr OBJECT IDENTIFIER ::= { wwpPhyModuleMIBObjects 2 }


 -- Notifications 
  
 wwpPhyModuleMIBNotificationPrefix  OBJECT IDENTIFIER ::= { wwpPhyModuleMIB 2 } 
 wwpPhyModuleMIBNotifications       OBJECT IDENTIFIER ::=  
                       { wwpPhyModuleMIBNotificationPrefix 0 }

 -- Conformance information 
 
 wwpPhyModuleMIBConformance OBJECT IDENTIFIER ::= { wwpPhyModuleMIB 3 } 
 wwpPhyModuleMIBCompliances OBJECT IDENTIFIER ::= { wwpPhyModuleMIBConformance 1 } 		
 wwpPhyModuleMIBGroups      OBJECT IDENTIFIER ::= { wwpPhyModuleMIBConformance 2 }

 --
 -- whenever we start supporting the entity MIB , we can add the index
 -- entPhysicalIndex from the entity MIB to this MIB and define a table
 -- instead of the scalar variables
 -- 				
 		
 wwpPhyModSerialNum OBJECT-TYPE
     SYNTAX      DisplayString (SIZE (0..127))
     MAX-ACCESS  read-only
     STATUS      current
     DESCRIPTION
	     "Serial number of the box, represented as a string."
     ::= { wwpPhyModuleInfo 1 }
				
 wwpPhyModBoardRevision OBJECT-TYPE
     SYNTAX      DisplayString (SIZE (0..127))
     MAX-ACCESS  read-only
     STATUS      current
     DESCRIPTION
	     "Module board hardware revision represented as a string"
     ::= { wwpPhyModuleInfo 2 }
		
 wwpPhyModNumResets OBJECT-TYPE
     SYNTAX       Unsigned32 (0..2147483647)
     MAX-ACCESS   read-only
     STATUS       current
     DESCRIPTION
	     "This object defines the number of times that the module has
	      been restarted."
     ::= { wwpPhyModuleInfo 3 }
		
 wwpPhyModFwVer  OBJECT-TYPE
     SYNTAX       DisplayString
     MAX-ACCESS   read-only
     STATUS       current
     DESCRIPTION
	     "The FW boot loader version number."
     ::= { wwpPhyModuleInfo 4 }
		

 wwpPhyModAppVer OBJECT-TYPE
     SYNTAX       DisplayString (SIZE (0..127))
     MAX-ACCESS   read-only
     STATUS       current
     DESCRIPTION
	     "The application software version number."
     ::= { wwpPhyModuleInfo 5 }
		
 wwpPhyModPostResults OBJECT-TYPE
     SYNTAX       DisplayString
     MAX-ACCESS   read-only
     STATUS       current
     DESCRIPTION
	     "The test result string generated by the POST tests."
     ::= { wwpPhyModuleInfo 6 }
		
 wwpPhyModPostCode OBJECT-TYPE
     SYNTAX      Unsigned32 (0..2147483647)
     MAX-ACCESS  read-only
     STATUS      current
     DESCRIPTION
	     "The result code returned by the device POST test."
     ::= { wwpPhyModuleInfo 7 }
		
 wwpPhyModBootLoaderVer OBJECT-TYPE
     SYNTAX       DisplayString
     MAX-ACCESS   read-only
     STATUS       current
     DESCRIPTION
   	     "The boot loader version of the physical Module."
     ::= { wwpPhyModuleInfo 8 }
		
 wwpPhyModMfgDate OBJECT-TYPE
     SYNTAX      DateAndTime
     MAX-ACCESS  read-only
     STATUS      current
     DESCRIPTION	
	     "The date that the physical Module was manufactured."
     ::= { wwpPhyModuleInfo 9 }
		
 wwpPhyModBoardType OBJECT-TYPE
     SYNTAX       DisplayString
     MAX-ACCESS   read-only
     STATUS       current
     DESCRIPTION
	     "Board type"
     ::= { wwpPhyModuleInfo 10 }
		
 wwpPhyModMktDesc OBJECT-TYPE
     SYNTAX      OCTET STRING (SIZE (0..127))
     MAX-ACCESS  read-only
     STATUS      current
     DESCRIPTION
	     "Displays Marketing description string."
     ::= { wwpPhyModuleInfo 11 }

 wwpPhyModRebootOperation OBJECT-TYPE
     SYNTAX       INTEGER {
		       none(0),
		       reboot(1),
		       rebootReinit(2),
                       rebootDefault(3)
	          }
     MAX-ACCESS   read-write
     STATUS current
     DESCRIPTION
	     "Writing one of the specified values to this field causes
	      the specified type of reboot to occur.  
				
	      none is the value returned when this leaf is queried.
	      writing this value to the leaf will have no effect.
				
	      reboot causes the sytsem to reboot and restart using
	      its current configuration.
				
	      rebootReinit causes the module to remove all its
	      configuration and application files and get new
	      files and configuration via bootp/dhcp.

	      rebootDefault will reset the system to factory defaults.
              
	      If the system doesn't support any of these reboot option, it should
	      return error while trying to set this object to 
	      specific option."							
      DEFVAL { none }
      ::= { wwpPhyModuleRebootAttr 1 }
		
 wwpPhyModLastRebootTime OBJECT-TYPE
     SYNTAX       DateAndTime
     MAX-ACCESS   read-only
     STATUS       current
     DESCRIPTION 
	     "Indicates the date and time the module last rebooted itself."
     ::= { wwpPhyModuleRebootAttr 2 }
		
 wwpPhyModLastRebootReason OBJECT-TYPE
      SYNTAX            INTEGER {
			     hostRequest(1),
			     pwrFail(2),
                             unknown(3),
			     softwareForced(4)
			}
      MAX-ACCESS        read-only
      STATUS            current
      DESCRIPTION
	      "Indicates the reason for the last reboot."
      ::= { wwpPhyModuleRebootAttr 3 }
		
 				
 END

 --
 -- WWP-PHYSICAL-MODULE-MIB.my
 --
