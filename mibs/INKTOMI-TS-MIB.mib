-- This file is automatically generated from inktomi-ts-mib.tcl
-- DO NOT make changes here

-- The OBJECT-TYPE definitions with "Proxyvar: ..." text in their
-- descriptions are automatically mapped to Traffic Manager stubs.
-- This is done by mosy-to-mgrstubs.pl.

INKTOMI-TS-MIB DEFINITIONS ::= BEGIN

IMPORTS
				enterprises FROM RFC1155-SMI
     OBJECT-IDENTITY, MODULE-IDENTITY, OBJECT-TYPE, NOTIFICATION-TYPE,
    Gauge32, Integer32, Counter32, Counter64
FROM SNMPv2-SMI;
--     TruthValue, DisplayString, TestAndIncr, TimeStamp
-- FROM SNMPv2-TC
--      MODULE-COMPLIANCE, OBJECT-GROUP
-- FROM SNMPv2-CONF
--     inktomiModules, inktomiTSObjs, inktomiTSEvents
--FROM INKTOMI-GLOBAL-REG;

	vendorInktomi 	   	OBJECT IDENTIFIER ::= { enterprises 1967 }
	inktomiReg 	   	OBJECT IDENTIFIER ::= { vendorInktomi 1 }
	inktomiModules 	   	OBJECT IDENTIFIER ::= { inktomiReg 1 }
	inktomiGlobalRegModule 	   	OBJECT IDENTIFIER ::= { inktomiModules 1 }
	inktomiGeneric    	OBJECT IDENTIFIER ::= { vendorInktomi 2 }
	inktomiProducts 	   	OBJECT IDENTIFIER ::= { vendorInktomi 3 }
    inktomiExpr    	OBJECT IDENTIFIER ::= { vendorInktomi 6 }
    inktomiTSMIBs  	OBJECT IDENTIFIER ::= { inktomiProducts 1 }
    inktomiTSConformance 	OBJECT IDENTIFIER ::= { inktomiTSMIBs 1 }
	inktomiTSObjs      	OBJECT IDENTIFIER ::= { inktomiTSMIBs 2 }
	inktomiTSEvents   OBJECT IDENTIFIER ::= { inktomiTSMIBs 3 }

inktomiTrafficServerMibModule MODULE-IDENTITY
   LAST-UPDATED   "0103120000Z"
   ORGANIZATION   "Inktomi Corporation"
   CONTACT-INFO   "..."
   DESCRIPTION "The MIB module for Traffic Server
                $Id: inktomi-ts-mib.my,v 1.11 2001/04/30 22:58:50 ambles Exp $"
   REVISION       "0103120000Z"
   DESCRIPTION "Simple Traffic Server MIB"
::= { inktomiModules 2 }


--
-- Tree: inktomiTSObjs

--
-- Tree: inktomiTSObjs/tSProtocols
tSProtocols OBJECT-IDENTITY
  STATUS current
  DESCRIPTION
     "subtree"
  ::= { inktomiTSObjs 1}

--
-- Tree: inktomiTSObjs/tSProtocols/tsProtocolSummary
tsProtocolSummary OBJECT-IDENTITY
  STATUS current
  DESCRIPTION
     "subtree"
  ::= { tSProtocols 1}
tsClientThroughputOutKBit OBJECT-TYPE
  SYNTAX Gauge32
  UNITS ""
  MAX-ACCESS read-only
  STATUS current
  DESCRIPTION "
				Client Throughput all protocols (KBit/sec)
				proxyvar: proxy.node.client-throughput-out-kbit
			"
  ::= { tsProtocolSummary 1}
tsDocumentHitRate OBJECT-TYPE
  SYNTAX Gauge32
  UNITS ""
  MAX-ACCESS read-only
  STATUS current
  DESCRIPTION "
				Document Hit Rate all protocols average over 10 seconds(%)
				proxyvar: proxy.node.cache-hit-ratio-int-pct
			"
  ::= { tsProtocolSummary 2}
tsBandwidthSavingsRatio OBJECT-TYPE
  SYNTAX Gauge32
  UNITS ""
  MAX-ACCESS read-only
  STATUS current
  DESCRIPTION "
				The bandwidth hit rate in % for all protocols.
				Proxyvar: proxy.node.bandwidth-hit-ratio-int-pct
			"
  ::= { tsProtocolSummary 3}
tsServerConnections OBJECT-TYPE
  SYNTAX Gauge32
  UNITS ""
  MAX-ACCESS read-only
  STATUS current
  DESCRIPTION "
				The current number of connections to servers
				Proxyvar: proxy.node.current-server-connections
			"
  ::= { tsProtocolSummary 4}
tsClientConnections OBJECT-TYPE
  SYNTAX Gauge32
  UNITS ""
  MAX-ACCESS read-only
  STATUS current
  DESCRIPTION "
				The current number of connections to clients
				Proxyvar: proxy.node.current-client-connections
			"
  ::= { tsProtocolSummary 5}

--
-- Tree: inktomiTSObjs/tSProtocols/tsProtocolClusterSummary
tsProtocolClusterSummary OBJECT-IDENTITY
  STATUS current
  DESCRIPTION
     "subtree"
  ::= { tSProtocols 2}
tsClusterClientThroughputOutKBit OBJECT-TYPE
  SYNTAX Gauge32
  UNITS ""
  MAX-ACCESS read-only
  STATUS current
  DESCRIPTION "
				Client Throughput (KBit/sec) (cluster aggregate)
				proxyvar: proxy.cluster.client-throughput-out-kbit
			"
  ::= { tsProtocolClusterSummary 1}
tsClusterDocumentHitRate OBJECT-TYPE
  SYNTAX Gauge32
  UNITS ""
  MAX-ACCESS read-only
  STATUS current
  DESCRIPTION "
				Document Hit Rate (%) (cluster aggregate)
				proxyvar: proxy.cluster.cache-hit-ratio-int-pct
			"
  ::= { tsProtocolClusterSummary 2}
tsClusterBandwidthSavingsRatio OBJECT-TYPE
  SYNTAX Gauge32
  UNITS ""
  MAX-ACCESS read-only
  STATUS current
  DESCRIPTION "
				The bandwidth hit rate in % for all protocols. (cluster aggregate)
				Proxyvar: proxy.cluster.bandwidth-hit-ratio-int-pct
			"
  ::= { tsProtocolClusterSummary 3}
tsClusterServerConnections OBJECT-TYPE
  SYNTAX Gauge32
  UNITS ""
  MAX-ACCESS read-only
  STATUS current
  DESCRIPTION "
				The current number of connections to servers (cluster aggregate)
				Proxyvar: proxy.cluster.current-server-connections
			"
  ::= { tsProtocolClusterSummary 4}
tsClusterClientConnections OBJECT-TYPE
  SYNTAX Gauge32
  UNITS ""
  MAX-ACCESS read-only
  STATUS current
  DESCRIPTION "
				The current number of connections to clients (cluster aggregate)
				Proxyvar: proxy.cluster.current-client-connections
			"
  ::= { tsProtocolClusterSummary 5}

--
-- Tree: inktomiTSObjs/tSProtocols/tsProtocolHTTP
tsProtocolHTTP OBJECT-IDENTITY
  STATUS current
  DESCRIPTION
     "subtree"
  ::= { tSProtocols 3}

--
-- Tree: inktomiTSObjs/tSProtocols/tsProtocolHTTP/tsHttpStats
tsHttpStats OBJECT-IDENTITY
  STATUS current
  DESCRIPTION
     "subtree"
  ::= { tsProtocolHTTP 1}
httpXacts OBJECT-TYPE
  SYNTAX Gauge32
  UNITS ""
  MAX-ACCESS read-only
  STATUS current
  DESCRIPTION "
					The rate of documents served per second.
					Proxyvar: proxy.node.http.user-agent-xacts-per-second
				"
  ::= { tsHttpStats 1}
httpThroughput OBJECT-TYPE
  SYNTAX Gauge32
  UNITS ""
  MAX-ACCESS read-only
  STATUS current
  DESCRIPTION "
					throughput bytes/sec
					proxyvar: proxy.node.http.throughput
				"
  ::= { tsHttpStats 2}
httpCurrentlyOpenUA OBJECT-TYPE
  SYNTAX Gauge32
  UNITS ""
  MAX-ACCESS read-only
  STATUS current
  DESCRIPTION "
					current open client connections
					proxyvar: proxy.node.http.user-agent-current-connections-count
				"
  ::= { tsHttpStats 3}
httpHitRatio OBJECT-TYPE
  SYNTAX Gauge32
  UNITS ""
  MAX-ACCESS read-only
  STATUS current
  DESCRIPTION "
					The hit rate in % for HTTP requests.
					Proxyvar: proxy.node.http.cache-hit-ratio-int-pct
				"
  ::= { tsHttpStats 4}
httpBandwidthSavingsRatio OBJECT-TYPE
  SYNTAX Gauge32
  UNITS ""
  MAX-ACCESS read-only
  STATUS current
  DESCRIPTION "
					The bandwidth hit rate in % for HTTP requests.
					Proxyvar: proxy.node.http.bandwidth-hit-ratio-int-pct
				"
  ::= { tsHttpStats 5}
httpCurrentlyOpenOrigin OBJECT-TYPE
  SYNTAX Gauge32
  UNITS ""
  MAX-ACCESS read-only
  STATUS current
  DESCRIPTION "
					Open Origin Server Connections
					proxyvar: proxy.node.http.origin-server-current-connections-count
				"
  ::= { tsHttpStats 6}
httpUserAgentDocumentBytes OBJECT-TYPE
  SYNTAX Counter64
  UNITS ""
  MAX-ACCESS read-only
  STATUS current
  DESCRIPTION "
					Total Document Bytes (sent to HTTP user agents)
					proxyvar: proxy.process.http.user-agent-response-document-total-size
				"
  ::= { tsHttpStats 7}
httpUserAgentHeaderBytes OBJECT-TYPE
  SYNTAX Counter64
  UNITS ""
  MAX-ACCESS read-only
  STATUS current
  DESCRIPTION "
					Total Header Bytes (sent to HTTP user agents)
					proxyvar: proxy.process.http.user-agent-response-header-total-size
				"
  ::= { tsHttpStats 8}
httpUserAgentConnections OBJECT-TYPE
  SYNTAX Counter32
  UNITS ""
  MAX-ACCESS read-only
  STATUS current
  DESCRIPTION "
					Total Connections from HTTP user agents
					proxyvar: proxy.process.http.current-client-connections
				"
  ::= { tsHttpStats 9}
httpUserAgentTransactionsInProgress OBJECT-TYPE
  SYNTAX Gauge32
  UNITS ""
  MAX-ACCESS read-only
  STATUS current
  DESCRIPTION "
					Transactions In Progress from HTTP user agents
					proxyvar: proxy.process.http.current-client-transactions
				"
  ::= { tsHttpStats 10}
httpOriginServerTotalTransactions OBJECT-TYPE
  SYNTAX Counter32
  UNITS ""
  MAX-ACCESS read-only
  STATUS current
  DESCRIPTION "
					total Origin Server Transactions
					proxyvar: proxy.node.http.origin-server-total-transactions-count
				"
  ::= { tsHttpStats 11}
httpOriginServerTransactionsInProgress OBJECT-TYPE
  SYNTAX Gauge32
  UNITS ""
  MAX-ACCESS read-only
  STATUS current
  DESCRIPTION "
					Transactions In Progress to HTTP origin servers
					proxyvar: proxy.process.http.current-server-transactions
				"
  ::= { tsHttpStats 12}
httpOriginServerDocumentBytes OBJECT-TYPE
  SYNTAX Counter64
  UNITS ""
  MAX-ACCESS read-only
  STATUS current
  DESCRIPTION "
					Total Document Bytes (received from HTTP origin servers)
					proxyvar: proxy.process.http.origin-server-response-document-total-size
				"
  ::= { tsHttpStats 13}
httpOriginServerHeaderBytes OBJECT-TYPE
  SYNTAX Counter64
  UNITS ""
  MAX-ACCESS read-only
  STATUS current
  DESCRIPTION "
					Total Header Bytes (received from HTTP origin servers)
					proxyvar: proxy.process.http.origin-server-response-header-total-size
				"
  ::= { tsHttpStats 14}
httpOriginServerConnections OBJECT-TYPE
  SYNTAX Counter32
  UNITS ""
  MAX-ACCESS read-only
  STATUS current
  DESCRIPTION "
					Total Connections to HTTP origin servers
					proxyvar: proxy.process.http.current-server-connections
				"
  ::= { tsHttpStats 15}
httpOriginServerResponseBytes OBJECT-TYPE
  SYNTAX Counter64
  UNITS ""
  MAX-ACCESS read-only
  STATUS current
  DESCRIPTION "
					total Bytes from Origin Servers
					proxyvar: proxy.node.http.origin-server-total-response-bytes
				"
  ::= { tsHttpStats 16}
httpUserAgentResponseBytes OBJECT-TYPE
  SYNTAX Counter64
  UNITS ""
  MAX-ACCESS read-only
  STATUS current
  DESCRIPTION "
					total bytes to user agents
					proxyvar: proxy.node.http.user-agent-total-response-bytes
				"
  ::= { tsHttpStats 17}
httpUserAgentTransactions OBJECT-TYPE
  SYNTAX Counter32
  UNITS ""
  MAX-ACCESS read-only
  STATUS current
  DESCRIPTION "
					total Client Transactions
					proxyvar: proxy.node.http.user-agents-total-transactions-count
				"
  ::= { tsHttpStats 18}
httpTransactionErrorsPossbileAbortsMsec OBJECT-TYPE
  SYNTAX Gauge32
  UNITS ""
  MAX-ACCESS read-only
  STATUS current
  DESCRIPTION "
					proxyvar: proxy.node.http.transaction-msec-avg-10s.errors.possible-aborts
				"
  ::= { tsHttpStats 19}
httpTransactionMissChangedMsec OBJECT-TYPE
  SYNTAX Gauge32
  UNITS ""
  MAX-ACCESS read-only
  STATUS current
  DESCRIPTION "
					proxyvar: proxy.node.http.transaction-msec-avg-10s.miss-changed
				"
  ::= { tsHttpStats 20}
httpTransactionHitRevalidatedMsec OBJECT-TYPE
  SYNTAX Gauge32
  UNITS ""
  MAX-ACCESS read-only
  STATUS current
  DESCRIPTION "
					proxyvar: proxy.node.http.transaction-msec-avg-10s.hit-revalidated
				"
  ::= { tsHttpStats 21}
httpTransactionErrorsOtherMsec OBJECT-TYPE
  SYNTAX Gauge32
  UNITS ""
  MAX-ACCESS read-only
  STATUS current
  DESCRIPTION "
					proxyvar: proxy.node.http.transaction-msec-avg-10s.errors.other
				"
  ::= { tsHttpStats 22}
httpTransactionErrorsAbortsMsec OBJECT-TYPE
  SYNTAX Gauge32
  UNITS ""
  MAX-ACCESS read-only
  STATUS current
  DESCRIPTION "
					proxyvar: proxy.node.http.transaction-msec-avg-10s.errors.aborts
				"
  ::= { tsHttpStats 23}
httpTransactionErrorsEarlyHangupsMsec OBJECT-TYPE
  SYNTAX Gauge32
  UNITS ""
  MAX-ACCESS read-only
  STATUS current
  DESCRIPTION "
					proxyvar: proxy.node.http.transaction-msec-avg-10s.errors.early-hangups
				"
  ::= { tsHttpStats 24}
httpTransactionErrorsEmptyHangupsMsec OBJECT-TYPE
  SYNTAX Gauge32
  UNITS ""
  MAX-ACCESS read-only
  STATUS current
  DESCRIPTION "
					proxyvar: proxy.node.http.transaction-msec-avg-10s.errors.empty-hangups
				"
  ::= { tsHttpStats 25}
httpTransactionOtherUnclassifiedMsec OBJECT-TYPE
  SYNTAX Gauge32
  UNITS ""
  MAX-ACCESS read-only
  STATUS current
  DESCRIPTION "
					proxyvar: proxy.node.http.transaction-msec-avg-10s.other.unclassified
				"
  ::= { tsHttpStats 26}
httpTransactionErrorsPreAcceptHangupsMsec OBJECT-TYPE
  SYNTAX Gauge32
  UNITS ""
  MAX-ACCESS read-only
  STATUS current
  DESCRIPTION "
					proxyvar: proxy.node.http.transaction-msec-avg-10s.errors.pre-accept-hangups
				"
  ::= { tsHttpStats 27}
httpTransactionMissClientNoCacheMsec OBJECT-TYPE
  SYNTAX Gauge32
  UNITS ""
  MAX-ACCESS read-only
  STATUS current
  DESCRIPTION "
					proxyvar: proxy.node.http.transaction-msec-avg-10s.miss-client-no-cache
				"
  ::= { tsHttpStats 28}
httpTransactionMissNotCachableMsec OBJECT-TYPE
  SYNTAX Gauge32
  UNITS ""
  MAX-ACCESS read-only
  STATUS current
  DESCRIPTION "
					proxyvar: proxy.node.http.transaction-msec-avg-10s.miss-not-cacheable
				"
  ::= { tsHttpStats 29}
httpTransactionHitFreshMsec OBJECT-TYPE
  SYNTAX Gauge32
  UNITS ""
  MAX-ACCESS read-only
  STATUS current
  DESCRIPTION "
					proxyvar: proxy.node.http.transaction-msec-avg-10s.hit-fresh
				"
  ::= { tsHttpStats 30}
httpTransactionErrorsConnectFailedMsec OBJECT-TYPE
  SYNTAX Gauge32
  UNITS ""
  MAX-ACCESS read-only
  STATUS current
  DESCRIPTION "
					proxyvar: proxy.node.http.transaction-msec-avg-10s.errors.connect-failed
				"
  ::= { tsHttpStats 31}
httpTransactionMissColdMsec OBJECT-TYPE
  SYNTAX Gauge32
  UNITS ""
  MAX-ACCESS read-only
  STATUS current
  DESCRIPTION "
					proxyvar: proxy.node.http.transaction-msec-avg-10s.miss-cold
				"
  ::= { tsHttpStats 32}
httpTransactionErrorsPossibleAbortsPct OBJECT-TYPE
  SYNTAX Gauge32
  UNITS ""
  MAX-ACCESS read-only
  STATUS current
  DESCRIPTION "
					proxyvar: proxy.node.http.transaction-frac-avg-10s.errors.possible-aborts-int-pct
				"
  ::= { tsHttpStats 33}
httpTransactionErrorsPreAcceptHangupsPct OBJECT-TYPE
  SYNTAX Gauge32
  UNITS ""
  MAX-ACCESS read-only
  STATUS current
  DESCRIPTION "
					proxyvar: proxy.node.http.transaction-frac-avg-10s.errors.pre-accept-hangups-int-pct
				"
  ::= { tsHttpStats 34}
httpTransactionMissChangedPct OBJECT-TYPE
  SYNTAX Gauge32
  UNITS ""
  MAX-ACCESS read-only
  STATUS current
  DESCRIPTION "
					proxyvar: proxy.node.http.transaction-frac-avg-10s.miss-changed-int-pct
				"
  ::= { tsHttpStats 35}
httpTransactionErrorsOtherPct OBJECT-TYPE
  SYNTAX Gauge32
  UNITS ""
  MAX-ACCESS read-only
  STATUS current
  DESCRIPTION "
					proxyvar: proxy.node.http.transaction-frac-avg-10s.errors.other-int-pct
				"
  ::= { tsHttpStats 36}
httpTransactionHitFreshPct OBJECT-TYPE
  SYNTAX Gauge32
  UNITS ""
  MAX-ACCESS read-only
  STATUS current
  DESCRIPTION "
					proxyvar: proxy.node.http.transaction-frac-avg-10s.hit-fresh-int-pct
				"
  ::= { tsHttpStats 37}
httpTransactionErrorsConnectFailedPct OBJECT-TYPE
  SYNTAX Gauge32
  UNITS ""
  MAX-ACCESS read-only
  STATUS current
  DESCRIPTION "
					proxyvar: proxy.node.http.transaction-frac-avg-10s.errors.connect-failed-int-pct
				"
  ::= { tsHttpStats 38}
httpTransactionErrorsEarlyHangupsPct OBJECT-TYPE
  SYNTAX Gauge32
  UNITS ""
  MAX-ACCESS read-only
  STATUS current
  DESCRIPTION "
					proxyvar: proxy.node.http.transaction-frac-avg-10s.errors.early-hangups-int-pct
				"
  ::= { tsHttpStats 39}
httpTransactionErrorsEmptyHangupsPct OBJECT-TYPE
  SYNTAX Gauge32
  UNITS ""
  MAX-ACCESS read-only
  STATUS current
  DESCRIPTION "
					proxyvar: proxy.node.http.transaction-frac-avg-10s.errors.empty-hangups-int-pct
				"
  ::= { tsHttpStats 40}
httpTransactionMissColdPct OBJECT-TYPE
  SYNTAX Gauge32
  UNITS ""
  MAX-ACCESS read-only
  STATUS current
  DESCRIPTION "
					proxyvar: proxy.node.http.transaction-frac-avg-10s.miss-cold-int-pct
				"
  ::= { tsHttpStats 41}
httpTransactionOtherUnclassifiedPct OBJECT-TYPE
  SYNTAX Gauge32
  UNITS ""
  MAX-ACCESS read-only
  STATUS current
  DESCRIPTION "
					proxyvar: proxy.node.http.transaction-frac-avg-10s.other.unclassified-int-pct
				"
  ::= { tsHttpStats 42}
httpTransactionHitRevalidatedPct OBJECT-TYPE
  SYNTAX Gauge32
  UNITS ""
  MAX-ACCESS read-only
  STATUS current
  DESCRIPTION "
					proxyvar: proxy.node.http.transaction-frac-avg-10s.hit-revalidated-int-pct
				"
  ::= { tsHttpStats 43}
httpTransactionMissClientNoCachePct OBJECT-TYPE
  SYNTAX Gauge32
  UNITS ""
  MAX-ACCESS read-only
  STATUS current
  DESCRIPTION "
					proxyvar: proxy.node.http.transaction-frac-avg-10s.miss-client-no-cache-int-pct
				"
  ::= { tsHttpStats 44}
httpTransactionMissNotCachablePct OBJECT-TYPE
  SYNTAX Gauge32
  UNITS ""
  MAX-ACCESS read-only
  STATUS current
  DESCRIPTION "
					proxyvar: proxy.node.http.transaction-frac-avg-10s.miss-not-cacheable-int-pct
				"
  ::= { tsHttpStats 45}
httpTransactionErrorsAbortsPct OBJECT-TYPE
  SYNTAX Gauge32
  UNITS ""
  MAX-ACCESS read-only
  STATUS current
  DESCRIPTION "
					proxyvar: proxy.node.http.transaction-frac-avg-10s.errors.aborts-int-pct
				"
  ::= { tsHttpStats 46}
httpCurrentlyParentProxy OBJECT-TYPE
  SYNTAX Gauge32
  UNITS ""
  MAX-ACCESS read-only
  STATUS current
  DESCRIPTION "
					Currently open parent proxy connections
					proxyvar: proxy.node.http.current-parent-proxy-connections
				"
  ::= { tsHttpStats 47}

--
-- Tree: inktomiTSObjs/tSProtocols/tsProtocolHTTP/tsHttpClusterStats
tsHttpClusterStats OBJECT-IDENTITY
  STATUS current
  DESCRIPTION
     "subtree"
  ::= { tsProtocolHTTP 2}
clusterHttpHitRatio OBJECT-TYPE
  SYNTAX Gauge32
  UNITS ""
  MAX-ACCESS read-only
  STATUS current
  DESCRIPTION "
					The hit rate in % for HTTP requests (cluster aggregate).
					Proxyvar: proxy.cluster.http.cache-hit-ratio-int-pct
				"
  ::= { tsHttpClusterStats 1}
clusterBandwidthSavingsRatio OBJECT-TYPE
  SYNTAX Gauge32
  UNITS ""
  MAX-ACCESS read-only
  STATUS current
  DESCRIPTION "
					The bandwidth hit rate in % for HTTP requests (cluster aggregate).
					Proxyvar: proxy.cluster.http.bandwidth-hit-ratio-int-pct
				"
  ::= { tsHttpClusterStats 2}
clusterHttpCurrentlyOpenUA OBJECT-TYPE
  SYNTAX Gauge32
  UNITS ""
  MAX-ACCESS read-only
  STATUS current
  DESCRIPTION "
					current open client connections (cluster aggregate)
					proxyvar: proxy.cluster.http.user-agent-current-connections-count
				"
  ::= { tsHttpClusterStats 3}
clusterHttpCurrentlyOpenOrigin OBJECT-TYPE
  SYNTAX Gauge32
  UNITS ""
  MAX-ACCESS read-only
  STATUS current
  DESCRIPTION "
					Open Origin Server Connections (cluster aggregate)
					proxyvar: proxy.cluster.http.origin-server-current-connections-count
				"
  ::= { tsHttpClusterStats 4}
clusterHttpThroughput OBJECT-TYPE
  SYNTAX Gauge32
  UNITS ""
  MAX-ACCESS read-only
  STATUS current
  DESCRIPTION "
					throughput bytes/sec (cluster aggregate)
					proxyvar: proxy.cluster.http.throughput
				"
  ::= { tsHttpClusterStats 5}
clusterHttpXacts OBJECT-TYPE
  SYNTAX Gauge32
  UNITS ""
  MAX-ACCESS read-only
  STATUS current
  DESCRIPTION "
					The rate of documents served per second (cluster aggregate)
					Proxyvar: proxy.cluster.http.user-agent-xacts-per-second
				"
  ::= { tsHttpClusterStats 6}
clusterHttpUserAgentResponseBytes OBJECT-TYPE
  SYNTAX Counter64
  UNITS ""
  MAX-ACCESS read-only
  STATUS current
  DESCRIPTION "
					total bytes to user agents (cluster aggregate)
					proxyvar: proxy.cluster.http.user-agent-total-response-bytes
				"
  ::= { tsHttpClusterStats 7}
clusterHttpOriginServerResponseBytes OBJECT-TYPE
  SYNTAX Counter64
  UNITS ""
  MAX-ACCESS read-only
  STATUS current
  DESCRIPTION "
					total Bytes from Origin Servers (cluster aggregate)
					proxyvar: proxy.cluster.http.origin-server-total-response-bytes
				"
  ::= { tsHttpClusterStats 8}
clusterHttpOriginServerTransactions OBJECT-TYPE
  SYNTAX Counter32
  UNITS ""
  MAX-ACCESS read-only
  STATUS current
  DESCRIPTION "
					total Origin Server Transactions (cluster aggregate)
					proxyvar: proxy.cluster.http.origin-server-total-transactions-count
				"
  ::= { tsHttpClusterStats 9}
clusterHttpUserAgentTransactions OBJECT-TYPE
  SYNTAX Counter32
  UNITS ""
  MAX-ACCESS read-only
  STATUS current
  DESCRIPTION "
					total Client Transactions (cluster aggregate)
					proxyvar: proxy.cluster.http.user-agents-total-transactions-count
				"
  ::= { tsHttpClusterStats 10}
clusterHttpCurrentlyParentProxy OBJECT-TYPE
  SYNTAX Gauge32
  UNITS ""
  MAX-ACCESS read-only
  STATUS current
  DESCRIPTION "
					Currently open parent proxy connections (cluster aggregate)
					proxyvar: proxy.cluster.http.current-parent-proxy-connections
				"
  ::= { tsHttpClusterStats 11}

--
-- Tree: inktomiTSObjs/tSProtocols/tsProtocolFTP
tsProtocolFTP OBJECT-IDENTITY
  STATUS current
  DESCRIPTION
     "subtree"
  ::= { tSProtocols 4}

--
-- Tree: inktomiTSObjs/tSProtocols/tsProtocolFTP/tsFTPStats
tsFTPStats OBJECT-IDENTITY
  STATUS current
  DESCRIPTION
     "subtree"
  ::= { tsProtocolFTP 1}
ftpCurrentlyOpenConnections OBJECT-TYPE
  SYNTAX Gauge32
  UNITS ""
  MAX-ACCESS read-only
  STATUS current
  DESCRIPTION "
					Currently Open Connections
					proxyvar: proxy.process.ftp.connections-currently-open
				"
  ::= { tsFTPStats 1}
ftpSuccessfulPASV OBJECT-TYPE
  SYNTAX Counter32
  UNITS ""
  MAX-ACCESS read-only
  STATUS current
  DESCRIPTION "
					Successful PASV Connections
					proxyvar: proxy.process.ftp.connections-successful-pasv
				"
  ::= { tsFTPStats 2}
ftpUnsuccessfulPASV OBJECT-TYPE
  SYNTAX Counter32
  UNITS ""
  MAX-ACCESS read-only
  STATUS current
  DESCRIPTION "
					Unsuccessful PASV Connections
					proxyvar: proxy.process.ftp.connections-failed-pasv
				"
  ::= { tsFTPStats 3}
ftpSuccessfulPORT OBJECT-TYPE
  SYNTAX Counter32
  UNITS ""
  MAX-ACCESS read-only
  STATUS current
  DESCRIPTION "
					Successful PORT Connections
					proxyvar: proxy.process.ftp.connections-successful-port
				"
  ::= { tsFTPStats 4}
ftpUnsuccessfulPORT OBJECT-TYPE
  SYNTAX Counter32
  UNITS ""
  MAX-ACCESS read-only
  STATUS current
  DESCRIPTION "
					Unsuccessful PORT Connections
					proxyvar: proxy.process.ftp.connections-failed-port
				"
  ::= { tsFTPStats 5}
ftpClientOpenConnections OBJECT-TYPE
  SYNTAX Gauge32
  UNITS ""
  MAX-ACCESS read-only
  STATUS current
  DESCRIPTION "
					The current # of open FTP client connections
					Proxyvar: proxy.process.ftp.current-client-connections 
				"
  ::= { tsFTPStats 6}
ftpClientBytesRead OBJECT-TYPE
  SYNTAX Counter64
  UNITS ""
  MAX-ACCESS read-only
  STATUS current
  DESCRIPTION "
					The # of bytes read from FTP client connections
					Proxyvar: proxy.process.ftp.downstream.request-bytes
				"
  ::= { tsFTPStats 7}
ftpClientBytesWritten OBJECT-TYPE
  SYNTAX Counter64
  UNITS ""
  MAX-ACCESS read-only
  STATUS current
  DESCRIPTION "
					The # of bytes written to FTP client connections
					Proxyvar: proxy.process.ftp.downstream.response-bytes
				"
  ::= { tsFTPStats 8}
ftpServerOpenConnections OBJECT-TYPE
  SYNTAX Gauge32
  UNITS ""
  MAX-ACCESS read-only
  STATUS current
  DESCRIPTION "
					The current # of open FTP server connections
					Proxyvar: proxy.process.ftp.current-server-connections 
				"
  ::= { tsFTPStats 9}
ftpServerBytesRead OBJECT-TYPE
  SYNTAX Counter64
  UNITS ""
  MAX-ACCESS read-only
  STATUS current
  DESCRIPTION "
					The # of bytes read from FTP server connections
					Proxyvar: proxy.process.ftp.upstream.request-bytes
				"
  ::= { tsFTPStats 10}
ftpServerBytesWritten OBJECT-TYPE
  SYNTAX Counter64
  UNITS ""
  MAX-ACCESS read-only
  STATUS current
  DESCRIPTION "
					The # of bytes written to FTP server connections
					Proxyvar: proxy.process.ftp.upstream.response-bytes
				"
  ::= { tsFTPStats 11}
ftpFileHits OBJECT-TYPE
  SYNTAX Counter32
  UNITS ""
  MAX-ACCESS read-only
  STATUS current
  DESCRIPTION "
				    File hits
					Proxyvar: proxy.process.ftp.file-hits
				"
  ::= { tsFTPStats 12}
ftpFileMisses OBJECT-TYPE
  SYNTAX Counter32
  UNITS ""
  MAX-ACCESS read-only
  STATUS current
  DESCRIPTION "
				    File misses
					Proxyvar: proxy.process.ftp.file-misses
				"
  ::= { tsFTPStats 13}
ftpCwdHits OBJECT-TYPE
  SYNTAX Counter32
  UNITS ""
  MAX-ACCESS read-only
  STATUS current
  DESCRIPTION "
				    Change working directory hits
					Proxyvar: proxy.process.ftp.cwd-hits
				"
  ::= { tsFTPStats 14}
ftpCwdMisses OBJECT-TYPE
  SYNTAX Counter32
  UNITS ""
  MAX-ACCESS read-only
  STATUS current
  DESCRIPTION "
				    Change working directoyr misses
					Proxyvar: proxy.process.ftp.cwd-misses
				"
  ::= { tsFTPStats 15}
ftpDirectoryHits OBJECT-TYPE
  SYNTAX Counter32
  UNITS ""
  MAX-ACCESS read-only
  STATUS current
  DESCRIPTION "
				    List directory hits
					Proxyvar: proxy.process.ftp.directory-hits
				"
  ::= { tsFTPStats 16}
ftpDirectoryMisses OBJECT-TYPE
  SYNTAX Counter32
  UNITS ""
  MAX-ACCESS read-only
  STATUS current
  DESCRIPTION "
				    List directoyr misses
					Proxyvar: proxy.process.ftp.directory-misses
				"
  ::= { tsFTPStats 17}

--
-- Tree: inktomiTSObjs/tSProtocols/tsProtocolFTP/tsFTPClusterStats
tsFTPClusterStats OBJECT-IDENTITY
  STATUS current
  DESCRIPTION
     "subtree"
  ::= { tsProtocolFTP 2}

--
-- Tree: inktomiTSObjs/tSProtocols/tsProtocolSOCKS
tsProtocolSOCKS OBJECT-IDENTITY
  STATUS current
  DESCRIPTION
     "subtree"
  ::= { tSProtocols 5}

--
-- Tree: inktomiTSObjs/tSProtocols/tsProtocolSOCKS/tsSOCKSStats
tsSOCKSStats OBJECT-IDENTITY
  STATUS current
  DESCRIPTION
     "subtree"
  ::= { tsProtocolSOCKS 1}
socksUnsuccessfulConnections OBJECT-TYPE
  SYNTAX Counter32
  UNITS ""
  MAX-ACCESS read-only
  STATUS current
  DESCRIPTION "
					The # of unsuccessful connections to SOCKS server
					Proxyvar: proxy.process.socks.connections-unsuccessful
				"
  ::= { tsSOCKSStats 1}
socksSuccessfulConnections OBJECT-TYPE
  SYNTAX Counter32
  UNITS ""
  MAX-ACCESS read-only
  STATUS current
  DESCRIPTION "
					The # of successful connections to SOCKS server
					Proxyvar: proxy.process.socks.connections-successful
				"
  ::= { tsSOCKSStats 2}
socksOpenConnections OBJECT-TYPE
  SYNTAX Gauge32
  UNITS ""
  MAX-ACCESS read-only
  STATUS current
  DESCRIPTION "
					The current # of open connections to SOCKS server
					Proxyvar: proxy.process.socks.connections-currently-open
				"
  ::= { tsSOCKSStats 3}

--
-- Tree: inktomiTSObjs/tSProtocols/tsProtocolSOCKS/tsSOCKSClusterStats
tsSOCKSClusterStats OBJECT-IDENTITY
  STATUS current
  DESCRIPTION
     "subtree"
  ::= { tsProtocolSOCKS 2}

--
-- Tree: inktomiTSObjs/tSProtocols/tsProtocolNNTP
tsProtocolNNTP OBJECT-IDENTITY
  STATUS current
  DESCRIPTION
     "subtree"
  ::= { tSProtocols 6}

--
-- Tree: inktomiTSObjs/tSProtocols/tsProtocolNNTP/tsNNTPStats
tsNNTPStats OBJECT-IDENTITY
  STATUS current
  DESCRIPTION
     "subtree"
  ::= { tsProtocolNNTP 1}
nntpClientOpenConnections OBJECT-TYPE
  SYNTAX Gauge32
  UNITS ""
  MAX-ACCESS read-only
  STATUS current
  DESCRIPTION "
					The current # of open NNTP client connections
					Proxyvar: proxy.node.nntp.current-client-connections
				"
  ::= { tsNNTPStats 1}
nntpServerOpenConnections OBJECT-TYPE
  SYNTAX Gauge32
  UNITS ""
  MAX-ACCESS read-only
  STATUS current
  DESCRIPTION "
					The current # of open connections to NNTP servers
					Proxyvar: proxy.node.nntp.current-server-connections
				"
  ::= { tsNNTPStats 2}
nntpArticleHits OBJECT-TYPE
  SYNTAX Counter32
  UNITS ""
  MAX-ACCESS read-only
  STATUS current
  DESCRIPTION "
					The # of articles served from cache
					Proxyvar: proxy.process.nntp.article-hits
				"
  ::= { tsNNTPStats 3}
nntpArticleMisses OBJECT-TYPE
  SYNTAX Counter32
  UNITS ""
  MAX-ACCESS read-only
  STATUS current
  DESCRIPTION "
					The # of articles retreived from backing server
					Proxyvar: proxy.process.nntp.article-misses
				"
  ::= { tsNNTPStats 4}
nntpClientBytesWritten OBJECT-TYPE
  SYNTAX Counter32
  UNITS ""
  MAX-ACCESS read-only
  STATUS current
  DESCRIPTION "
					The # of bytes written to NNTP client connections
					Proxyvar: proxy.process.nntp.client-bytes-written
				"
  ::= { tsNNTPStats 5}
nntpClientBytesRead OBJECT-TYPE
  SYNTAX Counter32
  UNITS ""
  MAX-ACCESS read-only
  STATUS current
  DESCRIPTION "
					The # of bytes read from NNTP client connections
					Proxyvar: proxy.process.nntp.client-bytes-read
				"
  ::= { tsNNTPStats 6}
nntpFeedBytes OBJECT-TYPE
  SYNTAX Counter64
  UNITS ""
  MAX-ACCESS read-only
  STATUS current
  DESCRIPTION "
					The # of bytes read from NNTP feed
					Proxyvar: proxy.process.nntp.feed-bytes
				"
  ::= { tsNNTPStats 7}
nntpPullBytes OBJECT-TYPE
  SYNTAX Counter64
  UNITS ""
  MAX-ACCESS read-only
  STATUS current
  DESCRIPTION "
					The # of bytes pulled from backing server
					Proxyvar: proxy.process.nntp.pull-bytes
				"
  ::= { tsNNTPStats 8}
nntpGroupHits OBJECT-TYPE
  SYNTAX Counter32
  UNITS ""
  MAX-ACCESS read-only
  STATUS current
  DESCRIPTION "
					group hits
					Proxyvar: proxy.process.nntp.group-hits
				"
  ::= { tsNNTPStats 9}
nntpGroupRefreshes OBJECT-TYPE
  SYNTAX Counter32
  UNITS ""
  MAX-ACCESS read-only
  STATUS current
  DESCRIPTION "
					group refreshes
					Proxyvar: proxy.process.nntp.group-refreshes
				"
  ::= { tsNNTPStats 10}
nntpOverviewHits OBJECT-TYPE
  SYNTAX Counter32
  UNITS ""
  MAX-ACCESS read-only
  STATUS current
  DESCRIPTION "
					overview hits
					Proxyvar: proxy.process.nntp.overview-hits
				"
  ::= { tsNNTPStats 11}
nntpOverviewRefreshes OBJECT-TYPE
  SYNTAX Counter32
  UNITS ""
  MAX-ACCESS read-only
  STATUS current
  DESCRIPTION "
					overview refreshes
					Proxyvar: proxy.process.nntp.overview-refreshes
				"
  ::= { tsNNTPStats 12}
nntpPostBytes OBJECT-TYPE
  SYNTAX Counter64
  UNITS ""
  MAX-ACCESS read-only
  STATUS current
  DESCRIPTION "
					The # of bytes posted
					Proxyvar: proxy.process.nntp.post-bytes
				"
  ::= { tsNNTPStats 13}
nntpPosts OBJECT-TYPE
  SYNTAX Counter32
  UNITS ""
  MAX-ACCESS read-only
  STATUS current
  DESCRIPTION "
					The # of articles posted
					Proxyvar: proxy.process.nntp.posts
				"
  ::= { tsNNTPStats 14}
nntpServerBytesRead OBJECT-TYPE
  SYNTAX Counter32
  UNITS ""
  MAX-ACCESS read-only
  STATUS current
  DESCRIPTION "
					The # of bytes read from backing server
					Proxyvar: proxy.process.nntp.server-bytes-read
				"
  ::= { tsNNTPStats 15}
nntpServerBytesWritten OBJECT-TYPE
  SYNTAX Counter32
  UNITS ""
  MAX-ACCESS read-only
  STATUS current
  DESCRIPTION "
					The # of bytes written from backing server
					Proxyvar: proxy.process.nntp.server-bytes-written
				"
  ::= { tsNNTPStats 16}
nntpUpstreamTotalBytes OBJECT-TYPE
  SYNTAX Counter64
  UNITS ""
  MAX-ACCESS read-only
  STATUS current
  DESCRIPTION "
					The # of bytes read/written to backing server
					Proxyvar: proxy.node.nntp.upstream-total-bytes
				"
  ::= { tsNNTPStats 17}
nntpDownstreamTotalBytes OBJECT-TYPE
  SYNTAX Counter64
  UNITS ""
  MAX-ACCESS read-only
  STATUS current
  DESCRIPTION "
					The # of bytes read/written to clients
					Proxyvar: proxy.node.nntp.downstream-total-bytes
				"
  ::= { tsNNTPStats 18}

--
-- Tree: inktomiTSObjs/tSProtocols/tsProtocolNNTP/tsNNTPClusterStats
tsNNTPClusterStats OBJECT-IDENTITY
  STATUS current
  DESCRIPTION
     "subtree"
  ::= { tsProtocolNNTP 2}
nntpClusterUpstreamTotalBytes OBJECT-TYPE
  SYNTAX Counter64
  UNITS ""
  MAX-ACCESS read-only
  STATUS current
  DESCRIPTION "
					The # of bytes read/written to backing server. (cluster aggregate)
					Proxyvar: proxy.cluster.nntp.upstream-total-bytes
				"
  ::= { tsNNTPClusterStats 1}
nntpClusterDownstreamTotalBytes OBJECT-TYPE
  SYNTAX Counter64
  UNITS ""
  MAX-ACCESS read-only
  STATUS current
  DESCRIPTION "
					The # of bytes read/written to clients
					Proxyvar: proxy.cluster.nntp.downstream-total-bytes
				"
  ::= { tsNNTPClusterStats 2}
nntpClusterClientOpenConnections OBJECT-TYPE
  SYNTAX Gauge32
  UNITS ""
  MAX-ACCESS read-only
  STATUS current
  DESCRIPTION "
					The current # of open NNTP client connections. (cluster aggregate)
					Proxyvar: proxy.cluster.nntp.current-client-connections
				"
  ::= { tsNNTPClusterStats 3}
nntpClusterServerOpenConnections OBJECT-TYPE
  SYNTAX Gauge32
  UNITS ""
  MAX-ACCESS read-only
  STATUS current
  DESCRIPTION "
					The current # of open connections to NNTP servers. (cluster aggregate)
					Proxyvar: proxy.cluster.nntp.current-server-connections
				"
  ::= { tsNNTPClusterStats 4}

--
-- Tree: inktomiTSObjs/tSProtocols/tsProtocolRNI
tsProtocolRNI OBJECT-IDENTITY
  STATUS current
  DESCRIPTION
     "subtree"
  ::= { tSProtocols 7}

--
-- Tree: inktomiTSObjs/tSProtocols/tsProtocolRNI/tsRNIStats
tsRNIStats OBJECT-IDENTITY
  STATUS current
  DESCRIPTION
     "subtree"
  ::= { tsProtocolRNI 1}
rniObjectCount OBJECT-TYPE
  SYNTAX Counter32
  UNITS ""
  MAX-ACCESS read-only
  STATUS current
  DESCRIPTION "
					The total # of rni objects served
					Proxyvar: proxy.process.rni.object-count
				"
  ::= { tsRNIStats 1}
rniBlockHitCount OBJECT-TYPE
  SYNTAX Counter32
  UNITS ""
  MAX-ACCESS read-only
  STATUS current
  DESCRIPTION "
					The total # of rni block hits
					Proxyvar: proxy.process.rni.block-hit-count
				"
  ::= { tsRNIStats 2}
rniBlockMissCount OBJECT-TYPE
  SYNTAX Counter32
  UNITS ""
  MAX-ACCESS read-only
  STATUS current
  DESCRIPTION "
					The total # of rni block misses
					Proxyvar: proxy.process.rni.block-miss-count
				"
  ::= { tsRNIStats 3}
rniByteHitSum OBJECT-TYPE
  SYNTAX Counter32
  UNITS ""
  MAX-ACCESS read-only
  STATUS current
  DESCRIPTION "
					The total # of rni bytes hit
					Proxyvar: proxy.process.rni.byte-hit-sum
				"
  ::= { tsRNIStats 4}
rniByteMissSum OBJECT-TYPE
  SYNTAX Counter32
  UNITS ""
  MAX-ACCESS read-only
  STATUS current
  DESCRIPTION "
					The total # of rni bytes missed
					Proxyvar: proxy.process.rni.byte-miss-sum
				"
  ::= { tsRNIStats 5}
rniCurrentClientConnections OBJECT-TYPE
  SYNTAX Gauge32
  UNITS ""
  MAX-ACCESS read-only
  STATUS current
  DESCRIPTION "
					The current # of open rni client connections
					Proxyvar: proxy.process.rni.current-client-connections
				"
  ::= { tsRNIStats 6}
rniDownstreamRequests OBJECT-TYPE
  SYNTAX Counter32
  UNITS ""
  MAX-ACCESS read-only
  STATUS current
  DESCRIPTION "
					The total # of rni downstream requests
					Proxyvar: proxy.process.rni.downstream-requests
				"
  ::= { tsRNIStats 7}
rniDownstreamRequestBytes OBJECT-TYPE
  SYNTAX Counter64
  UNITS ""
  MAX-ACCESS read-only
  STATUS current
  DESCRIPTION "
					The total # of rni downstream request bytes
					Proxyvar: proxy.process.rni.downstream.request-bytes
				"
  ::= { tsRNIStats 8}
rniDownstreamResponseBytes OBJECT-TYPE
  SYNTAX Counter64
  UNITS ""
  MAX-ACCESS read-only
  STATUS current
  DESCRIPTION "
					The total # of rni downstream response bytes
					Proxyvar: proxy.process.rni.downstream.response-bytes
				"
  ::= { tsRNIStats 9}
rniCurrentServerConnections OBJECT-TYPE
  SYNTAX Gauge32
  UNITS ""
  MAX-ACCESS read-only
  STATUS current
  DESCRIPTION "
					The current # of open rni server connections
					Proxyvar: proxy.process.rni.current-server-connections
				"
  ::= { tsRNIStats 10}
rniUpstreamRequests OBJECT-TYPE
  SYNTAX Counter32
  UNITS ""
  MAX-ACCESS read-only
  STATUS current
  DESCRIPTION "
					The total # of rni upstream requests
					Proxyvar: proxy.process.rni.upstream-requests
				"
  ::= { tsRNIStats 11}
rniUpstreamRequestBytes OBJECT-TYPE
  SYNTAX Counter64
  UNITS ""
  MAX-ACCESS read-only
  STATUS current
  DESCRIPTION "
					The total # of rni upstream request bytes
					Proxyvar: proxy.process.rni.upstream.request-bytes
				"
  ::= { tsRNIStats 12}
rniUpstreamResponseBytes OBJECT-TYPE
  SYNTAX Counter64
  UNITS ""
  MAX-ACCESS read-only
  STATUS current
  DESCRIPTION "
					The total # of rni upstream response bytes
					Proxyvar: proxy.process.rni.upstream.response-bytes
				"
  ::= { tsRNIStats 13}

--
-- Tree: inktomiTSObjs/tSProtocols/tsProtocolRNI/tsRNIClusterStats
tsRNIClusterStats OBJECT-IDENTITY
  STATUS current
  DESCRIPTION
     "subtree"
  ::= { tsProtocolRNI 2}
rniClusterUpstreamTotalBytes OBJECT-TYPE
  SYNTAX Counter64
  UNITS ""
  MAX-ACCESS read-only
  STATUS current
  DESCRIPTION "
					The total # of byte sent/received from RNI servers. (cluster aggregate)
					Proxyvar: proxy.cluster.rni.upstream-total-bytes
				"
  ::= { tsRNIClusterStats 1}
rniClusterDownstreamTotalBytes OBJECT-TYPE
  SYNTAX Counter64
  UNITS ""
  MAX-ACCESS read-only
  STATUS current
  DESCRIPTION "
					The total # of byte sent/received from clients. (cluster aggregate)
					Proxyvar: proxy.cluster.rni.downstream-total-bytes
				"
  ::= { tsRNIClusterStats 2}
rniClusterCurrentServerConnections OBJECT-TYPE
  SYNTAX Counter32
  UNITS ""
  MAX-ACCESS read-only
  STATUS current
  DESCRIPTION "
					The current # of RNI server connections.  (cluster aggregate)
					Proxyvar: proxy.cluster.rni.current-server-connections
				"
  ::= { tsRNIClusterStats 3}
rniClusterCurrentClientConnections OBJECT-TYPE
  SYNTAX Counter32
  UNITS ""
  MAX-ACCESS read-only
  STATUS current
  DESCRIPTION "
					The current # of RNI client connections.  (cluster aggregate)
					Proxyvar: proxy.cluster.rni.current-client-connections
				"
  ::= { tsRNIClusterStats 4}
rniClusterUserAgentXactsPerSecond OBJECT-TYPE
  SYNTAX Gauge32
  UNITS ""
  MAX-ACCESS read-only
  STATUS current
  DESCRIPTION "
					The rate of RNI documents served per second (cluster aggregate)
					Proxyvar: proxy.cluster.rni.user-agent-xacts-per-second
				"
  ::= { tsRNIClusterStats 5}
rniClusterUserAgentsTotalDocumentsServed OBJECT-TYPE
  SYNTAX Counter32
  UNITS ""
  MAX-ACCESS read-only
  STATUS current
  DESCRIPTION "
					The total # of RNI documents served to clients. (cluster aggregate)
					Proxyvar: proxy.cluster.rni.user-agents-total-documents-served
				"
  ::= { tsRNIClusterStats 6}

--
-- Tree: inktomiTSObjs/tSProtocols/tsProtocolQT
tsProtocolQT OBJECT-IDENTITY
  STATUS current
  DESCRIPTION
     "subtree"
  ::= { tSProtocols 8}

--
-- Tree: inktomiTSObjs/tSProtocols/tsProtocolQT/tsQTStats
tsQTStats OBJECT-IDENTITY
  STATUS current
  DESCRIPTION
     "subtree"
  ::= { tsProtocolQT 1}
qtClientRequestBytes OBJECT-TYPE
  SYNTAX Counter32
  UNITS ""
  MAX-ACCESS read-only
  STATUS current
  DESCRIPTION "
					The total # of client Quick Time request bytes
					Proxyvar: proxy.process.qt.downstream.request-bytes
				"
  ::= { tsQTStats 1}
qtClientResponseBytes OBJECT-TYPE
  SYNTAX Counter32
  UNITS ""
  MAX-ACCESS read-only
  STATUS current
  DESCRIPTION "
					The total # of client Quick Time response bytes
					Proxyvar: proxy.process.qt.downstream.response-bytes	
				"
  ::= { tsQTStats 2}
qtServerRequestBytes OBJECT-TYPE
  SYNTAX Counter32
  UNITS ""
  MAX-ACCESS read-only
  STATUS current
  DESCRIPTION "
					The total # of server Quick Time request bytes
					Proxyvar: proxy.process.qt.upstream.request-bytes
				"
  ::= { tsQTStats 3}
qtServerResponseBytes OBJECT-TYPE
  SYNTAX Counter32
  UNITS ""
  MAX-ACCESS read-only
  STATUS current
  DESCRIPTION "
					The total # of server Quick Time response bytes
					Proxyvar: proxy.process.qt.upstream.response-bytes
				"
  ::= { tsQTStats 4}
qtCurrentClientConnections OBJECT-TYPE
  SYNTAX Counter32
  UNITS ""
  MAX-ACCESS read-only
  STATUS current
  DESCRIPTION "
					The total # of open Quick Time client connections
					Proxyvar: proxy.process.qt.current-client-connections
				"
  ::= { tsQTStats 5}
qtCurrentServerConnections OBJECT-TYPE
  SYNTAX Counter32
  UNITS ""
  MAX-ACCESS read-only
  STATUS current
  DESCRIPTION "
					The total # of open Quick Time server connections
					Proxyvar: proxy.process.qt.current-server-connections
				"
  ::= { tsQTStats 6}
qtCurrentLiveStreams OBJECT-TYPE
  SYNTAX Counter32
  UNITS ""
  MAX-ACCESS read-only
  STATUS current
  DESCRIPTION "
					The total # of live Quick Time connections
					Proxyvar: proxy.process.qt.current-unique-live-streams
				"
  ::= { tsQTStats 7}
qtClientServerBytesRead OBJECT-TYPE
  SYNTAX Counter32
  UNITS ""
  MAX-ACCESS read-only
  STATUS current
  DESCRIPTION "
					Proxyvar: proxy.process.qt.client.server-bytes-read
					The # of bytes read from Quick Time server connections
				"
  ::= { tsQTStats 8}
qtClientCacheBytesRead OBJECT-TYPE
  SYNTAX Counter32
  UNITS ""
  MAX-ACCESS read-only
  STATUS current
  DESCRIPTION "
					The # of bytes read from Quick Time cache
					Proxyvar: proxy.process.qt.client.cache-bytes-read
				"
  ::= { tsQTStats 9}

--
-- Tree: inktomiTSObjs/tSProtocols/tsProtocolQT/tsQTClusterStats
tsQTClusterStats OBJECT-IDENTITY
  STATUS current
  DESCRIPTION
     "subtree"
  ::= { tsProtocolQT 2}
qtClusterServerTotalBytes OBJECT-TYPE
  SYNTAX Counter64
  UNITS ""
  MAX-ACCESS read-only
  STATUS current
  DESCRIPTION "
					The total # of byte sent/received from QT servers. (cluster aggregate)
					Proxyvar: proxy.cluster.qt.upstream-total-bytes
				"
  ::= { tsQTClusterStats 1}
qtClusterClientTotalBytes OBJECT-TYPE
  SYNTAX Counter64
  UNITS ""
  MAX-ACCESS read-only
  STATUS current
  DESCRIPTION "
					The total # of byte sent/received from clients. (cluster aggregate)
					Proxyvar: proxy.cluster.qt.downstream-total-bytes
				"
  ::= { tsQTClusterStats 2}
qtClusterCurrentServerConnections OBJECT-TYPE
  SYNTAX Counter32
  UNITS ""
  MAX-ACCESS read-only
  STATUS current
  DESCRIPTION "
					The current # of QT server connections.  (cluster aggregate)
					Proxyvar: proxy.cluster.qt.current-server-connections
				"
  ::= { tsQTClusterStats 3}
qtClusterCurrentClientConnections OBJECT-TYPE
  SYNTAX Counter32
  UNITS ""
  MAX-ACCESS read-only
  STATUS current
  DESCRIPTION "
					The current # of QT client connections.  (cluster aggregate)
					Proxyvar: proxy.cluster.qt.current-client-connections
				"
  ::= { tsQTClusterStats 4}
qtClusterUserAgentXactsPerSecond OBJECT-TYPE
  SYNTAX Gauge32
  UNITS ""
  MAX-ACCESS read-only
  STATUS current
  DESCRIPTION "
					The rate of QT documents served per second (cluster aggregate)
					Proxyvar: proxy.cluster.qt.user-agent-xacts-per-second
				"
  ::= { tsQTClusterStats 5}
qtClusterUserAgentsTotalDocumentsServed OBJECT-TYPE
  SYNTAX Counter32
  UNITS ""
  MAX-ACCESS read-only
  STATUS current
  DESCRIPTION "
					The total # of QT documents served to clients. (cluster aggregate)
					Proxyvar: proxy.cluster.qt.user-agents-total-documents-served
				"
  ::= { tsQTClusterStats 6}

--
-- Tree: inktomiTSObjs/tSProtocols/tsProtocolWMT
tsProtocolWMT OBJECT-IDENTITY
  STATUS current
  DESCRIPTION
     "subtree"
  ::= { tSProtocols 9}

--
-- Tree: inktomiTSObjs/tSProtocols/tsProtocolWMT/tsWMTStats
tsWMTStats OBJECT-IDENTITY
  STATUS current
  DESCRIPTION
     "subtree"
  ::= { tsProtocolWMT 1}
wmtClientRequestBytes OBJECT-TYPE
  SYNTAX Counter32
  UNITS ""
  MAX-ACCESS read-only
  STATUS current
  DESCRIPTION "
					The total # of client Windows Media request bytes
					Proxyvar: proxy.process.wmt.downstream.request-bytes
				"
  ::= { tsWMTStats 1}
wmtClientResponseBytes OBJECT-TYPE
  SYNTAX Counter32
  UNITS ""
  MAX-ACCESS read-only
  STATUS current
  DESCRIPTION "
					The total # of client Windows Media response bytes
					Proxyvar: proxy.process.wmt.downstream.response-bytes
				"
  ::= { tsWMTStats 2}
wmtServerRequestBytes OBJECT-TYPE
  SYNTAX Counter32
  UNITS ""
  MAX-ACCESS read-only
  STATUS current
  DESCRIPTION "
					The total # of server Windows Media request bytes
					Proxyvar: proxy.process.wmt.upstream.request-bytes
				"
  ::= { tsWMTStats 3}
wmtServerResponseBytes OBJECT-TYPE
  SYNTAX Counter32
  UNITS ""
  MAX-ACCESS read-only
  STATUS current
  DESCRIPTION "
					The total # of server Windows Media response bytes
					Proxyvar: proxy.process.wmt.upstream.response-bytes	
				"
  ::= { tsWMTStats 4}
wmtCurrentClientConnections OBJECT-TYPE
  SYNTAX Counter32
  UNITS ""
  MAX-ACCESS read-only
  STATUS current
  DESCRIPTION "
					The total # of open Windows Media client connections
					Proxyvar: proxy.process.wmt.current-client-connections
				"
  ::= { tsWMTStats 5}
wmtCurrentServerConnections OBJECT-TYPE
  SYNTAX Counter32
  UNITS ""
  MAX-ACCESS read-only
  STATUS current
  DESCRIPTION "
					The total # of open Windows Media server connections
					Proxyvar: proxy.process.wmt.current-server-connections
				"
  ::= { tsWMTStats 6}

--
-- Tree: inktomiTSObjs/tSProtocols/tsProtocolWMT/tsWMTClusterStats
tsWMTClusterStats OBJECT-IDENTITY
  STATUS current
  DESCRIPTION
     "subtree"
  ::= { tsProtocolWMT 2}
wmtClusterServerTotalBytes OBJECT-TYPE
  SYNTAX Counter64
  UNITS ""
  MAX-ACCESS read-only
  STATUS current
  DESCRIPTION "
					The total # of byte sent/received from WMT servers. (cluster aggregate)
					Proxyvar: proxy.cluster.wmt.upstream-total-bytes
				"
  ::= { tsWMTClusterStats 1}
wmtClusterClientTotalBytes OBJECT-TYPE
  SYNTAX Counter64
  UNITS ""
  MAX-ACCESS read-only
  STATUS current
  DESCRIPTION "
					The total # of byte sent/received from clients. (cluster aggregate)
					Proxyvar: proxy.cluster.wmt.downstream-total-bytes
				"
  ::= { tsWMTClusterStats 2}
wmtClusterCurrentServerConnections OBJECT-TYPE
  SYNTAX Counter32
  UNITS ""
  MAX-ACCESS read-only
  STATUS current
  DESCRIPTION "
					The current # of WMT server connections.  (cluster aggregate)
					Proxyvar: proxy.cluster.wmt.current-server-connections
				"
  ::= { tsWMTClusterStats 3}
wmtClusterCurrentClientConnections OBJECT-TYPE
  SYNTAX Counter32
  UNITS ""
  MAX-ACCESS read-only
  STATUS current
  DESCRIPTION "
					The current # of WMT client connections.  (cluster aggregate)
					Proxyvar: proxy.cluster.wmt.current-client-connections
				"
  ::= { tsWMTClusterStats 4}
wmtClusterUserAgentXactsPerSecond OBJECT-TYPE
  SYNTAX Gauge32
  UNITS ""
  MAX-ACCESS read-only
  STATUS current
  DESCRIPTION "
					The rate of WMT documents served per second (cluster aggregate)
					Proxyvar: proxy.cluster.wmt.user-agent-xacts-per-second
				"
  ::= { tsWMTClusterStats 5}
wmtClusterUserAgentsTotalDocumentsServed OBJECT-TYPE
  SYNTAX Counter32
  UNITS ""
  MAX-ACCESS read-only
  STATUS current
  DESCRIPTION "
					The total # of WMT documents served to clients. (cluster aggregate)
					Proxyvar: proxy.cluster.wmt.user-agents-total-documents-served
				"
  ::= { tsWMTClusterStats 6}

--
-- Tree: inktomiTSObjs/tSEventSubsystem
tSEventSubsystem OBJECT-IDENTITY
  STATUS current
  DESCRIPTION
     "subtree"
  ::= { inktomiTSObjs 2}

--
-- Tree: inktomiTSObjs/tSCacheSubsystem
tSCacheSubsystem OBJECT-IDENTITY
  STATUS current
  DESCRIPTION
     "subtree"
  ::= { inktomiTSObjs 3}

--
-- Tree: inktomiTSObjs/tSCacheSubsystem/tSICPStats
tSICPStats OBJECT-IDENTITY
  STATUS current
  DESCRIPTION
     "subtree"
  ::= { tSCacheSubsystem 1}
tsICPRemoteQuery OBJECT-TYPE
  SYNTAX Counter32
  UNITS ""
  MAX-ACCESS read-only
  STATUS current
  DESCRIPTION "
				ICP Remote Query Requests
				proxyvar: proxy.process.icp.icp-remote-query-requests
			"
  ::= { tSICPStats 1}
tsICPRemoteResponses OBJECT-TYPE
  SYNTAX Counter32
  UNITS ""
  MAX-ACCESS read-only
  STATUS current
  DESCRIPTION "
				ICP Remote Responses
				proxyvar: proxy.process.icp.icp-remote-responses
			"
  ::= { tSICPStats 2}
tsICPCacheLookupSuccess OBJECT-TYPE
  SYNTAX Counter32
  UNITS ""
  MAX-ACCESS read-only
  STATUS current
  DESCRIPTION "
				Cache Lookup Success
				proxyvar: proxy.process.icp.cache-lookup-success
			"
  ::= { tSICPStats 3}
tsICPCacheLookupFail OBJECT-TYPE
  SYNTAX Counter32
  UNITS ""
  MAX-ACCESS read-only
  STATUS current
  DESCRIPTION "
				Cache Lookup Failures
				proxyvar: proxy.process.icp.cache-lookup-fail
			"
  ::= { tSICPStats 4}
tsICPQueryResponseWrite OBJECT-TYPE
  SYNTAX Counter32
  UNITS ""
  MAX-ACCESS read-only
  STATUS current
  DESCRIPTION "
				Query Response Writes
				proxyvar: proxy.process.icp.query-response-write
			"
  ::= { tSICPStats 5}
tsICPQueryHits OBJECT-TYPE
  SYNTAX Counter32
  UNITS ""
  MAX-ACCESS read-only
  STATUS current
  DESCRIPTION "
				ICP Query hits
				proxyvar: proxy.process.icp.icp-query-hits
			"
  ::= { tSICPStats 6}
tsICPQueryMisses OBJECT-TYPE
  SYNTAX Counter32
  UNITS ""
  MAX-ACCESS read-only
  STATUS current
  DESCRIPTION "
				ICP Query misses
				proxyvar: proxy.process.icp.icp-query-misses
			"
  ::= { tSICPStats 7}
tsICPQueryRequests OBJECT-TYPE
  SYNTAX Counter32
  UNITS ""
  MAX-ACCESS read-only
  STATUS current
  DESCRIPTION "
				ICP Query requests
				proxyvar: proxy.process.icp.icp-query-requests
			"
  ::= { tSICPStats 8}
tsICPResponseTime OBJECT-TYPE
  SYNTAX Gauge32
  UNITS ""
  MAX-ACCESS read-only
  STATUS current
  DESCRIPTION "
				Total ICP Response Time
				proxyvar: proxy.process.icp.total-icp-response-time
			"
  ::= { tSICPStats 9}
tsICPUDPSendQueries OBJECT-TYPE
  SYNTAX Counter32
  UNITS ""
  MAX-ACCESS read-only
  STATUS current
  DESCRIPTION "
				Total UDP Send Queries
				proxyvar: proxy.process.icp.total-udp-send-queries
			"
  ::= { tSICPStats 10}
tsICPRequestTime OBJECT-TYPE
  SYNTAX Gauge32
  UNITS ""
  MAX-ACCESS read-only
  STATUS current
  DESCRIPTION "
				Total ICP Request Time
				proxyvar: proxy.process.icp.total-icp-request-time
			"
  ::= { tSICPStats 11}

--
-- Tree: inktomiTSObjs/tSCacheSubsystem/tSCacheStats
tSCacheStats OBJECT-IDENTITY
  STATUS current
  DESCRIPTION
     "subtree"
  ::= { tSCacheSubsystem 2}
tSCachePercentFree OBJECT-TYPE
  SYNTAX Gauge32
  UNITS ""
  MAX-ACCESS read-only
  STATUS current
  DESCRIPTION "
				% free bytes in cache (cluster aggregate).
				proxyvar: proxy.node.cache.percent-free-int-pct
			"
  ::= { tSCacheStats 1}
tSCacheHTTPHits OBJECT-TYPE
  SYNTAX Counter32
  UNITS ""
  MAX-ACCESS read-only
  STATUS current
  DESCRIPTION "
				Objects Served From Cache (HTTP only)
				proxyvar: proxy.node.http.cache-total-hits
			"
  ::= { tSCacheStats 2}
tSCacheHits OBJECT-TYPE
  SYNTAX Counter32
  UNITS ""
  MAX-ACCESS read-only
  STATUS current
  DESCRIPTION "
				Objects Served From Cache (all protocols)
				proxyvar: proxy.node.cache-total-hits
			"
  ::= { tSCacheStats 3}
tSCacheMisses OBJECT-TYPE
  SYNTAX Counter32
  UNITS ""
  MAX-ACCESS read-only
  STATUS current
  DESCRIPTION "
				Objects Not Found in Cache (all protocols)
				proxyvar: proxy.node.cache-total-misses
			"
  ::= { tSCacheStats 4}
tSCacheCurrentXfers OBJECT-TYPE
  SYNTAX Gauge32
  UNITS ""
  MAX-ACCESS read-only
  STATUS current
  DESCRIPTION "
				Cache Xfers In Progress (HTTP only)
				proxyvar: proxy.node.http.cache-current-connections-count
			"
  ::= { tSCacheStats 5}
tSCacheBytesTotalMB OBJECT-TYPE
  SYNTAX Gauge32
  UNITS ""
  MAX-ACCESS read-only
  STATUS current
  DESCRIPTION "
				Cache Size (in MB)
				proxyvar: proxy.node.cache.bytes-total-mb
			"
  ::= { tSCacheStats 6}
tSCacheLinkActive OBJECT-TYPE
  SYNTAX Gauge32
  UNITS ""
  MAX-ACCESS read-only
  STATUS obsolete
  DESCRIPTION "
				Link operations in progress
				proxyvar: proxy.process.cache.link.active
			"
  ::= { tSCacheStats 7}
tSCacheLinkFailures OBJECT-TYPE
  SYNTAX Counter32
  UNITS ""
  MAX-ACCESS read-only
  STATUS obsolete
  DESCRIPTION "
				Link operations failed
				proxyvar: proxy.process.cache.link.failure
			"
  ::= { tSCacheStats 8}
tSCacheLinkSuccesses OBJECT-TYPE
  SYNTAX Counter32
  UNITS ""
  MAX-ACCESS read-only
  STATUS obsolete
  DESCRIPTION "
				Link operations suceeded
				proxyvar: proxy.process.cache.link.success
			"
  ::= { tSCacheStats 9}
tSCacheLookupActive OBJECT-TYPE
  SYNTAX Gauge32
  UNITS ""
  MAX-ACCESS read-only
  STATUS current
  DESCRIPTION "
				lookup operations in progress
				proxyvar: proxy.process.cache.lookup.active
			"
  ::= { tSCacheStats 10}
tSCacheLookupFailures OBJECT-TYPE
  SYNTAX Counter32
  UNITS ""
  MAX-ACCESS read-only
  STATUS current
  DESCRIPTION "
				lookup operations failed
				proxyvar: proxy.process.cache.lookup.failure
			"
  ::= { tSCacheStats 11}
tSCacheLookupSuccesses OBJECT-TYPE
  SYNTAX Counter32
  UNITS ""
  MAX-ACCESS read-only
  STATUS current
  DESCRIPTION "
				Lookup operations suceeded
				proxyvar: proxy.process.cache.lookup.success
			"
  ::= { tSCacheStats 12}
tSCacheReadActive OBJECT-TYPE
  SYNTAX Gauge32
  UNITS ""
  MAX-ACCESS read-only
  STATUS current
  DESCRIPTION "
				Read operations in progress
				proxyvar: proxy.process.cache.read.active
			"
  ::= { tSCacheStats 13}
tSCacheReadFailures OBJECT-TYPE
  SYNTAX Counter32
  UNITS ""
  MAX-ACCESS read-only
  STATUS current
  DESCRIPTION "
				Read operations failed
				proxyvar: proxy.process.cache.read.failure
			"
  ::= { tSCacheStats 14}
tSCacheReadSuccesses OBJECT-TYPE
  SYNTAX Counter32
  UNITS ""
  MAX-ACCESS read-only
  STATUS current
  DESCRIPTION "
				Read operations suceeded
				proxyvar: proxy.process.cache.read.success
			"
  ::= { tSCacheStats 15}
tSCacheRemoveActive OBJECT-TYPE
  SYNTAX Gauge32
  UNITS ""
  MAX-ACCESS read-only
  STATUS current
  DESCRIPTION "
				Remove operations in progress
				proxyvar: proxy.process.cache.remove.active
			"
  ::= { tSCacheStats 16}
tSCacheRemoveFailures OBJECT-TYPE
  SYNTAX Counter32
  UNITS ""
  MAX-ACCESS read-only
  STATUS current
  DESCRIPTION "
				Remove operations failed
				proxyvar: proxy.process.cache.remove.failure
			"
  ::= { tSCacheStats 17}
tSCacheRemoveSuccesses OBJECT-TYPE
  SYNTAX Counter32
  UNITS ""
  MAX-ACCESS read-only
  STATUS current
  DESCRIPTION "
				Remove operations suceeded
				proxyvar: proxy.process.cache.remove.success
			"
  ::= { tSCacheStats 18}
tSCacheUpdateActive OBJECT-TYPE
  SYNTAX Gauge32
  UNITS ""
  MAX-ACCESS read-only
  STATUS current
  DESCRIPTION "
				Update operations in progress
				proxyvar: proxy.process.cache.update.active
			"
  ::= { tSCacheStats 19}
tSCacheUpdateFailures OBJECT-TYPE
  SYNTAX Counter32
  UNITS ""
  MAX-ACCESS read-only
  STATUS current
  DESCRIPTION "
				Update operations failed
				proxyvar: proxy.process.cache.update.failure
			"
  ::= { tSCacheStats 20}
tSCacheUpdateSuccesses OBJECT-TYPE
  SYNTAX Counter32
  UNITS ""
  MAX-ACCESS read-only
  STATUS current
  DESCRIPTION "
				Update operations suceeded
				proxyvar: proxy.process.cache.update.success
			"
  ::= { tSCacheStats 21}
tSCacheWriteActive OBJECT-TYPE
  SYNTAX Gauge32
  UNITS ""
  MAX-ACCESS read-only
  STATUS current
  DESCRIPTION "
				Write operations in progress
				proxyvar: proxy.process.cache.write.active
			"
  ::= { tSCacheStats 22}
tSCacheWriteFailures OBJECT-TYPE
  SYNTAX Counter32
  UNITS ""
  MAX-ACCESS read-only
  STATUS current
  DESCRIPTION "
				Write operations failed
				proxyvar: proxy.process.cache.write.failure
			"
  ::= { tSCacheStats 23}
tSCacheWriteSuccesses OBJECT-TYPE
  SYNTAX Counter32
  UNITS ""
  MAX-ACCESS read-only
  STATUS current
  DESCRIPTION "
				Write operations suceeded
				proxyvar: proxy.process.cache.write.success
		"
  ::= { tSCacheStats 24}
tSCacheConnections OBJECT-TYPE
  SYNTAX Gauge32
  UNITS ""
  MAX-ACCESS read-only
  STATUS current
  DESCRIPTION "
				The current number of connections to the cache.
				proxyvar: proxy.node.current-cache-connections
			"
  ::= { tSCacheStats 25}

--
-- Tree: inktomiTSObjs/tSCacheSubsystem/tSCacheClusterStats
tSCacheClusterStats OBJECT-IDENTITY
  STATUS current
  DESCRIPTION
     "subtree"
  ::= { tSCacheSubsystem 3}
tSClusterCacheFreeMB OBJECT-TYPE
  SYNTAX Gauge32
  UNITS ""
  MAX-ACCESS read-only
  STATUS current
  DESCRIPTION "
				# of free MB in cache (cluster aggregate).
				proxyvar: proxy.cluster.cache.bytes-free-mb
			"
  ::= { tSCacheClusterStats 1}
tSClusterCachePercentFree OBJECT-TYPE
  SYNTAX Gauge32
  UNITS ""
  MAX-ACCESS read-only
  STATUS current
  DESCRIPTION "
				% free bytes in cache (cluster aggregate).
				proxyvar: proxy.cluster.cache.percent-free-int-pct
			"
  ::= { tSCacheClusterStats 2}
tSClusterCacheHTTPHits OBJECT-TYPE
  SYNTAX Counter32
  UNITS ""
  MAX-ACCESS read-only
  STATUS current
  DESCRIPTION "
				Objects Served From Cache (HTTP only) (cluster aggregate).
				proxyvar: proxy.cluster.http.cache-total-hits
			"
  ::= { tSCacheClusterStats 3}
tSClusterCacheHits OBJECT-TYPE
  SYNTAX Counter32
  UNITS ""
  MAX-ACCESS read-only
  STATUS current
  DESCRIPTION "
				Objects Served From Cache (all protocols) (cluster aggregate).
				proxyvar: proxy.cluster.cache-total-hits
			"
  ::= { tSCacheClusterStats 4}
tSClusterCacheMisses OBJECT-TYPE
  SYNTAX Counter32
  UNITS ""
  MAX-ACCESS read-only
  STATUS current
  DESCRIPTION "
				Objects Not Found in Cache (all protocols) (cluster aggregate).
				proxyvar: proxy.cluster.cache-total-misses
			"
  ::= { tSCacheClusterStats 5}
tSClusterCacheCurrentXfers OBJECT-TYPE
  SYNTAX Gauge32
  UNITS ""
  MAX-ACCESS read-only
  STATUS current
  DESCRIPTION "
				Cache Xfers In Progress (HTTP only) (cluster aggregate)
				proxyvar: proxy.cluster.http.cache-current-connections-count
			"
  ::= { tSCacheClusterStats 6}
tSClusterCacheConnections OBJECT-TYPE
  SYNTAX Gauge32
  UNITS ""
  MAX-ACCESS read-only
  STATUS current
  DESCRIPTION "
				The current number of connections to the cache. (cluster aggregate)
				proxyvar: proxy.cluster.current-cache-connections
			"
  ::= { tSCacheClusterStats 7}

--
-- Tree: inktomiTSObjs/tSCacheSubsystem/tSCacheGCSubsystem
tSCacheGCSubsystem OBJECT-IDENTITY
  STATUS current
  DESCRIPTION
     "subtree"
  ::= { tSCacheSubsystem 4}

--
-- Tree: inktomiTSObjs/tSCacheSubsystem/tSCacheEngineSubsystem
tSCacheEngineSubsystem OBJECT-IDENTITY
  STATUS current
  DESCRIPTION
     "subtree"
  ::= { tSCacheSubsystem 5}

--
-- Tree: inktomiTSObjs/tSDiskSubsystem
tSDiskSubsystem OBJECT-IDENTITY
  STATUS current
  DESCRIPTION
     "subtree"
  ::= { inktomiTSObjs 4}

--
-- Tree: inktomiTSObjs/tSHostDBSubsystem
tSHostDBSubsystem OBJECT-IDENTITY
  STATUS current
  DESCRIPTION
     "subtree"
  ::= { inktomiTSObjs 5}

--
-- Tree: inktomiTSObjs/tSHostDBSubsystem/tsDNSStats
tsDNSStats OBJECT-IDENTITY
  STATUS current
  DESCRIPTION
     "subtree"
  ::= { tSHostDBSubsystem 1}
dnsTotalLookups OBJECT-TYPE
  SYNTAX Counter32
  UNITS ""
  MAX-ACCESS read-only
  STATUS current
  DESCRIPTION "
				Total # of DNS lookups performed.
				proxyvar: proxy.process.dns.total-dns-lookups 
			"
  ::= { tsDNSStats 1}
dnsLookupRate OBJECT-TYPE
  SYNTAX Gauge32
  UNITS ""
  MAX-ACCESS read-only
  STATUS current
  DESCRIPTION "
				# of DNS lookups per second (cluster aggregate)
				proxyvar: proxy.node.dns.lookups-per-second
			"
  ::= { tsDNSStats 2}
dnsTotalLookupSuccesses OBJECT-TYPE
  SYNTAX Counter32
  UNITS ""
  MAX-ACCESS read-only
  STATUS current
  DESCRIPTION "
				Total # of successful DNS lookups performed.
				proxyvar: proxy.process.dns.lookup-successes
			"
  ::= { tsDNSStats 3}
dnsLookupTimeMs OBJECT-TYPE
  SYNTAX Gauge32
  UNITS ""
  MAX-ACCESS read-only
  STATUS current
  DESCRIPTION "
				Average time for DNS lookups to respond in milliseconds
				proxyvar: proxy.process.dns.lookup-avg-time
			"
  ::= { tsDNSStats 4}

--
-- Tree: inktomiTSObjs/tSHostDBSubsystem/tsClusterDNSStats
tsClusterDNSStats OBJECT-IDENTITY
  STATUS current
  DESCRIPTION
     "subtree"
  ::= { tSHostDBSubsystem 2}
tsClusterDNSTotalLookups OBJECT-TYPE
  SYNTAX Counter32
  UNITS ""
  MAX-ACCESS read-only
  STATUS current
  DESCRIPTION "
				Total # of DNS lookups performed (cluster aggregate)
				proxyvar: proxy.cluster.dns.total-dns-lookups 
			"
  ::= { tsClusterDNSStats 1}
tsClusterDNSLookupRate OBJECT-TYPE
  SYNTAX Gauge32
  UNITS ""
  MAX-ACCESS read-only
  STATUS current
  DESCRIPTION "
				# of DNS lookups per second (cluster aggregate)
				proxyvar: proxy.cluster.dns.lookups-per-second
			"
  ::= { tsClusterDNSStats 2}

--
-- Tree: inktomiTSObjs/tSHostDBSubsystem/tsHostDBStats
tsHostDBStats OBJECT-IDENTITY
  STATUS current
  DESCRIPTION
     "subtree"
  ::= { tSHostDBSubsystem 3}
hostDBTotalLookups OBJECT-TYPE
  SYNTAX Counter32
  UNITS ""
  MAX-ACCESS read-only
  STATUS current
  DESCRIPTION "
				proxyvar: proxy.process.hostdb.total-lookups 
			"
  ::= { tsHostDBStats 1}
hostDBTotalHits OBJECT-TYPE
  SYNTAX Counter32
  UNITS ""
  MAX-ACCESS read-only
  STATUS current
  DESCRIPTION "
				Total Hits
				proxyvar: proxy.process.hostdb.total-hits
			"
  ::= { tsHostDBStats 2}
hostDBAverageTTL OBJECT-TYPE
  SYNTAX Gauge32
  UNITS ""
  MAX-ACCESS read-only
  STATUS current
  DESCRIPTION "
				Average TTL of host entries in minutes
				proxyvar: proxy.process.hostdb.ttl
			"
  ::= { tsHostDBStats 3}

--
-- Tree: inktomiTSObjs/tSHostDBSubsystem/tSClusterHostDBStats
tSClusterHostDBStats OBJECT-IDENTITY
  STATUS current
  DESCRIPTION
     "subtree"
  ::= { tSHostDBSubsystem 4}
clusterHostdbHitRatio OBJECT-TYPE
  SYNTAX Gauge32
  UNITS ""
  MAX-ACCESS read-only
  STATUS current
  DESCRIPTION "
				HostDB Hit Rate% (cluster aggregate)
				proxyvar: proxy.cluster.hostdb.hit-ratio-int-pct
			"
  ::= { tSClusterHostDBStats 1}

--
-- Tree: inktomiTSObjs/tSClusterSubsystem
tSClusterSubsystem OBJECT-IDENTITY
  STATUS current
  DESCRIPTION
     "subtree"
  ::= { inktomiTSObjs 6}

--
-- Tree: inktomiTSObjs/tSClusterSubsystem/tsClusterNodeStats
tsClusterNodeStats OBJECT-IDENTITY
  STATUS current
  DESCRIPTION
     "subtree"
  ::= { tSClusterSubsystem 1}
clusterBytesRead OBJECT-TYPE
  SYNTAX Counter32
  UNITS ""
  MAX-ACCESS read-only
  STATUS current
  DESCRIPTION "
				proxyvar: proxy.process.cluster.read-bytes 
			"
  ::= { tsClusterNodeStats 1}
clusterBytesWritten OBJECT-TYPE
  SYNTAX Counter32
  UNITS ""
  MAX-ACCESS read-only
  STATUS current
  DESCRIPTION "
				proxyvar: proxy.process.cluster.write-bytes 
			"
  ::= { tsClusterNodeStats 2}
clusterConnectionsOpen OBJECT-TYPE
  SYNTAX Gauge32
  UNITS ""
  MAX-ACCESS read-only
  STATUS current
  DESCRIPTION "
				Number of connections currently open.
				proxyvar: proxy.process.cluster.connections-open
			"
  ::= { tsClusterNodeStats 3}
clusterConnectionsOpened OBJECT-TYPE
  SYNTAX Counter32
  UNITS ""
  MAX-ACCESS read-only
  STATUS current
  DESCRIPTION "
				Number of connections opened.
				proxyvar: proxy.process.cluster.connections-opened 
			"
  ::= { tsClusterNodeStats 4}
clusterNetBackups OBJECT-TYPE
  SYNTAX Counter32
  UNITS ""
  MAX-ACCESS read-only
  STATUS current
  DESCRIPTION "
				proxyvar: proxy.process.cluster.net-backup 
			"
  ::= { tsClusterNodeStats 5}
clusterNodeCount OBJECT-TYPE
  SYNTAX Gauge32
  UNITS ""
  MAX-ACCESS read-only
  STATUS current
  DESCRIPTION "
				proxyvar: proxy.process.cluster.nodes 
			"
  ::= { tsClusterNodeStats 6}

--
-- Tree: inktomiTSObjs/tSClusterSubsystem/tsClusterClusterStats
tsClusterClusterStats OBJECT-IDENTITY
  STATUS current
  DESCRIPTION
     "subtree"
  ::= { tSClusterSubsystem 2}

--
-- Tree: inktomiTSObjs/tsLoggingSubsystem
tsLoggingSubsystem OBJECT-IDENTITY
  STATUS current
  DESCRIPTION
     "subtree"
  ::= { inktomiTSObjs 7}

--
-- Tree: inktomiTSObjs/tsLoggingSubsystem/tsLogStats
tsLogStats OBJECT-IDENTITY
  STATUS current
  DESCRIPTION
     "subtree"
  ::= { tsLoggingSubsystem 1}
tsLogOpenFiles OBJECT-TYPE
  SYNTAX Gauge32
  UNITS ""
  MAX-ACCESS read-only
  STATUS current
  DESCRIPTION "
				Currently Open Log Files 
				proxyvar: proxy.process.log2.log-files-open
			"
  ::= { tsLogStats 1}
tsLogSpaceUsed OBJECT-TYPE
  SYNTAX Gauge32
  UNITS ""
  MAX-ACCESS read-only
  STATUS current
  DESCRIPTION "
				Space Used For Log Files 
				proxyvar: proxy.process.log2.log-files-space-used
			"
  ::= { tsLogStats 2}
tsLogAccessesLogged OBJECT-TYPE
  SYNTAX Counter32
  UNITS ""
  MAX-ACCESS read-only
  STATUS current
  DESCRIPTION "
				Number of Access Events Logged 
				proxyvar: proxy.process.log2.event-log-access
			"
  ::= { tsLogStats 3}
tsLogAccessesSkipped OBJECT-TYPE
  SYNTAX Counter32
  UNITS ""
  MAX-ACCESS read-only
  STATUS current
  DESCRIPTION "
				Number of Access Events Skipped 
				proxyvar: proxy.process.log2.event-log-access-skip
			"
  ::= { tsLogStats 4}
tsLogErrorsLogged OBJECT-TYPE
  SYNTAX Counter32
  UNITS ""
  MAX-ACCESS read-only
  STATUS current
  DESCRIPTION "
				Number of Error Events Logged 
				proxyvar: proxy.process.log2.event-log-error
			"
  ::= { tsLogStats 5}

--
-- Tree: inktomiTSObjs/tsNetworkSubsystem
tsNetworkSubsystem OBJECT-IDENTITY
  STATUS current
  DESCRIPTION
     "subtree"
  ::= { inktomiTSObjs 8}

--
-- Tree: inktomiTSObjs/tsNetworkSubsystem/tsNetworkStats
tsNetworkStats OBJECT-IDENTITY
  STATUS current
  DESCRIPTION
     "subtree"
  ::= { tsNetworkSubsystem 1}

--
-- Tree: inktomiTSObjs/tsNetworkSubsystem/tsNetworkClusterStats
tsNetworkClusterStats OBJECT-IDENTITY
  STATUS current
  DESCRIPTION
     "subtree"
  ::= { tsNetworkSubsystem 2}

--
-- Tree: inktomiTSObjs/tsIOSubsystem
tsIOSubsystem OBJECT-IDENTITY
  STATUS current
  DESCRIPTION
     "subtree"
  ::= { inktomiTSObjs 9}

--
-- Tree: inktomiTSObjs/tsOSSubsystem
tsOSSubsystem OBJECT-IDENTITY
  STATUS current
  DESCRIPTION
     "subtree"
  ::= { inktomiTSObjs 10}

-- STANDARD SNMP traps to Manager alarm mappings
--		  SNMP #define	symbol	Traffic Manager #define
-- SNMP-trap: COLD-START-TRAP coldStart MGMT-ALARM-PROXY-PROCESS-DIED
-- ...


--
-- Tree: inktomiTSEvents

--
-- Tree: inktomiTSEvents/inktomiTSLogEvents
inktomiTSLogEvents OBJECT-IDENTITY
  STATUS current
  DESCRIPTION
     "subtree"
  ::= { inktomiTSEvents 1}
loggingError NOTIFICATION-TYPE
  STATUS current
  DESCRIPTION "
			Warning. An error with logging occurred.
			mgralarm: MGMT-ALARM-PROXY-LOGGING-ERROR
		"
  ::= { inktomiTSLogEvents 0 1}
loggingWarning NOTIFICATION-TYPE
  STATUS current
  DESCRIPTION "
			Warning. An error with logging occurred.
			mgralarm: MGMT-ALARM-PROXY-LOGGING-WARNING
		"
  ::= { inktomiTSLogEvents 0 2}
logSpaceCrisis NOTIFICATION-TYPE
  STATUS current
  DESCRIPTION "
			Warning. An error with logging occurred.
			mgralarm: MGMT-ALARM-PROXY-LOG-SPACE-CRISIS
		"
  ::= { inktomiTSLogEvents 0 3}

--
-- Tree: inktomiTSEvents/inktomiTSCacheEvents
inktomiTSCacheEvents OBJECT-IDENTITY
  STATUS current
  DESCRIPTION
     "subtree"
  ::= { inktomiTSEvents 2}
cacheError NOTIFICATION-TYPE
  STATUS current
  DESCRIPTION "
			Warning. An error with the cache occurred.
			mgralarm: MGMT-ALARM-PROXY-CACHE-ERROR
		"
  ::= { inktomiTSCacheEvents 0 1}
cacheWarning NOTIFICATION-TYPE
  STATUS current
  DESCRIPTION "
			Warning. An error with the cache occurred.
			mgralarm: MGMT-ALARM-PROXY-CACHE-WARNING
		"
  ::= { inktomiTSCacheEvents 0 2}

--
-- Tree: inktomiTSEvents/inktomiTSProtocolEvents
inktomiTSProtocolEvents OBJECT-IDENTITY
  STATUS current
  DESCRIPTION
     "subtree"
  ::= { inktomiTSEvents 3}
nntpError NOTIFICATION-TYPE
  STATUS current
  DESCRIPTION "
			Warning.
			mgralarm: MGMT-ALARM-PROXY-NNTP-ERROR
		"
  ::= { inktomiTSProtocolEvents 0 1}

--
-- Tree: inktomiTSEvents/inktomiTSGeneralEvents
inktomiTSGeneralEvents OBJECT-IDENTITY
  STATUS current
  DESCRIPTION
     "subtree"
  ::= { inktomiTSEvents 4}
configurationUpdateFailed NOTIFICATION-TYPE
  STATUS current
  DESCRIPTION "
			Warning. Configuration files were not written properly.
			mgralarm: MGMT-ALARM-CONFIG-UPDATE-FAILED
		"
  ::= { inktomiTSGeneralEvents 0 1}
managerUIInitFailed NOTIFICATION-TYPE
  STATUS current
  DESCRIPTION "
			Warning. Management UI was not enabled on startup.
			mgralarm: MGMT-ALARM-WEB-ERROR
		"
  ::= { inktomiTSGeneralEvents 0 2}
invalidConfig NOTIFICATION-TYPE
  STATUS current
  DESCRIPTION "
			Warning. Traffic server was started with an invalid configuration.
			mgralarm: MGMT-ALARM-PROXY-CONFIG-ERROR
		"
  ::= { inktomiTSGeneralEvents 0 3}
processBorn NOTIFICATION-TYPE
  STATUS current
  DESCRIPTION "
			Warning.  Traffic manager started traffic server.
			mgralarm: MGMT-ALARM-PROXY-PROCESS-BORN
		"
  ::= { inktomiTSGeneralEvents 0 4}
systemError NOTIFICATION-TYPE
  STATUS current
  DESCRIPTION "
			Warning.  Miscellaneous error.
			mgralarm: MGMT-ALARM-PROXY-SYSTEM-ERROR
		"
  ::= { inktomiTSGeneralEvents 0 5}
testAlarm NOTIFICATION-TYPE
  STATUS current
  DESCRIPTION "
			Debug. Test alarm generated by CLI
			mgralarm: MGMT-ALARM-MGMT-TEST
		"
  ::= { inktomiTSGeneralEvents 0 6}

--
-- Tree: inktomiTSEvents/inktomiTSClusterEvents
inktomiTSClusterEvents OBJECT-IDENTITY
  STATUS current
  DESCRIPTION
     "subtree"
  ::= { inktomiTSEvents 5}
peerDied NOTIFICATION-TYPE
  STATUS current
  DESCRIPTION "
			Warning.  Traffic manager noticed that a peer node went down.
			mgralarm: MGMT-ALARM-PROXY-PEER-DIED
		"
  ::= { inktomiTSClusterEvents 0 1}
peerBorn NOTIFICATION-TYPE
  STATUS current
  DESCRIPTION "
			Warning.  Traffic manager noticed that a peer node came up.
			mgralarm: MGMT-ALARM-PROXY-PEER-BORN
		"
  ::= { inktomiTSClusterEvents 0 2}
pingFailure NOTIFICATION-TYPE
  STATUS current
  DESCRIPTION "
			Warning.  Problem in bringing up virtual IP interface.
			mgralarm: MGMT-ALARM-PING-FAILURE
		"
  ::= { inktomiTSClusterEvents 0 3}
END
