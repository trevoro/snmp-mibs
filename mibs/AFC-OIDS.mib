-- SCCS: %W%	%G% %U% AFC

AFC-OIDS DEFINITIONS ::= BEGIN
IMPORTS
	enterprises FROM RFC1155-SMI;

afc OBJECT IDENTIFIER ::= { enterprises 2067 }
--  CONTACT-INFO
--    Advanced Fibre Communications
--    One Willow Brook Court
--    Petaluma, CA  94954
--    Voice: 707-794-7700
--    Fax: 707-794-7777


--  Description
--	This module provides the authoritive definitions for the part of the
--	the MIB naming tree below AFC's enterprise ID.  AFC has been assigned
--	the enterprise ID of 2067 by the IANA (Internet Assigned Numbers
--	Authority)
--
--	Copyright 1997,1998 Advanced Fibre Communications, Inc.
--

afcProducts OBJECT IDENTIFIER ::= { afc 1  }
-- OBJECT-IDENTITY
--  Status
--	mandatory
--  Description
--	All OIDS associated with an AFC product.

umc OBJECT IDENTIFIER ::= { afcProducts  1  }
-- OBJECT-IDENTITY
--  Status
--	mandatory
--  Description
--	OIDS associated with AFC's UMC product line

umcCommon OBJECT IDENTIFIER ::= { umc 1 }
-- OBJECT-IDENTITY
--  Status
--	mandatory
--  Description
--	The base of the OID tree for MIB variables that are common
--	to all models of the UMC

umc1000 OBJECT IDENTIFIER ::= { umc 2 }
-- OBJECT-IDENTITY
--  Status
--	mandatory
--  Description
--	The base of the OID tree for MIB variables specific to the UMC-1000
--	product.

afcEms OBJECT IDENTIFIER ::= { afcProducts 2 }
-- OBJECT-IDENTITY
--  Status
--	mandatory
--  Description
--	OIDS associated with AFC's EMS product line

afcEmsPlatformSpecific OBJECT IDENTIFIER ::= { afcEms 1 }
-- OBJECT-IDENTITY
--  Status
--	mandatory
--  Description
--	The OIDS associated with EMS platform specific objects and traps

afcEmsOV OBJECT IDENTIFIER ::= { afcEmsPlatformSpecific 1 }
-- OBJECT-IDENTITY
--  Status
--	mandatory
--  Description
--	The base of the OID tree for MIB variables specific to the HP OpenView
--	based EMS platform.

END
