--
-- ACC-NOTIFICATION-MIB.my
-- MIB generated by MG-SOFT Visual MIB Builder Version 3.0 Build 285
-- Wednesday, July 31, 2002 at 15:19:05
--

	ACC-NOTIFICATION-MIB DEFINITIONS ::= BEGIN
 
		IMPORTS
			accCommon			
				FROM ANDOVER-CONTROLS-MIB			
			OBJECT-GROUP, MODULE-COMPLIANCE			
				FROM SNMPv2-CONF			
			IpAddress, Integer32, Unsigned32, OBJECT-TYPE, MODULE-IDENTITY			
				FROM SNMPv2-SMI			
			StorageType, RowStatus			
				FROM SNMPv2-TC;
	
	
		-- 1.3.6.1.4.1.10829.4.1
		accNotificationMIB MODULE-IDENTITY 
			LAST-UPDATED "200210300946Z"		-- October 30, 2002 at 09:46 GMT
			ORGANIZATION 
				"Andover Controls Corporation"
			CONTACT-INFO 
				"Technical Support
				Andover Controls Corporation
				300 Brickstone Square
				Andover, MA 01810
				USA
				978-470-0555"
			DESCRIPTION 
				"This MIB module defines MIB objects which provide
				mechanisms to remotely configure the parameters
				used by an ACC NetController software for the generation of
				notifications."
			REVISION "200210300946Z"		-- October 30, 2002 at 09:46 GMT
			DESCRIPTION 
				"Revision 1.0"
			::= { accCommon 1 }

		
	
	
--
-- Node definitions
--
	
		-- 1.3.6.1.4.1.10829.4.1.1
		accNotifyObjects OBJECT IDENTIFIER::= { accNotificationMIB 1 }

		
		-- 1.3.6.1.4.1.10829.4.1.1.1
		accNotifyList OBJECT IDENTIFIER::= { accNotifyObjects 1 }

		
		-- 1.3.6.1.4.1.10829.4.1.1.1.1
		accNotifyNumber OBJECT-TYPE
			SYNTAX Integer32
			MAX-ACCESS read-only
			STATUS current
			DESCRIPTION
				"count of entries in the Notify Table"
			::= { accNotifyList 1 }

		
		-- 1.3.6.1.4.1.10829.4.1.1.1.2
		accNotifyTable OBJECT-TYPE
			SYNTAX SEQUENCE OF AccNotifyEntry
			MAX-ACCESS not-accessible
			STATUS current
			DESCRIPTION
				"This table is used to select management targets which should
				receive notifications, as well as the type of notification
				which should be sent to each selected management target."
			::= { accNotifyList 2 }

		
		-- 1.3.6.1.4.1.10829.4.1.1.1.2.1
		accNotifyEntry OBJECT-TYPE
			SYNTAX AccNotifyEntry
			MAX-ACCESS not-accessible
			STATUS current
			DESCRIPTION
				"An entry in this table selects a set of management targets
				which should receive notifications, as well as the type of
				notification which should be sent to each selected
				management target."
			INDEX { notifyIndex }
			::= { accNotifyTable 1 }

		
		AccNotifyEntry ::=
			SEQUENCE { 
				notifyIndex
					Unsigned32,
				notifyAddress
					IpAddress,
				notifyType
					INTEGER,
				notifyStorageType
					StorageType,
				notifyRowStatus
					INTEGER
			 }

		-- 1.3.6.1.4.1.10829.4.1.1.1.2.1.1
		notifyIndex OBJECT-TYPE
			SYNTAX Unsigned32
			MAX-ACCESS read-only
			STATUS current
			DESCRIPTION
				"The locally arbitrary, but unique identifier associated
				with this accNotifyEntry."
			::= { accNotifyEntry 1 }

		
		-- 1.3.6.1.4.1.10829.4.1.1.1.2.1.2
		notifyAddress OBJECT-TYPE
			SYNTAX IpAddress
			MAX-ACCESS read-write
			STATUS current
			DESCRIPTION
				"This object contains an IP Address as the
				destination of a notification"
			::= { accNotifyEntry 2 }

		
		-- 1.3.6.1.4.1.10829.4.1.1.1.2.1.3
		notifyType OBJECT-TYPE
			SYNTAX INTEGER
				{
				none(0),
				trap(1)
				}
			MAX-ACCESS read-write
			STATUS current
			DESCRIPTION
				"This object determines the type of notification to
				be generated. 
								
				If the value of this object is none(0), then no 
				messages will be generated.
												
				If the value of this object is trap(1), then any
				messages generated for selected rows will contain
				SNMPv2-Trap PDUs.				
				"
			DEFVAL { none }
			::= { accNotifyEntry 3 }

		
		-- 1.3.6.1.4.1.10829.4.1.1.1.2.1.4
		notifyStorageType OBJECT-TYPE
			SYNTAX StorageType
			MAX-ACCESS read-only
			STATUS current
			DESCRIPTION
				"The storage type for this conceptual row."
			::= { accNotifyEntry 4 }

		
		-- 1.3.6.1.4.1.10829.4.1.1.1.2.1.5
		notifyRowStatus OBJECT-TYPE
			SYNTAX INTEGER { active(1), inActive(2) } -- subset of RowStatus
			MAX-ACCESS read-write
			STATUS current
			DESCRIPTION
				"The status of this conceptual row.
				
				To set a field, a manager must set the 
				this object to inActive(2), then do the set. After finish, 
				change it to active(1)."
			::= { accNotifyEntry 5 }

		
		-- 1.3.6.1.4.1.10829.4.1.3
		accNotifyConformance OBJECT IDENTIFIER::= { accNotificationMIB 3 }

		
		-- 1.3.6.1.4.1.10829.4.1.3.1
		accNotifyCompliances OBJECT IDENTIFIER::= { accNotifyConformance 1 }

		
		-- 1.3.6.1.4.1.10829.4.1.3.1.1
		accNotifyBasicCompliance MODULE-COMPLIANCE
			STATUS current
			DESCRIPTION 
				"Module Compliance"
			MODULE -- this module
				MANDATORY-GROUPS { accNotifyGroup }
			::= { accNotifyCompliances 1 }

		
		-- 1.3.6.1.4.1.10829.4.1.3.2
		accNotifyGroups OBJECT IDENTIFIER::= { accNotifyConformance 2 }

		
		-- 1.3.6.1.4.1.10829.4.1.3.2.1
		accNotifyGroup OBJECT-GROUP
			OBJECTS { notifyIndex, notifyAddress, notifyType, notifyStorageType, notifyRowStatus, 
				accNotifyNumber }
			STATUS current
			DESCRIPTION 
				"A collection of objects for selecting which management
				targets are used for generating notifications, and the
				type of notification to be generated for each selected
				management target."
			::= { accNotifyGroups 1 }

		
	
	END

--
-- ACC-NOTIFICATION-MIB.my
--
