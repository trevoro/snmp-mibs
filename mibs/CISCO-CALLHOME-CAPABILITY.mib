-- *****************************************************************
-- CISCO-CALLHOME-CAPABILITY.my:
-- Cisco CISCO-CALLHOME-MIB AGENT-CAPABILITIES
--
-- March 2004, Dipesh Gorashia
--
-- Copyright (c) 2004 by Cisco Systems, Inc.
-- All rights reserved.
-- *****************************************************************

CISCO-CALLHOME-CAPABILITY DEFINITIONS ::= BEGIN

IMPORTS
        MODULE-IDENTITY,
        Unsigned32
                FROM SNMPv2-SMI
        AGENT-CAPABILITIES
                FROM SNMPv2-CONF
        SnmpAdminString
                FROM SNMP-FRAMEWORK-MIB
        ciscoAgentCapability
                FROM CISCO-SMI;

ciscoCallHomeCapability MODULE-IDENTITY
        LAST-UPDATED    "200403300000Z"
        ORGANIZATION    "Cisco Systems, Inc."
        CONTACT-INFO
                "       Cisco Systems
                        Customer Service

                Postal: 170 West Tasman Drive
                        San Jose, CA  95134
                        USA

                   Tel: +1 800 553-NETS

                E-mail: cs-san@cisco.com,
                        cs-lan-switch-snmp@cisco.com"
        DESCRIPTION
                "The capabilities description of
                CISCO-CALLHOME-MIB."

        REVISION        "200403300000Z"
        DESCRIPTION
                "Initial version of this MIB module."
        ::= { ciscoAgentCapability 355 }

cCallHomeCapCatOSV08R0101Cat6k AGENT-CAPABILITIES
    PRODUCT-RELEASE      "Cisco CatOS 8.1(1) on Catalyst 6000/6500
                          and Cisco 7600 series devices."
    STATUS               current
    DESCRIPTION          "CISCO-CALLHOME-MIB capabilities."

    SUPPORTS             CISCO-CALLHOME-MIB
        INCLUDES         { chConfigurationGroup,
                           chMultipleSmtpServersGroup,
                           chStatisticsGroup,
                           ccmSysLogSeverityGroup,
                           ccmMIBNotificationsConfigGroup,
                           ccmMIBNotificationsGroup }

        VARIATION        callHomeAlertAction 
            SYNTAX       INTEGER { noOp (1),
                                   test (2) }
            DESCRIPTION  "Only noOp (1) and test (2) enumerations
                          are supported."

        VARIATION        callHomeDestProfileName
            SYNTAX       SnmpAdminString (SIZE (1..11))
            DESCRIPTION  "Implementation supports a profile name of
                          size 1 to 11 octets." 

        VARIATION        callHomeDestProfileMsgFormat
            SYNTAX       INTEGER { shortText (3) }
            ACCESS       read-only
            DESCRIPTION  "Implementation supports read-only access
                          for this object. Only shortText (3) is 
                          supported."

        VARIATION        callHomeDestProfileMaxMsgSize
            SYNTAX       Unsigned32 (0..159)
            DESCRIPTION  "Message size in the range 0 to 159 is
                          supported."

       VARIATION         callHomeDestProfileTrnsprtMthd 
            SYNTAX       INTEGER { email (1) } 
            ACCESS       read-only
            DESCRIPTION  "Implementation supports read-only access
                          for this object. Only email (1) enumeration 
                          is supported."

       VARIATION         callHomeDestProfileStatus
            SYNTAX       INTEGER { active (1) }
            ACCESS       read-only
            DESCRIPTION  "Implementation supports read-only access 
                          for this object. Only active (1) enumeration 
                          is supported."

       VARIATION         callHomeDestEmailAddressEntry
            CREATION-REQUIRES { callHomeDestEmailAddress }
            DESCRIPTION  "For callHomeDestEmailAddressStatus object 
                          for instance to be set to active (1),
                          a valid value for corresponding 
                          callHomeDestEmailAddress is required."

       VARIATION         callHomeDestEmailAddressStatus
            SYNTAX       INTEGER { active (1),
                                   createAndGo (4),
                                   destroy (6) }
            DESCRIPTION  "Only active (1), createAndGo (4) and destroy (6)
                          are supported."

       VARIATION         callHomeEmailFrom
            SYNTAX       SnmpAdminString (SIZE (0..63)) 
            DESCRIPTION  "Implementation only supports an address of 
                          size 0 to 63 octets."

       VARIATION         callHomeEmailReplyTo
            SYNTAX       SnmpAdminString (SIZE (0..63)) 
            DESCRIPTION  "Implementation only supports an address of
                          size 0 to 63 octets."

       VARIATION         ccmSmtpServersAddrType
            SYNTAX       INTEGER  { ipv4 (1) }
            DESCRIPTION  "Implementation only supports IPv4 addresses."

       VARIATION         ccmSmtpServersPort
            ACCESS       read-only
            DESCRIPTION  "Implementation supports read-only access
                          for this object."

       VARIATION         ccmSmtpServersStatus
            SYNTAX       INTEGER  { active (1),
                                    createAndGo (4),
                                    destroy (6) }
            DESCRIPTION  "Only active (1), createAndGo (4) and destroy (6)
                          are supported."

    ::= { ciscoCallHomeCapability 1 }

END
