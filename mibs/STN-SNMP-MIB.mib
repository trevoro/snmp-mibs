-- *****************************************************************
--
-- stn-snmp.mib:  
--      Spring Tide Networks Interface MIB file.
--
--
--      Copyright (c) 1999, 2000 by Spring Tide Networks, Inc.
--                      ALL RIGHTS RESERVED       
--
-- *****************************************************************

-- MIB Object definitions for Spring Tide Network Snmp 

STN-SNMP-MIB DEFINITIONS ::= BEGIN

    IMPORTS
        MODULE-IDENTITY,
        OBJECT-TYPE,
        Integer32,
        IpAddress
                FROM SNMPv2-SMI

        DisplayString
                FROM SNMPv2-TC

        MODULE-COMPLIANCE, 
        OBJECT-GROUP
                FROM SNMPv2-CONF

        stnSystems
                FROM SPRING-TIDE-NETWORKS-SMI;


    stnSnmpMIB       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
                "STN SNMP MIB."
        ::= { stnSystems 14 }


    stnSnmp                 OBJECT IDENTIFIER ::= { stnSnmpMIB 1 }
    stnSnmpMibConformance   OBJECT IDENTIFIER ::= { stnSnmpMIB 2 }

    
    --
    -- Snmp Virtual Router Table
    --
    stnSnmpVirtualRouterTable OBJECT-TYPE
        SYNTAX        SEQUENCE OF StnSnmpVirtualRouterEntry
        MAX-ACCESS    not-accessible
        STATUS        current
        DESCRIPTION   "A list of virtual router entries."
        ::= { stnSnmp 1 }
 
    stnSnmpVirtualRouterEntry OBJECT-TYPE
        SYNTAX          StnSnmpVirtualRouterEntry
        MAX-ACCESS      not-accessible
        STATUS          current
        DESCRIPTION     "Entry contains Snmp information about a particular router."
        INDEX           { stnSnmpRouterInstance }
        ::= { stnSnmpVirtualRouterTable 1 }

 
    StnSnmpVirtualRouterEntry ::= SEQUENCE {
                stnSnmpRouterInstance       Integer32,
                stnSnmpEnabled              INTEGER,
                stnSnmpReadCommunity        DisplayString,
                stnSnmpReadView             DisplayString,
                stnSnmpContextName          DisplayString,
                stnSnmpWriteCommunity       DisplayString
                }

    stnSnmpRouterInstance OBJECT-TYPE
        SYNTAX          Integer32
        MAX-ACCESS      read-only
        STATUS          current
        DESCRIPTION     "A sequence number that identifies a particular 
                         router in the chassis."
        ::= { stnSnmpVirtualRouterEntry 1 }

    stnSnmpEnabled OBJECT-TYPE
        SYNTAX          INTEGER { 
                                enabled(1),    
                                disabled(2)
                                }
        MAX-ACCESS      read-only
        STATUS          current
        DESCRIPTION     "Indicates whether the SNMP agent process is enabled 
                         on this router"
        ::= { stnSnmpVirtualRouterEntry 2 }

    stnSnmpReadCommunity OBJECT-TYPE
        SYNTAX          DisplayString
        MAX-ACCESS      read-only
        STATUS          current
        DESCRIPTION     "Snmp read community string for this router."
        ::= { stnSnmpVirtualRouterEntry  3 }    

    stnSnmpReadView OBJECT-TYPE
        SYNTAX          DisplayString
        MAX-ACCESS      read-only
        STATUS          current
        DESCRIPTION     "The name of Snmp read view for this router."
        ::= { stnSnmpVirtualRouterEntry  4 }

    stnSnmpContextName OBJECT-TYPE
        SYNTAX          DisplayString
        MAX-ACCESS      read-only
        STATUS          current
        DESCRIPTION     "The name of Snmp context for this router."
        ::= { stnSnmpVirtualRouterEntry  5 }

    stnSnmpWriteCommunity OBJECT-TYPE
        SYNTAX          DisplayString
        MAX-ACCESS      read-only
        STATUS          current
        DESCRIPTION     "Snmp write community string for this router."
        ::= { stnSnmpVirtualRouterEntry  6 }


    --
    -- Snmp Trap Host Table
    --
    stnSnmpTrapHostTable OBJECT-TYPE
        SYNTAX        SEQUENCE OF StnSnmpTrapHostEntry
        MAX-ACCESS    not-accessible
        STATUS        current
        DESCRIPTION   "A list of SNMP trap hosts."
        ::= { stnSnmp 2 }
 
    stnSnmpTrapHostEntry OBJECT-TYPE
        SYNTAX          StnSnmpTrapHostEntry
        MAX-ACCESS      not-accessible
        STATUS          current
        DESCRIPTION     "Entry contains information about a particular 
                         SNMP trap host."
        INDEX           { stnSnmpTrapHostIndex }
        ::= { stnSnmpTrapHostTable 1 }

 
    StnSnmpTrapHostEntry ::= SEQUENCE {
                stnSnmpTrapHostIndex            Integer32,
                stnSnmpTrapHostIpAddress        IpAddress,
                stnSnmpTrapHostPort             Integer32
                }

    stnSnmpTrapHostIndex OBJECT-TYPE
        SYNTAX          Integer32
        MAX-ACCESS      read-only
        STATUS          current
        DESCRIPTION     "A sequence number that identifies a particular 
                         SNMP trap host."
        ::= { stnSnmpTrapHostEntry 1 }

    stnSnmpTrapHostIpAddress OBJECT-TYPE
        SYNTAX          IpAddress
        MAX-ACCESS      read-only
        STATUS          current
        DESCRIPTION     "The IP address of this SNMP trap host." 
        ::= { stnSnmpTrapHostEntry 2 }

    stnSnmpTrapHostPort OBJECT-TYPE
        SYNTAX          Integer32
        MAX-ACCESS      read-only
        STATUS          current
        DESCRIPTION     "The port number of this SNMP trap host."
        ::= { stnSnmpTrapHostEntry 3 }

    --
    -- Conformance information
    --

    stnSnmpMIBConformance OBJECT IDENTIFIER ::= { stnSnmpMIB 3 }
    stnSnmpMIBCompliances  OBJECT IDENTIFIER ::= { stnSnmpMIBConformance 1 }
    stnSnmpMIBGroups       OBJECT IDENTIFIER ::= { stnSnmpMIBConformance 2 }


    --
    -- Compliance statements
    --

    stnSnmpMIBComplianceRev1 MODULE-COMPLIANCE
        STATUS  current 
        DESCRIPTION
                "The compliance statement for entities which implement
                 the Spring Tide Networks Snmp MIB."
        MODULE  -- this module
                MANDATORY-GROUPS { stnSnmpMIBGroup }
        ::= { stnSnmpMIBCompliances 1 }


    --
    -- Conformance Units
    --

    stnSnmpMIBGroup OBJECT-GROUP
        OBJECTS {
                stnSnmpRouterInstance,
                stnSnmpEnabled,
                stnSnmpReadCommunity,
                stnSnmpReadView,
                stnSnmpContextName   
        }
        STATUS current
        DESCRIPTION 
            "A collection of STN objects providing router Snmp information."
        ::= { stnSnmpMIBGroups 1 }

   
END
