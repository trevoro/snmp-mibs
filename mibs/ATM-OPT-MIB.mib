-- 2.15.1.2 modified 2001-10-01 10:31:27-04


        ATM-OPT-MIB DEFINITIONS ::= BEGIN

        IMPORTS
            Counter, enterprises
                FROM RFC1155-SMI

            OBJECT-TYPE
                FROM RFC-1212;

                         codex OBJECT IDENTIFIER ::= { enterprises 449 }
            cdxProductSpecific OBJECT IDENTIFIER ::= { codex 2 }
                       cdx6500 OBJECT IDENTIFIER ::= { cdxProductSpecific 1 }

         cdx6500Configuration  OBJECT IDENTIFIER ::= { cdx6500 2 }
       cdx6500CfgProtocolGroup OBJECT IDENTIFIER ::= { cdx6500Configuration 1 }
   cdx6500PCTPortProtocolGroup OBJECT IDENTIFIER ::= { cdx6500CfgProtocolGroup 1 }
cdx6500PCTStationProtocolGroup OBJECT IDENTIFIER ::= { cdx6500CfgProtocolGroup 3 }

             cdx6500Statistics OBJECT IDENTIFIER ::= { cdx6500 3 }
      cdx6500StatProtocolGroup OBJECT IDENTIFIER ::= { cdx6500Statistics 1 }
   cdx6500PSTPortProtocolGroup OBJECT IDENTIFIER ::= { cdx6500StatProtocolGroup 1 }
cdx6500PSTStationProtocolGroup OBJECT IDENTIFIER ::= { cdx6500StatProtocolGroup 3 }

               cdx6500Controls OBJECT IDENTIFIER ::= { cdx6500 4 }

        DisplayString ::=
            OCTET STRING
        -- This data type is used to model textual information taken
        -- from the NVT ASCII character set.  By convention, objects
        -- with this syntax are declared as having SIZE (0..255)


        -- The ATM Port Configuration Table

        cdx6500PPCTATMPortTable OBJECT-TYPE
            SYNTAX SEQUENCE OF Cdx6500PPCTATMPortEntry
            ACCESS not-accessible
            STATUS mandatory
            DESCRIPTION
                "This table contains ATM Port configuration
                 parameters."
        ::= { cdx6500PCTPortProtocolGroup 35 }

        cdx6500PPCTATMPortEntry OBJECT-TYPE
            SYNTAX Cdx6500PPCTATMPortEntry
            ACCESS not-accessible
            STATUS mandatory
            DESCRIPTION
                "Entries in the ATM Port Configuration Table."
            INDEX { atmPCfgPortNumber }
        ::= { cdx6500PPCTATMPortTable 1 }

        Cdx6500PPCTATMPortEntry ::=
            SEQUENCE {
                atmPCfgPortNumber
                    INTEGER,
                atmPCfgPortType
                    INTEGER,
                atmPCfgMaxVPIRange
                    INTEGER,
                atmPCfgMaxVCIRange
                    INTEGER,
                atmPCfgLinkAssuranceTimer
                    INTEGER,
                atmPCfgLinkAssuranceCount
                    INTEGER,
                atmPCfgCCActDeactTimer
                    INTEGER,
                atmPCfgCCActDeactCount
                    INTEGER,
		atmPCfgVCCTrafficPrioritization
		    INTEGER
		}

        atmPCfgPortNumber OBJECT-TYPE
            SYNTAX  INTEGER 
            ACCESS  read-only
            STATUS  mandatory
            DESCRIPTION
                "Port number of this port."
        ::= { cdx6500PPCTATMPortEntry 1 }

        atmPCfgPortType OBJECT-TYPE
            SYNTAX INTEGER {
                   atm(57)
                   }
            ACCESS read-only
            STATUS mandatory
            DESCRIPTION
                "Port type of the Port."
--            DEFVAL { atm }
        ::= { cdx6500PPCTATMPortEntry 2 }

        atmPCfgMaxVPIRange  OBJECT-TYPE
            SYNTAX INTEGER 
            ACCESS read-only
            STATUS deprecated
            DESCRIPTION
                 "This parameter specifies the maximum VPI value that any station on
		  this port can operate with. Increasing this value has the effect of
		  decreasing the maximum VPI that can be specified ."
        ::= { cdx6500PPCTATMPortEntry 3 }

        atmPCfgMaxVCIRange  OBJECT-TYPE
            SYNTAX INTEGER
            ACCESS read-only
            STATUS deprecated
            DESCRIPTION
                 "This parameter specifies the maximum VCI value that any station on
		  this port can operate with. Increasing this value has the effect of
		  decreasing the maximum VCI that can be specified ."
        ::= { cdx6500PPCTATMPortEntry 4 }

        atmPCfgLinkAssuranceTimer  OBJECT-TYPE
            SYNTAX INTEGER
            ACCESS read-only
            STATUS deprecated
            DESCRIPTION
                 "If PVC Link Assurance Method is set to LOOPBACK, this is the
		  amount of time in seconds between sending F5 loopback cells ."
        ::= { cdx6500PPCTATMPortEntry 5 }

        atmPCfgLinkAssuranceCount OBJECT-TYPE
            SYNTAX INTEGER
            ACCESS read-only
            STATUS deprecated
            DESCRIPTION
                 "If PVC Link Assurance Method is set to LOOPBACK, this is the
		  number of retries sent before declaring that the link is down ."
        ::= { cdx6500PPCTATMPortEntry 6 }

        atmPCfgCCActDeactTimer  OBJECT-TYPE
            SYNTAX INTEGER
            ACCESS read-only
            STATUS deprecated
            DESCRIPTION
                 "If PVC Link Assurance Method is set to NEGOTIATE CC cells this is the
		  amount of time in seconds between retransmissions of Activate or
		  Deactivate cells."
        ::= { cdx6500PPCTATMPortEntry 7 }

        atmPCfgCCActDeactCount OBJECT-TYPE
            SYNTAX INTEGER
            ACCESS read-only
            STATUS deprecated
            DESCRIPTION
                 "If PVC Link Assurance Method is set to NEGOTIATE CC cells this is the
		  number of times to send an Activate or Deactivate cell before declaring
		  that the negotiation procedure has failed ."
        ::= { cdx6500PPCTATMPortEntry 8 }

        atmPCfgVCCTrafficPrioritization OBJECT-TYPE
            SYNTAX INTEGER {
		   disable	(1),
		   sequence	(2),
		   priority	(3)
		   }
            ACCESS read-only
            STATUS mandatory
            DESCRIPTION
		"All station VCCs that operate on the port must run with the same traffic
		 prioritization dicipline.  This port parameter specifies the priorization
		 as follows:
   		 DISABLE  - There is no prioritization of traffic within a VCC.
   		 SEQUENCE - High priority and normal priority traffic are placed in separate
			    queues which are serviced in sequential round robin order.
   		 PRIORITY - High priority and normal priority traffic are placed in separate
			    queues. The high priority queue is serviced completely before 
			    the low priority queue."
        ::= { cdx6500PPCTATMPortEntry 9 }

        -- The ATM Station Configuration Table

        cdx6500SPCTATMStationTable OBJECT-TYPE
            SYNTAX SEQUENCE OF Cdx6500SPCTATMStationEntry
            ACCESS  not-accessible
            STATUS  mandatory
            DESCRIPTION
                "This table contains ATM Station configuration
                 parameters."
        ::= { cdx6500PCTStationProtocolGroup 10 }

        cdx6500SPCTATMStationEntry OBJECT-TYPE
            SYNTAX  Cdx6500SPCTATMStationEntry
            ACCESS  not-accessible
            STATUS  mandatory
            DESCRIPTION
                "Entries in the ATM Station Configuration Table."
            INDEX  { atmSCfgPortNumber, atmSCfgStnNumber }
        ::= { cdx6500SPCTATMStationTable 1 }
        Cdx6500SPCTATMStationEntry ::=
            SEQUENCE {
                atmSCfgPortNumber
                    INTEGER,
                atmSCfgStnNumber
                    INTEGER,
                atmSCfgVPI
                    INTEGER,
                atmSCfgVCI
                    INTEGER,
                atmSCfgLinkAssuranceMethod
                    INTEGER,
                atmSCfgTrafficServiceCategory
                    INTEGER,
                atmSCfgPeakCellRate
                    INTEGER,
		atmSCfgVBRTrafficShaping
		    INTEGER,
		atmSCfgVCCPriorityLevel
		    INTEGER,
		atmSCfgSustainableCellRate
		    INTEGER,
		atmSCfgMaximumBustSize
		    INTEGER
	 	}

        atmSCfgPortNumber OBJECT-TYPE
            SYNTAX INTEGER 
            ACCESS read-only
            STATUS mandatory
            DESCRIPTION
                "The ATM port number corresponding to this station."
        ::= { cdx6500SPCTATMStationEntry 1 }

        atmSCfgStnNumber OBJECT-TYPE
            SYNTAX INTEGER 
            ACCESS read-only
            STATUS mandatory
            DESCRIPTION
                "The number of the configured ATM Station."
        ::= { cdx6500SPCTATMStationEntry 2 }

        atmSCfgVPI OBJECT-TYPE
            SYNTAX INTEGER 
            ACCESS read-only
            STATUS mandatory
            DESCRIPTION
                "The Virtual Path Identifier (VPI) is the provisioned virtual path
		 number for the station of circuit type PVC on the ATM port."
        ::= { cdx6500SPCTATMStationEntry 3 }

        atmSCfgVCI OBJECT-TYPE
            SYNTAX INTEGER 
            ACCESS read-only
            STATUS mandatory
            DESCRIPTION
                "The Virtual Circuit Identifier (VCI) is the provisioned virtual circuit
		 number for the station of circuit type PVC on the ATM port."
        ::= { cdx6500SPCTATMStationEntry 4 }

        atmSCfgLinkAssuranceMethod OBJECT-TYPE
            SYNTAX INTEGER {
		disabled	(1),
		loopback	(2),
		enabled		(3),
		nogotiate	(4)
		}
            ACCESS read-only
            STATUS mandatory
            DESCRIPTION
                "PVC link assurance method to use:
		   DISABLED  - No checking is performed
	           LOOPBACK  - Periodically send a loopback cell
	           NEGOTIATE - Negotiate use of CC cells
		   ENABLED   - Always use CC cells ."
        ::= { cdx6500SPCTATMStationEntry 5 }

        atmSCfgTrafficServiceCategory OBJECT-TYPE
            SYNTAX INTEGER {
			ubr	(1),
			cbr	(2),
			vbr	(3)
			}
            ACCESS read-only
            STATUS mandatory
            DESCRIPTION
                "The service category is the traffic type for the operation
		  of the station. The traffic types are:
			UBR    - Unspecified Bit Rate
		        CBR    - Constant Bit Rate
			VBR    - Variable Bit Rate."
        ::= { cdx6500SPCTATMStationEntry 6 }

        atmSCfgPeakCellRate OBJECT-TYPE
            SYNTAX INTEGER
            ACCESS read-only
            STATUS mandatory
            DESCRIPTION
                "This parameter (PCR) specifies the rate (cells per second) the
		 network agrees to receive cells from the station 
		 PCR is configuredin multiples of 20 cells per second."
        ::= { cdx6500SPCTATMStationEntry 7 }

        atmSCfgVBRTrafficShaping OBJECT-TYPE
            SYNTAX INTEGER {
			single	(2),
			dual	(1)
			}
            ACCESS read-only
            STATUS mandatory
            DESCRIPTION
		"Specifies whether a station configured for VBR traffic category conforms
		 to single or dual leaky bucket traffic shaping. Single leaky bucket means
		 the traffic is shaped to only a PCR.  Dual bucket shaping means traffic is
		 shaped to PCR as well as SCR and MBS.
   			SINGLE - Single Bucket VBR
   			DUAL   - Dual Bucket VBR."
        ::= { cdx6500SPCTATMStationEntry 8 }

        atmSCfgVCCPriorityLevel OBJECT-TYPE
            SYNTAX INTEGER {
			normal	(1),
			high	(2)
			}
            ACCESS read-only
            STATUS mandatory
            DESCRIPTION
		"This parameter controls the priority of the station VCC in comparison to
		 other stations within the same service category (either UBR or VBR). For
		 VBR traffic category, setting this parameter to HIGH classifies a VCC as
		 VBRrt (VBR real time). For VBRnrt (non-real time) select NORMAL.
   			NORMAL - Normal priority
   			HIGH   - High priority."
        ::= { cdx6500SPCTATMStationEntry 9 }

        atmSCfgSustainableCellRate OBJECT-TYPE
            SYNTAX INTEGER (128..30000)
            ACCESS read-only
            STATUS deprecated
            DESCRIPTION
		"This parameter (SCR) specifies the rate (cells per second) the
		 network agrees to receive cells from the station. This parameter
		 characterizes the amount of sustainable bandwidth for VBR traffic
		 class. The SCR cannot be greater than the link speed:
		 3620 for T1, 4800 for E1, 105500 for T3 (96000 for PLCP), 81040 for E3."
        ::= { cdx6500SPCTATMStationEntry 10 }

        atmSCfgMaximumBustSize OBJECT-TYPE
            SYNTAX INTEGER(1..65535)
            ACCESS read-only
            STATUS deprecated
            DESCRIPTION
		"Maximum burst size for VBR traffic in cells"
        ::= { cdx6500SPCTATMStationEntry 11 }

        -- ATM Port Statistics Table
        -- This table replaces cdx6500PPSTFRDTEPortTable which is now
        -- obsolete
        cdx6500PPSTATMPStatsTable OBJECT IDENTIFIER
        ::= { cdx6500PSTPortProtocolGroup 36 }

        cdx6500PPSTATMPortTable OBJECT-TYPE
            SYNTAX SEQUENCE OF Cdx6500PPSTATMPortEntry
            ACCESS not-accessible
            STATUS mandatory
            DESCRIPTION
                "This table contains ATM Port Statistics parameters."
        ::= { cdx6500PPSTATMPStatsTable 1 }

        cdx6500PPSTATMPortEntry OBJECT-TYPE
            SYNTAX Cdx6500PPSTATMPortEntry
            ACCESS not-accessible
            STATUS mandatory
            DESCRIPTION
                "Entries in the ATM Port Statistics Table."
            INDEX { atmPStatsPortNumber }
        ::= { cdx6500PPSTATMPortTable 1 }

        Cdx6500PPSTATMPortEntry ::=
            SEQUENCE {
                atmPStatsPortNumber
                    INTEGER,
                atmPStatsPortType
                    INTEGER,
                atmPStatsPortStatus
                    DisplayString 
             }

        atmPStatsPortNumber OBJECT-TYPE
            SYNTAX INTEGER 
            ACCESS read-only
            STATUS mandatory
            DESCRIPTION
                "The port number of the ATM port."
        ::= { cdx6500PPSTATMPortEntry 1 }

        atmPStatsPortType OBJECT-TYPE
            SYNTAX INTEGER {
                   atm(57)
                   }
            ACCESS read-only
            STATUS mandatory
            DESCRIPTION
                "Port type of this port."
        ::= { cdx6500PPSTATMPortEntry 2 }

        atmPStatsPortStatus OBJECT-TYPE
            SYNTAX DisplayString
            ACCESS read-only
            STATUS mandatory
            DESCRIPTION
                "Specifies the current port status."
        ::= { cdx6500PPSTATMPortEntry 3 }


        cdx6500PPSTATMDataSummaryTable OBJECT-TYPE
            SYNTAX SEQUENCE OF Cdx6500PPSTATMDataSummaryEntry
            ACCESS not-accessible
            STATUS mandatory
            DESCRIPTION
                "This table contains ATM Port Data Summary
                 Statistics parameters."
        ::= { cdx6500PPSTATMPStatsTable 2 }

        cdx6500PPSTATMDataSummaryEntry OBJECT-TYPE
            SYNTAX Cdx6500PPSTATMDataSummaryEntry
            ACCESS not-accessible
            STATUS mandatory
            DESCRIPTION
                "Entries in the ATM Port Data Summary Statistics Table."
            INDEX { atmDataSummPortNumber }
        ::= { cdx6500PPSTATMDataSummaryTable 1 }

        Cdx6500PPSTATMDataSummaryEntry ::=
            SEQUENCE {
                atmDataSummPortNumber
                    INTEGER,
                atmPStatsOctetsInTotal
                    Counter,
                atmPStatsOctetsOutTotal
                    Counter,
                atmPStatsOctetsInPerSec
                    INTEGER,
                atmPStatsOctetsOutPerSec
                    INTEGER,
                atmPStatsFramesInTotal
                    Counter,
                atmPStatsFramesOutTotal
                    Counter,
                atmPStatsFramesInPerSec
                    INTEGER,
                atmPStatsFramesOutPerSec
                    INTEGER,
                atmPStatsOAMCellInTotal
                    Counter,
                atmPStatsOAMCellOutTotal
                    Counter,
                atmPStatsATMCellInTotal
                    Counter,
                atmPStatsATMCellOutTotal
                    Counter,
		atmPStatsErrorCellCor
		    INTEGER,
		atmPStatsErrorCellDis
		    INTEGER,
		atmPStatsCellDelineateState
		    DisplayString,
		atmPStatsCellStateChangeTime
		    DisplayString,
		atmPStatsDiscardedFrames
		    Counter
            }

        atmDataSummPortNumber OBJECT-TYPE
            SYNTAX INTEGER 
            ACCESS read-only
            STATUS mandatory
            DESCRIPTION
                "The port number of the ATM port."
        ::= { cdx6500PPSTATMDataSummaryEntry 1 }

        atmPStatsOctetsInTotal OBJECT-TYPE
            SYNTAX Counter
            ACCESS read-only
            STATUS mandatory
            DESCRIPTION
                "Number of characters received since last boot or statistics
                 reset."
        ::= { cdx6500PPSTATMDataSummaryEntry 2 }

        atmPStatsOctetsOutTotal OBJECT-TYPE
            SYNTAX Counter
            ACCESS read-only
            STATUS mandatory
            DESCRIPTION
                "Number of characters transmitted since last boot or statistics
                 reset."
        ::= { cdx6500PPSTATMDataSummaryEntry 3 }

        atmPStatsOctetsInPerSec OBJECT-TYPE
            SYNTAX INTEGER
            ACCESS read-only
            STATUS mandatory
            DESCRIPTION
                "Average number of characters received per second."
        ::= { cdx6500PPSTATMDataSummaryEntry 4 }

        atmPStatsOctetsOutPerSec  OBJECT-TYPE
            SYNTAX INTEGER
            ACCESS read-only
            STATUS mandatory
            DESCRIPTION
                "Average number of characters transmitted per second."
        ::= { cdx6500PPSTATMDataSummaryEntry 5 }

        atmPStatsFramesInTotal OBJECT-TYPE
            SYNTAX Counter
            ACCESS read-only
            STATUS mandatory
            DESCRIPTION
                "Number of frames received since last boot or statistics
                 reset."
        ::= { cdx6500PPSTATMDataSummaryEntry 6 }

        atmPStatsFramesOutTotal OBJECT-TYPE
            SYNTAX Counter
            ACCESS read-only
            STATUS mandatory
            DESCRIPTION
                "Number of frames transmitted since last boot or statistics
                 reset."
        ::= { cdx6500PPSTATMDataSummaryEntry 7 }

        atmPStatsFramesInPerSec OBJECT-TYPE
            SYNTAX INTEGER
            ACCESS read-only
            STATUS mandatory
            DESCRIPTION
                "Average number of frames received per second."
        ::= { cdx6500PPSTATMDataSummaryEntry 8 }


        atmPStatsFramesOutPerSec OBJECT-TYPE
            SYNTAX INTEGER
            ACCESS read-only
            STATUS mandatory
            DESCRIPTION
                "Average number of frames transmitted per second."
        ::= { cdx6500PPSTATMDataSummaryEntry 9 }

        atmPStatsOAMCellInTotal OBJECT-TYPE
            SYNTAX Counter 
            ACCESS read-only
            STATUS mandatory
            DESCRIPTION
                "Number of OAM Cells received since last boot or statistics."
        ::= { cdx6500PPSTATMDataSummaryEntry 10 }

        atmPStatsOAMCellOutTotal OBJECT-TYPE
            SYNTAX Counter 
            ACCESS read-only
            STATUS mandatory
            DESCRIPTION
                "Number of OAM Cells transmitted since last boot or statistics."
        ::= { cdx6500PPSTATMDataSummaryEntry 11 }

        atmPStatsATMCellInTotal OBJECT-TYPE
            SYNTAX Counter
            ACCESS read-only
            STATUS mandatory
            DESCRIPTION
                "Number of ATM Cells received since last boot or statistics."
        ::= { cdx6500PPSTATMDataSummaryEntry 12 }

        atmPStatsATMCellOutTotal OBJECT-TYPE
            SYNTAX Counter
            ACCESS read-only
            STATUS mandatory
            DESCRIPTION
                "Number of ATM Cells transmitted since last boot or statistics."
        ::= { cdx6500PPSTATMDataSummaryEntry 13 }

        atmPStatsErrorCellCor OBJECT-TYPE
            SYNTAX INTEGER 
            ACCESS read-only
            STATUS mandatory
            DESCRIPTION
                "HEC(Cor) errors in Physical Layer."
        ::= { cdx6500PPSTATMDataSummaryEntry 14 }

        atmPStatsErrorCellDis OBJECT-TYPE
            SYNTAX INTEGER 
            ACCESS read-only
            STATUS mandatory
            DESCRIPTION
                "HEC(Dis) errors in Physical Layer."
        ::= { cdx6500PPSTATMDataSummaryEntry 15 }

        atmPStatsCellDelineateState OBJECT-TYPE
            SYNTAX DisplayString 
            ACCESS read-only
            STATUS mandatory
            DESCRIPTION
                "ATM Physical Layer state."
        ::= { cdx6500PPSTATMDataSummaryEntry 16 }

        atmPStatsCellStateChangeTime OBJECT-TYPE
            SYNTAX DisplayString 
            ACCESS read-only
            STATUS mandatory
            DESCRIPTION
                "The state change time in ATM Physical Layer."
        ::= { cdx6500PPSTATMDataSummaryEntry 17 }

        atmPStatsDiscardedFrames OBJECT-TYPE
            SYNTAX Counter 
            ACCESS read-only
            STATUS mandatory
            DESCRIPTION
                "The total number of dicarded frames."
        ::= { cdx6500PPSTATMDataSummaryEntry 18 }
        -- ATM Station Statistics Table

        cdx6500SPSTATMSStatsTable OBJECT IDENTIFIER
        ::= { cdx6500PSTStationProtocolGroup 11 }

        -- General ATM Statistics Table
        atmSGenStatsTable OBJECT-TYPE
            SYNTAX SEQUENCE OF Cdx6500atmSGenStatsEntry
            ACCESS not-accessible
            STATUS mandatory
            DESCRIPTION
                "This table contains ATM Station Statistics parameters."
        ::= { cdx6500SPSTATMSStatsTable 1 }

        cdx6500atmSGenStatsEntry OBJECT-TYPE
            SYNTAX Cdx6500atmSGenStatsEntry
            ACCESS not-accessible
            STATUS mandatory
            DESCRIPTION
                "Entries in the ATM Station Statistics Table."
            INDEX { atmSGenStatsPortNumber, atmSGenStatsStnNumber }
        ::= { atmSGenStatsTable 1 }

        Cdx6500atmSGenStatsEntry ::=
            SEQUENCE {
                atmSGenStatsPortNumber
                    INTEGER,
                atmSGenStatsStnNumber
                    INTEGER,
                atmSStatsStnStatus
                    DisplayString,
		atmSStatsVPI
		    INTEGER, 
		atmSStatsVCI
		    INTEGER, 
		atmSStatsAdmState
		    INTEGER, 
		atmSStatsPeer
		    INTEGER, 
		atmSStatsAdjacent
		    INTEGER 
		}

        atmSGenStatsPortNumber OBJECT-TYPE
            SYNTAX INTEGER 
            ACCESS read-only
            STATUS mandatory
            DESCRIPTION
                "The ATM port number corresponding to this station."
        ::= { cdx6500atmSGenStatsEntry 1 }

        atmSGenStatsStnNumber OBJECT-TYPE
            SYNTAX INTEGER
            ACCESS read-only
            STATUS mandatory
            DESCRIPTION
                "The number of the ATM Station."
        ::= { cdx6500atmSGenStatsEntry 2 }

        atmSStatsStnStatus OBJECT-TYPE
            SYNTAX DisplayString
            ACCESS read-only
            STATUS mandatory
            DESCRIPTION
                "Status of the station."
        ::= { cdx6500atmSGenStatsEntry 3 }

        atmSStatsVPI OBJECT-TYPE
            SYNTAX INTEGER 
            ACCESS read-only
            STATUS mandatory
            DESCRIPTION
                "The VPI of ATM Station."
        ::= { cdx6500atmSGenStatsEntry 4 }

        atmSStatsVCI OBJECT-TYPE
            SYNTAX INTEGER 
            ACCESS read-only
            STATUS mandatory
            DESCRIPTION
                "The VCI of the ATM Station."
        ::= { cdx6500atmSGenStatsEntry 5 }

        atmSStatsAdmState OBJECT-TYPE
            SYNTAX INTEGER {
			disable(1),
			enable(2)
			}
            ACCESS read-only
            STATUS mandatory
            DESCRIPTION
                "The VCI of the ATM Station."
        ::= { cdx6500atmSGenStatsEntry 6 }

        atmSStatsPeer OBJECT-TYPE
            SYNTAX INTEGER 
            ACCESS read-only
            STATUS mandatory
            DESCRIPTION
                "The Peer state of the ATM Station."
        ::= { cdx6500atmSGenStatsEntry 7 }

        atmSStatsAdjacent OBJECT-TYPE
            SYNTAX INTEGER 
            ACCESS read-only
            STATUS mandatory
            DESCRIPTION
                "The Adjacent state of the ATM Station."
        ::= { cdx6500atmSGenStatsEntry 8 }

        -- Data Summary Statistics Table
        atmSDataSummaryStatsTable OBJECT-TYPE
            SYNTAX SEQUENCE OF Cdx6500atmSDataSummaryStatsEntry
            ACCESS not-accessible
            STATUS mandatory
            DESCRIPTION
                "This table contains ATM Station Data Summary Statistics
                 parameters."
        ::= { cdx6500SPSTATMSStatsTable 2 }

        cdx6500atmSDataSummaryStatsEntry OBJECT-TYPE
            SYNTAX Cdx6500atmSDataSummaryStatsEntry
            ACCESS not-accessible
            STATUS mandatory
            DESCRIPTION
                "Entries in the ATM Station Data Summary Statistics Table."
            INDEX { atmSDataSummStatsPortNumber,
                    atmSDataSummStatsStnNumber }
        ::= { atmSDataSummaryStatsTable 1 }

        Cdx6500atmSDataSummaryStatsEntry ::=
            SEQUENCE {
                atmSDataSummStatsPortNumber
                    INTEGER,
                atmSDataSummStatsStnNumber
                    INTEGER,
                atmSStatsOctetsInTotal
                    Counter,
                atmSStatsOctetsOutTotal
                    Counter,
                atmSStatsFrameInTotal
                    Counter,
                atmSStatsFrameOutTotal
                    Counter,
                atmSStatsF5CellInTotal
                    Counter,
                atmSStatsF5CellOutTotal
                    Counter,
	        atmSStatsAISCellInTotal
		    Counter,
                atmSStatsRDICellInTotal
                    Counter,
                atmSStatsRDICellOutTotal
                    Counter,
                atmSStatsCCCellInTotal
                    Counter,
                atmSStatsCCCellOutTotal
                    Counter,
		atmSStatsVCFailure
		    INTEGER,
		atmSStatsVCAssuranceState
		    DisplayString,
		atmSStatsOctetsInPerSec
		    Counter,
		atmSStatsOctetsOutPerSec
		    Counter,
		atmSStatsFramesInPerSec
		    Counter,
		atmSStatsFramesOutPerSec
		    Counter,
		atmSStatsDiscardedFrames
		    Counter,
		atmSStatsCIBitInForIWF
		    Counter,
		atmSStatsCIBitOutForIWF
		    Counter,
		atmSStatsCLPBitInForIWF
		    Counter,
		atmSStatsCLPBitOutForIWF
		    Counter,
		atmSStatsUUBitInForIWF
		    Counter,
		atmSStatsUUBitOutForIWF
		    Counter
		
		}

        atmSDataSummStatsPortNumber OBJECT-TYPE
            SYNTAX INTEGER 
            ACCESS read-only
            STATUS mandatory
            DESCRIPTION
                "The ATM port number corresponding to this station."
        ::= { cdx6500atmSDataSummaryStatsEntry 1 }

        atmSDataSummStatsStnNumber OBJECT-TYPE
            SYNTAX INTEGER 
            ACCESS read-only
            STATUS mandatory
            DESCRIPTION
                "The number of the ATM station."
        ::= { cdx6500atmSDataSummaryStatsEntry 2 }

        atmSStatsOctetsInTotal OBJECT-TYPE
            SYNTAX Counter
            ACCESS read-only
            STATUS mandatory
            DESCRIPTION
                "Number of characters received since last node boot or
                 statistics reset."
        ::= { cdx6500atmSDataSummaryStatsEntry 3 }

        atmSStatsOctetsOutTotal OBJECT-TYPE
            SYNTAX Counter
            ACCESS read-only
            STATUS mandatory
            DESCRIPTION
                "Number of characters transmitted since last node boot or
                 statistics reset."
        ::= { cdx6500atmSDataSummaryStatsEntry 4 }

        atmSStatsFrameInTotal OBJECT-TYPE
            SYNTAX Counter
            ACCESS read-only
            STATUS mandatory
            DESCRIPTION
                "Number of frames transmitted since last node boot
                 or statistics reset."
        ::= { cdx6500atmSDataSummaryStatsEntry 5 }

        atmSStatsFrameOutTotal OBJECT-TYPE
            SYNTAX Counter
            ACCESS read-only
            STATUS mandatory
            DESCRIPTION
                "Number of frames transmitted since last node boot or
                 statistics reset."
        ::= { cdx6500atmSDataSummaryStatsEntry 6 }

        atmSStatsF5CellInTotal OBJECT-TYPE
            SYNTAX Counter
            ACCESS read-only
            STATUS mandatory
            DESCRIPTION
                "Number of F5 Cells received since last node boot
                 or statistics reset."
        ::= { cdx6500atmSDataSummaryStatsEntry 7 }

        atmSStatsF5CellOutTotal OBJECT-TYPE
            SYNTAX Counter
            ACCESS read-only
            STATUS mandatory
            DESCRIPTION
                "Number of F5 Cells transmitted since last node boot or
                 statistics reset."
        ::= { cdx6500atmSDataSummaryStatsEntry 8 }

        atmSStatsAISCellInTotal OBJECT-TYPE
            SYNTAX Counter
            ACCESS read-only
            STATUS mandatory
            DESCRIPTION
                "Number of AIS Cells received since last node boot
                 or statistics reset."
        ::= { cdx6500atmSDataSummaryStatsEntry 9 }

        atmSStatsRDICellInTotal OBJECT-TYPE
            SYNTAX Counter
            ACCESS read-only
            STATUS mandatory
            DESCRIPTION
                "Number of RDI Cells received since last node boot
                 or statistics reset."
        ::= { cdx6500atmSDataSummaryStatsEntry 10 }

        atmSStatsRDICellOutTotal OBJECT-TYPE
            SYNTAX Counter
            ACCESS read-only
            STATUS mandatory
            DESCRIPTION
                "Number of RDI Cells transmitted since last node boot or
                 statistics reset."
        ::= { cdx6500atmSDataSummaryStatsEntry 11 }

        atmSStatsCCCellInTotal OBJECT-TYPE
            SYNTAX Counter
            ACCESS read-only
            STATUS mandatory
            DESCRIPTION
                "Number of CC Cells received since last node boot
                 or statistics reset."
        ::= { cdx6500atmSDataSummaryStatsEntry 12 }

        atmSStatsCCCellOutTotal OBJECT-TYPE
            SYNTAX Counter
            ACCESS read-only
            STATUS mandatory
            DESCRIPTION
                "Number of CC Cells transmitted since last node boot or
                 statistics reset."
        ::= { cdx6500atmSDataSummaryStatsEntry 13 }

        atmSStatsVCFailure OBJECT-TYPE
            SYNTAX INTEGER 
            ACCESS read-only
            STATUS mandatory
            DESCRIPTION
                "The state of VC Failures."
        ::= { cdx6500atmSDataSummaryStatsEntry 14 }

        atmSStatsVCAssuranceState OBJECT-TYPE
            SYNTAX DisplayString 
            ACCESS read-only
            STATUS mandatory
            DESCRIPTION
                "The state of VC AssuranceState."
        ::= { cdx6500atmSDataSummaryStatsEntry 15 }

        atmSStatsOctetsInPerSec OBJECT-TYPE
            SYNTAX Counter 
            ACCESS read-only
            STATUS mandatory
            DESCRIPTION
                "The number of Octests in per second."
        ::= { cdx6500atmSDataSummaryStatsEntry 16 }

        atmSStatsOctetsOutPerSec OBJECT-TYPE
            SYNTAX Counter 
            ACCESS read-only
            STATUS mandatory
            DESCRIPTION
                "The number of Octests out per second."
        ::= { cdx6500atmSDataSummaryStatsEntry 17 }

        atmSStatsFramesInPerSec OBJECT-TYPE
            SYNTAX Counter 
            ACCESS read-only
            STATUS mandatory
            DESCRIPTION
                "The number of frames in per second."
        ::= { cdx6500atmSDataSummaryStatsEntry 18 }

        atmSStatsFramesOutPerSec OBJECT-TYPE
            SYNTAX Counter 
            ACCESS read-only
            STATUS mandatory
            DESCRIPTION
                "The number of frames out per second."
        ::= { cdx6500atmSDataSummaryStatsEntry 19 }

        atmSStatsDiscardedFrames OBJECT-TYPE
            SYNTAX Counter 
            ACCESS read-only
            STATUS mandatory
            DESCRIPTION
                "The total number of frames discarded."
        ::= { cdx6500atmSDataSummaryStatsEntry 20 }

        atmSStatsCIBitInForIWF OBJECT-TYPE
            SYNTAX Counter 
            ACCESS read-only
            STATUS mandatory
            DESCRIPTION
                "The total number of CI Bit in."
        ::= { cdx6500atmSDataSummaryStatsEntry 21 }

        atmSStatsCIBitOutForIWF OBJECT-TYPE
            SYNTAX Counter 
            ACCESS read-only
            STATUS mandatory
            DESCRIPTION
                "The total number of CI Bit out."
        ::= { cdx6500atmSDataSummaryStatsEntry 22 }

        atmSStatsCLPBitInForIWF OBJECT-TYPE
            SYNTAX Counter 
            ACCESS read-only
            STATUS mandatory
            DESCRIPTION
                "The total number of CLP Bit in."
        ::= { cdx6500atmSDataSummaryStatsEntry 23 }

        atmSStatsCLPBitOutForIWF OBJECT-TYPE
            SYNTAX Counter 
            ACCESS read-only
            STATUS mandatory
            DESCRIPTION
                "The total number of CLP Bit out."
        ::= { cdx6500atmSDataSummaryStatsEntry 24 }

        atmSStatsUUBitInForIWF OBJECT-TYPE
            SYNTAX Counter 
            ACCESS read-only
            STATUS mandatory
            DESCRIPTION
                "The total number of UU Bit in."
        ::= { cdx6500atmSDataSummaryStatsEntry 25 }

        atmSStatsUUBitOutForIWF OBJECT-TYPE
            SYNTAX Counter 
            ACCESS read-only
            STATUS mandatory
            DESCRIPTION
                "The total number of UU Bit out."
        ::= { cdx6500atmSDataSummaryStatsEntry 26 }

        -- The ATM Port Control Table
        cdx6500ContATMTable OBJECT IDENTIFIER
        ::= { cdx6500Controls 24 }

        cdx6500ATMPContTable OBJECT-TYPE
            SYNTAX SEQUENCE OF Cdx6500ATMPContEntry
            ACCESS not-accessible
            STATUS mandatory
            DESCRIPTION
                "Control parameters for ATM ports."
        ::= { cdx6500ContATMTable 1 }

        cdx6500ATMPContEntry OBJECT-TYPE
            SYNTAX Cdx6500ATMPContEntry
            ACCESS not-accessible
            STATUS mandatory
            DESCRIPTION
                "Each control applies to a single ATM port."
            INDEX { atmPContPortNumber }
        ::= { cdx6500ATMPContTable 1 }

        Cdx6500ATMPContEntry ::=
            SEQUENCE {
                atmPContPortNumber
                    INTEGER,
                atmPContPortControl
                    INTEGER
                }
        atmPContPortNumber OBJECT-TYPE
            SYNTAX INTEGER 
            ACCESS not-accessible
            STATUS mandatory
            DESCRIPTION
                "Port number of the ATM port."
        ::= { cdx6500ATMPContEntry 1 }

        atmPContPortControl OBJECT-TYPE
            SYNTAX INTEGER {
                   boot       (1),
                   resetstats (2)
                   }
            ACCESS write-only
            STATUS mandatory
            DESCRIPTION
                "Control operations for the specified ATM port.
                 boot       - Boots the ATM port
                 resetstats - Resets the ATM port statistics."
        ::= { cdx6500ATMPContEntry 2 }

        -- The ATM Station Control Table

        cdx6500ATMSContTable OBJECT-TYPE
            SYNTAX SEQUENCE OF Cdx6500ATMSContEntry
            ACCESS not-accessible
            STATUS mandatory
            DESCRIPTION
                "Control parameters for ATM stations."
        ::= { cdx6500ContATMTable 2 }

        cdx6500ATMSContEntry OBJECT-TYPE
            SYNTAX Cdx6500ATMSContEntry
            ACCESS not-accessible
            STATUS mandatory
            DESCRIPTION
                "Each control applies to a single ATM station."
            INDEX { atmSContPortNumber, atmSContStnNumber }
        ::= { cdx6500ATMSContTable 1 }

        Cdx6500ATMSContEntry ::=
            SEQUENCE {
                atmSContPortNumber
                    INTEGER,
                atmSContStnNumber
                    INTEGER,
                atmSContStnControl
                    INTEGER
            }

        atmSContPortNumber OBJECT-TYPE
            SYNTAX INTEGER (1..255)
            ACCESS not-accessible
            STATUS mandatory
            DESCRIPTION
                "The ATM port number corresponding to this station."
        ::= { cdx6500ATMSContEntry 1 }

        atmSContStnNumber OBJECT-TYPE
            SYNTAX INTEGER (1..254)
            ACCESS not-accessible
            STATUS mandatory
            DESCRIPTION
                "ATM station number."
        ::= { cdx6500ATMSContEntry 2 }

        atmSContStnControl OBJECT-TYPE
            SYNTAX INTEGER {
                   boot       (1),
                   resetstats (2)
                   }
            ACCESS write-only
            STATUS mandatory
            DESCRIPTION
                "Control operations for the specified ATM station.
                 boot       - Boots the ATM station
                 resetstats - Resets the ATM station statistics."
        ::= { cdx6500ATMSContEntry 3 }

	END
