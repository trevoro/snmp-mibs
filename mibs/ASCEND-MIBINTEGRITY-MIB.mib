--			Ascend mibintegrity MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBINTEGRITY-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsystemIntegrityProfile  OBJECT IDENTIFIER ::= { configuration 81}

	-- The mibsystemIntegrityProfile table
	--
	-- This table contains parameters for the mibsystemIntegrityProfile profile
	--

    mibsystemIntegrityProfileTable	OBJECT-TYPE
	SYNTAX		SEQUENCE OF MibsystemIntegrityProfileEntry
	ACCESS		not-accessible
	STATUS		mandatory
	DESCRIPTION	"A list of mibsystemIntegrityProfile profile entries."
	::= { mibsystemIntegrityProfile 1 }

    mibsystemIntegrityProfileEntry	OBJECT-TYPE
	SYNTAX		MibsystemIntegrityProfileEntry
	ACCESS		not-accessible
	STATUS		mandatory
	DESCRIPTION	"A mibsystemIntegrityProfile entry containing objects that
			 maps to the parameters of mibsystemIntegrityProfile profile."
	INDEX		{ systemIntegrityProfile-Index-o }
	::= { mibsystemIntegrityProfileTable 1 }

    MibsystemIntegrityProfileEntry ::=
	SEQUENCE {
	    systemIntegrityProfile-Index-o
		INTEGER,
	    systemIntegrityProfile-EnableCentralizedDetection
		INTEGER,
	    systemIntegrityProfile-RatioCentralizedDetection
		INTEGER,
	    systemIntegrityProfile-Action-o
		INTEGER
	}

    systemIntegrityProfile-Index-o	OBJECT-TYPE
	SYNTAX	INTEGER
	ACCESS	read-only
	STATUS	mandatory
	DESCRIPTION	""
	::= { mibsystemIntegrityProfileEntry 1 }

    systemIntegrityProfile-EnableCentralizedDetection	OBJECT-TYPE
	SYNTAX	INTEGER {
		    no (1),
		    yes (2)
		}
	ACCESS	read-write
	STATUS	mandatory
	DESCRIPTION	"Master can also do cetralized integrity for the whole system on the top of all cards doing their own distributed integrity testing. The recommended value is no. By default all LIMs do correction every few hours and that should be enough for LIMs."
	::= { mibsystemIntegrityProfileEntry 2 }

    systemIntegrityProfile-RatioCentralizedDetection	OBJECT-TYPE
	SYNTAX	INTEGER
	ACCESS	read-write
	STATUS	mandatory
	DESCRIPTION	"If centralized detection is enabled then the ratio of problem detection between the Master and all other cards. For example if ratio is 5 then master CM would do 5 self tests before triggering centralized LIM test."
	::= { mibsystemIntegrityProfileEntry 3 }

    systemIntegrityProfile-Action-o	OBJECT-TYPE
	SYNTAX	INTEGER {
		    noAction (1),
		    createProfile (2),
		    deleteProfile (3)
		}
	ACCESS	read-write
	STATUS	mandatory
	DESCRIPTION	""
	::= { mibsystemIntegrityProfileEntry 4 }


	-- The mibsystemIntegrityProfile__integrity_config table
	--
	-- This table contains parameters for the mibsystemIntegrityProfile__integrity_config profile
	--

    mibsystemIntegrityProfile-IntegrityConfigTable	OBJECT-TYPE
	SYNTAX		SEQUENCE OF MibsystemIntegrityProfile-IntegrityConfigEntry
	ACCESS		not-accessible
	STATUS		mandatory
	DESCRIPTION	"A list of mibsystemIntegrityProfile__integrity_config profile entries."
	::= { mibsystemIntegrityProfile 2 }

    mibsystemIntegrityProfile-IntegrityConfigEntry	OBJECT-TYPE
	SYNTAX		MibsystemIntegrityProfile-IntegrityConfigEntry
	ACCESS		not-accessible
	STATUS		mandatory
	DESCRIPTION	"A mibsystemIntegrityProfile__integrity_config entry containing objects that
			 maps to the parameters of mibsystemIntegrityProfile__integrity_config profile."
	INDEX		{ systemIntegrityProfile-IntegrityConfig-Index-o, systemIntegrityProfile-IntegrityConfig-Index1-o }
	::= { mibsystemIntegrityProfile-IntegrityConfigTable 1 }

    MibsystemIntegrityProfile-IntegrityConfigEntry ::=
	SEQUENCE {
	    systemIntegrityProfile-IntegrityConfig-Index-o
		INTEGER,
	    systemIntegrityProfile-IntegrityConfig-Index1-o
		INTEGER,
	    systemIntegrityProfile-IntegrityConfig-EnableContinuousDetection
		INTEGER,
	    systemIntegrityProfile-IntegrityConfig-DetectionInterval
		INTEGER,
	    systemIntegrityProfile-IntegrityConfig-OnlyOneCorrection
		INTEGER,
	    systemIntegrityProfile-IntegrityConfig-CorrectionFactor
		INTEGER,
	    systemIntegrityProfile-IntegrityConfig-AutoCorrectionEnable
		INTEGER,
	    systemIntegrityProfile-IntegrityConfig-IntervalAutoCorrection
		INTEGER
	}

    systemIntegrityProfile-IntegrityConfig-Index-o	OBJECT-TYPE
	SYNTAX	INTEGER
	ACCESS	read-only
	STATUS	mandatory
	DESCRIPTION	""
	::= { mibsystemIntegrityProfile-IntegrityConfigEntry 1 }

    systemIntegrityProfile-IntegrityConfig-Index1-o	OBJECT-TYPE
	SYNTAX	INTEGER
	ACCESS	read-only
	STATUS	mandatory
	DESCRIPTION	""
	::= { mibsystemIntegrityProfile-IntegrityConfigEntry 2 }

    systemIntegrityProfile-IntegrityConfig-EnableContinuousDetection	OBJECT-TYPE
	SYNTAX	INTEGER {
		    no (1),
		    yes (2)
		}
	ACCESS	read-write
	STATUS	mandatory
	DESCRIPTION	"MAGIC testing, detection and correction enabled in continous mode? It is recommended yes for the CMs and no for all LIMs."
	::= { mibsystemIntegrityProfile-IntegrityConfigEntry 3 }

    systemIntegrityProfile-IntegrityConfig-DetectionInterval	OBJECT-TYPE
	SYNTAX	INTEGER
	ACCESS	read-write
	STATUS	mandatory
	DESCRIPTION	"Detection interval in miliseconds for continuous detection. The system tries to detect any abnormality at defined miliseconds interval. The recommended value is 100 ms for CMs."
	::= { mibsystemIntegrityProfile-IntegrityConfigEntry 4 }

    systemIntegrityProfile-IntegrityConfig-OnlyOneCorrection	OBJECT-TYPE
	SYNTAX	INTEGER {
		    no (1),
		    yes (2)
		}
	ACCESS	read-write
	STATUS	mandatory
	DESCRIPTION	"If yes then apply MAGIC correction only once. If no then apply MAGIC correction multiple times in a row. Only one correction is recommended."
	::= { mibsystemIntegrityProfile-IntegrityConfigEntry 5 }

    systemIntegrityProfile-IntegrityConfig-CorrectionFactor	OBJECT-TYPE
	SYNTAX	INTEGER
	ACCESS	read-write
	STATUS	mandatory
	DESCRIPTION	"MAGIC correction factor. How many detection of problems result in to a correction. The system keeps history of past 20 tests. If correction-factor is 1 then only one failure out of past 20 tests would result in a correction. If correction-factor is 5 then 5 failure out of 20 would result in a correction."
	::= { mibsystemIntegrityProfile-IntegrityConfigEntry 6 }

    systemIntegrityProfile-IntegrityConfig-AutoCorrectionEnable	OBJECT-TYPE
	SYNTAX	INTEGER {
		    no (1),
		    yes (2)
		}
	ACCESS	read-write
	STATUS	mandatory
	DESCRIPTION	"If auto correction is enabled for this card or not. Applicable only for LIM cards. LIM tries to correct problem every few hours automatically."
	::= { mibsystemIntegrityProfile-IntegrityConfigEntry 7 }

    systemIntegrityProfile-IntegrityConfig-IntervalAutoCorrection	OBJECT-TYPE
	SYNTAX	INTEGER
	ACCESS	read-write
	STATUS	mandatory
	DESCRIPTION	"All slot cards (LIM) automatically tries to correct themselves at specified interval in mili seconds. Some LIMs are capable of doing detection before correction. Those LIMs would try to detect the problem and then correct it."
	::= { mibsystemIntegrityProfile-IntegrityConfigEntry 8 }

END
