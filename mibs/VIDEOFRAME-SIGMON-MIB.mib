VIDEOFRAME-SIGMON-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                        vfProducts(4)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--  Object Synopsis
	--  
	--
	--  All objects within this MIB are prefixed with the OBJECT
	--  IDENTIFIER "p", where "p" is:
	--
	--  iso(1).org(3).dod(6).internet(1).private(4).enterprises(1).
	--          videoframe(4596).vfProducts(4)
	--	
	--  or, 1.3.6.1.4.1.4596.4
	--
	--
	--  Object Name                               Object Id         
	--  --------------------------------          --------------
	--
	--	vfSigmonFrame								p.2
	--		vfSigmonFrameModuleTypes				p.2.1
	--		vfFrameSlotTable						p.2.2
	--		vfFrameSlotEntry						p.2.2.1
	--			vfFrameSlotNumber					p.2.2.1.1.n
	--			vfFrameSlotStatus					p.2.2.1.2.n
	--			vfModuleTypeRegObjectID				p.2.2.1.3.n
	--			vfModuleTypeRootOID					p.2.2.1.4.n
	--			vfModulePartNo						p.2.2.1.5.n
	--			vfModuleDescription					p.2.2.1.6.n
	--			vfModuleTrapEnable					p.2.2.1.7.n
	--			vfModuleAlarmAutoReArm				p.2.2.1.8.n
	--		vfFrameOfflineSwitch					p.2.3
	--		vfFrameLocateIndicator					p.2.4
	--		vfFrameAdminState						p.2.5
	--		vfNumDerivedNotifications				p.2.6
	--		vfDerivedNotificationTable				p.2.7
	--		vfDerivedNotificationEntry				p.2.7.1
	--			vfDnFunctionNumber					p.2.7.1.1.n
	--			vfDnFunctionDescription				p.2.7.1.2.n
	--			vfDnNotificationLevel				p.2.7.1.3.n
	--			vfDnNotificationEnable				p.2.7.1.4.n
	--			vfDnNotificationAutoReArm			p.2.7.1.5.n
	--			vfDnNotificationState				p.2.7.1.6.n
	--			vfDnNotificationAcknowledge			p.2.7.1.7.n
	--		vfSigmonFrameEvents						p.2.8
	--			vfSigmonFrameEventsV2				p.2.8.0
	--				vfFrameSlotStatusChange			p.2.8.0.1
	--		vfSigmonFrameDerivedEvents				p.2.9
	--			vfSigmonFrameDerivedEventsV2		p.2.9.0
	--				derivedNotificationLevelA		p.2.9.0.1
	--				derivedNotificationLevelB		p.2.9.0.2
	--				derivedNotificationLevelC		p.2.9.0.3
	--				derivedNotificationLevelD		p.2.9.0.4
	--
	--	DERIVED NOTIFICATIONS
	--		Derived notifications are events that are derived from a logical combination
	--	of basic events, covering one or more signals from one or more modules.
	--  The derived notification functions are defined apart from the SNMP agent,
	--	in the frame configuration file.  These functions are numbered in the file, and
	--  their (function) numbers are used in the SNMP agent to refer to these functions.
	--  Generally, when one of these functions are triggered, an SNMP trap will be
	--  triggered by the SNMP agent.
	--
	--	AUTO RE-ARM
	--		Both basic alarms and derived notifications have two modes
	--	of operation:  Single Notification with Acknowledge (normal), and Auto Re-Arm.
	--  In the normal mode, when an alarm or derived notification is triggered,
	--  a single trap is sent to the trap target(s).  No further traps for the same
	--  function on the same signal(s) will be issued until the alarm or notification
	--  is acknowledged.  For every alarm or notification, there is a corresponding
	--  acknowledge object in this MIB, to be used by the SNMP manager to acknowledge
	--  the alarm or notification.
	--
	--	In auto re-arm mode, the alarm or notification is re-armed internally each
	--  time it is triggered.  In this mode, multiple repetitive traps may be issued,
	--  at a rate corresponding to the alarm threshold duration or period.
	--   

	IMPORTS
		OBJECT-TYPE FROM RFC1155-SMI
		MODULE-IDENTITY, OBJECT-IDENTITY, NOTIFICATION-TYPE,
		Integer32, IpAddress
			FROM SNMPv2-SMI
		DisplayString, RowStatus
			FROM SNMPv2-TC
		MODULE-COMPLIANCE, OBJECT-GROUP
			FROM SNMPv2-CONF
		vfProducts, vfProductsReg, vfMIBModules
			FROM VIDEOFRAME-REGISTRATIONS-MIB
		vfBoxId
			FROM VIDEOFRAME-GENERIC-MIB;

	videoframeSigmonMIB MODULE-IDENTITY
		LAST-UPDATED "0101190000Z"
		ORGANIZATION "Videoframe Systems"
		CONTACT-INFO
			"Videoframe Systems
			P.O. Box 1991,
			Grass Valley, CA 95945, USA.

			+1 (530) 477-2000

			http://www.videoframesystems.com"
	DESCRIPTION
		"This MIB describes the device
		specific objects of the Videoframe Signal Monitoring Frame, 
		and augments MIB-2 and VF-GENERIC in the identification 
		of this Videoframe Systems managed device.

		This module will be extended, or modified 
		as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end-users, 
		and other interested parties a non-exclusive 
		license to use this specification in connection 
		with the management of Videoframe Systems products.

		Copyright 2001 Videoframe, Inc."
	REVISION      "0108300000Z"
	DESCRIPTION
		"First release."
	::= { vfMIBModules 3 }

	--
	-- Signal Monitoring product registrations. vfProductsReg from vf-reg
	--

	vfProductsSignalMonitoringFrameReg OBJECT-IDENTITY
		STATUS	current
		DESCRIPTION
			"Videoframe signal monitoring frame with hot-swappable
			 modules, and monitoring via SNMP and gvg modular protocol."
	::= { vfProductsReg 4 }

	vfProductsVF200Reg OBJECT-IDENTITY
		STATUS	current
		DESCRIPTION
			"VF200 2RU modular frame for Signal Monitoring
			 and machine control functions."
	::= { vfProductsReg 5 }

	--
	--  The Sigmon MIB top-level groups
	--

	vfSigmonFrame				OBJECT IDENTIFIER ::= { vfProducts 2 }
	vfSigmonFrameModuleTypes	OBJECT IDENTIFIER ::= { vfSigmonFrame 1 }
	vfSigmonFrameEvents			OBJECT IDENTIFIER ::= { vfSigmonFrame 8 }
	vfSigmonFrameEventsV2		OBJECT IDENTIFIER ::= { vfSigmonFrameEvents 0 }
	vfSigmonFrameDerivedEvents	OBJECT IDENTIFIER ::= { vfSigmonFrame 9 }
	vfSigmonFrameDerivedEventsV2	OBJECT IDENTIFIER ::= { vfSigmonFrameDerivedEvents 0 }

	--
	--  The vf200 Signal Monitoring MIB Object Definitions
	--

--
-- Table for slot status, and module ID and status for module
-- installed in this slot.
--

vfFrameSlotTable	OBJECT-TYPE
	SYNTAX	SEQUENCE OF VfFrameSlotEntry
	MAX-ACCESS	not-accessible
	STATUS	current
	DESCRIPTION
		"Each row contains information about one slot in the
		 managed VF200 frame."

	::=	{ vfSigmonFrame 2 }

vfFrameSlotEntry	OBJECT-TYPE
	SYNTAX	VfFrameSlotEntry
	MAX-ACCESS	not-accessible
	STATUS	current
	DESCRIPTION
		"Information about one slot in the
		 managed VF200 frame."
	INDEX	{ vfFrameSlotNumber }

	::= 	{ vfFrameSlotTable 1 }

VfFrameSlotEntry ::=
	SEQUENCE
		{
			vfFrameSlotNumber			INTEGER,
			vfFrameSlotStatus			INTEGER,
			vfModuleTypeRegObjectID		OBJECT IDENTIFIER,
			vfModuleTypeRootOID			OBJECT IDENTIFIER,
			vfModulePartNo				DisplayString,
			vfModuleDescription			DisplayString,
			vfModuleTrapEnable			INTEGER,
			vfModuleAlarmAutoReArm		INTEGER
		}

vfFrameSlotNumber	OBJECT-TYPE
	SYNTAX	INTEGER(0..12)
	MAX-ACCESS	read-only
	STATUS	current
	DESCRIPTION
		"Slot number in frame."

	::= { vfFrameSlotEntry 1 }

vfFrameSlotStatus	OBJECT-TYPE
	SYNTAX INTEGER
			{
				empty(1),
				moduleUninitialized(2),
				moduleValid(3),
				illegalSlot(4)
			}
	MAX-ACCESS	read-only
	STATUS	current
	DESCRIPTION
		"State of this slot.  Illegal means the slot does not exist.
		 moduleValid means the correct firmware has been loaded to
		 the module and it is ready for operation."
	::= { vfFrameSlotEntry 2 }

vfModuleTypeRegObjectID	OBJECT-TYPE
	SYNTAX	OBJECT IDENTIFIER
	MAX-ACCESS	read-only
	STATUS	current
	DESCRIPTION
		"MIB-registered identification of the module currently
		 installed in this slot."
	::= { vfFrameSlotEntry 3 }

	--
	--	vfModuleTypeRootOID returns the root OID of the MIB for this module
	--  type.  Under this OID, the module type has a
	--	table of installed modules, indexed by slot, and a MIB walker
	--  will need to look at the <slot #>th entry in this table to see
	--	the module-specific information for the module installed in this slot.
	--  There may also be expansion tables under the module-type root OID,
	--  for cases where the module may process multiple peer streams or signals.
	--  These expansion tables are indexed by slot # and stream or signal #.
	--
				
vfModuleTypeRootOID	OBJECT-TYPE
	SYNTAX	OBJECT IDENTIFIER
	MAX-ACCESS	read-only
	STATUS	current
	DESCRIPTION
		"Root OID of the module-specific managed information for the module
		 currently installed in this slot."
	::= { vfFrameSlotEntry 4 }
			
vfModulePartNo	OBJECT-TYPE
	SYNTAX	DisplayString (SIZE ( 0..20 ))
	MAX-ACCESS	read-only
	STATUS	current
	DESCRIPTION
		"Videoframe part no. of module currently installed in slot
		 - should match module nameplate."

	::= { vfFrameSlotEntry 5 }

vfModuleDescription	OBJECT-TYPE
	SYNTAX	DisplayString (SIZE ( 0..40 ))
	MAX-ACCESS	read-only
	STATUS	current
	DESCRIPTION
		"Description of module currently installed in slot
		 - should match module nameplate."

	::= { vfFrameSlotEntry 6 }

vfModuleTrapEnable	OBJECT-TYPE
	SYNTAX	INTEGER
			{
				enabled(1),
				disabled(2)
			}
	MAX-ACCESS	read-write
	STATUS	current
	DESCRIPTION
		"Enables or disables the Trap that is associated
		 with a slot status change event or module event."

	::= { vfFrameSlotEntry 7 }

vfModuleAlarmAutoReArm	OBJECT-TYPE
	SYNTAX	INTEGER
			{
				enabled(1),
				disabled(2)
			}
	MAX-ACCESS	read-write
	STATUS	current
	DESCRIPTION
		"Enables or disables automatic re-arming of alarms from
		 signal monitoring modules."

	::= { vfFrameSlotEntry 8 }

	--
	--	Frame Offline Switch
	--

vfFrameOfflineSwitch	OBJECT-TYPE
	SYNTAX	INTEGER
			{
				online(1),
				offline(2)
			}
	MAX-ACCESS	read-only
	STATUS	current
	DESCRIPTION
		"Indicates the state of the 'offline' switch for the frame.
		 'offline' indicates the switch is set to take the frame offline."
	::= { vfSigmonFrame 3 }

	--
	--	Frame Locate Indicator
	--

vfFrameLocateIndicator	OBJECT-TYPE
	SYNTAX	INTEGER
			{
				flash(1),
				off(2)
			}
	MAX-ACCESS	read-write
	STATUS	current
	DESCRIPTION
		"Set to flash (1) to cause the locate LED on the front of the frame to
		 begin flashing.  Set to off to stop flashing.  This is used to
		 verify the identity of a particular unit among racks of units."
	::= { vfSigmonFrame 4 }

vfFrameAdminState OBJECT-TYPE
		SYNTAX		INTEGER {
						vfFrameOnline(1),
						vfFrameInMaintenance(2),
						vfFrameDisabled(3),
						vfFrameResetting(4)
					}
		MAX-ACCESS	read-write
		STATUS		current
		DESCRIPTION
			"The desired operational state of this device.  Use this
			 object to command the frame to a different operational
			 state (vfBoxState from the vf-generic MIB module).

			NOTE: It is mandatory that a managed device
			support all of the enumerated device states.

			vfFrameOnline(1) - The device is running and 
			ready to process load.

			vfFrameInMaintenance(2) - The device is online, 
			but either the device as a whole, or one or more of 
			its components are in maintenance mode. Maintenance 
			mode could be described as a mode where diagnostics 
			are being run on the device, or some tasks such as 
			device configuration are being excuted on the 
			device that has inhibited its normal operation.

			vfFrameDisabled(3) - The device has been explicitly disabled 
			from its normal mode of operation, such as when
			selected as the backup of a redundant pair.

			vfFrameResetting(4) - The device is in a
			reset cycle. Any information collected, or dynamic 
			configuration of the device prior to this state 
			may be lost."
	::= { vfSigmonFrame 5 }

	--
	-- Derived Notifications
	--

vfNumDerivedNotifications	OBJECT-TYPE
	SYNTAX	INTEGER(0..65535)
	MAX-ACCESS	read-only
	STATUS	current
	DESCRIPTION
		"Number of derived notifications defined in vf200 configuration
		 file for this unit.  Gives size of derived notifications table."

	::= { vfSigmonFrame 6 }

--
-- Table for derived notifications of signal anomalies based on
-- logical combinations of multiple alarms.  Definitions of derived
-- alarm functions are contained in a configuration file for the frame.
--

vfDerivedNotificationTable	OBJECT-TYPE
	SYNTAX	SEQUENCE OF VfDerivedNotificationEntry
	MAX-ACCESS	not-accessible
	STATUS	current
	DESCRIPTION
		"Each row contains information about one derived notification
		 defined for the managed VF200 frame."

	::=	{ vfSigmonFrame 7 }

vfDerivedNotificationEntry	OBJECT-TYPE
	SYNTAX	VfDerivedNotificationEntry
	MAX-ACCESS	not-accessible
	STATUS	current
	DESCRIPTION
		"A row in the derived notification table."
	INDEX	{ vfDnFunctionNumber }

	::= 	{ vfDerivedNotificationTable 1 }

VfDerivedNotificationEntry ::=
	SEQUENCE
		{
			vfDnFunctionNumber				Integer32,
			vfDnFunctionDescription			DisplayString,
			vfDnNotificationLevel			INTEGER,
			vfDnNotificationEnable			INTEGER,
			vfDnNotificationAutoReArm		INTEGER,
			vfDnNotificationState			INTEGER,
			vfDnNotificationAcknowledge		INTEGER
		}

vfDnFunctionNumber	OBJECT-TYPE
	SYNTAX	Integer32
	MAX-ACCESS	read-only
	STATUS	current
	DESCRIPTION
		"Derived Notification Function Number.  Identifies
		 derived notification function, define in frame config. file."

	::= { vfDerivedNotificationEntry 1 }

vfDnFunctionDescription	OBJECT-TYPE
	SYNTAX	DisplayString	(SIZE (0..120))
	MAX-ACCESS	read-only
	STATUS	current
	DESCRIPTION
		"Derived Notification Description.  Describes
		 derived notification function for the operator.
		 Set in frame config. file."

	::= { vfDerivedNotificationEntry 2 }

vfDnNotificationLevel	OBJECT-TYPE
	SYNTAX	INTEGER
				{
					levelA(1),
					levelB(2),
					levelC(3),
					levelD(4)
				}
	MAX-ACCESS	read-write
	STATUS	current
	DESCRIPTION
		"Notification level for this derived notification.
		 selects which trap will be sent for the notification,
		 out of four possible."
	::= { vfDerivedNotificationEntry 3 }

vfDnNotificationEnable	OBJECT-TYPE
	SYNTAX INTEGER
			{
				enabled(1),
				disabled(2)
			}
	MAX-ACCESS	read-write
	STATUS	current
	DESCRIPTION
		"Use to enable or disable this derived notification function."
	::= { vfDerivedNotificationEntry 4 }

vfDnNotificationAutoReArm	OBJECT-TYPE
	SYNTAX INTEGER
			{
				enabled(1),
				disabled(2)
			}
	MAX-ACCESS	read-write
	STATUS	current
	DESCRIPTION
		"Use to enable or disable automatic re-arming of this derived
		 notification function.  Auto re-arming allows multiple
		 unacknowledged activations of the derived notification. It
		 re-arms the function after notification so that the specified
		 alarms are again monitored according to the logic function."
	::= { vfDerivedNotificationEntry 5 }

vfDnNotificationState	OBJECT-TYPE
		SYNTAX	INTEGER
				{
					ready(1),
					triggered(2)
				}
		MAX-ACCESS	read-only
		STATUS		current
		DESCRIPTION
			"The current state of this derived notification function."
	::= { vfDerivedNotificationEntry 6 }

vfDnNotificationAcknowledge	OBJECT-TYPE
	SYNTAX INTEGER
			{
				idle(1),
				unacknowledged(2),
				acknowledge(3)
			}
	MAX-ACCESS	read-write
	STATUS	current
	DESCRIPTION
		"Use to acknowledge a derived notification.
		 If notificationAutoReArm is disabled, this will re-arm the
		 notification.  Otherwise, it is automatically re-armed, and
		 this object is not used."
	::= { vfDerivedNotificationEntry 7 }

	--
	-- Sigmon Events
	--

vfFrameSlotStatusChange	NOTIFICATION-TYPE
	OBJECTS
		{
			vfBoxId,
			vfFrameSlotStatus,
			vfModulePartNo,
			vfModuleDescription
		}
	STATUS	current
	DESCRIPTION
		"A slot status change occurred."
	::= { vfSigmonFrameEventsV2 1 }


derivedNotificationLevelA	NOTIFICATION-TYPE
	OBJECTS
		{
			vfBoxId,
			vfDnFunctionNumber,
			vfDnFunctionDescription
		}
	STATUS	current
	DESCRIPTION
		"A LevelA derived notification was triggered."
	::= { vfSigmonFrameDerivedEventsV2 1 }

derivedNotificationLevelB	NOTIFICATION-TYPE
	OBJECTS
		{
			vfBoxId,
			vfDnFunctionNumber,
			vfDnFunctionDescription
		}
	STATUS	current
	DESCRIPTION
		"A LevelB derived notification was triggered."
	::= { vfSigmonFrameDerivedEventsV2 2 }

derivedNotificationLevelC	NOTIFICATION-TYPE
	OBJECTS
		{
			vfBoxId,
			vfDnFunctionNumber,
			vfDnFunctionDescription
		}
	STATUS	current
	DESCRIPTION
		"A LevelC derived notification was triggered."
	::= { vfSigmonFrameDerivedEventsV2 3 }

derivedNotificationLevelD	NOTIFICATION-TYPE
	OBJECTS
		{
			vfBoxId,
			vfDnFunctionNumber,
			vfDnFunctionDescription
		}
	STATUS	current
	DESCRIPTION
		"A LevelD derived notification was triggered."
	::= { vfSigmonFrameDerivedEventsV2 4 }


END
