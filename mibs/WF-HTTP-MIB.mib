WF-HTTP-MIB DEFINITIONS ::= BEGIN

    IMPORTS

      Counter, TimeTicks
        FROM RFC1155-SMI
      OBJECT-TYPE
        FROM RFC-1212
      DisplayString
        FROM RFC1213-MIB
      wfHttpGroup
        FROM Wellfleet-COMMON-MIB;


  wfHttp OBJECT IDENTIFIER ::= { wfHttpGroup 1 }

  -- There are four groups of objects:
  -- wfHttpSrv (wfHttp.1) is a list of configuration values
  -- wfHttpSummaryEntry (wfHttp.2.1) is a list of summary counters
  -- wfHttpRequestEntry (wfHttp.2.2) is a table of counters for each request type
  -- wfHttpResponseEntry (wfHttp.2.3) is a table of counters for each response type

  wfHttpSrv OBJECT IDENTIFIER ::= { wfHttp 1 }

  wfHttpSrvDelete OBJECT-TYPE
      SYNTAX INTEGER {
                 create(1),
                 delete(2)
              }
      ACCESS read-write
      STATUS mandatory
      DESCRIPTION
          "Set to delete this server instance."
      DEFVAL { create }
      ::= { wfHttpSrv 1 }

  wfHttpSrvDisable OBJECT-TYPE
      SYNTAX INTEGER {
                 enabled(1),
                 disabled(2)
             }
      ACCESS read-write
      STATUS mandatory
      DESCRIPTION
          "Used to enable/disable the server."
      DEFVAL { enabled }
      ::= { wfHttpSrv 2 }

  wfHttpSrvState OBJECT-TYPE
      SYNTAX INTEGER {
                 up(1),
                 down(2),
                 init(3),
                 notpresent(4)
              }
      ACCESS read-only
      STATUS mandatory
      DESCRIPTION
          "Current state of the server entity."
      DEFVAL { notpresent }
      ::= { wfHttpSrv 3 }

  wfHttpSrvPort OBJECT-TYPE
      SYNTAX INTEGER (0..4096)
      ACCESS read-write
      STATUS mandatory
      DESCRIPTION
          "The port number this server listens to requests on."
      DEFVAL { 80 }
      ::= { wfHttpSrv 4 }

  wfHttpSrvMaxCacheCount OBJECT-TYPE
      SYNTAX INTEGER (3..10)
      ACCESS read-write
      STATUS mandatory
      DESCRIPTION
          "The maximum number of archives that will
           be cached in system RAM. Increasing this
           value will improve performance for multiple
           simultaneous request at the cost of memory
           utilization."
      DEFVAL { 3 }
      ::= { wfHttpSrv 5 }

  wfHttpSrvMaxCacheAge OBJECT-TYPE
      SYNTAX INTEGER (1..10)
      ACCESS read-write
      STATUS mandatory
      DESCRIPTION
          "The maximumtime in seconds that an archive
           will be cached in system RAM."
      DEFVAL { 3 }
      ::= { wfHttpSrv 6 }


  wfHttpSrvAuthType OBJECT-TYPE
      SYNTAX INTEGER {
                basic(1),
                digest(2)
             }
      ACCESS read-write
      STATUS mandatory
      DESCRIPTION
          "The authentication type to use when authorizating
           requests"
      DEFVAL { basic }
      ::= { wfHttpSrv 7 }

  wfHttpSrvHostName OBJECT-TYPE
      SYNTAX DisplayString
      ACCESS read-write
      STATUS mandatory
      DESCRIPTION
          "The fully qualified domain name used for the HTTP server. If
           the name is set it domain name service must also by provided
           to allow clients to resolve the name. If this parameter is
           not configured the IP address of one of the router's interface
           will be used as the host name."
      ::= { wfHttpSrv 8 }

  wfHttpSrvHelpBaseUrl OBJECT-TYPE
      SYNTAX DisplayString
      ACCESS read-write
      STATUS mandatory
      DESCRIPTION
          "A url that is used in all BASE tags that reside in help pages. 
           This base url combined with a relative url points to more 
           detailed information too large for storage on the router."
      DEFVAL { "http://support.baynetworks.com/library/tpubs/"}
      ::= { wfHttpSrv 9 }

  wfHttpStatistics OBJECT IDENTIFIER ::= { wfHttp 2 }

  wfHttpSummary OBJECT IDENTIFIER ::= { wfHttpStatistics 1 }

  wfHttpSummaryRequests OBJECT-TYPE
      SYNTAX Counter
      ACCESS read-only
      STATUS mandatory
      DESCRIPTION
          "The total number of requests generated or received by this entity."
      ::= { wfHttpSummary 1 }

  wfHttpSummaryRequestErrors OBJECT-TYPE
      SYNTAX Counter
      ACCESS read-only
      STATUS mandatory
      DESCRIPTION
          "Total number of request errors detected by this entity (as server)."
      ::= { wfHttpSummary 2 }

  wfHttpSummaryRequestDiscards OBJECT-TYPE
      SYNTAX Counter
      ACCESS read-only
      STATUS mandatory
      DESCRIPTION
          "Total number of requests discarded by this entity (as server)."
      ::= { wfHttpSummary 3 }

  wfHttpSummaryResponses OBJECT-TYPE
      SYNTAX Counter
      ACCESS read-only
      STATUS mandatory
      DESCRIPTION
          "Total number of responses generated or received by this entity."
      ::= { wfHttpSummary 4 }

  wfHttpSummaryResponseErrors OBJECT-TYPE
      SYNTAX Counter
      ACCESS read-only
      STATUS mandatory
      DESCRIPTION
          "Total number of response errors detected by this entity (as client)."
      ::= { wfHttpSummary 5 }

  wfHttpSummaryResponseDiscards OBJECT-TYPE
      SYNTAX Counter
      ACCESS read-only
      STATUS mandatory
      DESCRIPTION
          "The total number of responses discarded by this entity (as client)."
      ::= { wfHttpSummary 6 }

  wfHttpSummaryInUnknowns OBJECT-TYPE
      SYNTAX Counter
      ACCESS read-only
      STATUS mandatory
      DESCRIPTION
          "The total number of unknown messages received by this entity."
      ::= { wfHttpSummary 7 }

  wfHttpSummaryInBytes OBJECT-TYPE
      SYNTAX Counter
      ACCESS read-only
      STATUS mandatory
      DESCRIPTION
          "The total number of bytes received by this entity."
      ::= { wfHttpSummary 8 }

  wfHttpSummaryOutBytes OBJECT-TYPE
      SYNTAX Counter
      ACCESS read-only
      STATUS mandatory
      DESCRIPTION
          "The total number of bytes transmitted by this entity."
      ::= { wfHttpSummary 9 }

  wfHttpSummaryTimeOuts OBJECT-TYPE
      SYNTAX Counter
      ACCESS read-only
      STATUS mandatory
      DESCRIPTION
          "The number of timeouts for this entity."
      ::= { wfHttpSummary 10 }

  wfHttpSummaryStartTime OBJECT-TYPE
      SYNTAX TimeTicks
      ACCESS read-only
      STATUS mandatory
      DESCRIPTION
          "The value of sysUpTime at the time the server started."
      ::= { wfHttpSummary 11 }


  wfHttpRequestTable OBJECT-TYPE
      SYNTAX SEQUENCE OF WfHttpRequestEntry
      ACCESS not-accessible
      STATUS mandatory
      DESCRIPTION
          "Table providing detailed request statistics broken out by request type."
      ::= { wfHttpStatistics 2 }

  wfHttpRequestEntry OBJECT-TYPE
      SYNTAX WfHttpRequestEntry
      ACCESS not-accessible
      STATUS mandatory
      DESCRIPTION
          "An entry in the request table."
      INDEX { wfHttpRequestMethodIndex }
      ::= { wfHttpRequestTable 1 }

  WfHttpRequestEntry ::= SEQUENCE {
      wfHttpRequestMethodIndex     INTEGER,
      wfHttpRequestInCount         Counter,
      wfHttpRequestInLastTime      TimeTicks,
      wfHttpRequestOutCount        Counter,
      wfHttpRequestOutLastTime     TimeTicks
  }

  -- The codes for the method enumeration are not contiguous because they are 
  -- copied from the Internet draft, with some omissions.
  wfHttpRequestMethodIndex OBJECT-TYPE
      SYNTAX INTEGER {
                 get(1),
                 head(2),
                 trace(3),
                 post(4),
                 options(5),
                 put(6),
                 delete(7)
              }
      ACCESS read-only
      STATUS mandatory
      DESCRIPTION
          "The request method that these statistics apply to."
      ::= { wfHttpRequestEntry 1 }

  wfHttpRequestInCount OBJECT-TYPE
      SYNTAX Counter
      ACCESS read-only
      STATUS mandatory
      DESCRIPTION
          "The number of requests of this type received by the entity."
      ::= { wfHttpRequestEntry 2 }

  wfHttpRequestInLastTime OBJECT-TYPE
      SYNTAX TimeTicks
      ACCESS read-only
      STATUS mandatory
      DESCRIPTION
          "The value of sysUpTime at the time the last request was received."
      ::= { wfHttpRequestEntry 3 }

  wfHttpRequestOutCount OBJECT-TYPE
      SYNTAX Counter
      ACCESS read-only
      STATUS mandatory
      DESCRIPTION
          "The number of requests of this type generated by this entity."
      ::= { wfHttpRequestEntry 4 }

  wfHttpRequestOutLastTime OBJECT-TYPE
      SYNTAX TimeTicks
      ACCESS read-only
      STATUS mandatory
      DESCRIPTION
          "The value of sysUpTime at the time the last request was generated."
      ::= { wfHttpRequestEntry 5 }


  wfHttpResponseTable OBJECT-TYPE
      SYNTAX SEQUENCE OF WfHttpResponseEntry
      ACCESS not-accessible
      STATUS mandatory
      DESCRIPTION
          "Response table, providing break-out of responses by response type."
      ::= { wfHttpStatistics 3 }

  wfHttpResponseEntry OBJECT-TYPE
      SYNTAX WfHttpResponseEntry
      ACCESS not-accessible
      STATUS mandatory
      DESCRIPTION
          "An entry in the response table."
      INDEX { wfHttpResponseStatusIndex }
      ::= { wfHttpResponseTable 1 }

  WfHttpResponseEntry ::= SEQUENCE {
      wfHttpResponseStatusIndex    INTEGER,
      wfHttpResponseInCount        Counter,
      wfHttpResponseInLastTime     TimeTicks,
      wfHttpResponseOutCount       Counter,
      wfHttpResponseOutLastTime    TimeTicks
  }

  wfHttpResponseStatusIndex OBJECT-TYPE
      SYNTAX INTEGER {
		ok(200),
		created(201),
		accepted(202),
		no-content(204),
		moved-permanently(301),
		moved-temporarily(302),
		not-modified(304),
		bad-request(400),
		unauthorized(401),
		forbidden(403),
		not-found(404),
		internal-server-error(500),
		not-implemented(501),
		bad-gateway(502),
		service-unavailable(503)
              }
      ACCESS read-only
      STATUS mandatory
      DESCRIPTION
          "The response code for this row of the table."
      ::= { wfHttpResponseEntry 1 }

  wfHttpResponseInCount OBJECT-TYPE
      SYNTAX Counter
      ACCESS read-only
      STATUS mandatory
      DESCRIPTION
          "The number of times this response was received."
      ::= { wfHttpResponseEntry 2 }

  wfHttpResponseInLastTime OBJECT-TYPE
      SYNTAX TimeTicks
      ACCESS read-only
      STATUS mandatory
      DESCRIPTION
          "The value of sysUpTime when this response was last received."
      ::= { wfHttpResponseEntry 3 }

  wfHttpResponseOutCount OBJECT-TYPE
      SYNTAX Counter
      ACCESS read-only
      STATUS mandatory
      DESCRIPTION
          "The number of times this response was generated."
       ::= { wfHttpResponseEntry 4 }

  wfHttpResponseOutLastTime OBJECT-TYPE
      SYNTAX TimeTicks
      ACCESS read-only
      STATUS mandatory
      DESCRIPTION
          "The value of sysUpTime when this response was last sent."
      ::= { wfHttpResponseEntry 5 }


  END
