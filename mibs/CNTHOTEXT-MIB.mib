CNTHOTEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString
			FROM SNMPv2-TC
		apCntName, apCntOwner
			FROM CNTEXT-MIB
		cnthotExt
			FROM APENT-MIB;

--CNTHOTEXT MIB

    apCnthotExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content rule hot list"
      ::= { cnthotExt 1}


apCnthotTable OBJECT-TYPE
	SYNTAX          SEQUENCE OF APCnthotEntry
	MAX-ACCESS      not-accessible
	STATUS          current
	DESCRIPTION
		"A list of content rule hot list entries."
	::= { cnthotExt 2 }

apCnthotEntry OBJECT-TYPE
	SYNTAX          APCnthotEntry
	MAX-ACCESS      not-accessible
	STATUS          current
	DESCRIPTION
		"A list of content rule items which are considered hot."
	INDEX   { apCntOwner, apCntName, apCnthotIndex }
	--DEFAULT apjam-group apCntHotInst, apCnthotUri
	--DEFAULT apjam-popup-def apCntInst, Statistics, local
	::= { apCnthotTable 1 }

APCnthotEntry ::= SEQUENCE {
		apCnthotIndex                Integer32,
		apCnthotRate                 Integer32,
		apCnthotUri                  DisplayString,
		apCnthotSize                 Integer32
}

apCnthotIndex OBJECT-TYPE
	SYNTAX          Integer32
	MAX-ACCESS      read-only
	STATUS          current
	DESCRIPTION     
			"The index of the hot item within the hotlist."
	::= {apCnthotEntry 1}

apCnthotRate OBJECT-TYPE
	SYNTAX          Integer32
	MAX-ACCESS      read-only
	STATUS  		current
	DESCRIPTION     
		"The rate based on the hotlist type which is an indication of hotness."
	--DEFAULT ap-display-name	Hits
	--DEFAULT apjam-popup-ref apCntHotInst, Statistics
	::= {apCnthotEntry 2}

apCnthotUri OBJECT-TYPE
	SYNTAX          DisplayString (SIZE(1..255))
	MAX-ACCESS      read-only
	STATUS          current
	DESCRIPTION     
		"The name of the item of content."
	--DEFAULT ap-display-name	URI
	--DEFAULT apjam-popup-ref apCntHotInst, Statistics
	::= {apCnthotEntry 3}

apCnthotSize OBJECT-TYPE
	SYNTAX          Integer32
	MAX-ACCESS      read-only
	STATUS  		current
	DESCRIPTION     
		"The discerned size of the piece of content."
	--DEFAULT ap-display-name	Size
	--DEFAULT apjam-popup-ref apCntHotInst, Statistics
	::= {apCnthotEntry 4}

END
