-------------------------------------------------------------------------------
-- file: SVCSigStats.mib 
--
-- description:
--  This file contains the SNMP definitions for the SVC Signalling 
--  Statistics area.
--
-- history:
--  31A0611 / 96.02.09 / A. Brzezinski / Creation from V1.0 of MIBTemplate.mib
--  31A0611 / 96.03.21 / A. Brzezinski / Modifications after review meeting
--  31A0611 / 96.04.15 / A. Brzezinski / Changed order of tables to conform
--                                       with other statistics MIBs.
--  31A1147 / 98.01.27 / George Yue / Add Selective Call.
--
--%%history-start%%
--1996.04.15 brzezins 31A0611: File created. 
--1998.07.09 fernande 31A1216: atm.nb3.pm trib merge 
--%%history-end%%
--
-- Copyright 1996-1998 Newbridge Networks Corporation.  All Rights Reserved
-------------------------------------------------------------------------------
NNCEXTSVCSIGSTATS-MIB DEFINITIONS ::= BEGIN

  IMPORTS
    MODULE-IDENTITY, OBJECT-TYPE, Counter32, Gauge32 
            FROM SNMPv2-SMI
    TEXTUAL-CONVENTION, DateAndTime 
            FROM SNMPv2-TC
    MODULE-COMPLIANCE, OBJECT-GROUP 
            FROM SNMPv2-CONF
    ifIndex
            FROM IF-MIB
    nncExtensions
            FROM NNCGNI0001-SMI
    NncExtIntvlStateType, NncExtAbsIntvlNumberType, 
    NncExtRelIntvlNumberType, NncExtIntvlDurationType
            FROM NNC-INTERVAL-STATISTICS-TC-MIB;


  nncExtSVCSigStats MODULE-IDENTITY
    LAST-UPDATED   "9603211520Z"
    ORGANIZATION   "Newbridge Networks Corporation"
    CONTACT-INFO
                  "Newbridge Networks Corporation
                   Postal: 600 March Road
                         Kanata, Ontario
                         Canada K2K 2E6

                   Phone:  +1 613 591 3600
                   Fax:    +1 613 591 3680"
    
    DESCRIPTION
      "The MIB module containing management information for
       performance monitoring of SVC Signalling functions."
  
  ::= { nncExtensions 32 }


  nncExtSVCSigStatsObjects     OBJECT IDENTIFIER   ::=  { nncExtSVCSigStats 1 }
  nncExtSVCSigStatsTraps       OBJECT IDENTIFIER   ::=  { nncExtSVCSigStats 2 }
  nncExtSVCSigStatsGroups      OBJECT IDENTIFIER   ::=  { nncExtSVCSigStats 3 }
  nncExtSVCSigStatsCompliances OBJECT IDENTIFIER   ::=  { nncExtSVCSigStats 4 }


--------------------------------------------------------------------------------
-- Type Definitions
--------------------------------------------------------------------------------

  NncExtSetupAttemptsType ::= TEXTUAL-CONVENTION
    STATUS    current
    DESCRIPTION
    "Setup attempts counter for the incoming(outgoing) calls. 
     This counter counts the number of incoming(outgoing) call
     setup attempts (both successful and unsuccessful) during the
     time period of the interval. Retransmitted setup attempts are 
     redundant (for counting purposes) and should not be counted." 
    SYNTAX    Counter32

  NncExtConnectedCallsType ::= TEXTUAL-CONVENTION
    STATUS    current
    DESCRIPTION
    "Connect attempts counter for the incoming(outgoing) calls. 
     This counter counts the number of connect attempts for
     the incoming(outgoing) calls during the time period of the
     interval. Connect attempt for the incoming(outgoing) call
     is defined here by transmitting(receiving) CONNECT message
     by the switch."
    SYNTAX    Counter32

  NncExtTransitedCallsType ::= TEXTUAL-CONVENTION
    STATUS    current
    DESCRIPTION
    "Transited calls counter for the incoming(outgoing) calls. 
     This counter counts the number of incoming(outgoing) calls 
     that has been successfully transited to the outgoing 
     signalling link(incoming signalling link of the next 
     signalling entity) during the time period of the interval.
     Each increment of the counter indicates successful transition
     of the call through the switch." 
    SYNTAX    Counter32

  NncExtCalledPtyEventsType ::= TEXTUAL-CONVENTION
    STATUS    current
    DESCRIPTION
    "Received(transmitted) called party events cause code counter. 
     This counter counts the number of received(transmitted) called 
     party events cause codes during the time period of the interval.
     This counter is incremented when a RELEASE, RELEASE COMPLETE,
     ADD PARTY REJECT, or STATUS message that contains one of the 
     following cause code values is received(transmitted)
     (Note: These cause values apply to both UNI3.0 and UNI3.1):

     Cause Value    Meaning
     -----------    ----------------------------------------
         17         user busy
         18         no user responding
         21         call rejected
         22         number changed
         23         user rejects all calls with calling line
                    id restriction (CLIR)
         27         destination out of order
         31         normal, unspecified

     NOTE: For this counter, RELEASE COMPLETE messages that
     are a reply to a previous RELEASE message and contain
     the same cause value, are redundant (for counting
     purposes) and should not be counted."
    SYNTAX    Counter32

  NncExtCallingPtyEventsType ::= TEXTUAL-CONVENTION
    STATUS    current
    DESCRIPTION
    "Received(transmitted) calling party events cause code counter. 
     This counter counts the number of received(transmitted) calling 
     party events cause codes during the time period of the interval.
     This counter monitors error events that occur due to the 
     originating user doing something wrong. This counter is 
     incremented when a RELEASE, RELEASE COMPLETE, ADD PARTY REJECT, 
     or STATUS message that contains one of the following cause code 
     values is received(transmitted).
     (Note: These cause values apply to both UNI3.0 and UNI3.1
     unless otherwise stated):

     Cause Value    Meaning
     -----------    ----------------------------------------
         28         invalid number format (address incomplete)
         43         access information discarded
         57         bearer capability not authorized
         65         bearer capability not implemented
         73         unsupported combination of traffic parameters
         78         AAL parameters cannot be supported (UNI3.1 only)
         91         invalid transit network selection
         93         AAL parameters cannot be supported(UNI3.0 only)

     NOTE: For this counter, RELEASE COMPLETE messages that are a
     reply to a previous RELEASE messages and contain the same cause
     value, are redundant (for counting purposes) and should not
     be counted."
    SYNTAX    Counter32

  NncExtResUnavailableType ::= TEXTUAL-CONVENTION
    STATUS    current
    DESCRIPTION
    "Received(transmitted) resource unavailable cause code counter. 
     This counter counts the number of received(transmitted) resource 
     unavailable cause codes during the time period of the interval.
     This counter is incremented when a RELEASE, RELEASE COMPLETE,
     ADD PARTY REJECT, or STATUS message that contains one of the 
     following cause code values is received(transmitted)
     (Note: These cause values apply to both UNI3.0 and UNI3.1
     unless otherwise stated):

     Cause Value    Meaning
     -----------    ----------------------------------------
         35         requested VPCI/VCI not available
         37         user cell rate not available (UNI3.1 only)
         38         network out of order
         41         temporary failure
         45         no VPCI/VCI available
         47         resource unavailable, unspecified
         49         Quality of Service unavailable
         51         user cell rate not available (UNI3.0 only)
         58         bearer capability not presently available
         63         service or option not available, unspecified
         92         too many pending add party requests

     NOTE: For this counter, RELEASE COMPLETE messages that are
     a reply to a previous RELEASE message and contain the same
     cause value, are redundant (for counting purposes) and
     should not be counted."
    SYNTAX    Counter32

  NncExtRoutingFailureType ::= TEXTUAL-CONVENTION
    STATUS    current
    DESCRIPTION
    "Received(transmitted) routing failure cause code counter. 
     This counter counts the number of received(transmitted) routing 
     failure cause codes during the time period of the interval.
     This counter is incremented when a RELEASE, RELEASE COMPLETE,
     ADD PARTY REJECT, or STATUS message that contains one of the 
     following cause code values is received(transmitted)
     (Note: These cause values apply to both UNI3.0 and UNI3.1):

     Cause Value    Meaning
     -----------    ----------------------------------------
          1         unallocated (unassigned) number
          2         no route to specified transit network
          3         no route to destination
          88        incompatible destination

     NOTE: For this counter, RELEASE COMPLETE messages that are
     a reply to a previous RELEASE message and contain the same
     cause value, are redundant (for counting purposes) and
     should not be counted."
    SYNTAX    Counter32

  NncExtInvalidMessageType ::= TEXTUAL-CONVENTION
    STATUS    current
    DESCRIPTION
    "Received(transmitted) invalid message cause code counter. 
     This counter counts the number of received(transmitted) 
     invalid message cause codes during the time period of the 
     interval. This counter reflects any sort of incorrect 
     information in a message. This includes:

     - RELEASE, RELEASE COMPLETE, ADD PARTY REJECT, and
       STATUS messages received(transmitted), that contain
       any of the Cause values listed below.

     - Ignored messages. These messages are dropped because
       the message was so damaged that it could not be
       further processed. A list of dropped mesages is
       compiled below:
       
       1. Message with invalid protocol discriminator
       
       2. Message with errors in the call reference I.E.
          - Bits 5-8 of the first octet not equal to '0000'
          - Bits 1-4 of the first octet indicating a length
            other than 3 octets
          - RELEASE COMPLETE message received with a call
            reference that does not relate to a call active
            or in progress
          - SETUP message received with call reference flag
            incorrectly set to 1
          - SETUP message received with a call reference for
            a call that is already active or in progress.

       3. Message too short

     The following cause values are monitored by this counter
     (Note: These cause values apply to both UNI3.0 and UNI3.1
     unless otherwise stated): 

     Cause Value    Meaning
     -----------    ----------------------------------------
         10         VPCI/VCI unacceptable (UNI3.0 only)
         36         VPCI/VCI assignment failure (UNI3.1 only)
         81         invalid call reference value
         82         identified channel does not exist
         89         invalid endpoint reference
         96         mandatory information element is missing
         97         message type non-existent or not implemented
         99         information element non-existent or not 
                    implemented
        100         invalid information element contents
        101         message not compatible with call state
        104         incorrect message length
        111         protocol error, unspecified

     NOTE: For this counter, RELEASE COMPLETE messages that are
     a reply to a previous RELEASE message and contain the same
     cause value, are redundant (for counting purposes) and
     should not be counted."
    SYNTAX    Counter32

  NncExtTimerExpirationType ::= TEXTUAL-CONVENTION
    STATUS    current
    DESCRIPTION
    "Received(transmitted) timer expiration cause code counter. 
     This counter counts the number of received(transmitted) timer 
     expiration cause codes during the time period of the interval.
     This counter provides a count of network timer expiries, and 
     to some extent, host or switch timer expiries. The conditions 
     for incrementing this counter are:

     - Expiry of any network timer

     - Receipt of a RELEASE or RELEASE COMPLETE message with
       Cause #102, 'recovery on timer expiry'.

     NOTE: For this counter, RELEASE COMPLETE messages that are
     a reply to a previous RELEASE message and contain the same
     cause value, are redundant (for counting purposes) and
     should not be counted."
    SYNTAX    Counter32

  NncExtNormalCallClrType ::= TEXTUAL-CONVENTION
    STATUS    current
    DESCRIPTION
    "Received(transmitted) 'normal call clearing' cause code counter. 
     This counter counts the number of received(transmitted) 
     'normal call clearing' cause codes during the time period 
     of the interval.

     NOTE: For this counter, RELEASE COMPLETE messages that are
     a reply to a previous RELEASE message and contain the same
     cause value, are redundant (for counting purposes) and
     should not be counted."
    SYNTAX    Counter32

  NncExtOtherCausesType ::= TEXTUAL-CONVENTION
    STATUS    current
    DESCRIPTION
    "Received(transmitted) other causes cause code counter. 
     This counter counts the number of received(transmitted) 
     cause codes which do not belong to any of the predefined 
     cause codes groups during the time period of the interval.
     A 'response to STATUS ENQUIRY' cause code do not indicate 
     a failure condition and should not be counted.

     NOTE: For this counter, RELEASE COMPLETE messages that are
     a reply to a previous RELEASE message and contain the same
     cause value, are redundant (for counting purposes) and
     should not be counted."
    SYNTAX    Counter32

  NncExtScreeningFailuresType ::= TEXTUAL-CONVENTION
    STATUS    current
    DESCRIPTION
    "Incoming calls screening failures counter. This counter 
     counts the number of incoming calls that failed due to the 
     screening failure of the calling party number during the 
     time period of the interval."
    SYNTAX    Counter32

  NncExtActiveCallsType ::= TEXTUAL-CONVENTION
    STATUS    current
    DESCRIPTION
    "Active calls gauge. This gauge represents the total number of
     incoming and outgoing calls which are currently active. The
     active call is defined here as the call which has been initialized
     with the SETUP message but not released with RELEASE or RELEASE
     COMPLETE messages. Therefore all the call states except for a
     Null state correspond to the active call."
    SYNTAX    Gauge32

  NncExtSelectiveCallsType ::= TEXTUAL-CONVENTION
    STATUS    current
    DESCRIPTION
    "Incoming/outgoing selective calls counter. This counter counts
     the number of incoming/outgoing calls that matched called/calling
     party numbers specified in Address Translation Table during the 
     time period of the interval."
    SYNTAX    Counter32


--------------------------------------------------------------------------------
-- Object Definitions
--
-- This MIB module contains the following tables:
--
--  - SVC Signalling Stats Current Short Interval Table
--  - SVC Signalling Stats Previous Short Interval Table
--  - SVC Signalling Stats Current Long Interval Table
--  - SVC Signalling Stats Previous Long Interval Table
--  - SVC Signalling Stats Raw Table
--
--------------------------------------------------------------------------------


--------------------------------------------------------------------------------
--  Table 1: Current Short Interval Table
--------------------------------------------------------------------------------
  nncExtSVCSigStatsCurrShortTable OBJECT-TYPE
    SYNTAX       SEQUENCE OF NncExtSVCSigStatsCurrShortEntry
    MAX-ACCESS   not-accessible
    STATUS       current
    DESCRIPTION  
    "The nncExtSVCSigStatsCurrShortTable contains objects for monitoring 
     the performance of a signalling link during a current short interval."
  ::= { nncExtSVCSigStatsObjects 1 }


  nncExtSVCSigStatsCurrShortEntry OBJECT-TYPE
    SYNTAX      NncExtSVCSigStatsCurrShortEntry
    MAX-ACCESS  not-accessible
    STATUS      current
    DESCRIPTION  
    "An entry in the current short interval statistics table. Each 
     conceptual row contains current statistics for a particular 
     signalling link. ifIndex corresponds to the trunk group with
     an attached signalling link."
    INDEX       { ifIndex }
  ::= { nncExtSVCSigStatsCurrShortTable 1 }


  NncExtSVCSigStatsCurrShortEntry ::=
    SEQUENCE {
      nncExtSVCSigStatsCurrShortIntvlState         NncExtIntvlStateType,
      nncExtSVCSigStatsCurrShortAbsIntvlNumber     NncExtAbsIntvlNumberType,
      nncExtSVCSigStatsCurrShortIntvlStartTime     DateAndTime,
      nncExtSVCSigStatsCurrShortIntvlDuration      NncExtIntvlDurationType,
      nncExtSVCSigStatsCurrShortInSetupAttempts    NncExtSetupAttemptsType,
      nncExtSVCSigStatsCurrShortInConnectedCalls   NncExtConnectedCallsType,
      nncExtSVCSigStatsCurrShortInTransitedCalls   NncExtTransitedCallsType,
      nncExtSVCSigStatsCurrShortOutSetupAttempts   NncExtSetupAttemptsType,
      nncExtSVCSigStatsCurrShortOutConnectedCalls  NncExtConnectedCallsType,
      nncExtSVCSigStatsCurrShortOutTransitedCalls  NncExtTransitedCallsType,
      nncExtSVCSigStatsCurrShortRxCalledPtyEvents  NncExtCalledPtyEventsType,
      nncExtSVCSigStatsCurrShortRxCallingPtyEvents NncExtCallingPtyEventsType,
      nncExtSVCSigStatsCurrShortRxResUnavailable   NncExtResUnavailableType,
      nncExtSVCSigStatsCurrShortRxRoutingFailure   NncExtRoutingFailureType,
      nncExtSVCSigStatsCurrShortRxInvalidMessage   NncExtInvalidMessageType,
      nncExtSVCSigStatsCurrShortRxTimerExpiration  NncExtTimerExpirationType,
      nncExtSVCSigStatsCurrShortRxNormalCallClr    NncExtNormalCallClrType,
      nncExtSVCSigStatsCurrShortRxOtherCauses      NncExtOtherCausesType,
      nncExtSVCSigStatsCurrShortTxCalledPtyEvents  NncExtCalledPtyEventsType,
      nncExtSVCSigStatsCurrShortTxCallingPtyEvents NncExtCallingPtyEventsType,
      nncExtSVCSigStatsCurrShortTxResUnavailable   NncExtResUnavailableType,
      nncExtSVCSigStatsCurrShortTxRoutingFailure   NncExtRoutingFailureType,
      nncExtSVCSigStatsCurrShortTxInvalidMessage   NncExtInvalidMessageType,
      nncExtSVCSigStatsCurrShortTxTimerExpiration  NncExtTimerExpirationType,
      nncExtSVCSigStatsCurrShortTxNormalCallClr    NncExtNormalCallClrType,
      nncExtSVCSigStatsCurrShortTxOtherCauses      NncExtOtherCausesType,
      nncExtSVCSigStatsCurrShortScreeningFailures  NncExtScreeningFailuresType,
      nncExtSVCSigStatsCurrShortInCDNSelectiveCalls NncExtSelectiveCallsType,
      nncExtSVCSigStatsCurrShortInCGNSelectiveCalls NncExtSelectiveCallsType,
      nncExtSVCSigStatsCurrShortOutCDNSelectiveCalls NncExtSelectiveCallsType,
      nncExtSVCSigStatsCurrShortOutCGNSelectiveCalls NncExtSelectiveCallsType
    }

  nncExtSVCSigStatsCurrShortIntvlState             OBJECT-TYPE
    SYNTAX                                          NncExtIntvlStateType
    MAX-ACCESS                                      read-only
    STATUS                                          current
    DESCRIPTION                    
    "The state of the current short interval."
  ::= { nncExtSVCSigStatsCurrShortEntry 1 }

  nncExtSVCSigStatsCurrShortAbsIntvlNumber         OBJECT-TYPE
    SYNTAX                                          NncExtAbsIntvlNumberType
    MAX-ACCESS                                      read-only
    STATUS                                          current
    DESCRIPTION                    
    "The absolute index number of the current short interval."
  ::= { nncExtSVCSigStatsCurrShortEntry 2 }

  nncExtSVCSigStatsCurrShortIntvlStartTime         OBJECT-TYPE
    SYNTAX                                          DateAndTime
    MAX-ACCESS                                      read-only
    STATUS                                          current
    DESCRIPTION                    
    "The start time of the current short interval."
  ::= { nncExtSVCSigStatsCurrShortEntry 3 }

  nncExtSVCSigStatsCurrShortIntvlDuration          OBJECT-TYPE
    SYNTAX                                          NncExtIntvlDurationType
    UNITS                                           "seconds"
    MAX-ACCESS                                      read-only
    STATUS                                          current
    DESCRIPTION                    
    "The duration of the current short interval."
  ::= { nncExtSVCSigStatsCurrShortEntry 4 }

  nncExtSVCSigStatsCurrShortInSetupAttempts        OBJECT-TYPE
    SYNTAX                                          NncExtSetupAttemptsType
    MAX-ACCESS                                      read-only
    STATUS                                          current
    DESCRIPTION
    "Current short interval setup attempts counter for the incoming calls."
  ::= { nncExtSVCSigStatsCurrShortEntry 5 }

  nncExtSVCSigStatsCurrShortInConnectedCalls       OBJECT-TYPE
    SYNTAX                                          NncExtConnectedCallsType
    MAX-ACCESS                                      read-only
    STATUS                                          current
    DESCRIPTION
    "Current short interval connect attempts counter for the incoming calls." 
  ::= { nncExtSVCSigStatsCurrShortEntry 6 }

  nncExtSVCSigStatsCurrShortInTransitedCalls       OBJECT-TYPE
    SYNTAX                                          NncExtTransitedCallsType
    MAX-ACCESS                                      read-only
    STATUS                                          current
    DESCRIPTION
    "Current short interval transited calls counter for the incoming calls."
  ::= { nncExtSVCSigStatsCurrShortEntry 7 }

  nncExtSVCSigStatsCurrShortOutSetupAttempts       OBJECT-TYPE
    SYNTAX                                          NncExtSetupAttemptsType
    MAX-ACCESS                                      read-only
    STATUS                                          current
    DESCRIPTION
    "Current short interval setup attempts counter for the outgoing calls." 
  ::= { nncExtSVCSigStatsCurrShortEntry 8 }

  nncExtSVCSigStatsCurrShortOutConnectedCalls      OBJECT-TYPE
    SYNTAX                                          NncExtConnectedCallsType
    MAX-ACCESS                                      read-only
    STATUS                                          current
    DESCRIPTION
    "Current short interval connect attempts counter for the outgoing calls."
  ::= { nncExtSVCSigStatsCurrShortEntry 9 }

  nncExtSVCSigStatsCurrShortOutTransitedCalls      OBJECT-TYPE
    SYNTAX                                          NncExtTransitedCallsType
    MAX-ACCESS                                      read-only
    STATUS                                          current
    DESCRIPTION
    "Current short interval transited calls counter for the outgoing calls."
  ::= { nncExtSVCSigStatsCurrShortEntry 10 }

  nncExtSVCSigStatsCurrShortRxCalledPtyEvents      OBJECT-TYPE
    SYNTAX                                          NncExtCalledPtyEventsType
    MAX-ACCESS                                      read-only
    STATUS                                          current
    DESCRIPTION
    "Current short interval received called party events cause code counter." 
  ::= { nncExtSVCSigStatsCurrShortEntry 11 }

  nncExtSVCSigStatsCurrShortRxCallingPtyEvents     OBJECT-TYPE
    SYNTAX                                          NncExtCallingPtyEventsType
    MAX-ACCESS                                      read-only
    STATUS                                          current
    DESCRIPTION
    "Current short interval received calling party events cause code counter."
  ::= { nncExtSVCSigStatsCurrShortEntry 12 }

  nncExtSVCSigStatsCurrShortRxResUnavailable       OBJECT-TYPE
    SYNTAX                                          NncExtResUnavailableType
    MAX-ACCESS                                      read-only
    STATUS                                          current
    DESCRIPTION
    "Current short interval received resource unavailable cause code counter."
  ::= { nncExtSVCSigStatsCurrShortEntry 13 }

  nncExtSVCSigStatsCurrShortRxRoutingFailure       OBJECT-TYPE
    SYNTAX                                          NncExtRoutingFailureType
    MAX-ACCESS                                      read-only
    STATUS                                          current
    DESCRIPTION
    "Current short interval received routing failure cause code counter."
  ::= { nncExtSVCSigStatsCurrShortEntry 14 }

  nncExtSVCSigStatsCurrShortRxInvalidMessage       OBJECT-TYPE
    SYNTAX                                          NncExtInvalidMessageType
    MAX-ACCESS                                      read-only
    STATUS                                          current
    DESCRIPTION
    "Current short interval received invalid message cause code counter."
  ::= { nncExtSVCSigStatsCurrShortEntry 15 }

  nncExtSVCSigStatsCurrShortRxTimerExpiration      OBJECT-TYPE
    SYNTAX                                          NncExtTimerExpirationType
    MAX-ACCESS                                      read-only
    STATUS                                          current
    DESCRIPTION
    "Current short interval received timer expiration cause code counter."
  ::= { nncExtSVCSigStatsCurrShortEntry 16 }

  nncExtSVCSigStatsCurrShortRxNormalCallClr        OBJECT-TYPE
    SYNTAX                                          NncExtNormalCallClrType
    MAX-ACCESS                                      read-only
    STATUS                                          current
    DESCRIPTION
    "Current short interval received 'normal call clearing' cause code 
    counter."
  ::= { nncExtSVCSigStatsCurrShortEntry 17 }

  nncExtSVCSigStatsCurrShortRxOtherCauses          OBJECT-TYPE
    SYNTAX                                          NncExtOtherCausesType
    MAX-ACCESS                                      read-only
    STATUS                                          current
    DESCRIPTION
    "Current short interval received other causes cause code counter."
  ::= { nncExtSVCSigStatsCurrShortEntry 18 }

  nncExtSVCSigStatsCurrShortTxCalledPtyEvents      OBJECT-TYPE
    SYNTAX                                          NncExtCalledPtyEventsType
    MAX-ACCESS                                      read-only
    STATUS                                          current
    DESCRIPTION
    "Current short interval transmitted called party events cause code 
     counter."
  ::= { nncExtSVCSigStatsCurrShortEntry 19 }

  nncExtSVCSigStatsCurrShortTxCallingPtyEvents     OBJECT-TYPE
    SYNTAX                                          NncExtCallingPtyEventsType
    MAX-ACCESS                                      read-only
    STATUS                                          current
    DESCRIPTION
    "Current short interval transmitted calling party events cause code 
     counter."
  ::= { nncExtSVCSigStatsCurrShortEntry 20 }

  nncExtSVCSigStatsCurrShortTxResUnavailable       OBJECT-TYPE
    SYNTAX                                          NncExtResUnavailableType
    MAX-ACCESS                                      read-only
    STATUS                                          current
    DESCRIPTION
    "Current short interval transmitted resource unavailable cause code 
     counter."
  ::= { nncExtSVCSigStatsCurrShortEntry 21 }

  nncExtSVCSigStatsCurrShortTxRoutingFailure       OBJECT-TYPE
    SYNTAX                                          NncExtRoutingFailureType
    MAX-ACCESS                                      read-only
    STATUS                                          current
    DESCRIPTION
    "Current short interval transmitted routing failure cause code counter."
  ::= { nncExtSVCSigStatsCurrShortEntry 22 }

  nncExtSVCSigStatsCurrShortTxInvalidMessage       OBJECT-TYPE
    SYNTAX                                          NncExtInvalidMessageType
    MAX-ACCESS                                      read-only
    STATUS                                          current
    DESCRIPTION
    "Current short interval transmitted invalid message cause code counter."
  ::= { nncExtSVCSigStatsCurrShortEntry 23 }

  nncExtSVCSigStatsCurrShortTxTimerExpiration      OBJECT-TYPE
    SYNTAX                                          NncExtTimerExpirationType
    MAX-ACCESS                                      read-only
    STATUS                                          current
    DESCRIPTION
    "Current short interval transmitted timer expiration cause code counter."
  ::= { nncExtSVCSigStatsCurrShortEntry 24 }

  nncExtSVCSigStatsCurrShortTxNormalCallClr        OBJECT-TYPE
    SYNTAX                                          NncExtNormalCallClrType
    MAX-ACCESS                                      read-only
    STATUS                                          current
    DESCRIPTION
    "Current short interval transmitted 'normal call clearing' cause code 
    counter."
  ::= { nncExtSVCSigStatsCurrShortEntry 25 }

  nncExtSVCSigStatsCurrShortTxOtherCauses          OBJECT-TYPE
    SYNTAX                                          NncExtOtherCausesType
    MAX-ACCESS                                      read-only
    STATUS                                          current
    DESCRIPTION
    "Current short interval transmitted other causes cause code counter."
  ::= { nncExtSVCSigStatsCurrShortEntry 26 }

  nncExtSVCSigStatsCurrShortScreeningFailures      OBJECT-TYPE
    SYNTAX                                          NncExtScreeningFailuresType
    MAX-ACCESS                                      read-only
    STATUS                                          current
    DESCRIPTION
    "Current short interval incoming calls screening failures counter." 
  ::= { nncExtSVCSigStatsCurrShortEntry 27 }

  nncExtSVCSigStatsCurrShortInCDNSelectiveCalls     OBJECT-TYPE
    SYNTAX                                          NncExtSelectiveCallsType
    MAX-ACCESS                                      read-only
    STATUS                                          current
    DESCRIPTION
    "Current short interval selective calls counter for incoming called
     numbers."
  ::= { nncExtSVCSigStatsCurrShortEntry 28 }

  nncExtSVCSigStatsCurrShortInCGNSelectiveCalls     OBJECT-TYPE
    SYNTAX                                          NncExtSelectiveCallsType
    MAX-ACCESS                                      read-only
    STATUS                                          current
    DESCRIPTION
    "Current short interval selective calls counter for incoming calling
     numbers."
  ::= { nncExtSVCSigStatsCurrShortEntry 29 }

  nncExtSVCSigStatsCurrShortOutCDNSelectiveCalls    OBJECT-TYPE
    SYNTAX                                          NncExtSelectiveCallsType
    MAX-ACCESS                                      read-only
    STATUS                                          current
    DESCRIPTION
    "Current short interval selective calls counter for outgoing called
     numbers."
  ::= { nncExtSVCSigStatsCurrShortEntry 30 }

  nncExtSVCSigStatsCurrShortOutCGNSelectiveCalls    OBJECT-TYPE
    SYNTAX                                          NncExtSelectiveCallsType
    MAX-ACCESS                                      read-only
    STATUS                                          current
    DESCRIPTION
    "Current short interval selective calls counter for outgoing calling
     numbers."
  ::= { nncExtSVCSigStatsCurrShortEntry 31 }


--------------------------------------------------------------------------------
--  Table 2: Previous Short Interval Table
--------------------------------------------------------------------------------
  nncExtSVCSigStatsPrevShortTable OBJECT-TYPE
    SYNTAX       SEQUENCE OF NncExtSVCSigStatsPrevShortEntry
    MAX-ACCESS   not-accessible
    STATUS       current
    DESCRIPTION  
    "The nncExtSVCSigStatsPrevShortTable contains objects for monitoring 
     the performance of a signalling link during a previous short interval."
  ::= { nncExtSVCSigStatsObjects 2 }


  nncExtSVCSigStatsPrevShortEntry OBJECT-TYPE
    SYNTAX      NncExtSVCSigStatsPrevShortEntry
    MAX-ACCESS  not-accessible
    STATUS      current
    DESCRIPTION  
    "An entry in the previous short interval statistics table. Each 
     conceptual row contains previous interval statistics for a particular 
     signalling link. ifIndex corresponds to the trunk group with
     an attached signalling link."
    INDEX       { ifIndex,
                  nncExtSVCSigStatsPrevShortIntvlNumber }
  ::= { nncExtSVCSigStatsPrevShortTable 1 }


  NncExtSVCSigStatsPrevShortEntry ::=
    SEQUENCE {
      nncExtSVCSigStatsPrevShortIntvlNumber        NncExtRelIntvlNumberType,
      nncExtSVCSigStatsPrevShortIntvlState         NncExtIntvlStateType,
      nncExtSVCSigStatsPrevShortAbsIntvlNumber     NncExtAbsIntvlNumberType,
      nncExtSVCSigStatsPrevShortIntvlStartTime     DateAndTime,
      nncExtSVCSigStatsPrevShortIntvlDuration      NncExtIntvlDurationType,
      nncExtSVCSigStatsPrevShortInSetupAttempts    NncExtSetupAttemptsType,
      nncExtSVCSigStatsPrevShortInConnectedCalls   NncExtConnectedCallsType,
      nncExtSVCSigStatsPrevShortInTransitedCalls   NncExtTransitedCallsType,
      nncExtSVCSigStatsPrevShortOutSetupAttempts   NncExtSetupAttemptsType,
      nncExtSVCSigStatsPrevShortOutConnectedCalls  NncExtConnectedCallsType,
      nncExtSVCSigStatsPrevShortOutTransitedCalls  NncExtTransitedCallsType,
      nncExtSVCSigStatsPrevShortRxCalledPtyEvents  NncExtCalledPtyEventsType,
      nncExtSVCSigStatsPrevShortRxCallingPtyEvents NncExtCallingPtyEventsType,
      nncExtSVCSigStatsPrevShortRxResUnavailable   NncExtResUnavailableType,
      nncExtSVCSigStatsPrevShortRxRoutingFailure   NncExtRoutingFailureType,
      nncExtSVCSigStatsPrevShortRxInvalidMessage   NncExtInvalidMessageType,
      nncExtSVCSigStatsPrevShortRxTimerExpiration  NncExtTimerExpirationType,
      nncExtSVCSigStatsPrevShortRxNormalCallClr    NncExtNormalCallClrType,
      nncExtSVCSigStatsPrevShortRxOtherCauses      NncExtOtherCausesType,
      nncExtSVCSigStatsPrevShortTxCalledPtyEvents  NncExtCalledPtyEventsType,
      nncExtSVCSigStatsPrevShortTxCallingPtyEvents NncExtCallingPtyEventsType,
      nncExtSVCSigStatsPrevShortTxResUnavailable   NncExtResUnavailableType,
      nncExtSVCSigStatsPrevShortTxRoutingFailure   NncExtRoutingFailureType,
      nncExtSVCSigStatsPrevShortTxInvalidMessage   NncExtInvalidMessageType,
      nncExtSVCSigStatsPrevShortTxTimerExpiration  NncExtTimerExpirationType,
      nncExtSVCSigStatsPrevShortTxNormalCallClr    NncExtNormalCallClrType,
      nncExtSVCSigStatsPrevShortTxOtherCauses      NncExtOtherCausesType,
      nncExtSVCSigStatsPrevShortScreeningFailures  NncExtScreeningFailuresType,
      nncExtSVCSigStatsPrevShortInCDNSelectiveCalls NncExtSelectiveCallsType,
      nncExtSVCSigStatsPrevShortInCGNSelectiveCalls NncExtSelectiveCallsType,
      nncExtSVCSigStatsPrevShortOutCDNSelectiveCalls NncExtSelectiveCallsType,
      nncExtSVCSigStatsPrevShortOutCGNSelectiveCalls NncExtSelectiveCallsType
    }

  nncExtSVCSigStatsPrevShortIntvlNumber            OBJECT-TYPE
    SYNTAX                                          NncExtRelIntvlNumberType
    MAX-ACCESS                                      not-accessible
    STATUS                                          current
    DESCRIPTION                    
    "The relative index of the previous short interval."
  ::= { nncExtSVCSigStatsPrevShortEntry 1 }

  nncExtSVCSigStatsPrevShortIntvlState             OBJECT-TYPE
    SYNTAX                                          NncExtIntvlStateType
    MAX-ACCESS                                      read-only
    STATUS                                          current
    DESCRIPTION                    
    "The state of the previous short interval."
  ::= { nncExtSVCSigStatsPrevShortEntry 2 }

  nncExtSVCSigStatsPrevShortAbsIntvlNumber         OBJECT-TYPE
    SYNTAX                                          NncExtAbsIntvlNumberType
    MAX-ACCESS                                      read-only
    STATUS                                          current
    DESCRIPTION                    
    "The absolute index number of the previous short interval."
  ::= { nncExtSVCSigStatsPrevShortEntry 3 }

  nncExtSVCSigStatsPrevShortIntvlStartTime         OBJECT-TYPE
    SYNTAX                                          DateAndTime
    MAX-ACCESS                                      read-only
    STATUS                                          current
    DESCRIPTION                    
    "The start time of the previous short interval."
  ::= { nncExtSVCSigStatsPrevShortEntry 4 }

  nncExtSVCSigStatsPrevShortIntvlDuration          OBJECT-TYPE
    SYNTAX                                          NncExtIntvlDurationType
    UNITS                                           "seconds"
    MAX-ACCESS                                      read-only
    STATUS                                          current
    DESCRIPTION                    
    "The duration of the previous short interval."
  ::= { nncExtSVCSigStatsPrevShortEntry 5 }

  nncExtSVCSigStatsPrevShortInSetupAttempts        OBJECT-TYPE
    SYNTAX                                          NncExtSetupAttemptsType
    MAX-ACCESS                                      read-only
    STATUS                                          current
    DESCRIPTION
    "Previous short interval setup attempts counter for the incoming calls."
  ::= { nncExtSVCSigStatsPrevShortEntry 6 }

  nncExtSVCSigStatsPrevShortInConnectedCalls       OBJECT-TYPE
    SYNTAX                                          NncExtConnectedCallsType
    MAX-ACCESS                                      read-only
    STATUS                                          current
    DESCRIPTION
    "Previous short interval connect attempts counter for the incoming calls." 
  ::= { nncExtSVCSigStatsPrevShortEntry 7 }

  nncExtSVCSigStatsPrevShortInTransitedCalls       OBJECT-TYPE
    SYNTAX                                          NncExtTransitedCallsType
    MAX-ACCESS                                      read-only
    STATUS                                          current
    DESCRIPTION
    "Previous short interval transited calls counter for the incoming calls."
  ::= { nncExtSVCSigStatsPrevShortEntry 8 }

  nncExtSVCSigStatsPrevShortOutSetupAttempts       OBJECT-TYPE
    SYNTAX                                          NncExtSetupAttemptsType
    MAX-ACCESS                                      read-only
    STATUS                                          current
    DESCRIPTION
    "Previous short interval setup attempts counter for the outgoing calls." 
  ::= { nncExtSVCSigStatsPrevShortEntry 9 }

  nncExtSVCSigStatsPrevShortOutConnectedCalls      OBJECT-TYPE
    SYNTAX                                          NncExtConnectedCallsType
    MAX-ACCESS                                      read-only
    STATUS                                          current
    DESCRIPTION
    "Previous short interval connect attempts counter for the outgoing calls."
  ::= { nncExtSVCSigStatsPrevShortEntry 10 }

  nncExtSVCSigStatsPrevShortOutTransitedCalls      OBJECT-TYPE
    SYNTAX                                          NncExtTransitedCallsType
    MAX-ACCESS                                      read-only
    STATUS                                          current
    DESCRIPTION
    "Previous short interval transited calls counter for the outgoing calls."
  ::= { nncExtSVCSigStatsPrevShortEntry 11 }

  nncExtSVCSigStatsPrevShortRxCalledPtyEvents      OBJECT-TYPE
    SYNTAX                                          NncExtCalledPtyEventsType
    MAX-ACCESS                                      read-only
    STATUS                                          current
    DESCRIPTION
    "Previous short interval received called party events cause code counter." 
  ::= { nncExtSVCSigStatsPrevShortEntry 12 }

  nncExtSVCSigStatsPrevShortRxCallingPtyEvents     OBJECT-TYPE
    SYNTAX                                          NncExtCallingPtyEventsType
    MAX-ACCESS                                      read-only
    STATUS                                          current
    DESCRIPTION
    "Previous short interval received calling party events cause code counter."
  ::= { nncExtSVCSigStatsPrevShortEntry 13 }

  nncExtSVCSigStatsPrevShortRxResUnavailable       OBJECT-TYPE
    SYNTAX                                          NncExtResUnavailableType
    MAX-ACCESS                                      read-only
    STATUS                                          current
    DESCRIPTION
    "Previous short interval received resource unavailable cause code counter."
  ::= { nncExtSVCSigStatsPrevShortEntry 14 }

  nncExtSVCSigStatsPrevShortRxRoutingFailure       OBJECT-TYPE
    SYNTAX                                          NncExtRoutingFailureType
    MAX-ACCESS                                      read-only
    STATUS                                          current
    DESCRIPTION
    "Previous short interval received routing failure cause code counter."
  ::= { nncExtSVCSigStatsPrevShortEntry 15 }

  nncExtSVCSigStatsPrevShortRxInvalidMessage       OBJECT-TYPE
    SYNTAX                                          NncExtInvalidMessageType
    MAX-ACCESS                                      read-only
    STATUS                                          current
    DESCRIPTION
    "Previous short interval received invalid message cause code counter."
  ::= { nncExtSVCSigStatsPrevShortEntry 16 }

  nncExtSVCSigStatsPrevShortRxTimerExpiration      OBJECT-TYPE
    SYNTAX                                          NncExtTimerExpirationType
    MAX-ACCESS                                      read-only
    STATUS                                          current
    DESCRIPTION
    "Previous short interval received timer expiration cause code counter."
  ::= { nncExtSVCSigStatsPrevShortEntry 17 }

  nncExtSVCSigStatsPrevShortRxNormalCallClr        OBJECT-TYPE
    SYNTAX                                          NncExtNormalCallClrType
    MAX-ACCESS                                      read-only
    STATUS                                          current
    DESCRIPTION
    "Previous short interval received 'normal call clearing' cause code 
    counter."
  ::= { nncExtSVCSigStatsPrevShortEntry 18 }

  nncExtSVCSigStatsPrevShortRxOtherCauses          OBJECT-TYPE
    SYNTAX                                          NncExtOtherCausesType
    MAX-ACCESS                                      read-only
    STATUS                                          current
    DESCRIPTION
    "Previous short interval received other causes cause code counter."
  ::= { nncExtSVCSigStatsPrevShortEntry 19 }

  nncExtSVCSigStatsPrevShortTxCalledPtyEvents      OBJECT-TYPE
    SYNTAX                                          NncExtCalledPtyEventsType
    MAX-ACCESS                                      read-only
    STATUS                                          current
    DESCRIPTION
    "Previous short interval transmitted called party events cause code 
     counter."
  ::= { nncExtSVCSigStatsPrevShortEntry 20 }

  nncExtSVCSigStatsPrevShortTxCallingPtyEvents     OBJECT-TYPE
    SYNTAX                                          NncExtCallingPtyEventsType
    MAX-ACCESS                                      read-only
    STATUS                                          current
    DESCRIPTION
    "Previous short interval transmitted calling party events cause code 
     counter."
  ::= { nncExtSVCSigStatsPrevShortEntry 21 }

  nncExtSVCSigStatsPrevShortTxResUnavailable       OBJECT-TYPE
    SYNTAX                                          NncExtResUnavailableType
    MAX-ACCESS                                      read-only
    STATUS                                          current
    DESCRIPTION
    "Previous short interval transmitted resource unavailable cause code 
     counter."
  ::= { nncExtSVCSigStatsPrevShortEntry 22 }

  nncExtSVCSigStatsPrevShortTxRoutingFailure       OBJECT-TYPE
    SYNTAX                                          NncExtRoutingFailureType
    MAX-ACCESS                                      read-only
    STATUS                                          current
    DESCRIPTION
    "Previous short interval transmitted routing failure cause code counter."
  ::= { nncExtSVCSigStatsPrevShortEntry 23 }

  nncExtSVCSigStatsPrevShortTxInvalidMessage       OBJECT-TYPE
    SYNTAX                                          NncExtInvalidMessageType
    MAX-ACCESS                                      read-only
    STATUS                                          current
    DESCRIPTION
    "Previous short interval transmitted invalid message cause code counter."
  ::= { nncExtSVCSigStatsPrevShortEntry 24 }

  nncExtSVCSigStatsPrevShortTxTimerExpiration      OBJECT-TYPE
    SYNTAX                                          NncExtTimerExpirationType
    MAX-ACCESS                                      read-only
    STATUS                                          current
    DESCRIPTION
    "Previous short interval transmitted timer expiration cause code counter."
  ::= { nncExtSVCSigStatsPrevShortEntry 25 }

  nncExtSVCSigStatsPrevShortTxNormalCallClr        OBJECT-TYPE
    SYNTAX                                          NncExtNormalCallClrType
    MAX-ACCESS                                      read-only
    STATUS                                          current
    DESCRIPTION
    "Previous short interval transmitted 'normal call clearing' cause code 
    counter."
  ::= { nncExtSVCSigStatsPrevShortEntry 26 }

  nncExtSVCSigStatsPrevShortTxOtherCauses          OBJECT-TYPE
    SYNTAX                                          NncExtOtherCausesType
    MAX-ACCESS                                      read-only
    STATUS                                          current
    DESCRIPTION
    "Previous short interval transmitted other causes cause code counter."
  ::= { nncExtSVCSigStatsPrevShortEntry 27 }

  nncExtSVCSigStatsPrevShortScreeningFailures      OBJECT-TYPE
    SYNTAX                                          NncExtScreeningFailuresType
    MAX-ACCESS                                      read-only
    STATUS                                          current
    DESCRIPTION
    "Previous short interval incoming calls screening failures counter." 
  ::= { nncExtSVCSigStatsPrevShortEntry 28 }

  nncExtSVCSigStatsPrevShortInCDNSelectiveCalls     OBJECT-TYPE
    SYNTAX                                          NncExtSelectiveCallsType
    MAX-ACCESS                                      read-only
    STATUS                                          current
    DESCRIPTION
    "Previous short interval selective calls counter for incoming called
     number." 
  ::= { nncExtSVCSigStatsPrevShortEntry 29 }

  nncExtSVCSigStatsPrevShortInCGNSelectiveCalls     OBJECT-TYPE
    SYNTAX                                          NncExtSelectiveCallsType
    MAX-ACCESS                                      read-only
    STATUS                                          current
    DESCRIPTION
    "Previous short interval selective calls counter for incoming calling
     number." 
  ::= { nncExtSVCSigStatsPrevShortEntry 30 }

  nncExtSVCSigStatsPrevShortOutCDNSelectiveCalls     OBJECT-TYPE
    SYNTAX                                          NncExtSelectiveCallsType
    MAX-ACCESS                                      read-only
    STATUS                                          current
    DESCRIPTION
    "Previous short interval selective calls counter for outgoing called
     number." 
  ::= { nncExtSVCSigStatsPrevShortEntry 31 }

  nncExtSVCSigStatsPrevShortOutCGNSelectiveCalls    OBJECT-TYPE
    SYNTAX                                          NncExtSelectiveCallsType
    MAX-ACCESS                                      read-only
    STATUS                                          current
    DESCRIPTION
    "Previous short interval selective calls counter for outgoing calling
     number." 
  ::= { nncExtSVCSigStatsPrevShortEntry 32 }


--------------------------------------------------------------------------------
--  Table 3: Current Long Interval Table
--------------------------------------------------------------------------------
  nncExtSVCSigStatsCurrLongTable OBJECT-TYPE
    SYNTAX       SEQUENCE OF NncExtSVCSigStatsCurrLongEntry
    MAX-ACCESS   not-accessible
    STATUS       current
    DESCRIPTION  
    "The nncExtSVCSigStatsCurrLongTable contains objects for monitoring 
     the performance of a signalling link during a current long interval."
  ::= { nncExtSVCSigStatsObjects 3 }


  nncExtSVCSigStatsCurrLongEntry OBJECT-TYPE
    SYNTAX      NncExtSVCSigStatsCurrLongEntry
    MAX-ACCESS  not-accessible
    STATUS      current
    DESCRIPTION  
    "An entry in the current long interval statistics table. Each 
     conceptual row contains current statistics for a particular 
     signalling link. ifIndex corresponds to the trunk group with
     an attached signalling link."
    INDEX       { ifIndex }
  ::= { nncExtSVCSigStatsCurrLongTable 1 }


  NncExtSVCSigStatsCurrLongEntry ::=
    SEQUENCE {
      nncExtSVCSigStatsCurrLongIntvlState         NncExtIntvlStateType,
      nncExtSVCSigStatsCurrLongAbsIntvlNumber     NncExtAbsIntvlNumberType,
      nncExtSVCSigStatsCurrLongIntvlStartTime     DateAndTime,
      nncExtSVCSigStatsCurrLongIntvlDuration      NncExtIntvlDurationType,
      nncExtSVCSigStatsCurrLongInSetupAttempts    NncExtSetupAttemptsType,
      nncExtSVCSigStatsCurrLongInConnectedCalls   NncExtConnectedCallsType,
      nncExtSVCSigStatsCurrLongInTransitedCalls   NncExtTransitedCallsType,
      nncExtSVCSigStatsCurrLongOutSetupAttempts   NncExtSetupAttemptsType,
      nncExtSVCSigStatsCurrLongOutConnectedCalls  NncExtConnectedCallsType,
      nncExtSVCSigStatsCurrLongOutTransitedCalls  NncExtTransitedCallsType,
      nncExtSVCSigStatsCurrLongRxCalledPtyEvents  NncExtCalledPtyEventsType,
      nncExtSVCSigStatsCurrLongRxCallingPtyEvents NncExtCallingPtyEventsType,
      nncExtSVCSigStatsCurrLongRxResUnavailable   NncExtResUnavailableType,
      nncExtSVCSigStatsCurrLongRxRoutingFailure   NncExtRoutingFailureType,
      nncExtSVCSigStatsCurrLongRxInvalidMessage   NncExtInvalidMessageType,
      nncExtSVCSigStatsCurrLongRxTimerExpiration  NncExtTimerExpirationType,
      nncExtSVCSigStatsCurrLongRxNormalCallClr    NncExtNormalCallClrType,
      nncExtSVCSigStatsCurrLongRxOtherCauses      NncExtOtherCausesType,
      nncExtSVCSigStatsCurrLongTxCalledPtyEvents  NncExtCalledPtyEventsType,
      nncExtSVCSigStatsCurrLongTxCallingPtyEvents NncExtCallingPtyEventsType,
      nncExtSVCSigStatsCurrLongTxResUnavailable   NncExtResUnavailableType,
      nncExtSVCSigStatsCurrLongTxRoutingFailure   NncExtRoutingFailureType,
      nncExtSVCSigStatsCurrLongTxInvalidMessage   NncExtInvalidMessageType,
      nncExtSVCSigStatsCurrLongTxTimerExpiration  NncExtTimerExpirationType,
      nncExtSVCSigStatsCurrLongTxNormalCallClr    NncExtNormalCallClrType,
      nncExtSVCSigStatsCurrLongTxOtherCauses      NncExtOtherCausesType,
      nncExtSVCSigStatsCurrLongScreeningFailures  NncExtScreeningFailuresType,
      nncExtSVCSigStatsCurrLongInCDNSelectiveCalls NncExtSelectiveCallsType,
      nncExtSVCSigStatsCurrLongInCGNSelectiveCalls NncExtSelectiveCallsType,
      nncExtSVCSigStatsCurrLongOutCDNSelectiveCalls NncExtSelectiveCallsType,
      nncExtSVCSigStatsCurrLongOutCGNSelectiveCalls NncExtSelectiveCallsType
    }

  nncExtSVCSigStatsCurrLongIntvlState              OBJECT-TYPE
    SYNTAX                                          NncExtIntvlStateType
    MAX-ACCESS                                      read-only
    STATUS                                          current
    DESCRIPTION                    
    "The state of the current long interval."
  ::= { nncExtSVCSigStatsCurrLongEntry 1 }

  nncExtSVCSigStatsCurrLongAbsIntvlNumber          OBJECT-TYPE
    SYNTAX                                          NncExtAbsIntvlNumberType
    MAX-ACCESS                                      read-only
    STATUS                                          current
    DESCRIPTION                    
    "The absolute index number of the current long interval."
  ::= { nncExtSVCSigStatsCurrLongEntry 2 }

  nncExtSVCSigStatsCurrLongIntvlStartTime          OBJECT-TYPE
    SYNTAX                                          DateAndTime
    MAX-ACCESS                                      read-only
    STATUS                                          current
    DESCRIPTION                    
    "The start time of the current long interval."
  ::= { nncExtSVCSigStatsCurrLongEntry 3 }

  nncExtSVCSigStatsCurrLongIntvlDuration           OBJECT-TYPE
    SYNTAX                                          NncExtIntvlDurationType
    UNITS                                           "seconds"
    MAX-ACCESS                                      read-only
    STATUS                                          current
    DESCRIPTION                    
    "The duration of the current long interval."
  ::= { nncExtSVCSigStatsCurrLongEntry 4 }

  nncExtSVCSigStatsCurrLongInSetupAttempts         OBJECT-TYPE
    SYNTAX                                          NncExtSetupAttemptsType
    MAX-ACCESS                                      read-only
    STATUS                                          current
    DESCRIPTION
    "Current long interval setup attempts counter for the incoming calls."
  ::= { nncExtSVCSigStatsCurrLongEntry 5 }

  nncExtSVCSigStatsCurrLongInConnectedCalls        OBJECT-TYPE
    SYNTAX                                          NncExtConnectedCallsType
    MAX-ACCESS                                      read-only
    STATUS                                          current
    DESCRIPTION
    "Current long interval connect attempts counter for the incoming calls." 
  ::= { nncExtSVCSigStatsCurrLongEntry 6 }

  nncExtSVCSigStatsCurrLongInTransitedCalls        OBJECT-TYPE
    SYNTAX                                          NncExtTransitedCallsType
    MAX-ACCESS                                      read-only
    STATUS                                          current
    DESCRIPTION
    "Current long interval transited calls counter for the incoming calls."
  ::= { nncExtSVCSigStatsCurrLongEntry 7 }

  nncExtSVCSigStatsCurrLongOutSetupAttempts        OBJECT-TYPE
    SYNTAX                                          NncExtSetupAttemptsType
    MAX-ACCESS                                      read-only
    STATUS                                          current
    DESCRIPTION
    "Current long interval setup attempts counter for the outgoing calls." 
  ::= { nncExtSVCSigStatsCurrLongEntry 8 }

  nncExtSVCSigStatsCurrLongOutConnectedCalls       OBJECT-TYPE
    SYNTAX                                          NncExtConnectedCallsType
    MAX-ACCESS                                      read-only
    STATUS                                          current
    DESCRIPTION
    "Current long interval connect attempts counter for the outgoing calls."
  ::= { nncExtSVCSigStatsCurrLongEntry 9 }

  nncExtSVCSigStatsCurrLongOutTransitedCalls       OBJECT-TYPE
    SYNTAX                                          NncExtTransitedCallsType
    MAX-ACCESS                                      read-only
    STATUS                                          current
    DESCRIPTION
    "Current long interval transited calls counter for the outgoing calls."
  ::= { nncExtSVCSigStatsCurrLongEntry 10 }

  nncExtSVCSigStatsCurrLongRxCalledPtyEvents       OBJECT-TYPE
    SYNTAX                                          NncExtCalledPtyEventsType
    MAX-ACCESS                                      read-only
    STATUS                                          current
    DESCRIPTION
    "Current long interval received called party events cause code counter." 
  ::= { nncExtSVCSigStatsCurrLongEntry 11 }

  nncExtSVCSigStatsCurrLongRxCallingPtyEvents      OBJECT-TYPE
    SYNTAX                                          NncExtCallingPtyEventsType
    MAX-ACCESS                                      read-only
    STATUS                                          current
    DESCRIPTION
    "Current long interval received calling party events cause code counter."
  ::= { nncExtSVCSigStatsCurrLongEntry 12 }

  nncExtSVCSigStatsCurrLongRxResUnavailable        OBJECT-TYPE
    SYNTAX                                          NncExtResUnavailableType
    MAX-ACCESS                                      read-only
    STATUS                                          current
    DESCRIPTION
    "Current long interval received resource unavailable cause code counter."
  ::= { nncExtSVCSigStatsCurrLongEntry 13 }

  nncExtSVCSigStatsCurrLongRxRoutingFailure        OBJECT-TYPE
    SYNTAX                                          NncExtRoutingFailureType
    MAX-ACCESS                                      read-only
    STATUS                                          current
    DESCRIPTION
    "Current long interval received routing failure cause code counter."
  ::= { nncExtSVCSigStatsCurrLongEntry 14 }

  nncExtSVCSigStatsCurrLongRxInvalidMessage        OBJECT-TYPE
    SYNTAX                                          NncExtInvalidMessageType
    MAX-ACCESS                                      read-only
    STATUS                                          current
    DESCRIPTION
    "Current long interval received invalid message cause code counter."
  ::= { nncExtSVCSigStatsCurrLongEntry 15 }

  nncExtSVCSigStatsCurrLongRxTimerExpiration       OBJECT-TYPE
    SYNTAX                                          NncExtTimerExpirationType
    MAX-ACCESS                                      read-only
    STATUS                                          current
    DESCRIPTION
    "Current long interval received timer expiration cause code counter."
  ::= { nncExtSVCSigStatsCurrLongEntry 16 }

  nncExtSVCSigStatsCurrLongRxNormalCallClr         OBJECT-TYPE
    SYNTAX                                          NncExtNormalCallClrType
    MAX-ACCESS                                      read-only
    STATUS                                          current
    DESCRIPTION
    "Current long interval transmitted 'normal call clearing' cause code 
    counter."
  ::= { nncExtSVCSigStatsCurrLongEntry 17 }

  nncExtSVCSigStatsCurrLongRxOtherCauses           OBJECT-TYPE
    SYNTAX                                          NncExtOtherCausesType
    MAX-ACCESS                                      read-only
    STATUS                                          current
    DESCRIPTION
    "Current long interval received other causes cause code counter."
  ::= { nncExtSVCSigStatsCurrLongEntry 18 }

  nncExtSVCSigStatsCurrLongTxCalledPtyEvents       OBJECT-TYPE
    SYNTAX                                          NncExtCalledPtyEventsType
    MAX-ACCESS                                      read-only
    STATUS                                          current
    DESCRIPTION
    "Current long interval transmitted called party events cause code 
     counter."
  ::= { nncExtSVCSigStatsCurrLongEntry 19 }

  nncExtSVCSigStatsCurrLongTxCallingPtyEvents      OBJECT-TYPE
    SYNTAX                                          NncExtCallingPtyEventsType
    MAX-ACCESS                                      read-only
    STATUS                                          current
    DESCRIPTION
    "Current long interval transmitted calling party events cause code 
     counter."
  ::= { nncExtSVCSigStatsCurrLongEntry 20 }

  nncExtSVCSigStatsCurrLongTxResUnavailable        OBJECT-TYPE
    SYNTAX                                          NncExtResUnavailableType
    MAX-ACCESS                                      read-only
    STATUS                                          current
    DESCRIPTION
    "Current long interval transmitted resource unavailable cause code 
     counter."
  ::= { nncExtSVCSigStatsCurrLongEntry 21 }

  nncExtSVCSigStatsCurrLongTxRoutingFailure        OBJECT-TYPE
    SYNTAX                                          NncExtRoutingFailureType
    MAX-ACCESS                                      read-only
    STATUS                                          current
    DESCRIPTION
    "Current long interval transmitted routing failure cause code counter."
  ::= { nncExtSVCSigStatsCurrLongEntry 22 }

  nncExtSVCSigStatsCurrLongTxInvalidMessage        OBJECT-TYPE
    SYNTAX                                          NncExtInvalidMessageType
    MAX-ACCESS                                      read-only
    STATUS                                          current
    DESCRIPTION
    "Current long interval transmitted invalid message cause code counter."
  ::= { nncExtSVCSigStatsCurrLongEntry 23 }

  nncExtSVCSigStatsCurrLongTxTimerExpiration       OBJECT-TYPE
    SYNTAX                                          NncExtTimerExpirationType
    MAX-ACCESS                                      read-only
    STATUS                                          current
    DESCRIPTION
    "Current long interval transmitted timer expiration cause code counter."
  ::= { nncExtSVCSigStatsCurrLongEntry 24 }

  nncExtSVCSigStatsCurrLongTxNormalCallClr         OBJECT-TYPE
    SYNTAX                                          NncExtNormalCallClrType
    MAX-ACCESS                                      read-only
    STATUS                                          current
    DESCRIPTION
    "Current long interval transmitted 'normal call clearing' cause code 
    counter."
  ::= { nncExtSVCSigStatsCurrLongEntry 25 }

  nncExtSVCSigStatsCurrLongTxOtherCauses           OBJECT-TYPE
    SYNTAX                                          NncExtOtherCausesType
    MAX-ACCESS                                      read-only
    STATUS                                          current
    DESCRIPTION
    "Current long interval transmitted other causes cause code counter."
  ::= { nncExtSVCSigStatsCurrLongEntry 26 }

  nncExtSVCSigStatsCurrLongScreeningFailures       OBJECT-TYPE
    SYNTAX                                          NncExtScreeningFailuresType
    MAX-ACCESS                                      read-only
    STATUS                                          current
    DESCRIPTION
    "Current long interval incoming calls screening failures counter." 
  ::= { nncExtSVCSigStatsCurrLongEntry 27 }

  nncExtSVCSigStatsCurrLongInCDNSelectiveCalls     OBJECT-TYPE
    SYNTAX                                          NncExtSelectiveCallsType
    MAX-ACCESS                                      read-only
    STATUS                                          current
    DESCRIPTION
    "Current long interval selective calls counter for incoming called
    number." 
  ::= { nncExtSVCSigStatsCurrLongEntry 28 }

  nncExtSVCSigStatsCurrLongInCGNSelectiveCalls     OBJECT-TYPE
    SYNTAX                                          NncExtSelectiveCallsType
    MAX-ACCESS                                      read-only
    STATUS                                          current
    DESCRIPTION
    "Current long interval selective calls counter for incoming calling
    number." 
  ::= { nncExtSVCSigStatsCurrLongEntry 29 }

  nncExtSVCSigStatsCurrLongOutCDNSelectiveCalls    OBJECT-TYPE
    SYNTAX                                          NncExtSelectiveCallsType
    MAX-ACCESS                                      read-only
    STATUS                                          current
    DESCRIPTION
    "Current long interval selective calls counter for outgoing called
    number." 
  ::= { nncExtSVCSigStatsCurrLongEntry 30 }

  nncExtSVCSigStatsCurrLongOutCGNSelectiveCalls    OBJECT-TYPE
    SYNTAX                                          NncExtSelectiveCallsType
    MAX-ACCESS                                      read-only
    STATUS                                          current
    DESCRIPTION
    "Current long interval selective calls counter for outgoing calling
    number." 
  ::= { nncExtSVCSigStatsCurrLongEntry 31 }


--------------------------------------------------------------------------------
--  Table 4: Previous Long Interval Table
--------------------------------------------------------------------------------
  nncExtSVCSigStatsPrevLongTable OBJECT-TYPE
    SYNTAX       SEQUENCE OF NncExtSVCSigStatsPrevLongEntry
    MAX-ACCESS   not-accessible
    STATUS       current
    DESCRIPTION  
    "The nncExtSVCSigStatsPrevLongTable contains objects for monitoring 
     the performance of a signalling link during a previous long interval."
  ::= { nncExtSVCSigStatsObjects 4 }


  nncExtSVCSigStatsPrevLongEntry OBJECT-TYPE
    SYNTAX      NncExtSVCSigStatsPrevLongEntry
    MAX-ACCESS  not-accessible
    STATUS      current
    DESCRIPTION  
    "An entry in the previous long interval statistics table. Each 
     conceptual row contains previous interval statistics for a particular 
     signalling link. ifIndex corresponds to the trunk group with
     an attached signalling link."
    INDEX       { ifIndex,
                  nncExtSVCSigStatsPrevLongIntvlNumber }
  ::= { nncExtSVCSigStatsPrevLongTable 1 }


  NncExtSVCSigStatsPrevLongEntry ::=
    SEQUENCE {
      nncExtSVCSigStatsPrevLongIntvlNumber        NncExtRelIntvlNumberType,
      nncExtSVCSigStatsPrevLongIntvlState         NncExtIntvlStateType,
      nncExtSVCSigStatsPrevLongAbsIntvlNumber     NncExtAbsIntvlNumberType,
      nncExtSVCSigStatsPrevLongIntvlStartTime     DateAndTime,
      nncExtSVCSigStatsPrevLongIntvlDuration      NncExtIntvlDurationType,
      nncExtSVCSigStatsPrevLongInSetupAttempts    NncExtSetupAttemptsType,
      nncExtSVCSigStatsPrevLongInConnectedCalls   NncExtConnectedCallsType,
      nncExtSVCSigStatsPrevLongInTransitedCalls   NncExtTransitedCallsType,
      nncExtSVCSigStatsPrevLongOutSetupAttempts   NncExtSetupAttemptsType,
      nncExtSVCSigStatsPrevLongOutConnectedCalls  NncExtConnectedCallsType,
      nncExtSVCSigStatsPrevLongOutTransitedCalls  NncExtTransitedCallsType,
      nncExtSVCSigStatsPrevLongRxCalledPtyEvents  NncExtCalledPtyEventsType,
      nncExtSVCSigStatsPrevLongRxCallingPtyEvents NncExtCallingPtyEventsType,
      nncExtSVCSigStatsPrevLongRxResUnavailable   NncExtResUnavailableType,
      nncExtSVCSigStatsPrevLongRxRoutingFailure   NncExtRoutingFailureType,
      nncExtSVCSigStatsPrevLongRxInvalidMessage   NncExtInvalidMessageType,
      nncExtSVCSigStatsPrevLongRxTimerExpiration  NncExtTimerExpirationType,
      nncExtSVCSigStatsPrevLongRxNormalCallClr    NncExtNormalCallClrType,
      nncExtSVCSigStatsPrevLongRxOtherCauses      NncExtOtherCausesType,
      nncExtSVCSigStatsPrevLongTxCalledPtyEvents  NncExtCalledPtyEventsType,
      nncExtSVCSigStatsPrevLongTxCallingPtyEvents NncExtCallingPtyEventsType,
      nncExtSVCSigStatsPrevLongTxResUnavailable   NncExtResUnavailableType,
      nncExtSVCSigStatsPrevLongTxRoutingFailure   NncExtRoutingFailureType,
      nncExtSVCSigStatsPrevLongTxInvalidMessage   NncExtInvalidMessageType,
      nncExtSVCSigStatsPrevLongTxTimerExpiration  NncExtTimerExpirationType,
      nncExtSVCSigStatsPrevLongTxNormalCallClr    NncExtNormalCallClrType,
      nncExtSVCSigStatsPrevLongTxOtherCauses      NncExtOtherCausesType,
      nncExtSVCSigStatsPrevLongScreeningFailures  NncExtScreeningFailuresType,
      nncExtSVCSigStatsPrevLongInCDNSelectiveCalls NncExtSelectiveCallsType,
      nncExtSVCSigStatsPrevLongInCGNSelectiveCalls NncExtSelectiveCallsType,
      nncExtSVCSigStatsPrevLongOutCDNSelectiveCalls NncExtSelectiveCallsType,
      nncExtSVCSigStatsPrevLongOutCGNSelectiveCalls NncExtSelectiveCallsType
    }

  nncExtSVCSigStatsPrevLongIntvlNumber             OBJECT-TYPE
    SYNTAX                                          NncExtRelIntvlNumberType
    MAX-ACCESS                                      not-accessible
    STATUS                                          current
    DESCRIPTION                    
    "The relative index of the previous long interval."
  ::= { nncExtSVCSigStatsPrevLongEntry 1 }

  nncExtSVCSigStatsPrevLongIntvlState              OBJECT-TYPE
    SYNTAX                                          NncExtIntvlStateType
    MAX-ACCESS                                      read-only
    STATUS                                          current
    DESCRIPTION                    
    "The state of the previous long interval."
  ::= { nncExtSVCSigStatsPrevLongEntry 2 }

  nncExtSVCSigStatsPrevLongAbsIntvlNumber          OBJECT-TYPE
    SYNTAX                                          NncExtAbsIntvlNumberType
    MAX-ACCESS                                      read-only
    STATUS                                          current
    DESCRIPTION                    
    "The absolute index number of the previous long interval."
  ::= { nncExtSVCSigStatsPrevLongEntry 3 }

  nncExtSVCSigStatsPrevLongIntvlStartTime          OBJECT-TYPE
    SYNTAX                                          DateAndTime
    MAX-ACCESS                                      read-only
    STATUS                                          current
    DESCRIPTION                    
    "The start time of the previous long interval."
  ::= { nncExtSVCSigStatsPrevLongEntry 4 }

  nncExtSVCSigStatsPrevLongIntvlDuration           OBJECT-TYPE
    SYNTAX                                          NncExtIntvlDurationType
    UNITS                                           "seconds"
    MAX-ACCESS                                      read-only
    STATUS                                          current
    DESCRIPTION                    
    "The duration of the previous long interval."
  ::= { nncExtSVCSigStatsPrevLongEntry 5 }

  nncExtSVCSigStatsPrevLongInSetupAttempts         OBJECT-TYPE
    SYNTAX                                          NncExtSetupAttemptsType
    MAX-ACCESS                                      read-only
    STATUS                                          current
    DESCRIPTION
    "Previous long interval setup attempts counter for the incoming calls."
  ::= { nncExtSVCSigStatsPrevLongEntry 6 }

  nncExtSVCSigStatsPrevLongInConnectedCalls        OBJECT-TYPE
    SYNTAX                                          NncExtConnectedCallsType
    MAX-ACCESS                                      read-only
    STATUS                                          current
    DESCRIPTION
    "Previous long interval connect attempts counter for the incoming calls." 
  ::= { nncExtSVCSigStatsPrevLongEntry 7 }

  nncExtSVCSigStatsPrevLongInTransitedCalls        OBJECT-TYPE
    SYNTAX                                          NncExtTransitedCallsType
    MAX-ACCESS                                      read-only
    STATUS                                          current
    DESCRIPTION
    "Previous long interval transited calls counter for the incoming calls."
  ::= { nncExtSVCSigStatsPrevLongEntry 8 }

  nncExtSVCSigStatsPrevLongOutSetupAttempts        OBJECT-TYPE
    SYNTAX                                          NncExtSetupAttemptsType
    MAX-ACCESS                                      read-only
    STATUS                                          current
    DESCRIPTION
    "Previous long interval setup attempts counter for the outgoing calls." 
  ::= { nncExtSVCSigStatsPrevLongEntry 9 }

  nncExtSVCSigStatsPrevLongOutConnectedCalls       OBJECT-TYPE
    SYNTAX                                          NncExtConnectedCallsType
    MAX-ACCESS                                      read-only
    STATUS                                          current
    DESCRIPTION
    "Previous long interval connect attempts counter for the outgoing calls."
  ::= { nncExtSVCSigStatsPrevLongEntry 10 }

  nncExtSVCSigStatsPrevLongOutTransitedCalls       OBJECT-TYPE
    SYNTAX                                          NncExtTransitedCallsType
    MAX-ACCESS                                      read-only
    STATUS                                          current
    DESCRIPTION
    "Previous long interval transited calls counter for the outgoing calls."
  ::= { nncExtSVCSigStatsPrevLongEntry 11 }

  nncExtSVCSigStatsPrevLongRxCalledPtyEvents       OBJECT-TYPE
    SYNTAX                                          NncExtCalledPtyEventsType
    MAX-ACCESS                                      read-only
    STATUS                                          current
    DESCRIPTION
    "Previous long interval received called party events cause code counter." 
  ::= { nncExtSVCSigStatsPrevLongEntry 12 }

  nncExtSVCSigStatsPrevLongRxCallingPtyEvents      OBJECT-TYPE
    SYNTAX                                          NncExtCallingPtyEventsType
    MAX-ACCESS                                      read-only
    STATUS                                          current
    DESCRIPTION
    "Previous long interval received calling party events cause code counter."
  ::= { nncExtSVCSigStatsPrevLongEntry 13 }

  nncExtSVCSigStatsPrevLongRxResUnavailable        OBJECT-TYPE
    SYNTAX                                          NncExtResUnavailableType
    MAX-ACCESS                                      read-only
    STATUS                                          current
    DESCRIPTION
    "Previous long interval received resource unavailable cause code counter."
  ::= { nncExtSVCSigStatsPrevLongEntry 14 }

  nncExtSVCSigStatsPrevLongRxRoutingFailure        OBJECT-TYPE
    SYNTAX                                          NncExtRoutingFailureType
    MAX-ACCESS                                      read-only
    STATUS                                          current
    DESCRIPTION
    "Previous long interval received routing failure cause code counter."
  ::= { nncExtSVCSigStatsPrevLongEntry 15 }

  nncExtSVCSigStatsPrevLongRxInvalidMessage        OBJECT-TYPE
    SYNTAX                                          NncExtInvalidMessageType
    MAX-ACCESS                                      read-only
    STATUS                                          current
    DESCRIPTION
    "Previous long interval received invalid message cause code counter."
  ::= { nncExtSVCSigStatsPrevLongEntry 16 }

  nncExtSVCSigStatsPrevLongRxTimerExpiration       OBJECT-TYPE
    SYNTAX                                          NncExtTimerExpirationType
    MAX-ACCESS                                      read-only
    STATUS                                          current
    DESCRIPTION
    "Previous long interval received timer expiration cause code counter."
  ::= { nncExtSVCSigStatsPrevLongEntry 17 }

  nncExtSVCSigStatsPrevLongRxNormalCallClr         OBJECT-TYPE
    SYNTAX                                          NncExtNormalCallClrType
    MAX-ACCESS                                      read-only
    STATUS                                          current
    DESCRIPTION
    "Previous long interval received 'normal call clearing' cause code 
    counter."
  ::= { nncExtSVCSigStatsPrevLongEntry 18 }

  nncExtSVCSigStatsPrevLongRxOtherCauses           OBJECT-TYPE
    SYNTAX                                          NncExtOtherCausesType
    MAX-ACCESS                                      read-only
    STATUS                                          current
    DESCRIPTION
    "Previous long interval received other causes cause code counter."
  ::= { nncExtSVCSigStatsPrevLongEntry 19 }

  nncExtSVCSigStatsPrevLongTxCalledPtyEvents       OBJECT-TYPE
    SYNTAX                                          NncExtCalledPtyEventsType
    MAX-ACCESS                                      read-only
    STATUS                                          current
    DESCRIPTION
    "Previous long interval transmitted called party events cause code 
     counter."
  ::= { nncExtSVCSigStatsPrevLongEntry 20 }

  nncExtSVCSigStatsPrevLongTxCallingPtyEvents      OBJECT-TYPE
    SYNTAX                                          NncExtCallingPtyEventsType
    MAX-ACCESS                                      read-only
    STATUS                                          current
    DESCRIPTION
    "Previous long interval transmitted calling party events cause code 
     counter."
  ::= { nncExtSVCSigStatsPrevLongEntry 21 }

  nncExtSVCSigStatsPrevLongTxResUnavailable        OBJECT-TYPE
    SYNTAX                                          NncExtResUnavailableType
    MAX-ACCESS                                      read-only
    STATUS                                          current
    DESCRIPTION
    "Previous long interval transmitted resource unavailable cause code 
     counter."
  ::= { nncExtSVCSigStatsPrevLongEntry 22 }

  nncExtSVCSigStatsPrevLongTxRoutingFailure        OBJECT-TYPE
    SYNTAX                                          NncExtRoutingFailureType
    MAX-ACCESS                                      read-only
    STATUS                                          current
    DESCRIPTION
    "Previous long interval transmitted routing failure cause code counter."
  ::= { nncExtSVCSigStatsPrevLongEntry 23 }

  nncExtSVCSigStatsPrevLongTxInvalidMessage        OBJECT-TYPE
    SYNTAX                                          NncExtInvalidMessageType
    MAX-ACCESS                                      read-only
    STATUS                                          current
    DESCRIPTION
    "Previous long interval transmitted invalid message cause code counter."
  ::= { nncExtSVCSigStatsPrevLongEntry 24 }

  nncExtSVCSigStatsPrevLongTxTimerExpiration       OBJECT-TYPE
    SYNTAX                                          NncExtTimerExpirationType
    MAX-ACCESS                                      read-only
    STATUS                                          current
    DESCRIPTION
    "Previous long interval transmitted timer expiration cause code counter."
  ::= { nncExtSVCSigStatsPrevLongEntry 25 }

  nncExtSVCSigStatsPrevLongTxNormalCallClr         OBJECT-TYPE
    SYNTAX                                          NncExtNormalCallClrType
    MAX-ACCESS                                      read-only
    STATUS                                          current
    DESCRIPTION
    "Previous long interval transmitted 'normal call clearing' cause code 
    counter."
  ::= { nncExtSVCSigStatsPrevLongEntry 26 }

  nncExtSVCSigStatsPrevLongTxOtherCauses           OBJECT-TYPE
    SYNTAX                                          NncExtOtherCausesType
    MAX-ACCESS                                      read-only
    STATUS                                          current
    DESCRIPTION
    "Previous long interval transmitted other causes cause code counter."
  ::= { nncExtSVCSigStatsPrevLongEntry 27 }

  nncExtSVCSigStatsPrevLongScreeningFailures       OBJECT-TYPE
    SYNTAX                                          NncExtScreeningFailuresType
    MAX-ACCESS                                      read-only
    STATUS                                          current
    DESCRIPTION
    "Previous long interval incoming calls screening failures counter." 
  ::= { nncExtSVCSigStatsPrevLongEntry 28 }

  nncExtSVCSigStatsPrevLongInCDNSelectiveCalls     OBJECT-TYPE
    SYNTAX                                          NncExtSelectiveCallsType
    MAX-ACCESS                                      read-only
    STATUS                                          current
    DESCRIPTION
    "Previous long interval selective calls counter for incoming called
    number." 
  ::= { nncExtSVCSigStatsPrevLongEntry 29 }

  nncExtSVCSigStatsPrevLongInCGNSelectiveCalls     OBJECT-TYPE
    SYNTAX                                          NncExtSelectiveCallsType
    MAX-ACCESS                                      read-only
    STATUS                                          current
    DESCRIPTION
    "Previous long interval selective calls counter for incoming calling
    number." 
  ::= { nncExtSVCSigStatsPrevLongEntry 30 }

  nncExtSVCSigStatsPrevLongOutCDNSelectiveCalls    OBJECT-TYPE
    SYNTAX                                          NncExtSelectiveCallsType
    MAX-ACCESS                                      read-only
    STATUS                                          current
    DESCRIPTION
    "Previous long interval selective calls counter for outgoing called
    number." 
  ::= { nncExtSVCSigStatsPrevLongEntry 31 }

  nncExtSVCSigStatsPrevLongOutCGNSelectiveCalls    OBJECT-TYPE
    SYNTAX                                          NncExtSelectiveCallsType
    MAX-ACCESS                                      read-only
    STATUS                                          current
    DESCRIPTION
    "Previous long interval selective calls counter for outgoing calling
    number." 
  ::= { nncExtSVCSigStatsPrevLongEntry 32 }


--------------------------------------------------------------------------------
--  Table 5: Raw Table
--------------------------------------------------------------------------------
  nncExtSVCSigStatsRawTable OBJECT-TYPE
    SYNTAX       SEQUENCE OF NncExtSVCSigStatsRawEntry
    MAX-ACCESS   not-accessible
    STATUS       current
    DESCRIPTION  
    "The nncExtSVCSigStatsRawTable contains objects for monitoring 
     the performance of a signalling link since the last service
     card bootup."
  ::= { nncExtSVCSigStatsObjects 5 }


  nncExtSVCSigStatsRawEntry OBJECT-TYPE
    SYNTAX      NncExtSVCSigStatsRawEntry
    MAX-ACCESS  not-accessible
    STATUS      current
    DESCRIPTION  
    "An entry in the raw statistics table. Each conceptual row contains 
     current statistics for a particular signalling link. ifIndex 
     corresponds to the trunk group with an attached signalling link."
    INDEX       { ifIndex }
  ::= { nncExtSVCSigStatsRawTable 1 }


  NncExtSVCSigStatsRawEntry ::=
    SEQUENCE {
      nncExtSVCSigStatsRawState              NncExtIntvlStateType,
      nncExtSVCSigStatsRawStartTime          DateAndTime,
      nncExtSVCSigStatsRawDuration           NncExtIntvlDurationType,
      nncExtSVCSigStatsRawActiveCalls        NncExtActiveCallsType,
      nncExtSVCSigStatsRawInSetupAttempts    NncExtSetupAttemptsType,
      nncExtSVCSigStatsRawInConnectedCalls   NncExtConnectedCallsType,
      nncExtSVCSigStatsRawInTransitedCalls   NncExtTransitedCallsType,
      nncExtSVCSigStatsRawOutSetupAttempts   NncExtSetupAttemptsType,
      nncExtSVCSigStatsRawOutConnectedCalls  NncExtConnectedCallsType,
      nncExtSVCSigStatsRawOutTransitedCalls  NncExtTransitedCallsType,
      nncExtSVCSigStatsRawRxCalledPtyEvents  NncExtCalledPtyEventsType,
      nncExtSVCSigStatsRawRxCallingPtyEvents NncExtCallingPtyEventsType,
      nncExtSVCSigStatsRawRxResUnavailable   NncExtResUnavailableType,
      nncExtSVCSigStatsRawRxRoutingFailure   NncExtRoutingFailureType,
      nncExtSVCSigStatsRawRxInvalidMessage   NncExtInvalidMessageType,
      nncExtSVCSigStatsRawRxTimerExpiration  NncExtTimerExpirationType,
      nncExtSVCSigStatsRawRxNormalCallClr    NncExtNormalCallClrType,
      nncExtSVCSigStatsRawRxOtherCauses      NncExtOtherCausesType,
      nncExtSVCSigStatsRawTxCalledPtyEvents  NncExtCalledPtyEventsType,
      nncExtSVCSigStatsRawTxCallingPtyEvents NncExtCallingPtyEventsType,
      nncExtSVCSigStatsRawTxResUnavailable   NncExtResUnavailableType,
      nncExtSVCSigStatsRawTxRoutingFailure   NncExtRoutingFailureType,
      nncExtSVCSigStatsRawTxInvalidMessage   NncExtInvalidMessageType,
      nncExtSVCSigStatsRawTxTimerExpiration  NncExtTimerExpirationType,
      nncExtSVCSigStatsRawTxNormalCallClr    NncExtNormalCallClrType,
      nncExtSVCSigStatsRawTxOtherCauses      NncExtOtherCausesType,
      nncExtSVCSigStatsRawScreeningFailures  NncExtScreeningFailuresType,
      nncExtSVCSigStatsRawInCDNSelectiveCalls NncExtSelectiveCallsType,
      nncExtSVCSigStatsRawInCGNSelectiveCalls NncExtSelectiveCallsType,
      nncExtSVCSigStatsRawOutCDNSelectiveCalls NncExtSelectiveCallsType,
      nncExtSVCSigStatsRawOutCGNSelectiveCalls NncExtSelectiveCallsType
    }

  nncExtSVCSigStatsRawState                        OBJECT-TYPE
    SYNTAX                                          NncExtIntvlStateType
    MAX-ACCESS                                      read-only
    STATUS                                          current
    DESCRIPTION                    
    "The state of the raw statistics data."
  ::= { nncExtSVCSigStatsRawEntry 1 }

  nncExtSVCSigStatsRawStartTime                    OBJECT-TYPE
    SYNTAX                                          DateAndTime
    MAX-ACCESS                                      read-only
    STATUS                                          current
    DESCRIPTION                    
    "The time when the collection of the raw statistics data was started." 
  ::= { nncExtSVCSigStatsRawEntry 2 }

  nncExtSVCSigStatsRawDuration                     OBJECT-TYPE
    SYNTAX                                          NncExtIntvlDurationType
    UNITS                                           "seconds"
    MAX-ACCESS                                      read-only
    STATUS                                          current
    DESCRIPTION                    
    "The time since the collection of the raw statistics data was started."
  ::= { nncExtSVCSigStatsRawEntry 3 }

  nncExtSVCSigStatsRawActiveCalls                  OBJECT-TYPE
    SYNTAX                                          NncExtActiveCallsType
    MAX-ACCESS                                      read-only
    STATUS                                          current
    DESCRIPTION
    "The number of currently active calls."
  ::= { nncExtSVCSigStatsRawEntry 4 }


  nncExtSVCSigStatsRawInSetupAttempts              OBJECT-TYPE
    SYNTAX                                          NncExtSetupAttemptsType
    MAX-ACCESS                                      read-only
    STATUS                                          current
    DESCRIPTION
    "Setup attempts raw counter for the incoming calls."
  ::= { nncExtSVCSigStatsRawEntry 5 }

  nncExtSVCSigStatsRawInConnectedCalls             OBJECT-TYPE
    SYNTAX                                          NncExtConnectedCallsType
    MAX-ACCESS                                      read-only
    STATUS                                          current
    DESCRIPTION
    "Connect attempts raw counter for the incoming calls." 
  ::= { nncExtSVCSigStatsRawEntry 6 }

  nncExtSVCSigStatsRawInTransitedCalls             OBJECT-TYPE
    SYNTAX                                          NncExtTransitedCallsType
    MAX-ACCESS                                      read-only
    STATUS                                          current
    DESCRIPTION
    "Transited calls raw counter for the incoming calls."
  ::= { nncExtSVCSigStatsRawEntry 7 }

  nncExtSVCSigStatsRawOutSetupAttempts             OBJECT-TYPE
    SYNTAX                                          NncExtSetupAttemptsType
    MAX-ACCESS                                      read-only
    STATUS                                          current
    DESCRIPTION
    "Setup attempts raw counter for the outgoing calls." 
  ::= { nncExtSVCSigStatsRawEntry 8 }

  nncExtSVCSigStatsRawOutConnectedCalls            OBJECT-TYPE
    SYNTAX                                          NncExtConnectedCallsType
    MAX-ACCESS                                      read-only
    STATUS                                          current
    DESCRIPTION
    "Connect attempts raw counter for the outgoing calls."
  ::= { nncExtSVCSigStatsRawEntry 9 }

  nncExtSVCSigStatsRawOutTransitedCalls            OBJECT-TYPE
    SYNTAX                                          NncExtTransitedCallsType
    MAX-ACCESS                                      read-only
    STATUS                                          current
    DESCRIPTION
    "Transited calls raw counter for the outgoing calls."
  ::= { nncExtSVCSigStatsRawEntry 10 }

  nncExtSVCSigStatsRawRxCalledPtyEvents            OBJECT-TYPE
    SYNTAX                                          NncExtCalledPtyEventsType
    MAX-ACCESS                                      read-only
    STATUS                                          current
    DESCRIPTION
    "Received called party events cause code raw counter." 
  ::= { nncExtSVCSigStatsRawEntry 11 }

  nncExtSVCSigStatsRawRxCallingPtyEvents           OBJECT-TYPE
    SYNTAX                                          NncExtCallingPtyEventsType
    MAX-ACCESS                                      read-only
    STATUS                                          current
    DESCRIPTION
    "Received calling party events cause code raw counter."
  ::= { nncExtSVCSigStatsRawEntry 12 }

  nncExtSVCSigStatsRawRxResUnavailable             OBJECT-TYPE
    SYNTAX                                          NncExtResUnavailableType
    MAX-ACCESS                                      read-only
    STATUS                                          current
    DESCRIPTION
    "Received resource unavailable cause code raw counter."
  ::= { nncExtSVCSigStatsRawEntry 13 }

  nncExtSVCSigStatsRawRxRoutingFailure             OBJECT-TYPE
    SYNTAX                                          NncExtRoutingFailureType
    MAX-ACCESS                                      read-only
    STATUS                                          current
    DESCRIPTION
    "Received routing failure cause code raw counter."
  ::= { nncExtSVCSigStatsRawEntry 14 }

  nncExtSVCSigStatsRawRxInvalidMessage             OBJECT-TYPE
    SYNTAX                                          NncExtInvalidMessageType
    MAX-ACCESS                                      read-only
    STATUS                                          current
    DESCRIPTION
    "Received invalid message cause code raw counter."
  ::= { nncExtSVCSigStatsRawEntry 15 }

  nncExtSVCSigStatsRawRxTimerExpiration            OBJECT-TYPE
    SYNTAX                                          NncExtTimerExpirationType
    MAX-ACCESS                                      read-only
    STATUS                                          current
    DESCRIPTION
    "Received timer expiration cause code raw counter."
  ::= { nncExtSVCSigStatsRawEntry 16 }

  nncExtSVCSigStatsRawRxNormalCallClr              OBJECT-TYPE
    SYNTAX                                          NncExtNormalCallClrType
    MAX-ACCESS                                      read-only
    STATUS                                          current
    DESCRIPTION
    "Received 'normal call clearing' cause code raw counter."
  ::= { nncExtSVCSigStatsRawEntry 17 }

  nncExtSVCSigStatsRawRxOtherCauses                OBJECT-TYPE
    SYNTAX                                          NncExtOtherCausesType
    MAX-ACCESS                                      read-only
    STATUS                                          current
    DESCRIPTION
    "Received other causes cause code raw counter."
  ::= { nncExtSVCSigStatsRawEntry 18 }

  nncExtSVCSigStatsRawTxCalledPtyEvents            OBJECT-TYPE
    SYNTAX                                          NncExtCalledPtyEventsType
    MAX-ACCESS                                      read-only
    STATUS                                          current
    DESCRIPTION
    "Transmitted called party events cause code 
     raw counter."
  ::= { nncExtSVCSigStatsRawEntry 19 }

  nncExtSVCSigStatsRawTxCallingPtyEvents           OBJECT-TYPE
    SYNTAX                                          NncExtCallingPtyEventsType
    MAX-ACCESS                                      read-only
    STATUS                                          current
    DESCRIPTION
    "Transmitted calling party events cause code 
     raw counter."
  ::= { nncExtSVCSigStatsRawEntry 20 }

  nncExtSVCSigStatsRawTxResUnavailable             OBJECT-TYPE
    SYNTAX                                          NncExtResUnavailableType
    MAX-ACCESS                                      read-only
    STATUS                                          current
    DESCRIPTION
    "Transmitted resource unavailable cause code 
     raw counter."
  ::= { nncExtSVCSigStatsRawEntry 21 }

  nncExtSVCSigStatsRawTxRoutingFailure             OBJECT-TYPE
    SYNTAX                                          NncExtRoutingFailureType
    MAX-ACCESS                                      read-only
    STATUS                                          current
    DESCRIPTION
    "Transmitted routing failure cause code raw counter."
  ::= { nncExtSVCSigStatsRawEntry 22 }

  nncExtSVCSigStatsRawTxInvalidMessage             OBJECT-TYPE
    SYNTAX                                          NncExtInvalidMessageType
    MAX-ACCESS                                      read-only
    STATUS                                          current
    DESCRIPTION
    "Transmitted invalid message cause code raw counter."
  ::= { nncExtSVCSigStatsRawEntry 23 }

  nncExtSVCSigStatsRawTxTimerExpiration            OBJECT-TYPE
    SYNTAX                                          NncExtTimerExpirationType
    MAX-ACCESS                                      read-only
    STATUS                                          current
    DESCRIPTION
    "Transmitted timer expiration cause code raw counter."
  ::= { nncExtSVCSigStatsRawEntry 24 }

  nncExtSVCSigStatsRawTxNormalCallClr              OBJECT-TYPE
    SYNTAX                                          NncExtNormalCallClrType
    MAX-ACCESS                                      read-only
    STATUS                                          current
    DESCRIPTION
    "Transmitted 'normal call clearing' cause code raw counter."
  ::= { nncExtSVCSigStatsRawEntry 25 }

  nncExtSVCSigStatsRawTxOtherCauses                OBJECT-TYPE
    SYNTAX                                          NncExtOtherCausesType
    MAX-ACCESS                                      read-only
    STATUS                                          current
    DESCRIPTION
    "Transmitted other causes cause code raw counter."
  ::= { nncExtSVCSigStatsRawEntry 26 }

  nncExtSVCSigStatsRawScreeningFailures            OBJECT-TYPE
    SYNTAX                                          NncExtScreeningFailuresType
    MAX-ACCESS                                      read-only
    STATUS                                          current
    DESCRIPTION
    "Incoming calls screening failures raw counter." 
  ::= { nncExtSVCSigStatsRawEntry 27 }

  nncExtSVCSigStatsRawInCDNSelectiveCalls          OBJECT-TYPE
    SYNTAX                                          NncExtSelectiveCallsType
    MAX-ACCESS                                      read-only
    STATUS                                          current
    DESCRIPTION
    "Raw selective calls counter for incoming called number." 
  ::= { nncExtSVCSigStatsRawEntry 28 }

  nncExtSVCSigStatsRawInCGNSelectiveCalls          OBJECT-TYPE
    SYNTAX                                          NncExtSelectiveCallsType
    MAX-ACCESS                                      read-only
    STATUS                                          current
    DESCRIPTION
    "Raw selective calls counter for incoming calling number." 
  ::= { nncExtSVCSigStatsRawEntry 29 }

  nncExtSVCSigStatsRawOutCDNSelectiveCalls         OBJECT-TYPE
    SYNTAX                                          NncExtSelectiveCallsType
    MAX-ACCESS                                      read-only
    STATUS                                          current
    DESCRIPTION
    "Raw selective calls counter for outgoing called number." 
  ::= { nncExtSVCSigStatsRawEntry 30 }

  nncExtSVCSigStatsRawOutCGNSelectiveCalls         OBJECT-TYPE
    SYNTAX                                          NncExtSelectiveCallsType
    MAX-ACCESS                                      read-only
    STATUS                                          current
    DESCRIPTION
    "Raw selective calls counter for outgoing calling number." 
  ::= { nncExtSVCSigStatsRawEntry 31 }


--------------------------------------------------------------------------------
-- Conformance Group Definitions
--------------------------------------------------------------------------------
  nncExtSVCSigStatsCurrShortGroup    OBJECT-GROUP
    OBJECTS { 
      nncExtSVCSigStatsCurrShortIntvlState,
      nncExtSVCSigStatsCurrShortAbsIntvlNumber,
      nncExtSVCSigStatsCurrShortIntvlStartTime,
      nncExtSVCSigStatsCurrShortIntvlDuration,
      nncExtSVCSigStatsCurrShortInSetupAttempts,
      nncExtSVCSigStatsCurrShortInConnectedCalls,
      nncExtSVCSigStatsCurrShortInTransitedCalls,
      nncExtSVCSigStatsCurrShortOutSetupAttempts,
      nncExtSVCSigStatsCurrShortOutConnectedCalls,
      nncExtSVCSigStatsCurrShortOutTransitedCalls,
      nncExtSVCSigStatsCurrShortRxCalledPtyEvents,
      nncExtSVCSigStatsCurrShortRxCallingPtyEvents,
      nncExtSVCSigStatsCurrShortRxResUnavailable,
      nncExtSVCSigStatsCurrShortRxRoutingFailure,
      nncExtSVCSigStatsCurrShortRxInvalidMessage,
      nncExtSVCSigStatsCurrShortRxTimerExpiration,
      nncExtSVCSigStatsCurrShortRxNormalCallClr,
      nncExtSVCSigStatsCurrShortRxOtherCauses,
      nncExtSVCSigStatsCurrShortTxCalledPtyEvents,
      nncExtSVCSigStatsCurrShortTxCallingPtyEvents,
      nncExtSVCSigStatsCurrShortTxResUnavailable,
      nncExtSVCSigStatsCurrShortTxRoutingFailure,
      nncExtSVCSigStatsCurrShortTxInvalidMessage,
      nncExtSVCSigStatsCurrShortTxTimerExpiration,
      nncExtSVCSigStatsCurrShortTxNormalCallClr,
      nncExtSVCSigStatsCurrShortTxOtherCauses,
      nncExtSVCSigStatsCurrShortScreeningFailures,
      nncExtSVCSigStatsCurrShortInCDNSelectiveCalls,
      nncExtSVCSigStatsCurrShortInCGNSelectiveCalls,
      nncExtSVCSigStatsCurrShortOutCDNSelectiveCalls,
      nncExtSVCSigStatsCurrShortOutCGNSelectiveCalls
    }
    STATUS    current
    DESCRIPTION  
      "A collection of objects providing short,current 
       interval statistics for signalling links."
  ::= { nncExtSVCSigStatsGroups 1 }

  nncExtSVCSigStatsPrevShortGroup    OBJECT-GROUP
    OBJECTS { 
      nncExtSVCSigStatsPrevShortIntvlState,
      nncExtSVCSigStatsPrevShortAbsIntvlNumber,
      nncExtSVCSigStatsPrevShortIntvlStartTime,
      nncExtSVCSigStatsPrevShortIntvlDuration,
      nncExtSVCSigStatsPrevShortInSetupAttempts,
      nncExtSVCSigStatsPrevShortInConnectedCalls,
      nncExtSVCSigStatsPrevShortInTransitedCalls,
      nncExtSVCSigStatsPrevShortOutSetupAttempts,
      nncExtSVCSigStatsPrevShortOutConnectedCalls,
      nncExtSVCSigStatsPrevShortOutTransitedCalls,
      nncExtSVCSigStatsPrevShortRxCalledPtyEvents,
      nncExtSVCSigStatsPrevShortRxCallingPtyEvents,
      nncExtSVCSigStatsPrevShortRxResUnavailable,
      nncExtSVCSigStatsPrevShortRxRoutingFailure,
      nncExtSVCSigStatsPrevShortRxInvalidMessage,
      nncExtSVCSigStatsPrevShortRxTimerExpiration,
      nncExtSVCSigStatsPrevShortRxNormalCallClr,
      nncExtSVCSigStatsPrevShortRxOtherCauses,
      nncExtSVCSigStatsPrevShortTxCalledPtyEvents,
      nncExtSVCSigStatsPrevShortTxCallingPtyEvents,
      nncExtSVCSigStatsPrevShortTxResUnavailable,
      nncExtSVCSigStatsPrevShortTxRoutingFailure,
      nncExtSVCSigStatsPrevShortTxInvalidMessage,
      nncExtSVCSigStatsPrevShortTxTimerExpiration,
      nncExtSVCSigStatsPrevShortTxNormalCallClr,
      nncExtSVCSigStatsPrevShortTxOtherCauses,
      nncExtSVCSigStatsPrevShortScreeningFailures,
      nncExtSVCSigStatsPrevShortInCDNSelectiveCalls,
      nncExtSVCSigStatsPrevShortInCGNSelectiveCalls,
      nncExtSVCSigStatsPrevShortOutCDNSelectiveCalls,
      nncExtSVCSigStatsPrevShortOutCGNSelectiveCalls
    }
    STATUS    current
    DESCRIPTION  
      "A collection of objects providing short,non-current 
       interval statistics for signalling links."
  ::= { nncExtSVCSigStatsGroups 2 }

  nncExtSVCSigStatsCurrLongGroup    OBJECT-GROUP
    OBJECTS { 
      nncExtSVCSigStatsCurrLongIntvlState,
      nncExtSVCSigStatsCurrLongAbsIntvlNumber,
      nncExtSVCSigStatsCurrLongIntvlStartTime,
      nncExtSVCSigStatsCurrLongIntvlDuration,
      nncExtSVCSigStatsCurrLongInSetupAttempts,
      nncExtSVCSigStatsCurrLongInConnectedCalls,
      nncExtSVCSigStatsCurrLongInTransitedCalls,
      nncExtSVCSigStatsCurrLongOutSetupAttempts,
      nncExtSVCSigStatsCurrLongOutConnectedCalls,
      nncExtSVCSigStatsCurrLongOutTransitedCalls,
      nncExtSVCSigStatsCurrLongRxCalledPtyEvents,
      nncExtSVCSigStatsCurrLongRxCallingPtyEvents,
      nncExtSVCSigStatsCurrLongRxResUnavailable,
      nncExtSVCSigStatsCurrLongRxRoutingFailure,
      nncExtSVCSigStatsCurrLongRxInvalidMessage,
      nncExtSVCSigStatsCurrLongRxTimerExpiration,
      nncExtSVCSigStatsCurrLongRxNormalCallClr,
      nncExtSVCSigStatsCurrLongRxOtherCauses,
      nncExtSVCSigStatsCurrLongTxCalledPtyEvents,
      nncExtSVCSigStatsCurrLongTxCallingPtyEvents,
      nncExtSVCSigStatsCurrLongTxResUnavailable,
      nncExtSVCSigStatsCurrLongTxRoutingFailure,
      nncExtSVCSigStatsCurrLongTxInvalidMessage,
      nncExtSVCSigStatsCurrLongTxTimerExpiration,
      nncExtSVCSigStatsCurrLongTxNormalCallClr,
      nncExtSVCSigStatsCurrLongTxOtherCauses,
      nncExtSVCSigStatsCurrLongScreeningFailures,
      nncExtSVCSigStatsCurrLongInCDNSelectiveCalls,
      nncExtSVCSigStatsCurrLongInCGNSelectiveCalls,
      nncExtSVCSigStatsCurrLongOutCDNSelectiveCalls,
      nncExtSVCSigStatsCurrLongOutCGNSelectiveCalls
    }
    STATUS    current
    DESCRIPTION  
      "A collection of objects providing long,current 
       interval statistics for signalling links."
  ::= { nncExtSVCSigStatsGroups 3 }


  nncExtSVCSigStatsPrevLongGroup    OBJECT-GROUP
    OBJECTS { 
      nncExtSVCSigStatsPrevLongIntvlState,
      nncExtSVCSigStatsPrevLongAbsIntvlNumber,
      nncExtSVCSigStatsPrevLongIntvlStartTime,
      nncExtSVCSigStatsPrevLongIntvlDuration,
      nncExtSVCSigStatsPrevLongInSetupAttempts,
      nncExtSVCSigStatsPrevLongInConnectedCalls,
      nncExtSVCSigStatsPrevLongInTransitedCalls,
      nncExtSVCSigStatsPrevLongOutSetupAttempts,
      nncExtSVCSigStatsPrevLongOutConnectedCalls,
      nncExtSVCSigStatsPrevLongOutTransitedCalls,
      nncExtSVCSigStatsPrevLongRxCalledPtyEvents,
      nncExtSVCSigStatsPrevLongRxCallingPtyEvents,
      nncExtSVCSigStatsPrevLongRxResUnavailable,
      nncExtSVCSigStatsPrevLongRxRoutingFailure,
      nncExtSVCSigStatsPrevLongRxInvalidMessage,
      nncExtSVCSigStatsPrevLongRxTimerExpiration,
      nncExtSVCSigStatsPrevLongRxNormalCallClr,
      nncExtSVCSigStatsPrevLongRxOtherCauses,
      nncExtSVCSigStatsPrevLongTxCalledPtyEvents,
      nncExtSVCSigStatsPrevLongTxCallingPtyEvents,
      nncExtSVCSigStatsPrevLongTxResUnavailable,
      nncExtSVCSigStatsPrevLongTxRoutingFailure,
      nncExtSVCSigStatsPrevLongTxInvalidMessage,
      nncExtSVCSigStatsPrevLongTxTimerExpiration,
      nncExtSVCSigStatsPrevLongTxNormalCallClr,
      nncExtSVCSigStatsPrevLongTxOtherCauses,
      nncExtSVCSigStatsPrevLongScreeningFailures,
      nncExtSVCSigStatsPrevLongInCDNSelectiveCalls,
      nncExtSVCSigStatsPrevLongInCGNSelectiveCalls,
      nncExtSVCSigStatsPrevLongOutCDNSelectiveCalls,
      nncExtSVCSigStatsPrevLongOutCGNSelectiveCalls
    }
    STATUS    current
    DESCRIPTION  
      "A collection of objects providing long,non-current 
       interval statistics for signalling links."
  ::= { nncExtSVCSigStatsGroups 4 }

  nncExtSVCSigStatsRawGroup    OBJECT-GROUP
    OBJECTS { 
      nncExtSVCSigStatsRawState,
      nncExtSVCSigStatsRawStartTime,
      nncExtSVCSigStatsRawDuration,
      nncExtSVCSigStatsRawActiveCalls,
      nncExtSVCSigStatsRawInSetupAttempts,
      nncExtSVCSigStatsRawInConnectedCalls,
      nncExtSVCSigStatsRawInTransitedCalls,
      nncExtSVCSigStatsRawOutSetupAttempts,
      nncExtSVCSigStatsRawOutConnectedCalls,
      nncExtSVCSigStatsRawOutTransitedCalls,
      nncExtSVCSigStatsRawRxCalledPtyEvents,
      nncExtSVCSigStatsRawRxCallingPtyEvents,
      nncExtSVCSigStatsRawRxResUnavailable,
      nncExtSVCSigStatsRawRxRoutingFailure,
      nncExtSVCSigStatsRawRxInvalidMessage,
      nncExtSVCSigStatsRawRxTimerExpiration,
      nncExtSVCSigStatsRawRxNormalCallClr,
      nncExtSVCSigStatsRawRxOtherCauses,
      nncExtSVCSigStatsRawTxCalledPtyEvents,
      nncExtSVCSigStatsRawTxCallingPtyEvents,
      nncExtSVCSigStatsRawTxResUnavailable,
      nncExtSVCSigStatsRawTxRoutingFailure,
      nncExtSVCSigStatsRawTxInvalidMessage,
      nncExtSVCSigStatsRawTxTimerExpiration,
      nncExtSVCSigStatsRawTxNormalCallClr,
      nncExtSVCSigStatsRawTxOtherCauses,
      nncExtSVCSigStatsRawScreeningFailures,
      nncExtSVCSigStatsRawInCDNSelectiveCalls,
      nncExtSVCSigStatsRawInCGNSelectiveCalls,
      nncExtSVCSigStatsRawOutCDNSelectiveCalls,
      nncExtSVCSigStatsRawOutCGNSelectiveCalls
    }
    STATUS    current
    DESCRIPTION  
      "A collection of objects providing raw statistics 
       for signalling links."
  ::= { nncExtSVCSigStatsGroups 5 }


--------------------------------------------------------------------------------
-- Compliance Statements (mandatory)
--------------------------------------------------------------------------------
  nncExtSVCSigStatsCompliance  MODULE-COMPLIANCE
    STATUS    current
    DESCRIPTION  
      "The compliance statement for Newbridge SNMP entities
       which represent signalling links."
    MODULE 
    MANDATORY-GROUPS  { 
      nncExtSVCSigStatsRawGroup
    }
  ::= { nncExtSVCSigStatsCompliances 1 } 


-------------------------------------------------------------------------------
--  Review Minutes 
-------------------------------------------------------------------------------
-- MINUTES-BEGIN
-- REVIEW-DATE  "1996.03.19"
-- BODY  "
--
--
-- TO:  Jonathan Bosloy*, Nelson Gillette, Randy Jones*, Steve Buchko*, 
--  Andrew Paterson*, David Watkinson*, Frank Chen*
-- CC:  Numbers Admin, Melanie Paquette, Wing-Leung Chan, Sriram Darbha
-- FROM:  Art Brzezinski*
--
-- A meeting was held on 1996.03.19 to review SVCSigStats.mib.
-- Attendees are marked with * in the TO and CC lists above.
--
-- Outcome
--
-- It was the consensus of the review team that this file is acceptable 
-- with the indicated modifications.
--
-- Actions:
--  A1 -   Art Brzezinski to update the file as indicated in D1 below.  
--  Response:                          Status: CLOSED
--         File has been updated as indicated in D1 below.
--
--  A2 -   Art Brzezinski to check the latest atommib for possible 
--         overlap between the raw table counters and atommib counters.
--  Response:                          Status: CLOSED
--         Latest available mib (draft-ietf-atommib-atm2-05.txt) does
--         not contain counters that overlap with raw table counters.
-- 
--  A3 -   Art Brzezinski to implement call release counter.
--  Response:                          Status: CLOSED
--         'Normal call clearing' cause code counter has been
--         implemented to provide stats on normal call releases.
--
-- Decisions:
--  D1 -   SVCSigStats.mib shall be updated as follows:
--   a) document the meaning of ifIndex in table entry objects description
--   b) do not implement stats reset functionality
--   c) create and use local textual conventions for each counter
--   d) change duration of the interval units to seconds
--   e) enhance description of transited calls counters
--   f) enhance description of connected calls counters
--   g) enhance description of setup attempts counters to indicate that
--      retransmitted setup attempts are not counted
--   h) enhance description of other causes counters to indicate that
--      normal call clearing and response to status enquiry causes are
--      not counted
--   i) add active call counter to the raw table
--   j) rename the raw table to nncExtSvcSigStatsRawTable
--   k) enhance description of a screening failures counter to indicate
--      that the counter applies to the calling party number
--
--  "
--
-- END-MINUTES
--

-- MINUTES-BEGIN
-- REVIEW-DATE  "1998.02.19"
-- BODY  "
--
--
-- TO:  Pat Coghlan*, Beverley McMillan*, Shawn McAllister*, Craig Hennessey*, 
--  Ofelia Moldovan*, Glenn Karlsen*, Vlad Rakocevic*, Steve Fleury*,
--  Gord Urquhart*
-- CC:  Numbers Admin, Melanie Paquette, Jim Ko*, Jim Hurd*, Nelson Gillette*
-- FROM:  George Yue*
--
-- An EDR was closed on 1998.02.19 to review SVCSigStats.mib.
-- Attendees are marked with * in the TO and CC lists above.
--
-- Outcome
--
-- It was the consensus of the review team that this file is acceptable 
-- as is.
--
--  "
--
-- END-MINUTES
--

END -- DEFINITION OF NNCEXTSVCSIGSTATS-MIB
