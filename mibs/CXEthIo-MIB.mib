CXEthIo-MIB DEFINITIONS ::= BEGIN


IMPORTS
    Counter                 FROM RFC1155-SMI
    OBJECT-TYPE             FROM RFC-1212
    cxEthIo,
    Alias                   FROM CXProduct-SMI;


--  Active Configuration Table

--  The table describing:
--  active (current) parameters used in the Ethernet SAP and its associated 
--  hardware port. status and statistics for each hardware port that is 
--  associated with an Ethernet SAP.


ethSapOprTable OBJECT-TYPE
    SYNTAX  SEQUENCE OF EthSapOprEntry
    ACCESS  not-accessible
    STATUS  mandatory
    DESCRIPTION
"Provides configuration information for each Ethernet service access point 
and its associated hardware ports. It also provides statistical information 
about activity at the interface.

Each row of the table (entry) contains information that corresponds to a 
particular service access point."

    ::= { cxEthIo 1 }


    ethSapOprEntry OBJECT-TYPE
        SYNTAX  EthSapOprEntry
        ACCESS  not-accessible
        STATUS  mandatory
        DESCRIPTION
"Provides the configuration of a particular Ethernet service access point 
and its associated hardware port. It also provides statistical information 
about activity at the interface."
        INDEX { ethSapOprNumber }
        ::= { ethSapOprTable 1 }


    EthSapOprEntry ::=
        SEQUENCE {
            ethSapOprNumber
                INTEGER,
            ethSapOprAlias
                Alias,
            ethSapOprConnectorType
                INTEGER,
            ethSapOprDataGenerator
                INTEGER,
            ethSapOprGenFrames
                INTEGER,
            ethSapOprGenFrameSize
                INTEGER,
            ethSapOprLoopbackType
                INTEGER,
            ethOprControlStats
                INTEGER,
            ethStatOprLinkState
                INTEGER,
            ethStatOprInFrames
                Counter,
            ethStatOprInOctets
                Counter,
            ethStatOprInErrors
                Counter,
            ethStatOprInDiscards
                Counter,
            ethStatOprInBusyDiscards
                Counter,
            ethStatOprOutFrames
                Counter,
            ethStatOprOutOctets
                Counter,
            ethStatOprOutErrors
                Counter,
            ethStatOprOutDiscards
                Counter,
            ethStatOprOutCSLostFrames
                Counter,
            ethStatOprRxGenErrors
                Counter
            }


    ethSapOprNumber OBJECT-TYPE
        SYNTAX  INTEGER
        ACCESS  read-only
        STATUS  mandatory
        DESCRIPTION
"Identifies the service access point by a numerical value. Each 
service access point is assigned a unique number. The number is assigned by 
the system."
        ::= { ethSapOprEntry 1 }


    ethSapOprAlias OBJECT-TYPE
        SYNTAX  Alias
        ACCESS  read-only
        STATUS  mandatory
        DESCRIPTION
"Identifies the textual name (Alias) of this service access point. Each 
service access point must have a unique name.

Range of Values: 0-16 alphanumeric characters. (Note that the first 
character must be a letter and spaces are not allowed).

Default Value: None"
        ::= { ethSapOprEntry 2 }


    ethSapOprConnectorType OBJECT-TYPE
        SYNTAX INTEGER {
                    auto            (1),
                    aui             (2),
                    tbaset          (3),
                    baset-100	    (4)
                    }
        ACCESS  read-only
        STATUS  mandatory
        DESCRIPTION
"Identifies the connector type used for the hardware port. 

Options:
auto (1): (connector type detected automatically)

aui (2): 

tbaseT (3):

100baseT (4)  100 Mbs Ethernet

Default Value: auto"
        ::= { ethSapOprEntry 3 }


    ethSapOprDataGenerator OBJECT-TYPE
        SYNTAX  INTEGER {
                    disabled                (1),
                    enabled         (2),
                    enabled-verify  (3),
                    retrigger               (4)
                    }
        ACCESS  read-write
        STATUS  mandatory
        DESCRIPTION
"Determines whether the Data Generator is enabled. The Data Generator is 
used for testing purposes.

Options:
disabled (1)       

enabled (2)       

enabled-verify(3): The data generator is enabled and it checks what it 
receives against what it has sent. The result of the test is displayed in 
ethStatOprRxGenErrors. If this option is selected ethSapOprLoobackType must 
be set to remote.

retrigger (4): The data generator repeats the transmission as specified in 
ethSapOprGenFrames and ethSapOprGen.

Default Value: disabled

Configuration Changed: administrative

The change cannot be saved."
        ::= { ethSapOprEntry 4 }


    ethSapOprGenFrames OBJECT-TYPE
        SYNTAX  INTEGER
        ACCESS  read-write
        STATUS  mandatory
        DESCRIPTION
"Determines the number of times a frame will be generated (for testing 
purposes). Frames are generated every 1 msec. If the value is set to zero, 
then frames will be generated continuously (every 1 msec).

If the Data Generator is disabled (using ethSapOprDataGenerator), then the 
value is ignored.

Range of Values: 0 - 255

Default Value: 1"
        ::= { ethSapOprEntry 5 }


    ethSapOprGenFrameSize OBJECT-TYPE
        SYNTAX  INTEGER
        ACCESS  read-write
        STATUS  mandatory
        DESCRIPTION
"Determines the size of the frames (in bytes) to be generated (for testing 
purposes). If the Data Generator is disabled, then this value is ignored.

Range of Values: 0-1514 bytes

Default Value: 512 bytes

Configuration Changed: administrative

The change cannot be saved."
        ::= { ethSapOprEntry 6 }


    ethSapOprLoopbackType OBJECT-TYPE
        SYNTAX  INTEGER {
                    none            (1),
                    local           (2),
                    remote          (3),
                    both            (4)
                    }
        ACCESS  read-only
        STATUS  mandatory
        DESCRIPTION
"Determines whether the port performs remote loopback, local loopback or 
both.
                       
Options: 
none (1): Loopback is disabled. 

local (2): The Service Access Point associated with the port returns all 
frames to the originating layer without transmitting them.

remote (3): The port transmists back whatever it receives. (This implies 
that the Service Access Point associated with the port will not permit 
communications with any upper layer requesting service.) 

both (4): Both remote and local loopback enabled.

Default Value: none (1)

Configuration Changed: administrative

The change cannot be saved."
        ::= { ethSapOprEntry 7 }


-- gap (4) for future parameters


    ethOprControlStats OBJECT-TYPE
        SYNTAX  INTEGER {
                    clearSapStats   (1)
                    }
        ACCESS  write-only
        STATUS  mandatory
        DESCRIPTION
"Determines whether the statistics for the hardware port will be cleared. 
When the clearSapStats option is selected all the counters for the port are 
cleared.

Options:
clearSapStats (clears statistics for the hardware port)."
        ::= { ethSapOprEntry 12 }


-- gap (1) for future write-only commands


    ethStatOprLinkState OBJECT-TYPE
        SYNTAX INTEGER {
                    up              (1),
                    down            (2)
                    }
        ACCESS  read-only
        STATUS  mandatory
        DESCRIPTION
"Identifies whether the hardware port is available. If there is a problem 
with the port (e.g. a faulty connection) the value will be down.

Options:
up (1)

down (2)

Default Value: None" 

        ::= { ethSapOprEntry 14 }


    ethStatOprInFrames OBJECT-TYPE
        SYNTAX  Counter
        ACCESS  read-only
        STATUS  mandatory
        DESCRIPTION
"Identifies the total number of frames received by this port. The value 
indicates the activity at this interface.

Range of Values: 0 to 4, 294, 967, 295 

Default Value: None"
        ::= { ethSapOprEntry 15 }


    ethStatOprInOctets OBJECT-TYPE
        SYNTAX  Counter
        ACCESS  read-only
        STATUS  mandatory
        DESCRIPTION
"Identifies the total number of octets received by this port. The value 
indicates the activity at this interface.

Range of Values: 0 to 4, 294, 967, 295 

Default Value: None"
        ::= { ethSapOprEntry 16 }


ethStatOprInErrors OBJECT-TYPE
      SYNTAX  Counter
      ACCESS  read-only
      STATUS  mandatory
      DESCRIPTION
"Identifies the total number of errors received by this port. Errors include 
overrun errors, non-octet errors, and CRC errors.

A high count may indicate a hardware problem.

Range of Values: 0 to 4, 294, 967, 295

Default Value: None"
      ::= { ethSapOprEntry 17 }


   ethStatOprInDiscards OBJECT-TYPE
      SYNTAX  Counter
      ACCESS  read-only
      STATUS  mandatory
      DESCRIPTION
"Identifies the total number of frames received and discarded due to errors 
or other conditions (i.e. busy, lack of receive buffers, frames received 
while port not bound to an upper layer.)

A high count may indicate that the port is not bound to an upper 
layer.

Range of Values: 0 to 4,  294, 967, 295

Default Value: None"

      ::= { ethSapOprEntry 18 }


   ethStatOprInBusyDiscards OBJECT-TYPE
      SYNTAX  Counter
      ACCESS  read-only
      STATUS  mandatory
      DESCRIPTION
"Identifies the total number of frames received and discarded as a result of 
a lack of receive buffers.

A high count may indicate system resources are low.

Range of Values: 0 to 4, 294, 967, 295 

Default Value: None"
      ::= { ethSapOprEntry 19 }


   ethStatOprOutFrames OBJECT-TYPE
      SYNTAX  Counter
      ACCESS  read-only
      STATUS  mandatory
      DESCRIPTION
"Identifies the total number of frames transmitted by this port.

Range of Values: 0 to 4, 294, 967, 295 

Default Value: None"

      ::= { ethSapOprEntry 20 }


   ethStatOprOutOctets OBJECT-TYPE
      SYNTAX  Counter
      ACCESS  read-only
      STATUS  mandatory
      DESCRIPTION
"Identifies the total number of octets transmitted by this port.

Range of Values: 0 to 4, 294, 967, 295

Default Value: None"
      ::= { ethSapOprEntry 21 }


   ethStatOprOutErrors OBJECT-TYPE
      SYNTAX  Counter
      ACCESS  read-only
      STATUS  mandatory
      DESCRIPTION
"Identifies the total number of errors transmitted by this port. The count 
includes Transmitter Underrun, Carrier sense Lost During Frame
Transmission, Attempts Limits Expires, and Late Collisions.

A high count may indicate a hardware problem.

Range of Values: 0 to 4, 294, 967, 295

Default Value: None"
      ::= { ethSapOprEntry 22 }


   ethStatOprOutDiscards OBJECT-TYPE
      SYNTAX  Counter
      ACCESS  read-only
      STATUS  mandatory
      DESCRIPTION
"Identifies the total number of frames which were unsuccessfully transmitted 
due to a lack of transmit buffers. 

Range of Values: 0 to 4, 294, 967, 295  

Default Value: None"

      ::= { ethSapOprEntry 23 }


   ethStatOprOutCSLostFrames OBJECT-TYPE
      SYNTAX  Counter
      ACCESS  read-only
      STATUS  mandatory
      DESCRIPTION
"Identifies the total number of transmitted frames for which the carrier 
sense lost condition was encountered during transmission.

A high count may indicate that the device was unplugged during 
transmission.

Range of Values: 0 to 4, 294, 967, 295 

Default Value: None"
      ::= { ethSapOprEntry 24 }


   ethStatOprRxGenErrors OBJECT-TYPE
      SYNTAX  Counter
      ACCESS  read-only
      STATUS  mandatory
      DESCRIPTION
"Identifies the total number of  frames received that contain errors (for a 
port that has enable-verify set in ethSapOprDataGenerator.) 

Range of Values: 0 to 4, 294, 967, 295

Default Value: None"

      ::= { ethSapOprEntry 25 }



--  Planned Configuration Table

--  The table describing:
--  parameters used to configure each Ethernet SAP and its associated 
--  hardware port.


ethSapAdmTable OBJECT-TYPE
   SYNTAX  SEQUENCE OF EthSapAdmEntry
   ACCESS  not-accessible
   STATUS  mandatory
   DESCRIPTION
"Provides configuration information for each Ethernet service access point 
and its associated hardware port.

Each row (entry) of the table corresponds to a particular service access 
point."

   ::= { cxEthIo 2 }


   ethSapAdmEntry OBJECT-TYPE
      SYNTAX  EthSapAdmEntry
      ACCESS  not-accessible
      STATUS  mandatory
      DESCRIPTION
"Provides configuration information for a particular Ethernet service access 
point and its associated hardware port."
      INDEX { ethSapAdmNumber }
      ::= { ethSapAdmTable 1 }


    EthSapAdmEntry ::=
        SEQUENCE {
            ethSapAdmNumber
                INTEGER,
            ethSapAdmAlias
                Alias,
            ethSapAdmConnectorType
                INTEGER,
            ethSapAdmDataGenerator
                INTEGER,
            ethSapAdmGenFrames
                INTEGER,
            ethSapAdmGenFrameSize
                INTEGER,
            ethSapAdmLoopbackType
                INTEGER
            }


   ethSapAdmNumber OBJECT-TYPE
      SYNTAX  INTEGER
      ACCESS  read-only
      STATUS  mandatory
      DESCRIPTION
"Identifies the service access point by a number. Each service access point 
is assigned a unique number. The number is assigned by the system."
      ::= { ethSapAdmEntry 1 }


   ethSapAdmAlias OBJECT-TYPE
      SYNTAX  Alias
      ACCESS  read-write
      STATUS  mandatory
      DESCRIPTION
"Determines the textual name (alias) of this service access point. Each 
service access point is assigned a unique name.

Range of Values: 0-16 alphanumeric characters. (Note that the first 
character must be a letter; spaces are not allowed).

Related Parameters: The alias must be the same as the one used in 
cxCfgIpxPortSubnetworkSAPAlias and cxCfgIpAdEntSubnetworkSAPAlias."
      ::= { ethSapAdmEntry 2 }


    ethSapAdmConnectorType OBJECT-TYPE
        SYNTAX INTEGER {
                    auto           (1),
                    aui            (2),
                    tbaseT         (3),
                    baset-100	   (4)
                    }
        ACCESS  read-write
        STATUS  mandatory
        DESCRIPTION
"Identifies the connector type used for the hardware port. 

Options:
auto (1): connector type detected automatically

aui (2)

tbaseT (3)

100baseT (4)  100 Mbs Ethernet

Default Value: auto (1)

Configuration Changed: administrative

Further 
action: to activate changed
value, click on Action in EMS menu
bar, then click on Reset with Save."
        DEFVAL { auto }
        ::= { ethSapAdmEntry 3 }


   ethSapAdmDataGenerator OBJECT-TYPE
      SYNTAX  INTEGER {
           disabled     (1),
           enabled      (2),
           enabled-verify (3)
           }
      ACCESS  read-write
      STATUS  mandatory
      DESCRIPTION
"Determines whether the Data Generator is enabled. The Data Generator is 
used for testing purposes.

Options:
disabled (1)

enabled.(2)

enabled-verify.(3) The data generator is enabled and it checks what it 
receives against what it has sent. The result of the test is displayed in 
ethStatAdmrRxGenErrors. If this option is selected, ethSapOprLoobackType 
must be set to remote.

Default Value: disabled (1)

Configuration Changed: administrative"
      DEFVAL { disabled }
      ::= { ethSapAdmEntry 4 }


   ethSapAdmGenFrames OBJECT-TYPE
      SYNTAX  INTEGER (0..255)
      ACCESS  read-write
      STATUS  mandatory
      DESCRIPTION
"Determines the number of times a frame will be generated (for testing 
purposes). Frames are generated every 1 msec. If the value is set to zero, 
then frames will be generated continuously (every 1 msec).

If the Data Generator is disabled (using ethSapAdmDataGenerator), then the 
value is ignored.

Range of Values: 0 - 255

Default Value: 1

Configuration Changed: administrative"
        DEFVAL { 1 }
      ::= { ethSapAdmEntry 5 }


   ethSapAdmGenFrameSize OBJECT-TYPE
      SYNTAX  INTEGER (0..1514)
      ACCESS  read-write
      STATUS  mandatory
      DESCRIPTION
"Determines the size of the frames (in bytes) to be generated (for testing 
purposes). If the Data Generator is disabled, then this value is 
ignored.

Range of Values: 0 -1514 bytes

Default Value:512 bytes

Configuration Changed: administrative"
        DEFVAL { 512 }
      ::= { ethSapAdmEntry 6 }


    ethSapAdmLoopbackType OBJECT-TYPE
        SYNTAX  INTEGER {
                    none            (1),
                    local           (2),
                    remote          (3),
                    both            (4)
                    }
        ACCESS  read-write
        STATUS  mandatory
        DESCRIPTION
"Determines whether the port performs remote loopback, local loopback or 
both.

Options: 
none (1): Loopback is disabled.  

local (2): The Service Access Point associated with the port returns all 
frames to the originating layer without transmitting them.

remote (3): The port transmists back whatever it receives. (This implies 
that the Service Access Point associated with the port will not permit 
communications with any upper layer requesting service.)   

both (4): Both remote and local loopback enabled.

Default Value: none (1) 

Configuration Changed: administrative."
        DEFVAL { none }
        ::= { ethSapAdmEntry 7 }


END
