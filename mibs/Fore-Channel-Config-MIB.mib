-- 
-- Copyright 1999 by Fore Systems, Inc. 
-- Converted to SMIv2 rfc 2578,2579,2580 - STD 58
--
-- Copyright 1998 by Fore Systems, Inc.
-- All Rights Reserved

Fore-Channel-Config-MIB DEFINITIONS ::= BEGIN

IMPORTS
	OBJECT-TYPE,
	MODULE-IDENTITY	      FROM	SNMPv2-SMI
	asx		      FROM	Fore-Common-MIB
	ifIndex		      FROM	IF-MIB;

-- MIB Groups

channelControlGroup             MODULE-IDENTITY
          LAST-UPDATED         "9911050000Z"
          ORGANIZATION         "FORE"
          CONTACT-INFO         
               "      Postal:   FORE Systems Inc.
                                1000 FORE Drive
                                Warrendale, PA 15086-7502
                      Tel:      +1 724 742 6900
                      Email:    nm_mibs@fore.com
                      Web:      http://www.fore.com"
          DESCRIPTION  "
      This mib is used to configure channelized operating modes
      for interfaces that can operate in either channelized
      or concatenated mode.  For now, this is used to support
      the configuration of the Channelized OC12 netmod.  In
      that netmod, each port can operate as an STS12c atm
      cell source, or it can be configured to operate as
      4 STS3c streams channelized over an STS12 sonet path,
      or it can operate as 12xDS3 streams carried in STS3
      paths, which in turn, are multiplexed into an STS12
      path.

      This mib exports a single table which contains an
      row for each channelizable port in the switch.
      Each row has 1 modifiable column to set the operating
      mode of the port.  Note that changing a port's operating
      mode may make dramatic modifications to this and other
      tables as switching the mode of an interface may create or
      destory other interfaces."
    ::= { asx 11 }

channelConfigTable   OBJECT-TYPE
			SYNTAX  SEQUENCE OF ChannelConfigEntry
			MAX-ACCESS	not-accessible
			STATUS	current
			DESCRIPTION
			"A table of channelized port configuration information."
			::= { channelControlGroup 1 }

channelConfigEntry   OBJECT-TYPE
			SYNTAX ChannelConfigEntry
			MAX-ACCESS not-accessible
			STATUS current
			DESCRIPTION
				"A table entry containing channelized port
				 configuration information"
			INDEX { ifIndex }
			::= { channelConfigTable 1 }

ChannelConfigEntry ::=
		SEQUENCE {
			channelConfigMode	INTEGER
		}

channelConfigMode OBJECT-TYPE
		SYNTAX INTEGER {
			sts12c(0),
			sts3cX4(1),
			ds3X12(2)
		}
		MAX-ACCESS	read-write
		STATUS		current
		DESCRIPTION
		"This value indicates the current operating mode
		 of the specified interface.  Note that not all
		 modes may be chosen for a particular interface.
		 Also note that even though values are given in
		the Sonet hierarchy, these values can also be use
		to set the corresponding SDH hierarchy value if
		the underlying port is operating in SDH mode."
	::= { channelConfigEntry 1 }


END
