--			Ascend mibnat MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBNAT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibnatProfile  OBJECT IDENTIFIER ::= { configuration 95}

	-- The mibnatProfile table
	--
	-- This table contains parameters for the mibnatProfile profile
	--

    mibnatProfileTable	OBJECT-TYPE
	SYNTAX		SEQUENCE OF MibnatProfileEntry
	ACCESS		not-accessible
	STATUS		mandatory
	DESCRIPTION	"A list of mibnatProfile profile entries."
	::= { mibnatProfile 1 }

    mibnatProfileEntry	OBJECT-TYPE
	SYNTAX		MibnatProfileEntry
	ACCESS		not-accessible
	STATUS		mandatory
	DESCRIPTION	"A mibnatProfile entry containing objects that
			 maps to the parameters of mibnatProfile profile."
	INDEX		{ natProfile-NatProfile }
	::= { mibnatProfileTable 1 }

    MibnatProfileEntry ::=
	SEQUENCE {
	    natProfile-NatRouting
		INTEGER,
	    natProfile-NatProfile
		DisplayString,
	    natProfile-NatLan
		INTEGER,
	    natProfile-DefaultServer
		IpAddress,
	    natProfile-TunnelServer
		IpAddress,
	    natProfile-FrameRelayAddress
		IpAddress,
	    natProfile-StickyAddress
		INTEGER,
	    natProfile-StickyTimeout
		INTEGER,
	    natProfile-NoNatAddress
		IpAddress,
	    natProfile-AlternateNaptAddress
		IpAddress,
	    natProfile-NaptIdleTcpTimeout
		INTEGER,
	    natProfile-NatAddrPoolNum
		INTEGER,
	    natProfile-Action-o
		INTEGER
	}

    natProfile-NatRouting	OBJECT-TYPE
	SYNTAX	INTEGER {
		    no (1),
		    yes (2)
		}
	ACCESS	read-write
	STATUS	mandatory
	DESCRIPTION	"A boolean. When set to TRUE it translates all the lan addresses to dynamicaly assigned internet address."
	::= { mibnatProfileEntry 2 }

    natProfile-NatProfile	OBJECT-TYPE
	SYNTAX	DisplayString
	ACCESS	read-only
	STATUS	mandatory
	DESCRIPTION	"The name of this NAT profile, used in other types of profiles to refer to this NAT profile."
	::= { mibnatProfileEntry 3 }

    natProfile-NatLan	OBJECT-TYPE
	SYNTAX	INTEGER {
		    natlanSingleIp (1),
		    natlanMultiIp (2),
		    natlanPoolIp (3)
		}
	ACCESS	read-write
	STATUS	mandatory
	DESCRIPTION	"Which NAT addressing option to use."
	::= { mibnatProfileEntry 4 }

    natProfile-DefaultServer	OBJECT-TYPE
	SYNTAX	IpAddress
	ACCESS	read-write
	STATUS	mandatory
	DESCRIPTION	"The LAN address of the Default Server on the Lan side"
	::= { mibnatProfileEntry 5 }

    natProfile-TunnelServer	OBJECT-TYPE
	SYNTAX	IpAddress
	ACCESS	read-write
	STATUS	mandatory
	DESCRIPTION	"The IP address of the Tunnel Server on the Lan side"
	::= { mibnatProfileEntry 6 }

    natProfile-FrameRelayAddress	OBJECT-TYPE
	SYNTAX	IpAddress
	ACCESS	read-write
	STATUS	mandatory
	DESCRIPTION	"The Frame Relay/ATM VC user assigned IP address"
	::= { mibnatProfileEntry 7 }

    natProfile-StickyAddress	OBJECT-TYPE
	SYNTAX	INTEGER {
		    no (1),
		    yes (2)
		}
	ACCESS	read-write
	STATUS	mandatory
	DESCRIPTION	"A Boolen. When set to TRUE enables the sticky IP address feature - the router will try to retain the last IP address it got from the host by negotiating it with the host."
	::= { mibnatProfileEntry 8 }

    natProfile-StickyTimeout	OBJECT-TYPE
	SYNTAX	INTEGER
	ACCESS	read-write
	STATUS	mandatory
	DESCRIPTION	"A number. Represents the number of minutes the router will try to request the sticky IP address counting from the end of the last session."
	::= { mibnatProfileEntry 9 }

    natProfile-NoNatAddress	OBJECT-TYPE
	SYNTAX	IpAddress
	ACCESS	read-write
	STATUS	mandatory
	DESCRIPTION	"Address of subnet which should be exempted from Network Address Translation. An address of 0.0.0.0 means that selective NAT is disabled."
	::= { mibnatProfileEntry 10 }

    natProfile-AlternateNaptAddress	OBJECT-TYPE
	SYNTAX	IpAddress
	ACCESS	read-write
	STATUS	mandatory
	DESCRIPTION	"Public address to use on the WAN for sindle-address NAT instead of the address negotiated via IPCP. A value of 0.0.0.0 means use the address negotiated via IPCP."
	::= { mibnatProfileEntry 11 }

    natProfile-NaptIdleTcpTimeout	OBJECT-TYPE
	SYNTAX	INTEGER
	ACCESS	read-write
	STATUS	mandatory
	DESCRIPTION	"The flush timer interval in minutes for idle TCP connection entries in the NAPT table. Defaults to 24 hours."
	::= { mibnatProfileEntry 12 }

    natProfile-NatAddrPoolNum	OBJECT-TYPE
	SYNTAX	INTEGER
	ACCESS	read-write
	STATUS	mandatory
	DESCRIPTION	"Designates the address pool to use for Address Pool NAT."
	::= { mibnatProfileEntry 14 }

    natProfile-Action-o	OBJECT-TYPE
	SYNTAX	INTEGER {
		    noAction (1),
		    createProfile (2),
		    deleteProfile (3)
		}
	ACCESS	read-write
	STATUS	mandatory
	DESCRIPTION	""
	::= { mibnatProfileEntry 13 }


	-- The mibnatProfile__static_mappings table
	--
	-- This table contains parameters for the mibnatProfile__static_mappings profile
	--

    mibnatProfile-StaticMappingsTable	OBJECT-TYPE
	SYNTAX		SEQUENCE OF MibnatProfile-StaticMappingsEntry
	ACCESS		not-accessible
	STATUS		mandatory
	DESCRIPTION	"A list of mibnatProfile__static_mappings profile entries."
	::= { mibnatProfile 2 }

    mibnatProfile-StaticMappingsEntry	OBJECT-TYPE
	SYNTAX		MibnatProfile-StaticMappingsEntry
	ACCESS		not-accessible
	STATUS		mandatory
	DESCRIPTION	"A mibnatProfile__static_mappings entry containing objects that
			 maps to the parameters of mibnatProfile__static_mappings profile."
	INDEX		{ natProfile-StaticMappings-NatProfile, natProfile-StaticMappings-Index-o }
	::= { mibnatProfile-StaticMappingsTable 1 }

    MibnatProfile-StaticMappingsEntry ::=
	SEQUENCE {
	    natProfile-StaticMappings-NatProfile
		DisplayString,
	    natProfile-StaticMappings-Index-o
		INTEGER,
	    natProfile-StaticMappings-ValidEntry
		INTEGER,
	    natProfile-StaticMappings-DestPort
		INTEGER,
	    natProfile-StaticMappings-Protocol
		INTEGER,
	    natProfile-StaticMappings-LocalPort
		INTEGER,
	    natProfile-StaticMappings-LocalAddress
		IpAddress
	}

    natProfile-StaticMappings-NatProfile	OBJECT-TYPE
	SYNTAX	DisplayString
	ACCESS	read-only
	STATUS	mandatory
	DESCRIPTION	""
	::= { mibnatProfile-StaticMappingsEntry 8 }

    natProfile-StaticMappings-Index-o	OBJECT-TYPE
	SYNTAX	INTEGER
	ACCESS	read-only
	STATUS	mandatory
	DESCRIPTION	""
	::= { mibnatProfile-StaticMappingsEntry 1 }

    natProfile-StaticMappings-ValidEntry	OBJECT-TYPE
	SYNTAX	INTEGER {
		    no (1),
		    yes (2)
		}
	ACCESS	read-write
	STATUS	mandatory
	DESCRIPTION	"When TRUE, this filter entry has been defined and properly initialized. When FALSE, this entry should be skipped"
	::= { mibnatProfile-StaticMappingsEntry 3 }

    natProfile-StaticMappings-DestPort	OBJECT-TYPE
	SYNTAX	INTEGER
	ACCESS	read-write
	STATUS	mandatory
	DESCRIPTION	"The destPort represents the destination port number from TCP/UDP packets from the Wan to the Lan."
	::= { mibnatProfile-StaticMappingsEntry 4 }

    natProfile-StaticMappings-Protocol	OBJECT-TYPE
	SYNTAX	INTEGER {
		    smTcp (1),
		    smUdp (2)
		}
	ACCESS	read-write
	STATUS	mandatory
	DESCRIPTION	"The protocol represents the protocol type"
	::= { mibnatProfile-StaticMappingsEntry 5 }

    natProfile-StaticMappings-LocalPort	OBJECT-TYPE
	SYNTAX	INTEGER
	ACCESS	read-write
	STATUS	mandatory
	DESCRIPTION	"The localPort represents the local port number for machines on the Lan side."
	::= { mibnatProfile-StaticMappingsEntry 6 }

    natProfile-StaticMappings-LocalAddress	OBJECT-TYPE
	SYNTAX	IpAddress
	ACCESS	read-write
	STATUS	mandatory
	DESCRIPTION	"The localAddress represents the local IP Address of machines on the Lan side."
	::= { mibnatProfile-StaticMappingsEntry 7 }

END
