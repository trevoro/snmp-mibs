BAS-RIPv2-MIB DEFINITIONS ::= BEGIN

   IMPORTS
       MODULE-IDENTITY, OBJECT-TYPE, Counter32,
       TimeTicks, IpAddress                     FROM SNMPv2-SMI
       TEXTUAL-CONVENTION, RowStatus            FROM SNMPv2-TC
       basAliasRip, BasChassisId,
	BasSlotId, BasInterfaceId,
	BasLogicalPortId			FROM BAS-MIB;


   --  This MIB module uses the extended OBJECT-TYPE macro as
   --  defined in [9].

basRip2  MODULE-IDENTITY
	LAST-UPDATED "9810071415Z"
	ORGANIZATION "Broadband Access Systems"
	CONTACT-INFO
		" Tech Support
		  Broadband Access Systems
		  201 Forest Street
		  Marlboro, MA  01752
		  U.S.A.

		  508-485-8200
		  support@basystems.com"
	DESCRIPTION
		"This module defines the MIB objects
		 for a Broadband Access System IP Forwarding component."
	::= { basAliasRip  1 }

basRipObjects		OBJECT IDENTIFIER ::= { basAliasRip 1 }

 --  RIP-2 Management Information Base

 -- the RouteTag type represents the contents of the
 -- Route Domain field in the packet header or route entry.
 -- The use of the Route Domain is deprecated.

 RouteTag ::= TEXTUAL-CONVENTION
     STATUS      current
     DESCRIPTION
        "the RouteTag type represents the contents of the Route Domain
        field in the packet header or route entry"
    SYNTAX      OCTET STRING (SIZE (2))


--4.1 Global Counters

--      The RIP-2 Globals Group.
--      Implementation of this group is mandatory for systems
--      which implement RIP-2.

-- These counters are intended to facilitate debugging quickly
-- changing routes or failing neighbors


basRip2GlobalsTable OBJECT-TYPE
	SYNTAX		SEQUENCE OF BasRip2GlobalsEntry
	MAX-ACCESS	not-accessible
	STATUS		current
	DESCRIPTION
		"A list of Route Server forwarding table 
		distribution mechanism statistics."
	::= { basRipObjects 1 }

basRip2GlobalEntry OBJECT-TYPE
	SYNTAX		BasRip2GlobalsEntry
	MAX-ACCESS	not-accessible
	STATUS		current
	DESCRIPTION
		"Objects for the CIDR mib."
	INDEX   { basRip2GlobalChassis, basRip2GlobalSlot, basRip2GlobalIf, basRip2GlobalLPort }
	::= { basRip2GlobalsTable 1 }

BasRip2GlobalsEntry ::=
	SEQUENCE {
		basRip2GlobalRouteChanges	Counter32,
		basRip2GlobalQueries	Counter32,
		basRip2GlobalChassis	BasChassisId,
		basRip2GlobalSlot	BasSlotId,
		basRip2GlobalIf	BasInterfaceId,
		basRip2GlobalLPort	BasLogicalPortId
	}

    basRip2GlobalRouteChanges OBJECT-TYPE
        SYNTAX   Counter32
        MAX-ACCESS   read-only
        STATUS   current
        DESCRIPTION
           "The number of route changes made to the IP Route
           Database by RIP.  This does not include the refresh
           of a route's age."
       ::= { basRip2GlobalEntry 1 }

    basRip2GlobalQueries OBJECT-TYPE
        SYNTAX   Counter32
        MAX-ACCESS   read-only
        STATUS   current
        DESCRIPTION
           "The number of responses sent to RIP queries
           from other systems."
       ::= { basRip2GlobalEntry 2 }

    basRip2GlobalChassis OBJECT-TYPE
	SYNTAX		BasChassisId
	MAX-ACCESS	not-accessible
	STATUS		current
	DESCRIPTION
		"The BAS Chassis ID of the Route Server."
	::= { basRip2GlobalEntry 3 }

    basRip2GlobalSlot OBJECT-TYPE
	SYNTAX		BasSlotId
	MAX-ACCESS	not-accessible
	STATUS		current
	DESCRIPTION
		"The BAS Slot ID of the Route Server."
	::= { basRip2GlobalEntry 4}

    basRip2GlobalIf OBJECT-TYPE
	SYNTAX		BasInterfaceId
	MAX-ACCESS	not-accessible
	STATUS		current
	DESCRIPTION
		"The BAS interface ID of the Route Server."
	::= { basRip2GlobalEntry 5 }

     basRip2GlobalLPort OBJECT-TYPE
	SYNTAX		BasLogicalPortId
	MAX-ACCESS	not-accessible
	STATUS		current
	DESCRIPTION
		"The BAS logical port ID of the Route Server."
	::= { basRip2GlobalEntry 6 }

--4.2 RIP Interface Tables

--  RIP Interfaces Groups
--  Implementation of these Groups is mandatory for systems
--  which implement RIP-2.

-- The RIP Interface Status Table.

    basRip2IfStatTable OBJECT-TYPE
        SYNTAX   SEQUENCE OF BasRip2IfStatEntry
        MAX-ACCESS   not-accessible
        STATUS   current
        DESCRIPTION
           "A list of subnets which require separate
           status monitoring in RIP."
       ::= { basRipObjects 2 }

   basRip2IfStatEntry OBJECT-TYPE
       SYNTAX   BasRip2IfStatEntry
       MAX-ACCESS   not-accessible
       STATUS   current
       DESCRIPTION
          "A Single Routing Domain in a single Subnet."
      INDEX { basRip2GlobalChassis, basRip2GlobalSlot, basRip2GlobalIf, basRip2GlobalLPort, basRip2IfStatAddress }
      ::= { basRip2IfStatTable 1 }

    BasRip2IfStatEntry ::=
        SEQUENCE {
            basRip2IfStatAddress
                IpAddress,
            basRip2IfStatRcvBadPackets
                Counter32,
            basRip2IfStatRcvBadRoutes
                Counter32,
            basRip2IfStatSentUpdates
                Counter32,
            basRip2IfStatStatus
                RowStatus,
	    basRip2IfStatChassis	BasChassisId,
	    basRip2IfStatSlot	BasSlotId,
	    basRip2IfStatIf	BasInterfaceId,
	    basRip2IfStatLPort	BasLogicalPortId
    }

     basRip2IfStatAddress OBJECT-TYPE
        SYNTAX   IpAddress
        MAX-ACCESS   read-only
        STATUS   current
        DESCRIPTION
           "The IP Address of this system on the indicated
           subnet. For unnumbered interfaces, the value 0.0.0.N,
           where the least significant 24 bits (N) is the ifIndex
           for the IP Interface in network byte order."
       ::= { basRip2IfStatEntry 1 }

    basRip2IfStatRcvBadPackets OBJECT-TYPE
        SYNTAX   Counter32
        MAX-ACCESS   read-only
        STATUS   current
        DESCRIPTION
           "The number of RIP response packets received by
           the RIP process which were subsequently discarded
           for any reason (e.g. a version 0 packet, or an
           unknown command type)."
       ::= { basRip2IfStatEntry 2 }

    basRip2IfStatRcvBadRoutes OBJECT-TYPE
        SYNTAX   Counter32
        MAX-ACCESS   read-only
        STATUS   current


        DESCRIPTION
           "The number of routes, in valid RIP packets,
           which were ignored for any reason (e.g. unknown
           address family, or invalid metric)."
       ::= { basRip2IfStatEntry 3 }

    basRip2IfStatSentUpdates OBJECT-TYPE
        SYNTAX   Counter32
        MAX-ACCESS   read-only
        STATUS   current
        DESCRIPTION
           "The number of triggered RIP updates actually
           sent on this interface.  This explicitly does
           NOT include full updates sent containing new
           information."
       ::= { basRip2IfStatEntry 4 }

    basRip2IfStatStatus OBJECT-TYPE
        SYNTAX   RowStatus
        MAX-ACCESS   read-create
        STATUS   current
        DESCRIPTION
           "Writing invalid has the effect of deleting
           this interface."
       ::= { basRip2IfStatEntry 5 }


    basRip2IfStatChassis OBJECT-TYPE
	SYNTAX		BasChassisId
	MAX-ACCESS	not-accessible
	STATUS		current
	DESCRIPTION
		"The BAS Chassis ID of the Route Server."
	::= { basRip2IfStatEntry 6 }

    basRip2IfStatSlot OBJECT-TYPE
	SYNTAX		BasSlotId
	MAX-ACCESS	not-accessible
	STATUS		current
	DESCRIPTION
		"The BAS Slot ID of the Route Server."
	::= { basRip2IfStatEntry 7}

    basRip2IfStatIf OBJECT-TYPE
	SYNTAX		BasInterfaceId
	MAX-ACCESS	not-accessible
	STATUS		current
	DESCRIPTION
		"The BAS interface ID of the Route Server."
	::= { basRip2IfStatEntry 8 }

     basRip2IfStatLPort OBJECT-TYPE
	SYNTAX		BasLogicalPortId
	MAX-ACCESS	not-accessible
	STATUS		current
	DESCRIPTION
		"The BAS logical port ID of the Route Server."
	::= { basRip2IfStatEntry 9 }

-- The RIP Interface Configuration Table.

    basRip2IfConfTable OBJECT-TYPE
        SYNTAX   SEQUENCE OF BasRip2IfConfEntry
        MAX-ACCESS   not-accessible
        STATUS   current
        DESCRIPTION
           "A list of subnets which require separate
           configuration in RIP."
       ::= {  basRipObjects 3 }

   basRip2IfConfEntry OBJECT-TYPE
       SYNTAX   BasRip2IfConfEntry
       MAX-ACCESS   not-accessible
       STATUS   current
       DESCRIPTION
          "A Single Routing Domain in a single Subnet."
      INDEX { basRip2IfConfChassis, basRip2IfConfSlot, basRip2IfConfIf, basRip2IfConfLPort, basRip2IfConfAddress }
      ::= { basRip2IfConfTable 1 }

    BasRip2IfConfEntry ::=
        SEQUENCE {


            basRip2IfConfAddress
                IpAddress,
            basRip2IfConfDomain
                RouteTag,
            basRip2IfConfAuthType
                INTEGER,
            basRip2IfConfAuthKey
                OCTET STRING (SIZE(0..16)),
            basRip2IfConfSend
                INTEGER,
            basRip2IfConfReceive
                INTEGER,
            basRip2IfConfDefaultMetric
                INTEGER,
            basRip2IfConfStatus
                RowStatus,
            basRip2IfConfSrcAddress
                IpAddress,
	    basRip2IfConfChassis	BasChassisId,
	    basRip2IfConfSlot	BasSlotId,
	    basRip2IfConfIf	BasInterfaceId,
	    basRip2IfConfLPort	BasLogicalPortId

    }

    basRip2IfConfAddress OBJECT-TYPE
        SYNTAX   IpAddress
        MAX-ACCESS   read-only
        STATUS   current
        DESCRIPTION
           "The IP Address of this system on the indicated
           subnet.  For unnumbered interfaces, the value 0.0.0.N,
           where the least significant 24 bits (N) is the ifIndex
           for the IP Interface in network byte order."
       ::= { basRip2IfConfEntry 1 }

    basRip2IfConfDomain OBJECT-TYPE
        SYNTAX   RouteTag
        MAX-ACCESS   read-create
        STATUS   obsolete
        DESCRIPTION
           "Value inserted into the Routing Domain field
           of all RIP packets sent on this interface."
       DEFVAL { '0000'h }
       ::= { basRip2IfConfEntry 2 }

    basRip2IfConfAuthType OBJECT-TYPE
        SYNTAX   INTEGER {
                    noAuthentication (1),
                    simplePassword (2),
                    md5 (3)
                 }
        MAX-ACCESS   read-create


        STATUS   current
        DESCRIPTION
           "The type of Authentication used on this
           interface."
       DEFVAL { noAuthentication }
       ::= { basRip2IfConfEntry 3 }

    basRip2IfConfAuthKey OBJECT-TYPE
        SYNTAX   OCTET STRING (SIZE(0..16))
        MAX-ACCESS   read-create
        STATUS   current
        DESCRIPTION
           "The value to be used as the Authentication Key
           whenever the corresponding instance of
           rip2IfConfAuthType has a value other than
           noAuthentication.  A modification of the corresponding
           instance of rip2IfConfAuthType does not modify
           the rip2IfConfAuthKey value.  If a string shorter
           than 16 octets is supplied, it will be left-
           justified and padded to 16 octets, on the right,
           with nulls (0x00).

           Reading this object always results in an  OCTET
           STRING of length zero; authentication may not
           be bypassed by reading the MIB object."
       DEFVAL { ''h }
       ::= { basRip2IfConfEntry 4 }

   basRip2IfConfSend OBJECT-TYPE
        SYNTAX   INTEGER {
                    doNotSend (1),
                    ripVersion1 (2),
                    rip1Compatible (3),
                    ripVersion2 (4),
                    ripV1Demand (5),
                    ripV2Demand (6)
                 }
        MAX-ACCESS   read-create
        STATUS   current
        DESCRIPTION
           "What the router sends on this interface.
           ripVersion1 implies sending RIP updates compliant
           with  RFC  1058.   rip1Compatible implies
           broadcasting RIP-2 updates using RFC 1058 route
           subsumption rules.  ripVersion2 implies
           multicasting RIP-2 updates.  ripV1Demand indicates
           the use of Demand RIP on a WAN interface under RIP
           Version 1 rules.  ripV2Demand indicates the use of


           Demand RIP on a WAN interface under Version 2 rules."
       DEFVAL { rip1Compatible }
       ::= { basRip2IfConfEntry 5 }

    basRip2IfConfReceive OBJECT-TYPE
        SYNTAX   INTEGER {
                    rip1 (1),
                    rip2 (2),
                    rip1OrRip2 (3),
                    doNotRecieve (4)
                 }
        MAX-ACCESS   read-create
        STATUS   current
        DESCRIPTION
           "This indicates which version of RIP updates
           are to be accepted.  Note that rip2 and
           rip1OrRip2 implies reception of multicast
           packets."
       DEFVAL { rip1OrRip2 }
       ::= { basRip2IfConfEntry 6 }

    basRip2IfConfDefaultMetric OBJECT-TYPE
        SYNTAX   INTEGER ( 0..15 )
        MAX-ACCESS   read-create
        STATUS   current
        DESCRIPTION
           "This variable indicates the metric that is to
           be used for the default route entry in RIP updates
           originated on this interface.  A value of zero
           indicates that no default route should be
           originated; in this case, a default route via
           another router may be propagated."
       ::= { basRip2IfConfEntry 7 }

    basRip2IfConfStatus OBJECT-TYPE
        SYNTAX   RowStatus
        MAX-ACCESS   read-create
        STATUS   current
        DESCRIPTION
           "Writing invalid has  the  effect  of  deleting
           this interface."
       ::= { basRip2IfConfEntry 8 }

    basRip2IfConfSrcAddress OBJECT-TYPE
        SYNTAX   IpAddress
        MAX-ACCESS   read-create
        STATUS   current
        DESCRIPTION


           "The IP Address this system will use as a source
            address on this interface.  If it is a numbered
            interface, this MUST be the same value as
            rip2IfConfAddress.  On unnumbered interfaces,
            it must be the value of rip2IfConfAddress for
            some interface on the system."
       ::= { basRip2IfConfEntry 9 }

    basRip2IfConfChassis OBJECT-TYPE
	SYNTAX		BasChassisId
	MAX-ACCESS	not-accessible
	STATUS		current
	DESCRIPTION
		"The BAS Chassis ID of the Route Server."
	::= { basRip2IfConfEntry 10 }

    basRip2IfConfSlot OBJECT-TYPE
	SYNTAX		BasSlotId
	MAX-ACCESS	not-accessible
	STATUS		current
	DESCRIPTION
		"The BAS Slot ID of the Route Server."
	::= { basRip2IfConfEntry 11}

    basRip2IfConfIf OBJECT-TYPE
	SYNTAX		BasInterfaceId
	MAX-ACCESS	not-accessible
	STATUS		current
	DESCRIPTION
		"The BAS interface ID of the Route Server."
	::= { basRip2IfConfEntry 12 }

     basRip2IfConfLPort OBJECT-TYPE
	SYNTAX		BasLogicalPortId
	MAX-ACCESS	not-accessible
	STATUS		current
	DESCRIPTION
		"The BAS logical port ID of the Route Server."
	::= { basRip2IfConfEntry 13 }

--4.3 Peer Table

--  Peer Table

--      The RIP Peer Group
--      Implementation of this Group is Optional

--      This group provides information about active peer
--      relationships intended to assist in debugging.  An
--      active peer is a router from which a valid RIP
--      updated has been heard in the last 180 seconds.

    basRip2PeerTable OBJECT-TYPE
        SYNTAX   SEQUENCE OF BasRip2PeerEntry
        MAX-ACCESS   not-accessible
        STATUS   current
        DESCRIPTION
           "A list of RIP Peers."
       ::= { basRipObjects 4 }

   basRip2PeerEntry OBJECT-TYPE
       SYNTAX   BasRip2PeerEntry
       MAX-ACCESS   not-accessible
       STATUS   current
       DESCRIPTION
          "Information regarding a single routing peer."
      INDEX { basRip2PeerChassis, basRip2PeerSlot, basRip2PeerIf, basRip2PeerLPort, basRip2PeerAddress, basRip2PeerDomain }
      ::= { basRip2PeerTable 1 }

    BasRip2PeerEntry ::=
        SEQUENCE {
            basRip2PeerAddress
                IpAddress,
            basRip2PeerDomain
                RouteTag,
            basRip2PeerLastUpdate
                TimeTicks,
            basRip2PeerVersion
                INTEGER,
            basRip2PeerRcvBadPackets


                Counter32,
            basRip2PeerRcvBadRoutes
                Counter32,
	    basRip2PeerChassis	BasChassisId,
	    basRip2PeerSlot	BasSlotId,
	    basRip2PeerIf	BasInterfaceId,
	    basRip2PeerLPort	BasLogicalPortId

            }

    basRip2PeerAddress OBJECT-TYPE
        SYNTAX   IpAddress
        MAX-ACCESS   read-only
        STATUS   current
        DESCRIPTION
           "The IP Address that the peer is using as its source
            address.  Note that on an unnumbered link, this may
            not be a member of any subnet on the system."
       ::= { basRip2PeerEntry 1 }

    basRip2PeerDomain OBJECT-TYPE
        SYNTAX   RouteTag
        MAX-ACCESS   read-only
        STATUS   current
        DESCRIPTION
           "The value in the Routing Domain field  in  RIP
           packets received from the peer.  As domain suuport
           is deprecated, this must be zero."
       ::= { basRip2PeerEntry 2 }

    basRip2PeerLastUpdate OBJECT-TYPE
        SYNTAX   TimeTicks
        MAX-ACCESS   read-only
        STATUS   current
        DESCRIPTION
           "The value of sysUpTime when the most recent
           RIP update was received from this system."
       ::= { basRip2PeerEntry 3 }

    basRip2PeerVersion OBJECT-TYPE
        SYNTAX   INTEGER ( 0..255 )
        MAX-ACCESS   read-only
        STATUS   current
        DESCRIPTION
           "The RIP version number in the header of the
           last RIP packet received."
       ::= { basRip2PeerEntry 4 }

    basRip2PeerRcvBadPackets OBJECT-TYPE
        SYNTAX   Counter32
        MAX-ACCESS   read-only
        STATUS   current
        DESCRIPTION


           "The number of RIP response packets from this
           peer discarded as invalid."
       ::= { basRip2PeerEntry 5 }

    basRip2PeerRcvBadRoutes OBJECT-TYPE
        SYNTAX   Counter32
        MAX-ACCESS   read-only
        STATUS   current
        DESCRIPTION
           "The number of routes from this peer that were
           ignored because the entry format was invalid."
       ::= { basRip2PeerEntry 6 }


    basRip2PeerChassis OBJECT-TYPE
	SYNTAX		BasChassisId
	MAX-ACCESS	not-accessible
	STATUS		current
	DESCRIPTION
		"The BAS Chassis ID of the Route Server."
	::= { basRip2PeerEntry 7 }

    basRip2PeerSlot OBJECT-TYPE
	SYNTAX		BasSlotId
	MAX-ACCESS	not-accessible
	STATUS		current
	DESCRIPTION
		"The BAS Slot ID of the Route Server."
	::= { basRip2PeerEntry 8}

    basRip2PeerIf OBJECT-TYPE
	SYNTAX		BasInterfaceId
	MAX-ACCESS	not-accessible
	STATUS		current
	DESCRIPTION
		"The BAS interface ID of the Route Server."
	::= { basRip2PeerEntry 9 }

     basRip2PeerLPort OBJECT-TYPE
	SYNTAX		BasLogicalPortId
	MAX-ACCESS	not-accessible
	STATUS		current
	DESCRIPTION
		"The BAS logical port ID of the Route Server."
	::= { basRip2PeerEntry 10 }

END
