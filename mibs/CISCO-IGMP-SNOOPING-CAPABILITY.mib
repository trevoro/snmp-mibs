-- *****************************************************************
-- CISCO-IGMP-SNOOPING-CAPABILITY.my:
-- Cisco CISCO-IGMP-SNOOPING-MIB AGENT-CAPABILITIES
--
-- July 2003, Binh Le
--
-- Copyright (c) 2003, 2004 by Cisco Systems, Inc.
-- All rights reserved.
-- *****************************************************************

CISCO-IGMP-SNOOPING-CAPABILITY DEFINITIONS ::= BEGIN

IMPORTS
        MODULE-IDENTITY
                FROM SNMPv2-SMI
        AGENT-CAPABILITIES
                FROM SNMPv2-CONF
        ciscoAgentCapability
                FROM CISCO-SMI;

ciscoIgmpSnoopingCapability MODULE-IDENTITY
        LAST-UPDATED    "200403100000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com,
                        cs-ipmulticast@cisco.com"
        DESCRIPTION
                "The capabilities description of
                 CISCO-IGMP-SNOOPING-MIB."

        REVISION        "200403100000Z" 
        DESCRIPTION
                "Added the following capability statements:
                        - cisCapCatOSV08R0301Cat6kPfc2
                        - cisCapCatOSV08R0301Cat6kPfc3."

        REVISION        "200308130000Z"
        DESCRIPTION
                "Initial version of this MIB module."
        ::= { ciscoAgentCapability 320 }

cisCapCatOSV08R0101Cat6kPfc  AGENT-CAPABILITIES 
    PRODUCT-RELEASE     "Cisco CatOS 8.1(1) on Catalyst 6000/6500
                         and Cisco 7600 series devices with PFC card."
    STATUS              current
    DESCRIPTION         "CISCO-IGMP-SNOOPING-MIB capabilities."

    SUPPORTS            CISCO-IGMP-SNOOPING-MIB
        INCLUDES        { cisSystemGroup, cisSystemV2Group, 
                          cisStatsGroup, cisBaseConfigGroup,
                          cisExtConfig1Group,
                          cisIgmpQuerierConfigGroup }

    ::= { ciscoIgmpSnoopingCapability 1 }

cisCapCatOSV08R0101Cat6kPfc2 AGENT-CAPABILITIES
    PRODUCT-RELEASE     "Cisco CatOS 8.1(1) on Catalyst 6000/6500 and
                         Cisco 7600 series devices with PFC2 card."
    STATUS              current
    DESCRIPTION         "CISCO-IGMP-SNOOPING-MIB capabilities."

    SUPPORTS            CISCO-IGMP-SNOOPING-MIB
        INCLUDES        { cisSystemGroup, cisSystemV2Group, 
                          cisSystemV3Group, cisStatsGroup, 
                          cisV3StatsGroup, cisBaseConfigGroup, 
                          cisGlobalIgmpV3ConfigGroup, 
                          cisExtConfig1Group, cisRateLimitGroup, 
                          cisIgmpQuerierConfigGroup }

        VARIATION       cisIgmpQuerierEnabled 
            DESCRIPTION "Can be set to 'true' only if 
                         cisV3ProcessEnabledAdminStatus is 'false'." 

        VARIATION       cisV3ProcessEnabledAdminStatus
            DESCRIPTION "Can be set to 'true' only if there is no
                         Querier enabled on any VLANs."

    ::= { ciscoIgmpSnoopingCapability 2 }

cisCapCatOSV08R0101Cat6kPfc3 AGENT-CAPABILITIES 
    PRODUCT-RELEASE     "Cisco CatOS 8.1(1) on Catalyst 6000/6500 and
                         Cisco 7600 series devices with PFC3 card."
    STATUS              current
    DESCRIPTION         "CISCO-IGMP-SNOOPING-MIB capabilities."

    SUPPORTS            CISCO-IGMP-SNOOPING-MIB
        INCLUDES        { cisSystemGroup, cisSystemV2Group, 
                          cisStatsGroup, cisBaseConfigGroup,
                          cisExtConfig1Group, cisRateLimitGroup,
                          cisIgmpQuerierConfigGroup }

        VARIATION       cisGeneralQueryRateLimit 
            ACCESS      not-implemented
            DESCRIPTION "Not supported." 

    ::= { ciscoIgmpSnoopingCapability 3 }

cisCapCatOSV08R0301Cat6kPfc2 AGENT-CAPABILITIES
    PRODUCT-RELEASE     "Cisco CatOS 8.3(1) on Catalyst 6000/6500 and
                         Cisco 7600 series devices with PFC2 card."
    STATUS              current
    DESCRIPTION         "CISCO-IGMP-SNOOPING-MIB capabilities."

    SUPPORTS            CISCO-IGMP-SNOOPING-MIB
    INCLUDES            { cisSystemGroup, cisSystemV2Group,
                          cisSystemV3Group, cisStatsGroup, 
                          cisV3StatsGroup, cisBaseConfigGroup,
                          cisGlobalIgmpV3ConfigGroup,
                          cisExtConfig1Group, 
                          cisIgmpQuerierConfigGroup }

        VARIATION       cisIgmpQuerierEnabled
            DESCRIPTION "Can be set to 'true' only if
                         cisV3ProcessEnabledAdminStatus is 'false'."

        VARIATION       cisV3ProcessEnabledAdminStatus
            DESCRIPTION "Can be set to 'true' only if there is no
                         Querier enabled on any VLANs."

   ::= { ciscoIgmpSnoopingCapability 4 }

cisCapCatOSV08R0301Cat6kPfc3 AGENT-CAPABILITIES
    PRODUCT-RELEASE     "Cisco CatOS 8.3(1) on Catalyst 6000/6500 and
                         Cisco 7600 series devices with PFC3 card."
    STATUS              current
    DESCRIPTION         "CISCO-IGMP-SNOOPING-MIB capabilities."

    SUPPORTS            CISCO-IGMP-SNOOPING-MIB
    INCLUDES            { cisSystemGroup, cisSystemV2Group,
                          cisSystemV3Group, cisV3StatsGroup,
                          cisGlobalIgmpV3ConfigGroup,
                          cisStatsGroup, cisBaseConfigGroup,
                          cisExtConfig1Group,
                          cisIgmpQuerierConfigGroup }

        VARIATION       cisIgmpQuerierEnabled
            DESCRIPTION "Can be set to 'true' only if
                         cisV3ProcessEnabledAdminStatus is 'false'."

        VARIATION       cisV3ProcessEnabledAdminStatus
            DESCRIPTION "Can be set to 'true' only if there is no
                         Querier enabled on any VLANs."

   ::= { ciscoIgmpSnoopingCapability 5 }

END
