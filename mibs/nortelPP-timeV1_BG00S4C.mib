Nortel-Magellan-Passport-TimeMIB
DEFINITIONS ::= BEGIN



IMPORTS

      OBJECT-TYPE
   FROM RFC-1212

      IpAddress
   FROM RFC1155-SMI

      components,
      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      NonReplicated,
      EnterpriseDateAndTime
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Time Enterprise MIB."

timeMIB OBJECT IDENTIFIER ::= { passportMIBs 13 }










-- Time
-- The Time component provides access to time and date information 
-- on this module. It has operational attributes and optional 
-- provisionable Server subcomponents.

time OBJECT IDENTIFIER ::= { components 19 }



timeRowStatusTable OBJECT-TYPE
   SYNTAX     SEQUENCE OF TimeRowStatusEntry
   ACCESS     not-accessible
   STATUS     mandatory
   DESCRIPTION
     "This entry controls the addition and deletion of 
      time components."
::= { time 1 }

timeRowStatusEntry OBJECT-TYPE
   SYNTAX     TimeRowStatusEntry
   ACCESS     not-accessible
   STATUS     mandatory
   DESCRIPTION
     "A single entry in the table represents a single 
      time component."
   INDEX {
      timeIndex }
::= { timeRowStatusTable 1 }

TimeRowStatusEntry ::= SEQUENCE {
   timeRowStatus
      RowStatus,
   timeComponentName
      DisplayString,
   timeStorageType
      StorageType,
   timeIndex
      NonReplicated }

timeRowStatus OBJECT-TYPE
   SYNTAX     RowStatus 
   ACCESS     read-only
   STATUS     mandatory
   DESCRIPTION
     "This variable is used as the basis for SNMP naming of
      time components.
      These components cannot be added nor deleted."
::= { timeRowStatusEntry 1 }

timeComponentName OBJECT-TYPE
   SYNTAX     DisplayString 
   ACCESS     read-only
   STATUS     mandatory
   DESCRIPTION
     "This variable provides the component's string name for
      use with the ASCII Console Interface"
::= { timeRowStatusEntry 2 }

timeStorageType OBJECT-TYPE
   SYNTAX     StorageType 
   ACCESS     read-only
   STATUS     mandatory
   DESCRIPTION
     "This variable represents the storage type value for the
      time tables."
::= { timeRowStatusEntry 4 }

timeIndex OBJECT-TYPE
   SYNTAX     NonReplicated 
   ACCESS     not-accessible
   STATUS     mandatory
   DESCRIPTION
     "This variable represents the index for the time tables."
::= { timeRowStatusEntry 10 }

timeOperTable OBJECT-TYPE
   SYNTAX     SEQUENCE OF TimeOperEntry
   ACCESS     not-accessible
   STATUS     mandatory
   DESCRIPTION
     "This group contains the operational attributes of the Time 
      component."
::= { time 10 }

timeOperEntry OBJECT-TYPE
   SYNTAX     TimeOperEntry
   ACCESS     not-accessible
   STATUS     mandatory
   DESCRIPTION
     "An entry in the timeOperTable."
   INDEX {
      timeIndex }
::= { timeOperTable 1 }

TimeOperEntry ::= SEQUENCE {
   timeNetworkTime
      EnterpriseDateAndTime,
   timeSyncStatus
      INTEGER,
   timeSyncSource
      IpAddress,
   timeTimeOffset
      Unsigned32,
   timeModuleTime
      EnterpriseDateAndTime,
   timeOffset
      INTEGER,
   timeMainServer
      IpAddress,
   timeXntpVersion
      Unsigned32 }

timeNetworkTime OBJECT-TYPE
   SYNTAX     EnterpriseDateAndTime (SIZE (0 | 19))
   ACCESS     read-write
   STATUS     obsolete
   DESCRIPTION
     "The networkTime attribute represents the current date and time. The 
      operator resets the current date and time by setting this attribute. If 
      syncStatus is synchronized or synchronizing, the set verb is 
      disabled."
::= { timeOperEntry 1 }

timeSyncStatus OBJECT-TYPE
   SYNTAX     INTEGER  {
                 synchronized(0),
                 unsynchronized(1),
                 synchronizing(4),
                 unspecified(5) }
   ACCESS     read-only
   STATUS     mandatory
   DESCRIPTION
     "This attribute indicates the XNTP (Network Time Protocol) 
      synchronization status of this module. If the value is synchronized 
      or synchronizing, the syncSource attribute indicates the IP address 
      of the main network time server.
      The values have the following meanings:
      synchronized -- The module is synchronized with the network time 
      server.
      unsynchronized -- There is no network time server selected as 
      XNTP server for the module to synchronize its time with.
      synchronizing -- The module is trying to synchronize with the 
      network time server.
      unknown -- The synchronization status of the module is unknown."
::= { timeOperEntry 2 }

timeSyncSource OBJECT-TYPE
   SYNTAX     IpAddress 
   ACCESS     read-only
   STATUS     obsolete
   DESCRIPTION
     "The syncSource is the IP address of the time server host to which 
      the module's syncStatus is synchronized. If the module's syncStatus 
      is unsynchronized, the address is 0.0.0.0."
::= { timeOperEntry 3 }

timeTimeOffset OBJECT-TYPE
   SYNTAX     Unsigned32 (0..1440)
   ACCESS     read-write
   STATUS     obsolete
   DESCRIPTION
     "The timeOffset attribute is the number of minutes, to add to the 
      reference time, which is equal to the Universal Coordinated Time 
      (UTC), to obtain the moduleTime."
   DEFVAL     { 0 }
::= { timeOperEntry 4 }

timeModuleTime OBJECT-TYPE
   SYNTAX     EnterpriseDateAndTime (SIZE (0 | 19))
   ACCESS     read-write
   STATUS     mandatory
   DESCRIPTION
     "This attribute indicates the current date and time on this module. 
      The moduleTime is obtained by adding an offset to the reference 
      time, which is the Universal Time Coordinated (UTC). When the 
      moduleTime is set, it keeps the value even if the card boots. It is the 
      time used for time stamps, such as in alarms and accounting data. 
      The operator resets the current date and time by setting this attribute 
      when syncStatus is unsynchronized. Setting this attribute is not 
      allowed if syncStatus is synchronized or synchronizing."
::= { timeOperEntry 5 }

timeOffset OBJECT-TYPE
   SYNTAX     INTEGER (-720..1440)
   ACCESS     read-write
   STATUS     mandatory
   DESCRIPTION
     "This attribute specifies the number of minutes to be added to the 
      reference time, which is Universal Coordinated Time (UTC), to 
      obtain the moduleTime. It keeps its value even if the card boots. 
      However, if the node is powered-off for more than 24 hours, it 
      resets to the default value, which is 0. The specified value should be 
      in the range -720 (-12 hours) to 720 (+12 hours). Values greater 
      than 720 are accepted for backward compatibility; for example, 780 
      (13 hours) corresponds to an offset of -11 hours. If a value greater 
      than 720 is entered, it will be displayed as a negative offset."
   DEFVAL     { 0 }
::= { timeOperEntry 6 }

timeMainServer OBJECT-TYPE
   SYNTAX     IpAddress 
   ACCESS     read-only
   STATUS     mandatory
   DESCRIPTION
     "This attribute indicates the IP address of the main network time 
      server that this module synchronizes with. If syncStatus is 
      unsynchronized, then mainServer is 0.0.0.0."
::= { timeOperEntry 7 }

timeXntpVersion OBJECT-TYPE
   SYNTAX     Unsigned32 (0..15)
   ACCESS     read-only
   STATUS     mandatory
   DESCRIPTION
     "This attribute indicates the current protocol version of XNTP 
      running on this module."
::= { timeOperEntry 8 }

timeSyncSourcesTable OBJECT-TYPE
   SYNTAX     SEQUENCE OF TimeSyncSourcesEntry
   ACCESS     not-accessible
   STATUS     mandatory
   DESCRIPTION
     "This attribute indicates the IP addresses of the network time servers 
      that this module synchronizes with. XNTP uses the clock values of 
      the network time servers to set its moduleTime."
::= { time 391 }

timeSyncSourcesEntry OBJECT-TYPE
   SYNTAX     TimeSyncSourcesEntry
   ACCESS     not-accessible
   STATUS     mandatory
   DESCRIPTION
     "An entry in the timeSyncSourcesTable."
   INDEX {
      timeIndex,
      timeSyncSourcesValue }
::= { timeSyncSourcesTable 1 }

TimeSyncSourcesEntry ::= SEQUENCE {
   timeSyncSourcesValue
      IpAddress }

timeSyncSourcesValue OBJECT-TYPE
   SYNTAX     IpAddress 
   ACCESS     read-only
   STATUS     mandatory
   DESCRIPTION
     "This variable represents both the value and the index for the
      timeSyncSourcesTable."
::= { timeSyncSourcesEntry 1 }


-- Time Server/n
-- The Server component represents a single network time server that 
-- this module can use for network time synchronization.

timeServer OBJECT IDENTIFIER ::= { time 3 }



timeServerRowStatusTable OBJECT-TYPE
   SYNTAX     SEQUENCE OF TimeServerRowStatusEntry
   ACCESS     not-accessible
   STATUS     mandatory
   DESCRIPTION
     "This entry controls the addition and deletion of 
      timeServer components."
::= { timeServer 1 }

timeServerRowStatusEntry OBJECT-TYPE
   SYNTAX     TimeServerRowStatusEntry
   ACCESS     not-accessible
   STATUS     mandatory
   DESCRIPTION
     "A single entry in the table represents a single 
      timeServer component."
   INDEX {
      timeIndex,
      timeServerIndex }
::= { timeServerRowStatusTable 1 }

TimeServerRowStatusEntry ::= SEQUENCE {
   timeServerRowStatus
      RowStatus,
   timeServerComponentName
      DisplayString,
   timeServerStorageType
      StorageType,
   timeServerIndex
      Integer32 }

timeServerRowStatus OBJECT-TYPE
   SYNTAX     RowStatus 
   ACCESS     read-write
   STATUS     mandatory
   DESCRIPTION
     "This variable is used as the basis for SNMP naming of
      timeServer components.
      These components can be added and deleted."
::= { timeServerRowStatusEntry 1 }

timeServerComponentName OBJECT-TYPE
   SYNTAX     DisplayString 
   ACCESS     read-only
   STATUS     mandatory
   DESCRIPTION
     "This variable provides the component's string name for
      use with the ASCII Console Interface"
::= { timeServerRowStatusEntry 2 }

timeServerStorageType OBJECT-TYPE
   SYNTAX     StorageType 
   ACCESS     read-only
   STATUS     mandatory
   DESCRIPTION
     "This variable represents the storage type value for the
      timeServer tables."
::= { timeServerRowStatusEntry 4 }

timeServerIndex OBJECT-TYPE
   SYNTAX     Integer32 (1..10)
   ACCESS     not-accessible
   STATUS     mandatory
   DESCRIPTION
     "This variable represents the index for the timeServer tables."
::= { timeServerRowStatusEntry 10 }

timeServerProvTable OBJECT-TYPE
   SYNTAX     SEQUENCE OF TimeServerProvEntry
   ACCESS     not-accessible
   STATUS     mandatory
   DESCRIPTION
     "This group contains the provisionable attributes of the Server 
      component."
::= { timeServer 11 }

timeServerProvEntry OBJECT-TYPE
   SYNTAX     TimeServerProvEntry
   ACCESS     not-accessible
   STATUS     mandatory
   DESCRIPTION
     "An entry in the timeServerProvTable."
   INDEX {
      timeIndex,
      timeServerIndex }
::= { timeServerProvTable 1 }

TimeServerProvEntry ::= SEQUENCE {
   timeServerIpAddress
      IpAddress,
   timeServerIpStack
      INTEGER }

timeServerIpAddress OBJECT-TYPE
   SYNTAX     IpAddress 
   ACCESS     read-write
   STATUS     mandatory
   DESCRIPTION
     "This attribute specifies the IP address of a network time server that 
      the module will attempt to synchronize with. The value of 
      ipAddress must be unique across all Server components."
::= { timeServerProvEntry 1 }

timeServerIpStack OBJECT-TYPE
   SYNTAX     INTEGER  {
                 ipiFrIpiVc(1),
                 vrIp(2) }
   ACCESS     read-write
   STATUS     mandatory
   DESCRIPTION
     "This attribute specifies the IP stack that XNTP uses to communi-
      cate with the network time server. If ipiFrIpiVc is selected, then an 
      IpiFr or IpiVc component must be provisioned on this module. If 
      vrIp is selected, then Ip must be provisioned under the management 
      Vr on this module."
   DEFVAL     { ipiFrIpiVc }
::= { timeServerProvEntry 2 }

timeServerStateTable OBJECT-TYPE
   SYNTAX     SEQUENCE OF TimeServerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { timeServer 12 }

timeServerStateEntry OBJECT-TYPE
   SYNTAX     TimeServerStateEntry
   ACCESS     not-accessible
   STATUS     mandatory
   DESCRIPTION
     "An entry in the timeServerStateTable."
   INDEX {
      timeIndex,
      timeServerIndex }
::= { timeServerStateTable 1 }

TimeServerStateEntry ::= SEQUENCE {
   timeServerAdminState
      INTEGER,
   timeServerOperationalState
      INTEGER,
   timeServerUsageState
      INTEGER }

timeServerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { timeServerStateEntry 1 }

timeServerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { timeServerStateEntry 2 }

timeServerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { timeServerStateEntry 3 }

timeServerOperTable OBJECT-TYPE
   SYNTAX     SEQUENCE OF TimeServerOperEntry
   ACCESS     not-accessible
   STATUS     mandatory
   DESCRIPTION
     "This group contains the operational attributes of the Server 
      component."
::= { timeServer 13 }

timeServerOperEntry OBJECT-TYPE
   SYNTAX     TimeServerOperEntry
   ACCESS     not-accessible
   STATUS     mandatory
   DESCRIPTION
     "An entry in the timeServerOperTable."
   INDEX {
      timeIndex,
      timeServerIndex }
::= { timeServerOperTable 1 }

TimeServerOperEntry ::= SEQUENCE {
   timeServerXntpVersion
      Unsigned32,
   timeServerStratum
      Unsigned32,
   timeServerPoll
      Unsigned32,
   timeServerPktSent
      Counter32,
   timeServerPktRecv
      Counter32,
   timeServerPktValid
      Counter32,
   timeServerStatus
      OCTET STRING }

timeServerXntpVersion OBJECT-TYPE
   SYNTAX     Unsigned32 (0..15)
   ACCESS     read-only
   STATUS     mandatory
   DESCRIPTION
     "This attribute indicates the version of XNTP currently in use by the 
      network time server."
::= { timeServerOperEntry 1 }

timeServerStratum OBJECT-TYPE
   SYNTAX     Unsigned32 (0..16)
   ACCESS     read-only
   STATUS     mandatory
   DESCRIPTION
     "This attribute indicates the stratum level of the clock on the network 
      time server."
::= { timeServerOperEntry 2 }

timeServerPoll OBJECT-TYPE
   SYNTAX     Unsigned32 (0..15)
   ACCESS     read-only
   STATUS     mandatory
   DESCRIPTION
     "This attribute indicates the time interval for the Passport module to 
      poll the network time server for time synchronization."
::= { timeServerOperEntry 3 }

timeServerPktSent OBJECT-TYPE
   SYNTAX     Counter32 
   ACCESS     read-only
   STATUS     mandatory
   DESCRIPTION
     "This attribute counts the packets sent to the network time server."
::= { timeServerOperEntry 4 }

timeServerPktRecv OBJECT-TYPE
   SYNTAX     Counter32 
   ACCESS     read-only
   STATUS     mandatory
   DESCRIPTION
     "This attribute counts the packets received from the network time 
      server, including the invalid packets."
::= { timeServerOperEntry 5 }

timeServerPktValid OBJECT-TYPE
   SYNTAX     Counter32 
   ACCESS     read-only
   STATUS     mandatory
   DESCRIPTION
     "This attribute counts the valid packets received from the network 
      time server."
::= { timeServerOperEntry 6 }

timeServerStatus OBJECT-TYPE
   SYNTAX     OCTET STRING (SIZE (2))
   ACCESS     read-only
   STATUS     mandatory
   DESCRIPTION
     "This attribute indicates the status of the network time server.
      main -- This network time server is working properly, and is the 
      system servers (synchronization sources) of the module.
      primary -- This network time server is working properly, and is the 
      primary servers (one of the synchronization sources) of the module
      secondary -- This network time server is working properly, but its 
      offset and dispersion is not stable or too high so that it can not be 
      selected as one of the primary time synchronization sources. But if 
      the primary synchronization sources are not available, it can take 
      over the responsibility and become the time synchronization source 
      of the module.
      unused -- This network time server is not used as a server 
      (synchronization source) of the module.
      noResponse -- This network time server is not responding to the 
      module's time synchronization request. This could be caused by 
      network error or protocol error, or network time server 
      configuration error.
      stratumTooHigh -- This network time server has the bad stratum 
      (higher than 16), or its stratum is higher than the module's stratum.
      leapUnsync -- This network time server's leap value indicates that 
      this network time server is not synchronized.
      clockUnsync -- This network time server's clock values indicates 
      that this network time server is not synchronized.
      rootTooNoisy -- This network time server's root dispersion is too 
      high, so that its time stamp is not used.
      peerTooNoisy -- The modules dispersion relative to this network 
      time server is too high, so this network time server's time stamp is 
      not used.
      faultStick -- This offset of the module relative to this network time 
      server is out of the range or too high, so that it can not be selected 
      as one of the primary time synchronization source.

      Description of bits:
      main(0)
      primary(1)
      secondary(2)
      unused(3)
      noResponse(4)
      stratumTooHigh(5)
      leapUnsync(6)
      clockUnsync(7)
      rootTooNoisy(8)
      peerTooNoisy(9)
      faultStick(10)"
::= { timeServerOperEntry 392 }


-- NetworkSynchronization 
-- The NetworkSynchronization component administers the network 
-- clock synchronization.

nS OBJECT IDENTIFIER ::= { components 20 }



nSRowStatusTable OBJECT-TYPE
   SYNTAX     SEQUENCE OF NSRowStatusEntry
   ACCESS     not-accessible
   STATUS     mandatory
   DESCRIPTION
     "This entry controls the addition and deletion of 
      nS components."
::= { nS 1 }

nSRowStatusEntry OBJECT-TYPE
   SYNTAX     NSRowStatusEntry
   ACCESS     not-accessible
   STATUS     mandatory
   DESCRIPTION
     "A single entry in the table represents a single 
      nS component."
   INDEX {
      nSIndex }
::= { nSRowStatusTable 1 }

NSRowStatusEntry ::= SEQUENCE {
   nSRowStatus
      RowStatus,
   nSComponentName
      DisplayString,
   nSStorageType
      StorageType,
   nSIndex
      NonReplicated }

nSRowStatus OBJECT-TYPE
   SYNTAX     RowStatus 
   ACCESS     read-write
   STATUS     mandatory
   DESCRIPTION
     "This variable is used as the basis for SNMP naming of
      nS components.
      These components can be added and deleted."
::= { nSRowStatusEntry 1 }

nSComponentName OBJECT-TYPE
   SYNTAX     DisplayString 
   ACCESS     read-only
   STATUS     mandatory
   DESCRIPTION
     "This variable provides the component's string name for
      use with the ASCII Console Interface"
::= { nSRowStatusEntry 2 }

nSStorageType OBJECT-TYPE
   SYNTAX     StorageType 
   ACCESS     read-only
   STATUS     mandatory
   DESCRIPTION
     "This variable represents the storage type value for the
      nS tables."
::= { nSRowStatusEntry 4 }

nSIndex OBJECT-TYPE
   SYNTAX     NonReplicated 
   ACCESS     not-accessible
   STATUS     mandatory
   DESCRIPTION
     "This variable represents the index for the nS tables."
::= { nSRowStatusEntry 10 }

nSProvTable OBJECT-TYPE
   SYNTAX     SEQUENCE OF NSProvEntry
   ACCESS     not-accessible
   STATUS     mandatory
   DESCRIPTION
     "This group contains all of the provisioning data for the 
      NetworkSynchronization component."
::= { nS 10 }

nSProvEntry OBJECT-TYPE
   SYNTAX     NSProvEntry
   ACCESS     not-accessible
   STATUS     mandatory
   DESCRIPTION
     "An entry in the nSProvTable."
   INDEX {
      nSIndex }
::= { nSProvTable 1 }

NSProvEntry ::= SEQUENCE {
   nSPrimaryReference
      RowPointer,
   nSSecondaryReference
      RowPointer,
   nSTertiaryReference
      RowPointer }

nSPrimaryReference OBJECT-TYPE
   SYNTAX     RowPointer 
   ACCESS     read-write
   STATUS     mandatory
   DESCRIPTION
     "This component name is the port that is the preferred choice as the 
      reference for the network clock."
::= { nSProvEntry 1 }

nSSecondaryReference OBJECT-TYPE
   SYNTAX     RowPointer 
   ACCESS     read-write
   STATUS     mandatory
   DESCRIPTION
     "This component name is the port that is the second choice for the 
      reference for the network clock."
::= { nSProvEntry 2 }

nSTertiaryReference OBJECT-TYPE
   SYNTAX     RowPointer 
   ACCESS     read-write
   STATUS     mandatory
   DESCRIPTION
     "This component name is the port that is the third choice for the 
      reference for the network clock."
::= { nSProvEntry 3 }

nSStateTable OBJECT-TYPE
   SYNTAX     SEQUENCE OF NSStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { nS 11 }

nSStateEntry OBJECT-TYPE
   SYNTAX     NSStateEntry
   ACCESS     not-accessible
   STATUS     mandatory
   DESCRIPTION
     "An entry in the nSStateTable."
   INDEX {
      nSIndex }
::= { nSStateTable 1 }

NSStateEntry ::= SEQUENCE {
   nSAdminState
      INTEGER,
   nSOperationalState
      INTEGER,
   nSUsageState
      INTEGER }

nSAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { nSStateEntry 1 }

nSOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { nSStateEntry 2 }

nSUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { nSStateEntry 3 }

nSOperTable OBJECT-TYPE
   SYNTAX     SEQUENCE OF NSOperEntry
   ACCESS     not-accessible
   STATUS     mandatory
   DESCRIPTION
     "This group contains the operational attributes for the network clock 
      sync"
::= { nS 12 }

nSOperEntry OBJECT-TYPE
   SYNTAX     NSOperEntry
   ACCESS     not-accessible
   STATUS     mandatory
   DESCRIPTION
     "An entry in the nSOperTable."
   INDEX {
      nSIndex }
::= { nSOperTable 1 }

NSOperEntry ::= SEQUENCE {
   nSClockSyncState
      INTEGER,
   nSActiveReference
      RowPointer,
   nSStandbyReference
      RowPointer }

nSClockSyncState OBJECT-TYPE
   SYNTAX     INTEGER  {
                 freeRun(0),
                 synchronizing(1),
                 synchronized(3) }
   ACCESS     read-only
   STATUS     mandatory
   DESCRIPTION
     "When the clockSyncState is in the freeRun state, either no 
      reference have beed provisioned or none of the provisioned 
      references have been found to be valid. The Stratum-3 clock is 
      allowed to run freely at its last adjusted frequency.  When the 
      clockSyncState is in the synchronizing state, the Stratum-3 is 
      trying to synchronize in frequency to a valid provisioned reference. 
      This state should last approximately 1-2 minutes, provided the 
      reference is stable.  Once frequency synchronization is acheived, a 
      null phase is acquired and the clockSyncState enters the 
      synchronized state. In this state, both phase and frequency are 
      tracked and compensated for. This node is now ready to support 
      transparent data services."
::= { nSOperEntry 1 }

nSActiveReference OBJECT-TYPE
   SYNTAX     RowPointer 
   ACCESS     read-only
   STATUS     mandatory
   DESCRIPTION
     "Indicates the active 8Khz clock reference source"
::= { nSOperEntry 2 }

nSStandbyReference OBJECT-TYPE
   SYNTAX     RowPointer 
   ACCESS     read-only
   STATUS     mandatory
   DESCRIPTION
     "Indicates the standby 8Khz clock reference source which will be 
      selected if a failure is detected on the active source."
::= { nSOperEntry 3 }




-- 
-- Version and Compliance statements
-- 



-- Object-Group Statement:
-- A list of all current accessible leaf objects.

-- OBJECTS { timeServerIpAddress,
--           nSRowStatus,
--           timeServerPktSent,
--           nSPrimaryReference,
--           timeComponentName,
--           timeServerPktRecv,
--           timeSyncSourcesValue,
--           nSUsageState,
--           timeServerUsageState,
--           timeStorageType,
--           timeMainServer,
--           timeSyncStatus,
--           nSComponentName,
--           timeServerComponentName,
--           timeModuleTime,
--           nSStorageType,
--           timeServerStorageType,
--           timeServerPktValid,
--           nSClockSyncState,
--           timeOffset,
--           nSOperationalState,
--           timeServerOperationalState,
--           timeServerStatus,
--           timeServerXntpVersion,
--           nSActiveReference,
--           nSTertiaryReference,
--           timeRowStatus,
--           timeServerAdminState,
--           timeServerIpStack,
--           nSStandbyReference,
--           timeXntpVersion,
--           nSSecondaryReference,
--           timeServerPoll,
--           timeServerRowStatus,
--           nSAdminState,
--           timeServerStratum }
-- STATUS  mandatory
-- DESCRIPTION
--   "A list of all current accessible leaf objects."

timeGroup OBJECT IDENTIFIER ::= { timeMIB 1 }
timeGroupBE OBJECT IDENTIFIER ::= { timeGroup 5 }
timeGroupBE01 OBJECT IDENTIFIER ::= { timeGroupBE 2 }
timeGroupBE01A OBJECT IDENTIFIER ::= { timeGroupBE01 2 }



-- Agent-Capabilities Statement:

-- PRODUCT-RELEASE "Passport Release 7.0 Time."
-- STATUS          mandatory
-- DESCRIPTION     "Time MIB: MIB Version BE01A,
--                  Software Version BG00S4C."
-- SUPPORTS        Nortel-Magellan-Passport-TimeMIB
--    INCLUDES     { timeGroupBE01A }

timeCapabilities OBJECT IDENTIFIER ::= { timeMIB 3 }
timeCapabilitiesBE OBJECT IDENTIFIER ::= { timeCapabilities 5 }
timeCapabilitiesBE01 OBJECT IDENTIFIER ::= { timeCapabilitiesBE 2 }
timeCapabilitiesBE01A OBJECT IDENTIFIER ::= { timeCapabilitiesBE01 2 }





END
