USR-L2TP-MIB DEFINITIONS ::= BEGIN
   IMPORTS
           OBJECT-IDENTITY, OBJECT-TYPE, MODULE-IDENTITY,
           Integer32, IpAddress, Counter32, Unsigned32
                  FROM SNMPv2-SMI
           TruthValue, RowStatus
                  FROM SNMPv2-TC
           common, DisplayString, UsrConfigStatus
                  FROM USR-DEFINITIONS-MIB;
   usrL2TP MODULE-IDENTITY
            LAST-UPDATED "200208121820Z"
            ORGANIZATION "CommWorks Corporation, a 3Com Company"
            CONTACT-INFO "Customer Support"
            DESCRIPTION
                    "The commWorks enterprise defined MIB objects for L2TP"
--          REVISION "200208121820Z"
--          DESCRIPTION "Changed labels to clarify behaviour of
--                       usrL2tpPasswordEncryptStyle."
--          REVISION "200204051850Z"
--          DESCRIPTION " Added objects to SEQUENCE and corrected
--                        SNMPv2 formats."
           ::= { common 55 }
   usrL2TPGlobal  OBJECT-IDENTITY
           STATUS          current
           DESCRIPTION
              "The root of the L2TP global Object-Identifiers."
           ::= { usrL2TP 1 }
   usrL2TPConfigTable OBJECT-TYPE
           SYNTAX          SEQUENCE OF UsrL2TPConfigEntry
           MAX-ACCESS      not-accessible
           STATUS          current
           DESCRIPTION
              ""
           ::= { usrL2TPGlobal 1 }
   usrL2tpConfigEntry OBJECT-TYPE
           SYNTAX          UsrL2TPConfigEntry
           MAX-ACCESS      not-accessible
           STATUS          current
           DESCRIPTION
              "."
           INDEX           { usrL2tpConfigIndex }
           ::= { usrL2TPConfigTable 1 }
   UsrL2TPConfigEntry ::= SEQUENCE {
           usrL2tpConfigIndex
                   Integer32,
           usrL2tpLoadBalancing
                   TruthValue,
	   		usrL2tpDialOut
					OCTET STRING,
			usrL2tpLnsFlag INTEGER ,
		usrL2tpPasswordEncryptStyle INTEGER,
 	usrL2TPLcpRenegotiateAtLNS INTEGER,
    		usrL2tpAuthenticationRequiredOnOutgoingTunnels
					TruthValue,
           usrL2tpNumberOfEchoRetransmissions
                   Integer32(0..65535),
           usrL2tpEchoRetransmissionInterval
                   Integer32(0..65535)
		}
   usrL2tpConfigIndex      OBJECT-TYPE
           SYNTAX          Integer32
           MAX-ACCESS      read-only
           STATUS          current
           DESCRIPTION
              " A unique value for each l2tp protocol stack. "
           ::= { usrL2tpConfigEntry 1 }
   usrL2tpLoadBalancing  OBJECT-TYPE
           SYNTAX          TruthValue
           MAX-ACCESS      read-write
           STATUS          current
           DESCRIPTION
              "Defines If Load Balancing is enabled or not."
           DEFVAL          { true }
		 --CONFIGURABLE
           ::= { usrL2tpConfigEntry 2 }
   usrL2tpDialOut OBJECT-TYPE       
        SYNTAX  OCTET STRING (SIZE(0..32))
        MAX-ACCESS  read-write
        STATUS  current
        DESCRIPTION
                "This variable is set through the CLI when the user
                 manually issues a L2TP dial-out."      
        ::= { usrL2tpConfigEntry 3 }
   usrL2tpLnsFlag OBJECT-TYPE
      SYNTAX   INTEGER { enabled(1), disabled(2) }
      MAX-ACCESS   read-write
      STATUS   current     
      DESCRIPTION
             "Setting this object to a value of enabled(1) will enable
              the L2TP lns enable feature. Setting this object to
              disabled(2) will disable the L2TP LNS feature."
     --CONFIGURABLE
   ::= { usrL2tpConfigEntry 4 } 
    usrL2tpPasswordEncryptStyle OBJECT-TYPE
      SYNTAX   INTEGER { noSalt(1), withSalt(2) }
      MAX-ACCESS   read-write
      STATUS   current     
      DESCRIPTION
             "Original labels were Draft-3 and Draft-6. This value
              defines the encryption style for tunnel password as 
              retrieved from RADIUS. It indicates whether or not
              a salt or secret key value will be used to encrypt 
              the password."
	DEFVAL { noSalt }
     --CONFIGURABLE
   ::= { usrL2tpConfigEntry  5 }
	usrL2TPLcpRenegotiateAtLNS OBJECT-TYPE
	SYNTAX  INTEGER {
		enabled(1),                                        
		disabled(2)
		} 
	MAX-ACCESS   read-write
	STATUS   current
	DESCRIPTION
		"This flag is used to enable/disable LCP renegotiation
		for calls when doing proxy LCP on LNS"
	--CONFIGURABLE    
	::= { usrL2tpConfigEntry 6 }
    usrL2tpAuthenticationRequiredOnOutgoingTunnels   OBJECT-TYPE
           SYNTAX          TruthValue
           MAX-ACCESS      read-write
           STATUS          current
           DESCRIPTION
              "When set to a value of true(1) requires that all
              outgoing tunnels request tunnel authentication."
           DEFVAL          { true }
		 --CONFIGURABLE
           ::= { usrL2tpConfigEntry 7 }
   usrL2tpNumberOfEchoRetransmissions  OBJECT-TYPE
           SYNTAX          Integer32 (0..65535)
           MAX-ACCESS      read-write
           STATUS          current
           DESCRIPTION
              "This object defines the number of Hello retransmission's
              which the L2TP stack will attempt before assuming that
              the peer is no longer reachable. The default value for
              this object is five (5)."
           DEFVAL          { 5 }
		 --CONFIGURABLE
           ::= { usrL2tpConfigEntry 8 }
   usrL2tpEchoRetransmissionInterval   OBJECT-TYPE
           SYNTAX          Integer32(0..65535)
           MAX-ACCESS      read-write
           STATUS          current
           DESCRIPTION
              "This object defines the number of seconds between each
              retransmission."
           DEFVAL          { 10 }
		 --CONFIGURABLE
           ::= { usrL2tpConfigEntry 9 }
   usrL2tpTunnel OBJECT IDENTIFIER ::= {usrL2TP 2}
   usrL2tpTunnelQueryTable OBJECT-TYPE
           SYNTAX          SEQUENCE OF UsrL2tpTunnelQueryEntry
           MAX-ACCESS      not-accessible
           STATUS          current
           DESCRIPTION
              "A table containing the READ ONLY propietary extension
			   parameters for L2TP Tunnel MIB."
           ::= { usrL2tpTunnel 1 }
   usrL2tpTunnelQueryEntry OBJECT-TYPE
           SYNTAX          UsrL2tpTunnelQueryEntry
           MAX-ACCESS      not-accessible
           STATUS          current
           DESCRIPTION
              "  "
           INDEX           { usrL2tpTunnelLogicalStackIndex,
                             usrL2tpTunnelLocalControlTunnelId }
           ::= { usrL2tpTunnelQueryTable 1 }
   UsrL2tpTunnelQueryEntry ::= SEQUENCE {
           usrL2tpTunnelLogicalStackIndex
                   Integer32,
           usrL2tpTunnelLocalControlTunnelId
                   Integer32,
           usrL2tpTunnelSecurityLevel
                   INTEGER,
		usrL2tpTunnelDisconnect
                   Integer32}
    usrL2tpTunnelLogicalStackIndex OBJECT-TYPE
           SYNTAX          Integer32
           MAX-ACCESS      read-only     
           STATUS          current
           DESCRIPTION
              "This object contains a reference to the logical
              l2tp protocol stack and must be the same as the
              l2tpConfigIndex."
           ::= { usrL2tpTunnelQueryEntry 1 }  
   usrL2tpTunnelLocalControlTunnelId OBJECT-TYPE   
           SYNTAX          Integer32
           MAX-ACCESS      read-only      
           STATUS          current
           DESCRIPTION
              "This object contains the local tunnel Identifier."
           ::= { usrL2tpTunnelQueryEntry 2 }      
   usrL2tpTunnelSecurityLevel OBJECT-TYPE
           SYNTAX          INTEGER{
                                    none(0),
                                    control-Only(1),
                                    data-Only(2),
                                    both-Data-And-Control(3)
                                  }
           MAX-ACCESS      read-only
           STATUS          current
           DESCRIPTION
              "This field contains the security level 
              of the tunnel."
		   ::= {usrL2tpTunnelQueryEntry 3}
	usrL2tpTunnelDisconnect	OBJECT-TYPE
           SYNTAX          Integer32
           MAX-ACCESS      read-write  
           STATUS          current
           DESCRIPTION
              "This object is used to disconnect a specific tunnel."
           ::= { usrL2tpTunnelQueryEntry 4 }
	 usrL2tpSession OBJECT-IDENTITY      
          STATUS         current    
          DESCRIPTION               
             "The root of L2TP Session Module Object-identifiers."
          ::= { usrL2TP 3 }
   usrL2tpSessionTable OBJECT-TYPE    
           SYNTAX    SEQUENCE OF UsrL2tpSessionEntry
           MAX-ACCESS not-accessible
           STATUS current
           DESCRIPTION
              ""
           ::= { usrL2tpSession 1 }
   usrL2tpSessionEntry OBJECT-TYPE
           SYNTAX          UsrL2tpSessionEntry
           MAX-ACCESS      not-accessible
           STATUS          current 
           DESCRIPTION
              "."
           INDEX           { usrL2tpSessionLogicalStackIndex,
                           usrL2tpSessionTunnelID , usrL2tpSessionLocalCallID }
           ::= { usrL2tpSessionTable 1 }
   UsrL2tpSessionEntry ::= SEQUENCE {
	   usrL2tpSessionLogicalStackIndex
                   Integer32,
       usrL2tpSessionTunnelID
                   Integer32,
       usrL2tpSessionLocalCallID
                   Integer32,
		usrL2tpSessionDisconnect	
                   Integer32
				}
   usrL2tpSessionLogicalStackIndex OBJECT-TYPE
           SYNTAX          Integer32
           MAX-ACCESS      read-only
           STATUS          current
           DESCRIPTION
              "This object contains a reference to the logical
              l2tp protocol stack and must be the same as the
              l2tpConfigIndex and l2tpTunelLogicalStackIndex."
           ::= { usrL2tpSessionEntry 1 }
   usrL2tpSessionTunnelID OBJECT-TYPE
           SYNTAX          Integer32
           MAX-ACCESS      read-only
           STATUS          current
           DESCRIPTION
              "This object contains the control Channel Tunnel
              identifier for this session"
           ::= { usrL2tpSessionEntry 2 }
   usrL2tpSessionLocalCallID  OBJECT-TYPE
           SYNTAX          Integer32
           MAX-ACCESS      read-only
           STATUS          current
           DESCRIPTION
              "This object contains the local call identifier
              for the session.  "
           ::= { usrL2tpSessionEntry 3 }
	    usrL2tpSessionDisconnect OBJECT-TYPE
           SYNTAX          Integer32
           MAX-ACCESS      read-write
           STATUS          current
           DESCRIPTION
              "This object is used to disconnect a specific tunnel."
           ::= { usrL2tpSessionEntry 4 }
	usrL2tpHostTable OBJECT-TYPE
        	SYNTAX SEQUENCE OF UsrL2tpHostEntry
        	MAX-ACCESS not-accessible
        	STATUS current
        	DESCRIPTION
                "The table of L2TP LNSs. "
			::= { usrL2TP 4 }
	usrL2tpHostEntry OBJECT-TYPE
		        SYNTAX UsrL2tpHostEntry
	        	MAX-ACCESS not-accessible
	        	STATUS current
	        	DESCRIPTION
	              "A (conceptual) entry for one pptp Host."
	        	INDEX { usrL2tpHostIndex }
				::= { usrL2tpHostTable 1 }
	UsrL2tpHostEntry ::= SEQUENCE {
	        usrL2tpHostIndex       Integer32,
	        usrL2tpHostAddress     IpAddress,
	        usrL2tpHostStatus      RowStatus,
	        usrL2tpSharedSecret    OCTET STRING,
	        usrL2tpSharedSecretStatus    TruthValue,
			usrL2tpSecurityLevel	INTEGER	
	        }
	usrL2tpHostIndex OBJECT-TYPE
	        SYNTAX          Integer32
	        MAX-ACCESS      not-accessible
	        STATUS          current
	        DESCRIPTION
	              "The logical identifier of the Host Table. "
			::= { usrL2tpHostEntry 1 }
	usrL2tpHostAddress OBJECT-TYPE
	        SYNTAX          IpAddress
	        MAX-ACCESS      read-write
	        STATUS          current
	        DESCRIPTION
	                "The specified or resolved ip address of the named Host. "
	        --CONFIGURABLE
			::= { usrL2tpHostEntry 2 }
	usrL2tpHostStatus OBJECT-TYPE
	        SYNTAX          RowStatus
	        MAX-ACCESS      read-write
	        STATUS          current
	        DESCRIPTION
	            "The status of this row of the Host Table. "
	        --CONFIGURABLE
			::= { usrL2tpHostEntry 3 }
	 usrL2tpSharedSecret OBJECT-TYPE
                SYNTAX          OCTET STRING  (SIZE(0..128))
                MAX-ACCESS      read-write
                STATUS          current
                DESCRIPTION
                      "The Shared Secret For This Host. "
		 --CONFIGURABLE
                        ::= { usrL2tpHostEntry 4 }
	 usrL2tpSharedSecretStatus OBJECT-TYPE
                SYNTAX          TruthValue 
                MAX-ACCESS      read-write
                STATUS          current
                DESCRIPTION
                      "The Shared Secret Status For This Host. "
		 --CONFIGURABLE
                        ::= { usrL2tpHostEntry 5 }
     usrL2tpSecurityLevel OBJECT-TYPE    
                SYNTAX          INTEGER{
                                    none(0),
                                    control-Only(1),
                                    data-Only(2),
                                    both-Data-And-Control(3)
                                  }
                MAX-ACCESS      read-write
                STATUS          current
                DESCRIPTION   
                      "The Security Level For This Host. "
		 --CONFIGURABLE
                        ::= { usrL2tpHostEntry 6 }
	usrL2TPConfigFileName OBJECT-TYPE
          SYNTAX      DisplayString
          MAX-ACCESS  read-only
          STATUS      current
          DESCRIPTION
          "The name of a ConfigFile to read/write permanent database records.
           If the value of this object is an empty string, then the
           L2TP process uses the default name `@file://L2tpProcess.cfg'. "
          ::= { usrL2TP 5 }
    usrL2TPCFMStatusFlag  OBJECT-TYPE
          SYNTAX         UsrConfigStatus
          MAX-ACCESS     read-write
          STATUS         current
          DESCRIPTION
                 "CFM Config Flag"
          ::= { usrL2TP 6 }                   
   -- mr5579 crigg - New L2TP stats for Statistics and MIBs v0.5
   usrL2tpStatsTable OBJECT-TYPE
           SYNTAX          SEQUENCE OF UsrL2tpStatsEntry
           MAX-ACCESS      not-accessible
           STATUS          current
           DESCRIPTION
              "A table containing a single row containing new
	       L2TP counters"
          ::= { usrL2TP 7 }                   
   usrL2tpStatsEntry OBJECT-TYPE
           SYNTAX          UsrL2tpStatsEntry
           MAX-ACCESS      not-accessible
           STATUS          current
           DESCRIPTION
              "  "
           INDEX           { usrL2tpStatsIndex }
           ::= { usrL2tpStatsTable 1 }
   UsrL2tpStatsEntry ::= SEQUENCE {
   	usrL2tpStatsIndex		  Integer32,
   	usrL2tpStatsTunnelSetupAttempts   Counter32,
   	usrL2tpStatsTunnelSetupCompleteds Counter32,
   	usrL2tpStatsTunnelSetupFaileds    Counter32,
   	usrL2tpStatsCountersResetTime     Unsigned32
	}                   
   usrL2tpStatsIndex          OBJECT-TYPE
           SYNTAX          Integer32
           MAX-ACCESS      read-only
           STATUS          current
           DESCRIPTION
              " Should be the same value as l2tpConfigIndex and l2tpStatsIndex
		to reference the same logical l2tp protocol stack. 
		On HiPer ARC, this index is always 1"
           ::= { usrL2tpStatsEntry 1 }
   usrL2tpStatsTunnelSetupAttempts             OBJECT-TYPE
           SYNTAX          Counter32
           MAX-ACCESS      read-only
           STATUS          current
           DESCRIPTION
              "Count of L2TP tunnel setup attempts.
	       Discontinuity is indicated by usrL2tpStatsCountersResetTime."
	   REFERENCE
	      "1051 PRD 3G R2.0 v1.2 sec 4.5.2.1"
           ::= { usrL2tpStatsEntry 2}
   usrL2tpStatsTunnelSetupCompleteds           OBJECT-TYPE
           SYNTAX          Counter32
           MAX-ACCESS      read-only
           STATUS          current
           DESCRIPTION
              "Count of L2TP tunnel setups completed  (L2TP tunnel
	       setup attempts that reached the established state).
	       Discontinuity is indicated by usrL2tpStatsCountersResetTime."
	   REFERENCE
	      "1051 PRD 3G R2.0 v1.2 sec 4.5.2.1"
           ::= { usrL2tpStatsEntry 3}
   usrL2tpStatsTunnelSetupFaileds              OBJECT-TYPE
           SYNTAX          Counter32
           MAX-ACCESS      read-only
           STATUS          current
           DESCRIPTION
              "Count of L2TP tunnel setups that failed  (L2TP tunnel
	       setup attempts that terminated without reaching the
	       established state).
	       Discontinuity is indicated by usrL2tpStatsCountersResetTime."
	   REFERENCE
	      "1051 PRD 3G R2.0 v1.2 sec 4.5.2.1"
           ::= { usrL2tpStatsEntry 4}
   usrL2tpStatsCountersResetTime              OBJECT-TYPE
           SYNTAX          Unsigned32 
           MAX-ACCESS      read-write
           STATUS          current
           DESCRIPTION
              "Reading:
		   Time the L2TP statistics counters were last reset.
	       Resetting counters causes a discontinuity in the monotonically 
	       increasing value of the counters.  Management stations that 
	       sample these counters need also to sample this object so that 
	       they can know that a discontinuity occured with respect to the
	       previous sample.  Its value is number of seconds since EPOCH.
	       EPOCH is seconds since 00:00:00 UTC, Jan 1, 1970.  
	       Writing:
		   Writing 0 causes the following global L2TP stats to be reset
		   to 0:
           		l2tpStatsFailedAuthentications
           		l2tpStatsMalformedPackets
           		l2tpStatsControlTunnelRecvPackets
           		l2tpStatsControlTunnelWithDataRecvPackets
          		l2tpStatsControlTunnelWithoutDataRecvPackets
          		l2tpStatsProcessedControlTunnelRecvPackets
           		l2tpStatsInSequenceControlTunnelRecvPackets
           		l2tpStatsOutSequenceControlTunnelRecvPackets
           		l2tpStatsInOrderControlTunnelRecvPackets
           		l2tpStatsOutOfOrderControlTunnelRecvPackets
           		l2tpStatsFlowDiscardedControlTunnelRecvPackets
           		l2tpStatsOutOfOrderDiscardedControlTunnelRecvPackets
           		l2tpStatsControlTunnelSendPackets
           		l2tpStatsControlTunnelWithdataSendPackets
           		l2tpStatsControlTunnelWithoutdataSendPackets
           		l2tpStatsControlTunnelFlowControlTimeouts
           		l2tpStatsLocalControlTunnelFlowControlEnables
           		l2tpStatsRemoteControlTunnelFlowControlEnables
           		l2tpStatsControlTunnelReassemblyTimeouts
           		l2tpStatsDataTunnelRecvPackets
           		l2tpStatsDataTunnelWithdataRecvPackets
           		l2tpStatsDataTunnelWithoutdataRecvPackets
           		l2tpStatsProcessedDataTunnelRecvPackets
           		l2tpStatsInSequenceDataTunnelRecvPackets
           		l2tpStatsOutSequenceDataTunnelRecvPackets
           		l2tpStatsInOrderDataTunnelRecvPackets
           		l2tpStatsOutOfOrderDataTunnelRecvPackets
           		l2tpStatsFlowDiscardedDataTunnelRecvPackets
           		l2tpStatsOutOfOrderDiscardedDataTunnelRecvPackets
           		l2tpStatsDataTunnelSendPackets
           		l2tpStatsDataTunnelWithdataSendPackets
           		l2tpStatsDataTunnelWithoutdataSendPackets
           		l2tpStatsDataTunnelFlowControlTimeouts
           		l2tpStatsLocalDataTunnelFlowControlEnables
           		l2tpStatsRemoteDataTunnelFlowControlEnables
           		l2tpStatsDataTunnelReassemblyTimeouts
			usrL2tpStatsTunnelSetupAttempts
			usrL2tpStatsTunnelSetupCompleteds
			usrL2tpStatsTunnelSetupFaileds
		    Writing other values are rejected.
		"
           ::= { usrL2tpStatsEntry 5}
END
