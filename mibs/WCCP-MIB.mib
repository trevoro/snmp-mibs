WCCP-MIB DEFINITIONS ::= BEGIN

	IMPORTS
		MODULE-IDENTITY,OBJECT-TYPE,Integer32,Counter32,Counter64
			FROM SNMPv2-SMI
		TEXTUAL-CONVENTION,TimeStamp,TruthValue,DisplayString
			FROM SNMPv2-TC
		MODULE-COMPLIANCE,OBJECT-GROUP
			FROM SNMPv2-CONF
		blueCoatMgmt
			 FROM BLUECOAT-MIB;

	deviceWccpMIB MODULE-IDENTITY
	LAST-UPDATED "0208280300Z"
	ORGANIZATION "Blue Coat Systems, Inc."
	CONTACT-INFO
	"support@bluecoat.com"
	DESCRIPTION
		"The deviceWccpMIB is used to monitor
		the status of the device's WCCP."
	::= { blueCoatMgmt 5 }

-- textual conventions

WccpServiceType ::= TEXTUAL-CONVENTION
	STATUS		current
	DESCRIPTION
		"Indicates the type of WCCP service being used.

		standard		standard or well known service is being used.
		dynamic			dynamic service is being used.
		unknown			cannot determine the type of service being used."

		SYNTAX INTEGER {
			standard(1),
			dynamic(2),
			unknown(3)
		}

WccpVersion ::= TEXTUAL-CONVENTION
	STATUS		current
	DESCRIPTION
		"Indicates the version of WCCP being used for a service.

		version1		WCCP version 1 being used for the service.
		version2		WCCP version 2 being used for the service.
		unknown			unknown version."

		SYNTAX INTEGER {
			version1(1),
			version2(2),
			unknown(3)
		}

deviceWccpEnabled OBJECT-TYPE
	SYNTAX		TruthValue
	MAX-ACCESS	read-only
	STATUS		current
	DESCRIPTION
		"This variable show whether WCCP is enabled or not."
	::= { deviceWccpMIB 1 }

deviceWccpMIBObjects
	OBJECT IDENTIFIER ::= { deviceWccpMIB 2 }

-- textual conventions

--
-- MIB variables
--

deviceWccpValues
	OBJECT IDENTIFIER ::= { deviceWccpMIBObjects 1 }

--
-- caheWccpValueTable
--

deviceWccpValueTable OBJECT-TYPE
	SYNTAX		SEQUENCE OF DeviceWccpValueEntry
	MAX-ACCESS	not-accessible
	STATUS		current
	DESCRIPTION
		"Table of WCCP services."
	::= { deviceWccpValues 1 }

deviceWccpValueEntry OBJECT-TYPE
	SYNTAX		DeviceWccpValueEntry
	MAX-ACCESS	not-accessible
	STATUS		current
	DESCRIPTION
		"A deviceWccpValueTable entry describes the
		status of a WCCP service."
	INDEX		{ deviceWccpIndex }
	::= { deviceWccpValueTable 1 }

DeviceWccpValueEntry ::= SEQUENCE {
	deviceWccpIndex				INTEGER,
	deviceWccpServiceID			Integer32,
	deviceWccpServiceType		WccpServiceType,
	deviceWccpServiceVersion		WccpVersion,
	deviceWccpPacketsRedir		Counter64,
	deviceWccpPacketsLowRedir	Counter32,
	deviceWccpBytesRedir			Counter64,
	deviceWccpBytesLowRedir		Counter32
	}

deviceWccpIndex	OBJECT-TYPE
	SYNTAX		INTEGER (1..2147483647)
	MAX-ACCESS	not-accessible
	STATUS		current
	DESCRIPTION
		"An arbitrary value which uniquely
		identifies the WCCP service."
	::= { deviceWccpValueEntry 1 }

deviceWccpServiceID OBJECT-TYPE
	SYNTAX		Integer32
	MAX-ACCESS	read-only
	STATUS		current
	DESCRIPTION
		"This variable indicates WCCP's service id."
	::= { deviceWccpValueEntry 2 }

deviceWccpServiceType OBJECT-TYPE
	SYNTAX		WccpServiceType
	MAX-ACCESS	read-only
	STATUS		current
	DESCRIPTION
		"This variable indicates WCCP's service type."
	::= { deviceWccpValueEntry 3 }

deviceWccpServiceVersion OBJECT-TYPE
	SYNTAX		WccpVersion
	MAX-ACCESS	read-only
	STATUS		current
	DESCRIPTION
		"This variable indicates the WCCP service's version."
	::= { deviceWccpValueEntry 4 }

deviceWccpPacketsRedir OBJECT-TYPE
	SYNTAX		Counter64
	MAX-ACCESS	read-only
	STATUS		current
	DESCRIPTION
		"This variable indicates the how many WCCP
		packets have been redirected."
	::= { deviceWccpValueEntry 5 }

deviceWccpPacketsLowRedir OBJECT-TYPE
	SYNTAX		Counter32
	MAX-ACCESS	read-only
	STATUS		current
	DESCRIPTION
		"This variable indicates the how many WCCP
		packets have been redirected - lower 32 bits."
	::= { deviceWccpValueEntry 6 }

deviceWccpBytesRedir OBJECT-TYPE
	SYNTAX		Counter64
	MAX-ACCESS	read-only
	STATUS		current
	DESCRIPTION
		"This variable indicates how many WCCP
		bytes have been redirected."
	::= { deviceWccpValueEntry 7 }

deviceWccpBytesLowRedir OBJECT-TYPE
	SYNTAX		Counter32
	MAX-ACCESS	read-only
	STATUS		current
	DESCRIPTION
		"This variable indicates how many WCCP
		bytes have been redirected - lower 32 bits."
	::= { deviceWccpValueEntry 8 }

END
