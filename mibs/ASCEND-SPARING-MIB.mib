-- $Id: sparing.mib,v 29.2.4.2 2000/02/02 23:30:31 ofatoore Exp $
--
--			Sparing MIB
--
--			Lucent Technologies
--			1701 Harbor Bay Pkwy
--			Alameda, CA 94502
--			+1 510 769 6001
--			info@ascend.com
--
--		Copyright (c) 1993-1999 Lucent Technologies
--		All rights reserved.
--
--	Overview:
--
--	Sparing MIB is part of the Ascend Enterprise MIB, it reports
--	current status of the trunk ports and line interface modules
--	in the system.
--
--      The sparing MIB is first available for the Stinger platform 
--      in TAOS 8.0
--
-- 26 Jul 99	of	Initially created


ASCEND-SPARING-MIB DEFINITIONS ::= BEGIN

    IMPORTS
        TimeTicks
	    FROM RFC1155-SMI
        OBJECT-TYPE
            FROM RFC-1212
        Counter32, Integer32
            FROM SNMPv2-SMI
        sparingGroup
              FROM ASCEND-MIB;
	--
	-- Ascend sparing Group
	--
	-- The sparingGroup provides statistics and state information
	-- for slots and interfaces with sparing support.

    sparingGlobalGroup	OBJECT IDENTIFIER ::= { sparingGroup 1 }
    sparingSlotGroup	OBJECT IDENTIFIER ::= { sparingGroup 2 }
    sparingIfGroup	OBJECT IDENTIFIER ::= { sparingGroup 3 }

--    SparingModusMode ::= TEXTUAL-CONVENTION
--  	STATUS          current
--        DESCRIPTION     "Possible sparing operation modes"
--        SYNTAX		Integer32 {
-- the sparing mode is unknown 
--                            unknown(1),   
-- sparing disabled 
--                            disable(2),   
-- manual sparing
--                            manual(3),    
-- automatic sparing
--                            automatic(4)  
--			}

--    SparingStatusStates ::= TEXTUAL-CONVENTION
--	STATUS          current
--        DESCRIPTION     "Possible sparing states"
--        SYNTAX		Integer32 { 
-- not currently used in sparing
--                            standby(1),   
-- failed to operate
--                            fault(2),     
-- actively being used in sparing
--                            active(3)     
--			}

--    SparingChangeReason ::= TEXTUAL-CONVENTION
--	STATUS          current
--        DESCRIPTION     "Reason for which a sparing change occurred"
--        SYNTAX		Integer32 { 
-- 
--                            unknown(1)     
-- manual configuration
--                            manual(2),     
-- automatic failure detection
--                            automatic(3),  
-- manual test configuration
--                            test(4)        
--			}

    sparingSlotMode     OBJECT-TYPE
--      SYNTAX          SparingModusMode
        SYNTAX		INTEGER { 
                            unknown(1),   -- the sparing mode is unknown
                            disable(2),   -- sparing disabled 
                            manual(3),    -- manual sparing
                            automatic(4)  -- automatic sparing
			}
        ACCESS          read-only
        STATUS          mandatory
        DESCRIPTION     "The administrative mode of the overall slot 
                         sparing function"
        ::= { sparingSlotGroup 1 }

    --
    --  Slot SparingTable
    --
    --  This table reports current LIM sparing status of a particular slot.
    --
    sparingSlotTable	OBJECT-TYPE
	SYNTAX		SEQUENCE OF SparingSlotEntry
	ACCESS		not-accessible
	STATUS		mandatory
	DESCRIPTION	"A table of slots with enabled sparing functionality.
                         The slot is represented by a row in the table if its
                         sparing capability is one of two:
                         - being a spare
                         - being able to be backed up by spare slot"
	::= { sparingSlotGroup 2 }

    sparingSlotEntry	OBJECT-TYPE
	SYNTAX		SparingSlotEntry
	ACCESS		not-accessible
	STATUS		mandatory
	DESCRIPTION	"Entry holding information about an individual slot 
                         that has sparing support "
	INDEX		{ sparingSlotPrimaryIndex, sparingSlotSparingIndex }
        ::= { sparingSlotTable 1 }

    SparingSlotEntry ::=
	SEQUENCE {
            sparingSlotPrimaryIndex     Integer32,
            sparingSlotSparingIndex     Integer32,
            sparingSlotStatus           INTEGER,
--          sparingSlotStatus           SparingStatusStates,
            sparingSlotLastStatusChange TimeTicks,
            sparingSlotLastChangeReason INTEGER,
--          sparingSlotLastChangeReason SparingChangeReason,
	    sparingSlotStatusChangeCount Counter32
	}

    sparingSlotPrimaryIndex	OBJECT-TYPE
	SYNTAX		Integer32
	ACCESS		read-only
	STATUS		mandatory
	DESCRIPTION	"The slot number of the module being backed up by
                         a spare. The index is the same as slotIndex."

	::= { sparingSlotEntry 1 }

    sparingSlotSparingIndex	OBJECT-TYPE
	SYNTAX		Integer32
	ACCESS		read-only
	STATUS		mandatory
	DESCRIPTION	"The slot number of the slot that is the backup for
                         sparingSlotPrimaryIndex. The index is the same as
                         slotIndex."
	::= { sparingSlotEntry 2 }

    sparingSlotStatus   OBJECT-TYPE
--	SYNTAX		SparingStatusStates
        SYNTAX          INTEGER {
                          standby(1),  -- operating in normal mode
			  fault(2),    -- failed, no spare available
                          active(3)    -- failed, spare is active
			}
	ACCESS		read-only
	STATUS		mandatory
	DESCRIPTION	"The current sparing state."
	::= { sparingSlotEntry 3 }

    sparingSlotLastStatusChange	OBJECT-TYPE
	SYNTAX		TimeTicks
	ACCESS		read-only
	STATUS		mandatory
	DESCRIPTION	"System uptime at the time of the last 
                         sparingSlotStatus change. This value is 0 if no change
                         of sparingSlotStatus was observed since reboot."
	::= { sparingSlotEntry 4 }

    sparingSlotLastChangeReason	OBJECT-TYPE
--	SYNTAX		SparingChangeReason
        SYNTAX		INTEGER { 
                            unknown(1),
                            manual(2),    -- manual configuration
                            automatic(3), -- automatic failure detection
                            test(4)       -- manual test configuration
			}
	ACCESS		read-only
	STATUS		mandatory
	DESCRIPTION	"The reason for last change in sparingSlotStatus."
	::= { sparingSlotEntry 5 }

    sparingSlotStatusChangeCount   OBJECT-TYPE
	SYNTAX		Counter32
	ACCESS		read-only
	STATUS		mandatory
	DESCRIPTION	"The number of changes in sparingSlotStatus since
                         the last restart of the subsystem."
	::= { sparingSlotEntry 6 }


    --
    --  Interface SparingTable
    --
    --  This table reports current LIM sparing status of a particular interface.
    --
    sparingIfTable	OBJECT-TYPE
	SYNTAX		SEQUENCE OF SparingIfEntry
	ACCESS		not-accessible
	STATUS		mandatory
	DESCRIPTION	"A table of interfaces with enabled sparing functionality.
                         The interface is represented by a row in the table if its
                         sparing capability is one of two:
                         - being a spare
                         - being able to be backed up by spare interface."
	::= { sparingIfGroup 2 }

    sparingIfEntry	OBJECT-TYPE
	SYNTAX		SparingIfEntry
	ACCESS		not-accessible
	STATUS		mandatory
	DESCRIPTION	"Entry holding information about an individual interface that
                         has sparing support"
	INDEX		{ sparingIfPrimaryIndex, sparingIfSparingIndex }
	::= { sparingIfTable 1 }

    SparingIfEntry ::=
	SEQUENCE {
            sparingIfPrimaryIndex      Integer32,
            sparingIfSparingIndex      Integer32,
            sparingIfStatus            INTEGER,
--          sparingIfStatus            SparingStatusStates,
            sparingIfLastStatusChange  TimeTicks,
            sparingIfLastChangeReason  INTEGER,
--          sparingIfLastChangeReason  SparingChangeReason,
	    sparingIfStatusChangeCount Counter32
	}

    sparingIfPrimaryIndex	OBJECT-TYPE
	SYNTAX		Integer32
	ACCESS		read-only
	STATUS		mandatory
	DESCRIPTION	"The interface number being backed up by a spare.
                         The sparingIfPrimaryIndex is the same as ifIndex."
	::= { sparingIfEntry 1 }

    sparingIfSparingIndex	OBJECT-TYPE
	SYNTAX		Integer32
	ACCESS		read-only
	STATUS		mandatory
	DESCRIPTION	"The interface number of the slot that is the backup
                         for sparingIfPrimaryIndex.
                         The sparingIfSparingIndex is the same as ifIndex."
	::= { sparingIfEntry 2 }

    sparingIfStatus   OBJECT-TYPE
--	SYNTAX		SparingStatusStates
        SYNTAX          INTEGER {
                          standby(1),  -- operating in normal mode
			  fault(2),    -- failed, no spare available
                          active(3)    -- failed, spare is active
			}
	ACCESS		read-only
	STATUS		mandatory
	DESCRIPTION	"The current sparing state."
	::= { sparingIfEntry 3 }

    sparingIfLastStatusChange	OBJECT-TYPE
	SYNTAX		TimeTicks
	ACCESS		read-only
	STATUS		mandatory
	DESCRIPTION	"System uptime at the time of the last 
                         sparingIfStatus change. This value is 0 if no change
                         of sparingIfStatus was observed since reboot."
	::= { sparingIfEntry 4 }

    sparingIfLastChangeReason	OBJECT-TYPE
--	SYNTAX		SparingChangeReason
        SYNTAX		INTEGER { 
                            unknown(1),
                            manual(2),   -- manual configuration
                            automatic(3) -- automatic failure detection
			}

	ACCESS		read-only
	STATUS		mandatory
	DESCRIPTION	"The reason for last change in sparingIfStatus."
	::= { sparingIfEntry 5 }

    sparingIfStatusChangeCount   OBJECT-TYPE
	SYNTAX		Counter32
	ACCESS		read-only
	STATUS		mandatory
	DESCRIPTION	"The number of changes in sparingIfStatus since
                         the last restart of the subsystem."
	::= { sparingIfEntry 6 }
 
END
