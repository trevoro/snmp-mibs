-- MIB generated by miftomib version 1.0a

ADAPTECCIOSTANDARDGROUPMIFDEFINITION-MIB DEFINITIONS ::= BEGIN

-- This file is the Adaptec CI/O MIF.

IMPORTS
    OBJECT-TYPE
    FROM RFC-1212
    Counter, enterprises
    FROM RFC1155-SMI
    DisplayString
    FROM RFC1213-MIB;

DmiCounter			::= Counter
DmiDate				::= INTEGER
DmiInteger			::= INTEGER
DmiInteger64		::= INTEGER
DmiInteger64X		::= INTEGER (-18446744073709551615..18446744073709551615)
DmiOctetstring		::= OCTET STRING
DmiDisplaystring	::= DisplayString
DmiDateX			::= OCTET STRING (SIZE (28))
DmiComponentIndex	::= INTEGER

adaptec             	OBJECT IDENTIFIER ::= {enterprises 795}
storagemanagement     	OBJECT IDENTIFIER ::= {adaptec 2}
isc18           	OBJECT IDENTIFIER ::= {storagemanagement 52}
dmtfGroups          	OBJECT IDENTIFIER ::= {isc18 1}

SComponentid ::= SEQUENCE {
	a1Manufacturer                          	DmiDisplaystring,
	a1Product                               	DmiDisplaystring,
	a1Version                               	DmiDisplaystring,
	a1SerialNumber                          	DmiDisplaystring,
	a1Installation                          	DmiDate,
	a1Verify                                	DmiInteger
}

tComponentid OBJECT-TYPE
	SYNTAX 		SEQUENCE OF SComponentid
	ACCESS		not-accessible
	STATUS		mandatory
	DESCRIPTION	"This group defines the attributes common to all components.
This groupis required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDate
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is stillinstalled and working."
	::= {eComponentid 6}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI to
SNMP translati
n."
	::= {dmtfGroups 99}

eMiftomib OBJECT-TYPE
	SYNTAX		SMiftomib
	ACCESS		not-accessible
	STATUS		mandatory
	DESCRIPTION	""
	INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB Object Identifier that corresponds to this MIF"
	::= {eMiftomib 2}

a99DisableTrap OBJECT-TYPE
	SYNTAX		DmiInteger
	ACCESS		read-write
	STATUS		mandatory
	DESCRIPTION	"This attribute can be changed to disable sending of traps
from this component"
	::= {eMiftomib 3}

SStorageDevices ::= SEQUENCE {
	a7001StorageDeviceIndex                 	DmiInteger,
	a7001Type                               	DmiInteger,
	a7001TypeDescription                    	DmiDisplaystring,
	a7001Sub-identifier                     	DmiDisplaystring,
	a7001MediaDataBlockSize                 	DmiInteger,
	a7001FormattedMediaCapacity             	DmiInteger64,
	a7001RemovableDevice                    	DmiInteger,
	a7001DeviceLoaded                       	DmiInteger,
	a7001RemovableMedia                     	DmiInteger,
	a7001MediaLoaded                        	DmiInteger,
	a7001Compression                        	DmiInteger,
	a7001Encryption                         	DmiInteger
}

tStorageDevices OBJECT-TYPE
	SYNTAX		SEQUENCE OF SStorageDevices
	ACCESS		not-accessible
	STATUS		mandatory
	DESCRIPTION	"This group defines the mass storage devices in this system."
	::= {dmtfGroups 7001}

eStorageDevices OBJECT-TYPE
	SYNTAX		SStorageDevices
	ACCESS		not-accessible
	STATUS		mandatory
	DESCRIPTION	""
	INDEX		{DmiComponentIndex, a7001StorageDeviceIndex}
	::= {tStorageDevices 1}

a7001StorageDeviceIndex OBJECT-TYPE
	SYNTAX		DmiInteger
	ACCESS		read-only
	STATUS		mandatory
	DESCRIPTION	"An index into the storage device table."
	::= {eStorageDevices 1}

a7001Type OBJECT-TYPE
	SYNTAX		INTEGER {
		vOther                                  	(1),
		vUnknown                                	(2),
		vRigidDiskDrive                         	(3),
		vFlexibleDisketteDrive                  	(4),
		vOpticalWrite-onceread-manyWormDrive    	(6),
		vMagneto-opticalDrive                   	(7),
		vCompactDiskDrive                       	(8),
		vFlashDisk                              	(9),
		vCartridgeRigidDiskDrive                	(10),
		vOpticalFloppyDrive                     	(11),
		vTapeDrive                              	(12),
		vSolidState                             	(13),
		vMediaChanger                           	(14),
		vDigitalVersatileDiskDvdDrive           	(15),
		vDigitalVersatileDiskDvdRamDrive        	(16)
	}
	ACCESS		read-only
	STATUS		mandatory
	DESCRIPTION	"The type of this mass storage device.  If 'Other' is used,
then the Type Description attribute shall be used."
	::= {eStorageDevices 2}

a7001TypeDescription OBJECT-TYPE
	SYNTAX		DmiDisplaystring
	ACCESS		read-only
	STATUS		mandatory
	DESCRIPTION	"A longer description of the storage device.  For example:
 3.5 inch flexible diskette drive using diskettes with a maximum capacity
of 1.44MB.  If 'Other' was specified above, then this field shall be used.
 Otherwise, the contents of this optional field shall not contradict the
Storage Device Type specified above."
	::= {eStorageDevices 3}

a7001Sub-identifier OBJECT-TYPE
	SYNTAX		DmiDisplaystring
	ACCESS		read-only
	STATUS		mandatory
	DESCRIPTION	"The sub-identifier for this storage device (e.g., the device's
SCSI logical unit number.)"
	::= {eStorageDevices 4}

a7001MediaDataBlockSize OBJECT-TYPE
	SYNTAX		DmiInteger
	ACCESS		read-only
	STATUS		mandatory
	DESCRIPTION	"The size in bytes of the data blocks used on the storage
media.  If the media block size is unknown or not consistent across the media,
then this value shall be zero."
	::= {eStorageDevices 5}

a7001FormattedMediaCapacity OBJECT-TYPE
	SYNTAX		DmiInteger64
	ACCESS		read-only
	STATUS		mandatory
	DESCRIPTION	"The total size in kbytes of this storage media after it has
been formatted."
	::= {eStorageDevices 6}

a7001RemovableDevice OBJECT-TYPE
	SYNTAX		INTEGER {
		vFalse                                  	(0),
		vTrue                                   	(1),
		vUnknown                                	(2)
	}
	ACCESS		read-only
	STATUS		mandatory
	DESCRIPTION	"If true, then this storage device is removable (e.g.:  PCMCIA
device)."
	::= {eStorageDevices 7}

a7001DeviceLoaded OBJECT-TYPE
	SYNTAX		INTEGER {
		vFalse                                  	(0),
		vTrue                                   	(1),
		vUnknown                                	(2)
	}
	ACCESS		read-only
	STATUS		mandatory
	DESCRIPTION	"If true, then the storage device is loaded.  If the device
is not removable, then this value shall be 'TRUE'."
	::= {eStorageDevices 8}

a7001RemovableMedia OBJECT-TYPE
	SYNTAX		INTEGER {
		vFalse                                  	(0),
		vTrue                                   	(1),
		vUnknown                                	(2)
	}
	ACCESS		read-only
	STATUS		mandatory
	DESCRIPTION	"If true, then the media in this storage device is removable."
	::= {eStorageDevices 9}

a7001MediaLoaded OBJECT-TYPE
	SYNTAX		INTEGER {
		vFalse                                  	(0),
		vTrue                                   	(1),
		vUnknown                                	(2)
	}
	ACCESS		read-only
	STATUS		mandatory
	DESCRIPTION	"If true, the media in this storage device is loaded.  If
the media is not removable, then this value shall be 'TRUE' "
	::= {eStorageDevices 10}

a7001Compression OBJECT-TYPE
	SYNTAX		INTEGER {
		vFalse                                  	(0),
		vTrue                                   	(1),
		vUnknown                                	(2)
	}
	ACCESS		read-only
	STATUS		mandatory
	DESCRIPTION	"If true, the storage device supports compression."
	::= {eStorageDevices 11}

a7001Encryption OBJECT-TYPE
	SYNTAX		INTEGER {
		vFalse                                  	(0),
		vTrue                                   	(1),
		vUnknown                                	(2)
	}
	ACCESS		read-only
	STATUS		mandatory
	DESCRIPTION	"If true, the storage device supports encryption."
	::= {eStorageDevices 12}

SStorageDevicesEvents ::= SEQUENCE {
	a7002StorageDevicesEventType            	DmiInteger,
	a7002EventSeverity                      	DmiInteger,
	a7002EventIsStateBased                  	DmiInteger,
	a7002EventStateKey                      	DmiInteger,
	a7002AssociatedGroup                    	DmiDisplaystring,
	a7002EventSystem                        	DmiInteger,
	a7002EventSubsystem                     	DmiInteger,
	a7002EventSolution                      	DmiInteger,
	a7002InstanceDataPresent                	DmiInteger,
	a7002EventMessage                       	DmiDisplaystring,
	a7002VendorSpecificData                 	DmiOctetstring
}

tStorageDevicesEvents OBJECT-TYPE
	SYNTAX		SEQUENCE OF SStorageDevicesEvents
	ACCESS		not-accessible
	STATUS		mandatory
	DESCRIPTION	"Storage Devices events."
	::= {dmtfGroups 7002}

eStorageDevicesEvents OBJECT-TYPE
	SYNTAX		SStorageDevicesEvents
	ACCESS		not-accessible
	STATUS		mandatory
	DESCRIPTION	""
	INDEX		{DmiComponentIndex, a7002AssociatedGroup}
	::= {tStorageDevicesEvents 1}

a7002StorageDevicesEventType OBJECT-TYPE
	SYNTAX		INTEGER {
		vRebuildInProgress                      	(1),
		vStorageDeviceReadying                  	(2),
		vStorageDeviceError                     	(3),
		vSelf-monitoringWarning                 	(4),
		vCioEvent                               	(5)
	}
	ACCESS		read-only
	STATUS		mandatory
	DESCRIPTION	"The type of Storage Devices event that has occurred."
	::= {eStorageDevicesEvents 1}

a7002EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eStorageDevicesEvents 2}

a7002EventIsStateBased OBJECT-TYPE
	SYNTAX		INTEGER {
		vFalse                                  	(0),
		vTrue                                   	(1)
	}
	ACCESS		read-only
	STATUS		mandatory
	DESCRIPTION	"The value of this attribute determined whether the Event
 being reported is a state-based Event or not.  If the value of this attribute
is TRUE then the Event is state-based.  Else the Event is not state-based"
	::= {eStorageDevicesEvents 3}

a7002EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eStorageDevicesEvents 4}

a7002AssociatedGroup OBJECT-TYPE
	SYNTAX		DmiDisplaystring
	ACCESS		read-only
	STATUS		mandatory
	DESCRIPTION	"Class string of the group which originated the event."
	::= {eStorageDevicesEvents 5}

a7002EventSystem OBJECT-TYPE
	SYNTAX		INTEGER {
		vOther                                  	(1),
		vUnknown                                	(2)
	}
	ACCESS		read-only
	STATUS		mandatory
	DESCRIPTION	"The major functional aspect of the product causing the fault."
	::= {eStorageDevicesEvents 6}

a7002EventSubsystem OBJECT-TYPE
	SYNTAX		INTEGER {
		vOther                                  	(1),
		vUnknown                                	(2)
	}
	ACCESS		read-only
	STATUS		mandatory
	DESCRIPTION	"The minor functional aspect of the product causing the fault."
	::= {eStorageDevicesEvents 7}

a7002EventSolution OBJECT-TYPE
	SYNTAX		INTEGER {
		vNotProvided                            	(1)
	}
	ACCESS		read-only
	STATUS		mandatory
	DESCRIPTION	"A solution to the problem that caused the event."
	::= {eStorageDevicesEvents 8}

a7002InstanceDataPresent OBJECT-TYPE
	SYNTAX		INTEGER {
		vFalse                                  	(0),
		vTrue                                   	(1)
	}
	ACCESS		read-only
	STATUS		mandatory
	DESCRIPTION	"Indicates whether second event block contains instance-specific
data."
	::= {eStorageDevicesEvents 9}

a7002EventMessage OBJECT-TYPE
	SYNTAX		DmiDisplaystring
	ACCESS		read-only
	STATUS		mandatory
	DESCRIPTION	"Auxiliary information related to the event."
	::= {eStorageDevicesEvents 10}

a7002VendorSpecificData OBJECT-TYPE
	SYNTAX		DmiOctetstring
	ACCESS		read-only
	STATUS		mandatory
	DESCRIPTION	"Auxiliary information related to the event."
	::= {eStorageDevicesEvents 11}

SStorageController ::= SEQUENCE {
	a7003ControllerIndex                    	DmiInteger,
	a7003Identification                     	DmiDisplaystring,
	a7003ProtectionManagement               	DmiInteger,
	a7003BusMaster                          	DmiInteger,
	a7003SecondsSinceLastPower-up           	DmiInteger
}

tStorageController OBJECT-TYPE
	SYNTAX		SEQUENCE OF SStorageController
	ACCESS		not-accessible
	STATUS		mandatory
	DESCRIPTION	"This group defines the storage controller in this system."
	::= {dmtfGroups 7003}

eStorageController OBJECT-TYPE
	SYNTAX		SStorageController
	ACCESS		not-accessible
	STATUS		mandatory
	DESCRIPTION	""
	INDEX		{DmiComponentIndex, a7003ControllerIndex}
	::= {tStorageController 1}

a7003ControllerIndex OBJECT-TYPE
	SYNTAX		DmiInteger
	ACCESS		read-only
	STATUS		mandatory
	DESCRIPTION	"An index into the Storage Controller table."
	::= {eStorageController 1}

a7003Identification OBJECT-TYPE
	SYNTAX		DmiDisplaystring
	ACCESS		read-only
	STATUS		mandatory
	DESCRIPTION	"e.g. Name, brand and hardware revision level of the storage
controller."
	::= {eStorageController 2}

a7003ProtectionManagement OBJECT-TYPE
	SYNTAX		INTEGER {
		vOther                                  	(1),
		vUnknown                                	(2),
		vUnprotected                            	(3),
		vProtected                              	(4),
		vProtectedThroughScsi-3ControllerCommand	(5),
		vProtectedThroughScsi-3ControllerComman1	(6)
	}
	ACCESS		read-only
	STATUS		mandatory
	DESCRIPTION	"Indicates whether or not the controller provides redundancy
or protection against device failures."
	::= {eStorageController 3}

a7003BusMaster OBJECT-TYPE
	SYNTAX		INTEGER {
		vFalse                                  	(0),
		vTrue                                   	(1),
		vUnknown                                	(2)
	}
	ACCESS		read-only
	STATUS		mandatory
	DESCRIPTION	"If true, then this storage controller is the bus master."
	::= {eStorageController 4}

a7003SecondsSinceLastPower-up OBJECT-TYPE
	SYNTAX		DmiInteger
	ACCESS		read-only
	STATUS		mandatory
	DESCRIPTION	"The number of seconds that have passed since this controller
was last powered on."
	::= {eStorageController 5}

SStorageControllerEvents ::= SEQUENCE {
	a7004StorageControllerEventType         	DmiInteger,
	a7004EventSeverity                      	DmiInteger,
	a7004EventIsStateBased                  	DmiInteger,
	a7004EventStateKey                      	DmiInteger,
	a7004AssociatedGroup                    	DmiDisplaystring,
	a7004EventSystem                        	DmiInteger,
	a7004EventSubsystem                     	DmiInteger,
	a7004EventSolution                      	DmiInteger,
	a7004InstanceDataPresent                	DmiInteger,
	a7004EventMessage                       	DmiDisplaystring,
	a7004VendorSpecificData                 	DmiOctetstring
}

tStorageControllerEvents OBJECT-TYPE
	SYNTAX		SEQUENCE OF SStorageControllerEvents
	ACCESS		not-accessible
	STATUS		mandatory
	DESCRIPTION	"Storage Controller events."
	::= {dmtfGroups 7004}

eStorageControllerEvents OBJECT-TYPE
	SYNTAX		SStorageControllerEvents
	ACCESS		not-accessible
	STATUS		mandatory
	DESCRIPTION	""
	INDEX		{DmiComponentIndex, a7004AssociatedGroup}
	::= {tStorageControllerEvents 1}

a7004StorageControllerEventType OBJECT-TYPE
	SYNTAX		INTEGER {
		vStorageControllerError                 	(1),
		vSelf-monitoringWarning1                	(2),
		vCioEvent                               	(3)
	}
	ACCESS		read-only
	STATUS		mandatory
	DESCRIPTION	"The type of Storage Controller event that has occurred."
	::= {eStorageControllerEvents 1}

a7004EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eStorageControllerEvents 2}

a7004EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eStorageControllerEvents 3}

a7004EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eStorageControllerEvents 4}

a7004AssociatedGroup OBJECT-TYPE
	SYNTAX		DmiDisplaystring
	ACCESS		read-only
	STATUS		mandatory
	DESCRIPTION	"Class string of the group which originated the event."
	::= {eStorageControllerEvents 5}

a7004EventSystem OBJECT-TYPE
	SYNTAX		INTEGER {
		vOther                                  	(1),
		vUnknown                                	(2)
	}
	ACCESS		read-only
	STATUS		mandatory
	DESCRIPTION	"The major functional aspect of the product causing the fault."
	::= {eStorageControllerEvents 6}

a7004EventSubsystem OBJECT-TYPE
	SYNTAX		INTEGER {
		vOther                                  	(1),
		vUnknown                                	(2)
	}
	ACCESS		read-only
	STATUS		mandatory
	DESCRIPTION	"The minor functional aspect of the product causing the fault."
	::= {eStorageControllerEvents 7}

a7004EventSolution OBJECT-TYPE
	SYNTAX		INTEGER {
		vNotProvided                            	(1)
	}
	ACCESS		read-only
	STATUS		mandatory
	DESCRIPTION	"A solution to the problem that caused the event."
	::= {eStorageControllerEvents 8}

a7004InstanceDataPresent OBJECT-TYPE
	SYNTAX		INTEGER {
		vFalse                                  	(0),
		vTrue                                   	(1)
	}
	ACCESS		read-only
	STATUS		mandatory
	DESCRIPTION	"Indicates whether second event block contains instance-specific
data."
	::= {eStorageControllerEvents 9}

a7004EventMessage OBJECT-TYPE
	SYNTAX		DmiDisplaystring
	ACCESS		read-only
	STATUS		mandatory
	DESCRIPTION	"Auxiliary information related to the event."
	::= {eStorageControllerEvents 10}

a7004VendorSpecificData OBJECT-TYPE
	SYNTAX		DmiOctetstring
	ACCESS		read-only
	STATUS		mandatory
	DESCRIPTION	"Auxiliary information related to the event."
	::= {eStorageControllerEvents 11}

SEnclosure ::= SEQUENCE {
	a7005EnclosureIndex                     	DmiInteger,
	a7005Type                               	DmiInteger,
	a7005Description                        	DmiDisplaystring
}

tEnclosure OBJECT-TYPE
	SYNTAX		SEQUENCE OF SEnclosure
	ACCESS		not-accessible
	STATUS		mandatory
	DESCRIPTION	"This group defines the enclosure in this system."
	::= {dmtfGroups 7005}

eEnclosure OBJECT-TYPE
	SYNTAX		SEnclosure
	ACCESS		not-accessible
	STATUS		mandatory
	DESCRIPTION	""
	INDEX		{DmiComponentIndex, a7005EnclosureIndex}
	::= {tEnclosure 1}

a7005EnclosureIndex OBJECT-TYPE
	SYNTAX		DmiInteger
	ACCESS		read-only
	STATUS		mandatory
	DESCRIPTION	"An index into the Enclosure table."
	::= {eEnclosure 1}

a7005Type OBJECT-TYPE
	SYNTAX		INTEGER {
		vOther                                  	(1),
		vUnknown                                	(2),
		vDecfault                               	(3),
		vSaf-te                                 	(4),
		vSes                                    	(5),
		vAemi                                   	(6)
	}
	ACCESS		read-only
	STATUS		mandatory
	DESCRIPTION	"Type of the enclosure."
	::= {eEnclosure 2}

a7005Description OBJECT-TYPE
	SYNTAX		DmiDisplaystring
	ACCESS		read-only
	STATUS		mandatory
	DESCRIPTION	"Description of the enclosure."
	::= {eEnclosure 3}

SEnclosureEvents ::= SEQUENCE {
	a7006EnclosureEventType                 	DmiInteger,
	a7006EventSeverity                      	DmiInteger,
	a7006EventIsStateBased                  	DmiInteger,
	a7006EventStateKey                      	DmiInteger,
	a7006AssociatedGroup                    	DmiDisplaystring,
	a7006EventSystem                        	DmiInteger,
	a7006EventSubsystem                     	DmiInteger,
	a7006EventSolution                      	DmiInteger,
	a7006InstanceDataPresent                	DmiInteger,
	a7006EventMessage                       	DmiDisplaystring,
	a7006VendorSpecificData                 	DmiOctetstring
}

tEnclosureEvents OBJECT-TYPE
	SYNTAX		SEQUENCE OF SEnclosureEvents
	ACCESS		not-accessible
	STATUS		mandatory
	DESCRIPTION	"Enclosure events."
	::= {dmtfGroups 7006}

eEnclosureEvents OBJECT-TYPE
	SYNTAX		SEnclosureEvents
	ACCESS		not-accessible
	STATUS		mandatory
	DESCRIPTION	""
	INDEX		{DmiComponentIndex, a7006AssociatedGroup}
	::= {tEnclosureEvents 1}

a7006EnclosureEventType OBJECT-TYPE
	SYNTAX		INTEGER {
		vCioEvent                               	(1)
	}
	ACCESS		read-only
	STATUS		mandatory
	DESCRIPTION	"The type of Enclosure event that has occurred."
	::= {eEnclosureEvents 1}

a7006EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEnclosureEvents 2}

a7006EventIsStateBased OBJECT-TYPE
	SYNTAX		INTEGER {
		vFalse                                  	(0),
		vTrue                                   	(1)
	}
	ACCESS		read-only
	STATUS		mandatory
	DESCRIPTION	"The value of this attribute determined whether the Event
 being reported is a state-based Event or not.  If the value of this attribute
is TRUE then the Event is state-based.  Else the Event is not state-based"
	::= {eEnclosureEvents 3}

a7006EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eEnclosureEvents 4}

a7006AssociatedGroup OBJECT-TYPE
	SYNTAX		DmiDisplaystring
	ACCESS		read-only
	STATUS		mandatory
	DESCRIPTION	"Class string of the group which originated the event."
	::= {eEnclosureEvents 5}

a7006EventSystem OBJECT-TYPE
	SYNTAX		INTEGER {
		vOther                                  	(1),
		vUnknown                                	(2)
	}
	ACCESS		read-only
	STATUS		mandatory
	DESCRIPTION	"The major functional aspect of the product causing the fault."
	::= {eEnclosureEvents 6}

a7006EventSubsystem OBJECT-TYPE
	SYNTAX		INTEGER {
		vOther                                  	(1),
		vUnknown                                	(2)
	}
	ACCESS		read-only
	STATUS		mandatory
	DESCRIPTION	"The minor functional aspect of the product causing the fault."
	::= {eEnclosureEvents 7}

a7006EventSolution OBJECT-TYPE
	SYNTAX		INTEGER {
		vNotProvided                            	(1)
	}
	ACCESS		read-only
	STATUS		mandatory
	DESCRIPTION	"A solution to the problem that caused the event."
	::= {eEnclosureEvents 8}

a7006InstanceDataPresent OBJECT-TYPE
	SYNTAX		INTEGER {
		vFalse                                  	(0),
		vTrue                                   	(1)
	}
	ACCESS		read-only
	STATUS		mandatory
	DESCRIPTION	"Indicates whether second event block contains instance-specific
data."
	::= {eEnclosureEvents 9}

a7006EventMessage OBJECT-TYPE
	SYNTAX		DmiDisplaystring
	ACCESS		read-only
	STATUS		mandatory
	DESCRIPTION	"Auxiliary information related to the event."
	::= {eEnclosureEvents 10}

a7006VendorSpecificData OBJECT-TYPE
	SYNTAX		DmiOctetstring
	ACCESS		read-only
	STATUS		mandatory
	DESCRIPTION	"Auxiliary information related to the event."
	::= {eEnclosureEvents 11}

SBusPort ::= SEQUENCE {
	a7007BusPortIndex                       	DmiInteger,
	a7007Protocol                           	DmiInteger,
	a7007ProtocolDescription                	DmiDisplaystring,
	a7007SignalCharacteristics              	DmiInteger,
	a7007AddressDescriptor                  	DmiDisplaystring,
	a7007Isochronous                        	DmiInteger,
	a7007MaximumWidth                       	DmiInteger,
	a7007MaximumTransferRate                	DmiInteger,
	a7007MaximumNumberOfAttachments         	DmiInteger,
	a7007ConnectorType                      	DmiInteger,
	a7007ConnectorTypeDescription           	DmiDisplaystring,
	a7007ConnectorGender                    	DmiInteger
}

tBusPort OBJECT-TYPE
	SYNTAX		SEQUENCE OF SBusPort
	ACCESS		not-accessible
	STATUS		mandatory
	DESCRIPTION	"This global table has one entry for each of the Bus Ports
in this Component."
	::= {dmtfGroups 7007}

eBusPort OBJECT-TYPE
	SYNTAX		SBusPort
	ACCESS		not-accessible
	STATUS		mandatory
	DESCRIPTION	""
	INDEX		{DmiComponentIndex, a7007BusPortIndex}
	::= {tBusPort 1}

a7007BusPortIndex OBJECT-TYPE
	SYNTAX		DmiInteger
	ACCESS		read-only
	STATUS		mandatory
	DESCRIPTION	"An index into the Bus Port table."
	::= {eBusPort 1}

a7007Protocol OBJECT-TYPE
	SYNTAX		INTEGER {
		vOther                                  	(1),
		vUnknown                                	(2),
		vEisa                                   	(3),
		vIsa                                    	(4),
		vPci                                    	(5),
		vAtaatapi                               	(6),
		vFlexibleDiskette                       	(7),
		v1496                                   	(8),
		vScsiParallelInterface                  	(9),
		vScsiFibreChannelProtocol               	(10),
		vScsiSerialBusProtocol                  	(11),
		vScsiSerialBusProtocol-21394            	(12),
		vScsiSerialStorageArchitecture          	(13),
		vVesa                                   	(14),
		vPcmcia                                 	(15),
		vUniversalSerialBus                     	(16),
		vParallelPort                           	(17),
		vEscon                                  	(18),
		vDiagnostic                             	(19),
		vI2c                                    	(20),
		vPower                                  	(21),
		vHippi                                  	(22),
		vMultibus                               	(23),
		vVme                                    	(24),
		vIpi                                    	(25),
		vIeee-488                               	(26),
		vRs232                                  	(27),
		vIeee802310base5                        	(28),
		vIeee802310base2                        	(29),
		vIeee80231base5                         	(30),
		vIeee802310broad36                      	(31),
		vIeee8023100basevg                      	(32),
		vIeee8025Token-ring                     	(33),
		vAnsiX3t95Fddi                          	(34),
		vMca                                    	(35)
	}
	ACCESS		read-only
	STATUS		mandatory
	DESCRIPTION	"The protocol describing the electrical characteristic of
the Bus Port.  If 'Other' is used, then the Protocol Description attribute
shall be used."
	::= {eBusPort 2}

a7007ProtocolDescription OBJECT-TYPE
	SYNTAX		DmiDisplaystring
	ACCESS		read-only
	STATUS		mandatory
	DESCRIPTION	"Additional description of the protocol described above. 
If 'Other' was specified above, then this field shall be used.  Otherwise,
the contents of this optional field shall not contradict the Protocol specified
above."
	::= {eBusPort 3}

a7007SignalCharacteristics OBJECT-TYPE
	SYNTAX		INTEGER {
		vOther                                  	(1),
		vUnknown                                	(2),
		vSingleEnded                            	(3),
		vDifferential                           	(4),
		vLowVoltageDifferential                 	(5),
		vOptical                                	(6)
	}
	ACCESS		read-only
	STATUS		mandatory
	DESCRIPTION	"The signal characteristics of the Bus Port being described."
	::= {eBusPort 4}

a7007AddressDescriptor OBJECT-TYPE
	SYNTAX		DmiDisplaystring
	ACCESS		read-only
	STATUS		mandatory
	DESCRIPTION	"The address descriptor of this bus port.  For example, the
SCSI address of this port."
	::= {eBusPort 5}

a7007Isochronous OBJECT-TYPE
	SYNTAX		INTEGER {
		vFalse                                  	(0),
		vTrue                                   	(1)
	}
	ACCESS		read-only
	STATUS		mandatory
	DESCRIPTION	"Indicates whether or not this bus port supports isochronous
transfers."
	::= {eBusPort 6}

a7007MaximumWidth OBJECT-TYPE
	SYNTAX		DmiInteger
	ACCESS		read-only
	STATUS		mandatory
	DESCRIPTION	"The maximum width, in bits, of this Bus Port's data path.
 A value of 1 should be used for serial."
	::= {eBusPort 7}

a7007MaximumTransferRate OBJECT-TYPE
	SYNTAX		DmiInteger
	ACCESS		read-only
	STATUS		mandatory
	DESCRIPTION	"The theoretical maximum transfer rate, in millions of bytes
per second, that this Bus Port is capable of achieving under ideal conditions.
 A value of zero should be used if the transfer rate is less than 1 million
bytes per second.  A value of 0x80000000 should be used if the transfer rate
is unknown."
	::= {eBusPort 8}

a7007MaximumNumberOfAttachments OBJECT-TYPE
	SYNTAX		DmiInteger
	ACCESS		read-only
	STATUS		mandatory
	DESCRIPTION	"The maximum number of directly addressable entities supported
by this bus port's protocol.  A value of zero should be used if the number
of attachments is unknown."
	::= {eBusPort 9}

a7007ConnectorType OBJECT-TYPE
	SYNTAX		INTEGER {
		vOther                                  	(1),
		vUnknown                                	(2),
		vNone                                   	(3),
		vScsiAHigh-densityShielded50Pins        	(4),
		vScsiAHigh-densityUnshielded50Pins      	(5),
		vScsiALow-densityShielded50Pins         	(6),
		vScsiALow-densityUnshielded50Pins       	(7),
		vScsiPHigh-densityShielded68Pins        	(8),
		vScsiPHigh-densityUnshielded68Pins      	(9),
		vScsiSca-i80Pins                        	(10),
		vScsiSca-ii80Pins                       	(11),
		vScsiFibreChannelDb9Copper              	(12),
		vScsiFibreChannelFibre                  	(13),
		vScsiFibreChannelSca-ii40Pins           	(14),
		vScsiFibreChannelSca-ii20Pins           	(15),
		vScsiFibreChannelBnc                    	(16),
		vAta3-12Inch40Pins                      	(17),
		vAta2-12Inch44Pins                      	(18),
		vSerial9Pin                             	(19),
		vSerial25Pin                            	(20),
		vRs23225Pin                             	(21),
		vRs422                                  	(22),
		vIeee-488                               	(23),
		vAui                                    	(24),
		vUptCategory3                           	(25),
		vUptCategory4                           	(26),
		vUptCategory5                           	(27),
		vBnc                                    	(28),
		vStpRj11                                	(29),
		vStpRj45                                	(30),
		vStpDb9                                 	(31),
		vFiberMic                               	(32),
		vAppleAui                               	(33),
		vPciSlot                                	(34),
		vIsaSlot                                	(35),
		vEisaSlot                               	(36),
		vVesaSlot                               	(37),
		vPcmciaSlot                             	(38),
		vPcCardSlot                             	(39),
		vFloppyDiskette5-14Inch                 	(40),
		vFloppyDiskette3-12Inch                 	(41),
		vHssdc6Pins                             	(42),
		vGbicSocket                             	(43),
		v13946Pins                              	(44),
		vScsiVhdciShielded68Pins                	(45)
	}
	ACCESS		read-only
	STATUS		mandatory
	DESCRIPTION	"Describes how options (cards, devices, etc.) physically connect
to this bus port.  If 'Other' is used, then the Connector Type Description
attribute shall be used."
	::= {eBusPort 10}

a7007ConnectorTypeDescription OBJECT-TYPE
	SYNTAX		DmiDisplaystring
	ACCESS		read-only
	STATUS		mandatory
	DESCRIPTION	"An additional text description of the type of connector describe
above.  If 'Other' was specified above, then this field shall be used.  Otherwis
, the contents of this optional field shall not contradict the connector
specified above."
	::= {eBusPort 11}

a7007ConnectorGender OBJECT-TYPE
	SYNTAX		INTEGER {
		vOther                                  	(1),
		vUnknown                                	(2),
		vFemale                                 	(3),
		vMale                                   	(4)
	}
	ACCESS		read-only
	STATUS		mandatory
	DESCRIPTION	"Indicates the gender of the connector described above."
	::= {eBusPort 12}

SBusPortEvents ::= SEQUENCE {
	a7008BusPortEventType                   	DmiInteger,
	a7008EventSeverity                      	DmiInteger,
	a7008EventIsStateBased                  	DmiInteger,
	a7008EventStateKey                      	DmiInteger,
	a7008AssociatedGroup                    	DmiDisplaystring,
	a7008EventSystem                        	DmiInteger,
	a7008EventSubsystem                     	DmiInteger,
	a7008EventSolution                      	DmiInteger,
	a7008InstanceDataPresent                	DmiInteger,
	a7008EventMessage                       	DmiDisplaystring,
	a7008VendorSpecificData                 	DmiOctetstring
}

tBusPortEvents OBJECT-TYPE
	SYNTAX		SEQUENCE OF SBusPortEvents
	ACCESS		not-accessible
	STATUS		mandatory
	DESCRIPTION	"Bus Port events."
	::= {dmtfGroups 7008}

eBusPortEvents OBJECT-TYPE
	SYNTAX		SBusPortEvents
	ACCESS		not-accessible
	STATUS		mandatory
	DESCRIPTION	""
	INDEX		{DmiComponentIndex, a7008AssociatedGroup}
	::= {tBusPortEvents 1}

a7008BusPortEventType OBJECT-TYPE
	SYNTAX		INTEGER {
		vBusPortError                           	(1)
	}
	ACCESS		read-only
	STATUS		mandatory
	DESCRIPTION	"The type of Bus Port event that has occurred."
	::= {eBusPortEvents 1}

a7008EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eBusPortEvents 2}

a7008EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eBusPortEvents 3}

a7008EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eBusPortEvents 4}

a7008AssociatedGroup OBJECT-TYPE
	SYNTAX		DmiDisplaystring
	ACCESS		read-only
	STATUS		mandatory
	DESCRIPTION	"Class string of the group which originated the event."
	::= {eBusPortEvents 5}

a7008EventSystem OBJECT-TYPE
	SYNTAX		INTEGER {
		vOther                                  	(1),
		vUnknown                                	(2)
	}
	ACCESS		read-only
	STATUS		mandatory
	DESCRIPTION	"The major functional aspect of the product causing the fault."
	::= {eBusPortEvents 6}

a7008EventSubsystem OBJECT-TYPE
	SYNTAX		INTEGER {
		vOther                                  	(1),
		vUnknown                                	(2)
	}
	ACCESS		read-only
	STATUS		mandatory
	DESCRIPTION	"The minor functional aspect of the product causing the fault."
	::= {eBusPortEvents 7}

a7008EventSolution OBJECT-TYPE
	SYNTAX		INTEGER {
		vNotProvided                            	(1)
	}
	ACCESS		read-only
	STATUS		mandatory
	DESCRIPTION	"A solution to the problem that caused the event."
	::= {eBusPortEvents 8}

a7008InstanceDataPresent OBJECT-TYPE
	SYNTAX		INTEGER {
		vFalse                                  	(0),
		vTrue                                   	(1)
	}
	ACCESS		read-only
	STATUS		mandatory
	DESCRIPTION	"Indicates whether second event block contains instance-specific
data."
	::= {eBusPortEvents 9}

a7008EventMessage OBJECT-TYPE
	SYNTAX		DmiDisplaystring
	ACCESS		read-only
	STATUS		mandatory
	DESCRIPTION	"Auxiliary information related to the event."
	::= {eBusPortEvents 10}

a7008VendorSpecificData OBJECT-TYPE
	SYNTAX		DmiOctetstring
	ACCESS		read-only
	STATUS		mandatory
	DESCRIPTION	"Auxiliary information related to the event."
	::= {eBusPortEvents 11}

SAggregatePhysicalExtent ::= SEQUENCE {
	a7009AggregatePhysicalExtentIndex       	DmiInteger,
	a7009NumberOfBlocks                     	DmiInteger64,
	a7009NumberOfBlocksOfCheckData          	DmiInteger64
}

tAggregatePhysicalExtent OBJECT-TYPE
	SYNTAX		SEQUENCE OF SAggregatePhysicalExtent
	ACCESS		not-accessible
	STATUS		mandatory
	DESCRIPTION	"Summary information about the addressable logical blocks
which are in the same redundancy group and reside on the same physical device."
	::= {dmtfGroups 7009}

eAggregatePhysicalExtent OBJECT-TYPE
	SYNTAX		SAggregatePhysicalExtent
	ACCESS		not-accessible
	STATUS		mandatory
	DESCRIPTION	""
	INDEX		{DmiComponentIndex, a7009AggregatePhysicalExtentIndex}
	::= {tAggregatePhysicalExtent 1}

a7009AggregatePhysicalExtentIndex OBJECT-TYPE
	SYNTAX		DmiInteger
	ACCESS		read-only
	STATUS		mandatory
	DESCRIPTION	"An index into the Aggregate Physical Extent table."
	::= {eAggregatePhysicalExtent 1}

a7009NumberOfBlocks OBJECT-TYPE
	SYNTAX		DmiInteger64
	ACCESS		read-only
	STATUS		mandatory
	DESCRIPTION	"The total number of blocks (including the check data blocks)
contained in this aggregate p_extent.  The block size is the same as the
storage device associated with this aggregate p_extent.  Note:  If no redundancy
group is associated with an aggregate p_extent, then this indicates the number
of p_extent blocks that are available."
	::= {eAggregatePhysicalExtent 2}

a7009NumberOfBlocksOfCheckData OBJECT-TYPE
	SYNTAX		DmiInteger64
	ACCESS		read-only
	STATUS		mandatory
	DESCRIPTION	"The number of  blocks contained in this aggregate p_extent
to be used as check data.  If the Aggregate p_extent is available, then this
value shall be zero."
	::= {eAggregatePhysicalExtent 3}

SAggregateProtectedSpaceExtent ::= SEQUENCE {
	a7010AggregateProtectedSpaceExtentIndex 	DmiInteger,
	a7010NumberOfBlocks                     	DmiInteger64
}

tAggregateProtectedSpaceExtent OBJECT-TYPE
	SYNTAX		SEQUENCE OF SAggregateProtectedSpaceExtent
	ACCESS		not-accessible
	STATUS		mandatory
	DESCRIPTION	"Summary information about the addressable logical blocks
which are in the same volume set and are derived from the same storage device."
	::= {dmtfGroups 7010}

eAggregateProtectedSpaceExtent OBJECT-TYPE
	SYNTAX		SAggregateProtectedSpaceExtent
	ACCESS		not-accessible
	STATUS		mandatory
	DESCRIPTION	""
	INDEX		{DmiComponentIndex, a7010AggregateProtectedSpaceExtentIndex}
	::= {tAggregateProtectedSpaceExtent 1}

a7010AggregateProtectedSpaceExtentIndex OBJECT-TYPE
	SYNTAX		DmiInteger
	ACCESS		read-only
	STATUS		mandatory
	DESCRIPTION	"An index into the Aggregate Protected Space Extent table."
	::= {eAggregateProtectedSpaceExtent 1}

a7010NumberOfBlocks OBJECT-TYPE
	SYNTAX		DmiInteger64
	ACCESS		read-only
	STATUS		mandatory
	DESCRIPTION	"The total number of user data blocks that are both located
on a single storage device and part or all of a single volume set. The block
size is the same as the storage device associated with this aggregate ps_extent.
 Note:  If no volume set is associated with an aggregate ps_extent, then
this number indicates the number of blocks that are available."
	::= {eAggregateProtectedSpaceExtent 2}

SVolumeSet ::= SEQUENCE {
	a7011VolumeSetIndex                     	DmiInteger,
	a7011Name                               	DmiDisplaystring,
	a7011TotalStorageCapacity               	DmiInteger64,
	a7011ProtectedSpaceStripeLength         	DmiInteger64,
	a7011ProtectedSpaceExtentInterleaveDepth	DmiInteger64
}

tVolumeSet OBJECT-TYPE
	SYNTAX		SEQUENCE OF SVolumeSet
	ACCESS		not-accessible
	STATUS		mandatory
	DESCRIPTION	"The volume set is a contiguous range of logical block addresses
presented to the operating environment for reading and writing user data.
 A volume set may be used as a physical extent"
	::= {dmtfGroups 7011}

eVolumeSet OBJECT-TYPE
	SYNTAX		SVolumeSet
	ACCESS		not-accessible
	STATUS		mandatory
	DESCRIPTION	""
	INDEX		{DmiComponentIndex, a7011VolumeSetIndex}
	::= {tVolumeSet 1}

a7011VolumeSetIndex OBJECT-TYPE
	SYNTAX		DmiInteger
	ACCESS		read-only
	STATUS		mandatory
	DESCRIPTION	"An index into the Volume Set table."
	::= {eVolumeSet 1}

a7011Name OBJECT-TYPE
	SYNTAX		DmiDisplaystring
	ACCESS		read-only
	STATUS		mandatory
	DESCRIPTION	"The name of the volume set."
	::= {eVolumeSet 2}

a7011TotalStorageCapacity OBJECT-TYPE
	SYNTAX		DmiInteger64
	ACCESS		read-only
	STATUS		mandatory
	DESCRIPTION	"The total size in bytes of the user data space of this volume
set."
	::= {eVolumeSet 3}

a7011ProtectedSpaceStripeLength OBJECT-TYPE
	SYNTAX		DmiInteger64
	ACCESS		read-only
	STATUS		mandatory
	DESCRIPTION	"The number of ps_extents which form a user data stripe. 
This value shall be zero except when the ps_extent group is used."
	::= {eVolumeSet 4}

a7011ProtectedSpaceExtentInterleaveDepth OBJECT-TYPE
	SYNTAX		DmiInteger64
	ACCESS		read-only
	STATUS		mandatory
	DESCRIPTION	"This is the number of ps_extents to stripe as a collective
set.  This value shall be zero except when the ps_extent group is used."
	::= {eVolumeSet 5}

SVolumeSetEvents ::= SEQUENCE {
	a7012VolumeSetEventType                 	DmiInteger,
	a7012EventSeverity                      	DmiInteger,
	a7012EventIsStateBased                  	DmiInteger,
	a7012EventStateKey                      	DmiInteger,
	a7012AssociatedGroup                    	DmiDisplaystring,
	a7012EventSystem                        	DmiInteger,
	a7012EventSubsystem                     	DmiInteger,
	a7012EventSolution                      	DmiInteger,
	a7012InstanceDataPresent                	DmiInteger,
	a7012EventMessage                       	DmiDisplaystring,
	a7012VendorSpecificData                 	DmiOctetstring
}

tVolumeSetEvents OBJECT-TYPE
	SYNTAX		SEQUENCE OF SVolumeSetEvents
	ACCESS		not-accessible
	STATUS		mandatory
	DESCRIPTION	"Volume Set events."
	::= {dmtfGroups 7012}

eVolumeSetEvents OBJECT-TYPE
	SYNTAX		SVolumeSetEvents
	ACCESS		not-accessible
	STATUS		mandatory
	DESCRIPTION	""
	INDEX		{DmiComponentIndex, a7012AssociatedGroup}
	::= {tVolumeSetEvents 1}

a7012VolumeSetEventType OBJECT-TYPE
	SYNTAX		INTEGER {
		vVolumeSetExposed                       	(1),
		vRebuildInProgress                      	(2),
		vProtectionDisabled                     	(3),
		vVolumeSetReadying                      	(4),
		vRecalculateActive                      	(5),
		vSpareInUse                             	(6),
		vVerifyInProgress                       	(7),
		vVolumeSetBroken                        	(8),
		vCioEvent                               	(9)
	}
	ACCESS		read-only
	STATUS		mandatory
	DESCRIPTION	"The type of Volume Set event that has occurred."
	::= {eVolumeSetEvents 1}

a7012EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eVolumeSetEvents 2}

a7012EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eVolumeSetEvents 3}

a7012EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eVolumeSetEvents 4}

a7012AssociatedGroup OBJECT-TYPE
	SYNTAX		DmiDisplaystring
	ACCESS		read-only
	STATUS		mandatory
	DESCRIPTION	"Class string of the group which originated the event."
	::= {eVolumeSetEvents 5}

a7012EventSystem OBJECT-TYPE
	SYNTAX		INTEGER {
		vOther                                  	(1),
		vUnknown                                	(2)
	}
	ACCESS		read-only
	STATUS		mandatory
	DESCRIPTION	"The major functional aspect of the product causing the fault."
	::= {eVolumeSetEvents 6}

a7012EventSubsystem OBJECT-TYPE
	SYNTAX		INTEGER {
		vOther                                  	(1),
		vUnknown                                	(2)
	}
	ACCESS		read-only
	STATUS		mandatory
	DESCRIPTION	"The minor functional aspect of the product causing the fault."
	::= {eVolumeSetEvents 7}

a7012EventSolution OBJECT-TYPE
	SYNTAX		INTEGER {
		vNotProvided                            	(1)
	}
	ACCESS		read-only
	STATUS		mandatory
	DESCRIPTION	"A solution to the problem that caused the event."
	::= {eVolumeSetEvents 8}

a7012InstanceDataPresent OBJECT-TYPE
	SYNTAX		INTEGER {
		vFalse                                  	(0),
		vTrue                                   	(1)
	}
	ACCESS		read-only
	STATUS		mandatory
	DESCRIPTION	"Indicates whether second event block contains instance-specific
data."
	::= {eVolumeSetEvents 9}

a7012EventMessage OBJECT-TYPE
	SYNTAX		DmiDisplaystring
	ACCESS		read-only
	STATUS		mandatory
	DESCRIPTION	"Auxiliary information related to the event."
	::= {eVolumeSetEvents 10}

a7012VendorSpecificData OBJECT-TYPE
	SYNTAX		DmiOctetstring
	ACCESS		read-only
	STATUS		mandatory
	DESCRIPTION	"Auxiliary information related to the event."
	::= {eVolumeSetEvents 11}

SVolumeSetActivityEvents ::= SEQUENCE {
	a7013VolumeSetEventType                 	DmiInteger,
	a7013EventSeverity                      	DmiInteger,
	a7013EventIsStateBased                  	DmiInteger,
	a7013EventStateKey                      	DmiInteger,
	a7013AssociatedGroup                    	DmiDisplaystring,
	a7013EventSystem                        	DmiInteger,
	a7013EventSubsystem                     	DmiInteger,
	a7013EventSolution                      	DmiInteger,
	a7013InstanceDataPresent                	DmiInteger,
	a7013EventMessage                       	DmiDisplaystring,
	a7013VendorSpecificData                 	DmiOctetstring
}

tVolumeSetActivityEvents OBJECT-TYPE
	SYNTAX		SEQUENCE OF SVolumeSetActivityEvents
	ACCESS		not-accessible
	STATUS		mandatory
	DESCRIPTION	"Volume Set activity events."
	::= {dmtfGroups 7013}

eVolumeSetActivityEvents OBJECT-TYPE
	SYNTAX		SVolumeSetActivityEvents
	ACCESS		not-accessible
	STATUS		mandatory
	DESCRIPTION	""
	INDEX		{DmiComponentIndex, a7013AssociatedGroup}
	::= {tVolumeSetActivityEvents 1}

a7013VolumeSetEventType OBJECT-TYPE
	SYNTAX		INTEGER {
		vCioEvent                               	(1)
	}
	ACCESS		read-only
	STATUS		mandatory
	DESCRIPTION	"The type of Volume Set activity event that has occurred."
	::= {eVolumeSetActivityEvents 1}

a7013EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eVolumeSetActivityEvents 2}

a7013EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eVolumeSetActivityEvents 3}

a7013EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eVolumeSetActivityEvents 4}

a7013AssociatedGroup OBJECT-TYPE
	SYNTAX		DmiDisplaystring
	ACCESS		read-only
	STATUS		mandatory
	DESCRIPTION	"Class string of the group which originated the event."
	::= {eVolumeSetActivityEvents 5}

a7013EventSystem OBJECT-TYPE
	SYNTAX		INTEGER {
		vOther                                  	(1),
		vUnknown                                	(2)
	}
	ACCESS		read-only
	STATUS		mandatory
	DESCRIPTION	"The major functional aspect of the product causing the fault."
	::= {eVolumeSetActivityEvents 6}

a7013EventSubsystem OBJECT-TYPE
	SYNTAX		INTEGER {
		vOther                                  	(1),
		vUnknown                                	(2)
	}
	ACCESS		read-only
	STATUS		mandatory
	DESCRIPTION	"The minor functional aspect of the product causing the fault."
	::= {eVolumeSetActivityEvents 7}

a7013EventSolution OBJECT-TYPE
	SYNTAX		INTEGER {
		vNotProvided                            	(1)
	}
	ACCESS		read-only
	STATUS		mandatory
	DESCRIPTION	"A solution to the problem that caused the event."
	::= {eVolumeSetActivityEvents 8}

a7013InstanceDataPresent OBJECT-TYPE
	SYNTAX		INTEGER {
		vFalse                                  	(0),
		vTrue                                   	(1)
	}
	ACCESS		read-only
	STATUS		mandatory
	DESCRIPTION	"Indicates whether second event block contains instance-specific
data."
	::= {eVolumeSetActivityEvents 9}

a7013EventMessage OBJECT-TYPE
	SYNTAX		DmiDisplaystring
	ACCESS		read-only
	STATUS		mandatory
	DESCRIPTION	"Auxiliary information related to the event."
	::= {eVolumeSetActivityEvents 10}

a7013VendorSpecificData OBJECT-TYPE
	SYNTAX		DmiOctetstring
	ACCESS		read-only
	STATUS		mandatory
	DESCRIPTION	"Auxiliary information related to the event."
	::= {eVolumeSetActivityEvents 11}

SRedundancyGroup ::= SEQUENCE {
	a7014RedundancyGroupIndex               	DmiInteger,
	a7014RedundancyType                     	DmiInteger
}

tRedundancyGroup OBJECT-TYPE
	SYNTAX		SEQUENCE OF SRedundancyGroup
	ACCESS		not-accessible
	STATUS		mandatory
	DESCRIPTION	"Redundancy Group"
	::= {dmtfGroups 7014}

eRedundancyGroup OBJECT-TYPE
	SYNTAX		SRedundancyGroup
	ACCESS		not-accessible
	STATUS		mandatory
	DESCRIPTION	""
	INDEX		{DmiComponentIndex, a7014RedundancyGroupIndex}
	::= {tRedundancyGroup 1}

a7014RedundancyGroupIndex OBJECT-TYPE
	SYNTAX		DmiInteger
	ACCESS		read-only
	STATUS		mandatory
	DESCRIPTION	"An index into the Redundancy Group table."
	::= {eRedundancyGroup 1}

a7014RedundancyType OBJECT-TYPE
	SYNTAX		INTEGER {
		vNone                                   	(0),
		vOther                                  	(1),
		vUnknown                                	(2),
		vCopy                                   	(3),
		vXor                                    	(4),
		vPplusq                                    	(5),
		vS                                      	(6),
		vPpluss                                    	(7)
	}
	ACCESS		read-only
	STATUS		mandatory
	DESCRIPTION	"This field specifies the type of the redundancy formed."
	::= {eRedundancyGroup 2}

SRedundancyGroupEvents ::= SEQUENCE {
	a7015RedundancyGroupEventType           	DmiInteger,
	a7015EventSeverity                      	DmiInteger,
	a7015EventIsStateBased                  	DmiInteger,
	a7015EventStateKey                      	DmiInteger,
	a7015AssociatedGroup                    	DmiDisplaystring,
	a7015EventSystem                        	DmiInteger,
	a7015EventSubsystem                     	DmiInteger,
	a7015EventSolution                      	DmiInteger,
	a7015InstanceDataPresent                	DmiInteger,
	a7015EventMessage                       	DmiDisplaystring,
	a7015VendorSpecificData                 	DmiOctetstring
}

tRedundancyGroupEvents OBJECT-TYPE
	SYNTAX		SEQUENCE OF SRedundancyGroupEvents
	ACCESS		not-accessible
	STATUS		mandatory
	DESCRIPTION	"Redundancy Group events."
	::= {dmtfGroups 7015}

eRedundancyGroupEvents OBJECT-TYPE
	SYNTAX		SRedundancyGroupEvents
	ACCESS		not-accessible
	STATUS		mandatory
	DESCRIPTION	""
	INDEX		{DmiComponentIndex, a7015AssociatedGroup}
	::= {tRedundancyGroupEvents 1}

a7015RedundancyGroupEventType OBJECT-TYPE
	SYNTAX		INTEGER {
		vRedundancyGroupExposed                 	(1),
		vRebuildInProgress                      	(2),
		vProtectionDisabled                     	(3),
		vRecalculationActive                    	(4),
		vVerifyInProgress                       	(5)
	}
	ACCESS		read-only
	STATUS		mandatory
	DESCRIPTION	"The type of Redundancy Group event that has occurred."
	::= {eRedundancyGroupEvents 1}

a7015EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eRedundancyGroupEvents 2}

a7015EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eRedundancyGroupEvents 3}

a7015EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eRedundancyGroupEvents 4}

a7015AssociatedGroup OBJECT-TYPE
	SYNTAX		DmiDisplaystring
	ACCESS		read-only
	STATUS		mandatory
	DESCRIPTION	"Class string of the group which originated the event."
	::= {eRedundancyGroupEvents 5}

a7015EventSystem OBJECT-TYPE
	SYNTAX		INTEGER {
		vOther                                  	(1),
		vUnknown                                	(2)
	}
	ACCESS		read-only
	STATUS		mandatory
	DESCRIPTION	"The major functional aspect of the product causing the fault."
	::= {eRedundancyGroupEvents 6}

a7015EventSubsystem OBJECT-TYPE
	SYNTAX		INTEGER {
		vOther                                  	(1),
		vUnknown                                	(2)
	}
	ACCESS		read-only
	STATUS		mandatory
	DESCRIPTION	"The minor functional aspect of the product causing the fault."
	::= {eRedundancyGroupEvents 7}

a7015EventSolution OBJECT-TYPE
	SYNTAX		INTEGER {
		vNotProvided                            	(1)
	}
	ACCESS		read-only
	STATUS		mandatory
	DESCRIPTION	"A solution to the problem that caused the event."
	::= {eRedundancyGroupEvents 8}

a7015InstanceDataPresent OBJECT-TYPE
	SYNTAX		INTEGER {
		vFalse                                  	(0),
		vTrue                                   	(1)
	}
	ACCESS		read-only
	STATUS		mandatory
	DESCRIPTION	"Indicates whether second event block contains instance-specific
data."
	::= {eRedundancyGroupEvents 9}

a7015EventMessage OBJECT-TYPE
	SYNTAX		DmiDisplaystring
	ACCESS		read-only
	STATUS		mandatory
	DESCRIPTION	"Auxiliary information related to the event."
	::= {eRedundancyGroupEvents 10}

a7015VendorSpecificData OBJECT-TYPE
	SYNTAX		DmiOctetstring
	ACCESS		read-only
	STATUS		mandatory
	DESCRIPTION	"Auxiliary information related to the event."
	::= {eRedundancyGroupEvents 11}

SSpareEvents ::= SEQUENCE {
	a7016SpareEventType                     	DmiInteger,
	a7016EventSeverity                      	DmiInteger,
	a7016EventIsStateBased                  	DmiInteger,
	a7016EventStateKey                      	DmiInteger,
	a7016AssociatedGroup                    	DmiDisplaystring,
	a7016EventSystem                        	DmiInteger,
	a7016EventSubsystem                     	DmiInteger,
	a7016EventSolution                      	DmiInteger,
	a7016InstanceDataPresent                	DmiInteger,
	a7016EventMessage                       	DmiDisplaystring,
	a7016VendorSpecificData                 	DmiOctetstring
}

tSpareEvents OBJECT-TYPE
	SYNTAX		SEQUENCE OF SSpareEvents
	ACCESS		not-accessible
	STATUS		mandatory
	DESCRIPTION	"Component Spare events."
	::= {dmtfGroups 7016}

eSpareEvents OBJECT-TYPE
	SYNTAX		SSpareEvents
	ACCESS		not-accessible
	STATUS		mandatory
	DESCRIPTION	""
	INDEX		{DmiComponentIndex, a7016AssociatedGroup}
	::= {tSpareEvents 1}

a7016SpareEventType OBJECT-TYPE
	SYNTAX		INTEGER {
		vComponentSpareBroken                   	(1),
		vComponentSpareInUse                    	(2),
		vComponentSpareReadying                 	(3),
		vCioEvent                               	(4)
	}
	ACCESS		read-only
	STATUS		mandatory
	DESCRIPTION	"The type of  Spare event that has occurred."
	::= {eSpareEvents 1}

a7016EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eSpareEvents 2}

a7016EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eSpareEvents 3}

a7016EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eSpareEvents 4}

a7016AssociatedGroup OBJECT-TYPE
	SYNTAX		DmiDisplaystring
	ACCESS		read-only
	STATUS		mandatory
	DESCRIPTION	"Class string of the group which originated the event."
	::= {eSpareEvents 5}

a7016EventSystem OBJECT-TYPE
	SYNTAX		INTEGER {
		vOther                                  	(1),
		vUnknown                                	(2),
		vDataSpare                              	(3),
		vComponentSpare                         	(4)
	}
	ACCESS		read-only
	STATUS		mandatory
	DESCRIPTION	"The major functional aspect of the product causing the fault."
	::= {eSpareEvents 6}

a7016EventSubsystem OBJECT-TYPE
	SYNTAX		INTEGER {
		vOther                                  	(1),
		vUnknown                                	(2)
	}
	ACCESS		read-only
	STATUS		mandatory
	DESCRIPTION	"The minor functional aspect of the product causing the fault."
	::= {eSpareEvents 7}

a7016EventSolution OBJECT-TYPE
	SYNTAX		INTEGER {
		vNotProvided                            	(1)
	}
	ACCESS		read-only
	STATUS		mandatory
	DESCRIPTION	"A solution to the problem that caused the event."
	::= {eSpareEvents 8}

a7016InstanceDataPresent OBJECT-TYPE
	SYNTAX		INTEGER {
		vFalse                                  	(0),
		vTrue                                   	(1)
	}
	ACCESS		read-only
	STATUS		mandatory
	DESCRIPTION	"Indicates whether second event block contains instance-specific
data."
	::= {eSpareEvents 9}

a7016EventMessage OBJECT-TYPE
	SYNTAX		DmiDisplaystring
	ACCESS		read-only
	STATUS		mandatory
	DESCRIPTION	"Auxiliary information related to the event."
	::= {eSpareEvents 10}

a7016VendorSpecificData OBJECT-TYPE
	SYNTAX		DmiOctetstring
	ACCESS		read-only
	STATUS		mandatory
	DESCRIPTION	"Auxiliary information related to the event."
	::= {eSpareEvents 11}

SMassStorageAssociation ::= SEQUENCE {
	a7017AssociationIndex                   	DmiInteger,
	a7017Type                               	DmiDisplaystring,
	a7017Reference1                         	DmiDisplaystring,
	a7017Reference2                         	DmiDisplaystring
}

tMassStorageAssociation OBJECT-TYPE
	SYNTAX		SEQUENCE OF SMassStorageAssociation
	ACCESS		not-accessible
	STATUS		mandatory
	DESCRIPTION	"Associations define the relationships between the various
components of the Storage Subsystem."
	::= {dmtfGroups 7017}

eMassStorageAssociation OBJECT-TYPE
	SYNTAX		SMassStorageAssociation
	ACCESS		not-accessible
	STATUS		mandatory
	DESCRIPTION	""
	INDEX		{DmiComponentIndex, a7017AssociationIndex}
	::= {tMassStorageAssociation 1}

a7017AssociationIndex OBJECT-TYPE
	SYNTAX		DmiInteger
	ACCESS		read-only
	STATUS		mandatory
	DESCRIPTION	"An index into the Association table."
	::= {eMassStorageAssociation 1}

a7017Type OBJECT-TYPE
	SYNTAX		DmiDisplaystring
	ACCESS		read-only
	STATUS		mandatory
	DESCRIPTION	"This field specifies the type of the association. One of
the following strings shall be used to represent a known Mass Storage Associatio
 type: Physical Organization, Logical Organization, Logical to Physical Organiza
ion,Redundancy Organization, Spare Organization, Cache, FRU, Operational
State,Statistical, SubComponentSoftware, or Worldwide Identifier."
	::= {eMassStorageAssociation 2}

a7017Reference1 OBJECT-TYPE
	SYNTAX		DmiDisplaystring
	ACCESS		read-only
	STATUS		mandatory
	DESCRIPTION	"A reference to an object.  The references shall use the format
of 'x-dmi//<locator>/dmi/row; cid=<>; gid=<>; key=<>'."
	::= {eMassStorageAssociation 3}

a7017Reference2 OBJECT-TYPE
	SYNTAX		DmiDisplaystring
	ACCESS		read-only
	STATUS		mandatory
	DESCRIPTION	"A reference to an object.  The references shall use the format
of 'x-dmi//<locator>/dmi/row; cid=<>; gid=<>; key=<>'."
	::= {eMassStorageAssociation 4}

SAssociationEvents ::= SEQUENCE {
	a7018AssociationEventType               	DmiInteger,
	a7018EventSeverity                      	DmiInteger,
	a7018EventIsStateBased                  	DmiInteger,
	a7018EventStateKey                      	DmiInteger,
	a7018AssociatedGroup                    	DmiDisplaystring,
	a7018EventSystem                        	DmiInteger,
	a7018EventSubsystem                     	DmiInteger,
	a7018EventSolution                      	DmiInteger,
	a7018InstanceDataPresent                	DmiInteger,
	a7018EventMessage                       	DmiDisplaystring,
	a7018VendorSpecificData                 	DmiOctetstring
}

tAssociationEvents OBJECT-TYPE
	SYNTAX		SEQUENCE OF SAssociationEvents
	ACCESS		not-accessible
	STATUS		mandatory
	DESCRIPTION	"Association events."
	::= {dmtfGroups 7018}

eAssociationEvents OBJECT-TYPE
	SYNTAX		SAssociationEvents
	ACCESS		not-accessible
	STATUS		mandatory
	DESCRIPTION	""
	INDEX		{DmiComponentIndex, a7018AssociatedGroup}
	::= {tAssociationEvents 1}

a7018AssociationEventType OBJECT-TYPE
	SYNTAX		INTEGER {
		vNewObjectDetected                      	(1),
		vExistingObjectReplaced                 	(2),
		vExistingObjectIsGone                   	(3)
	}
	ACCESS		read-only
	STATUS		mandatory
	DESCRIPTION	"The type of association where a change has occurred."
	::= {eAssociationEvents 1}

a7018EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eAssociationEvents 2}

a7018EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eAssociationEvents 3}

a7018EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eAssociationEvents 4}

a7018AssociatedGroup OBJECT-TYPE
	SYNTAX		DmiDisplaystring
	ACCESS		read-only
	STATUS		mandatory
	DESCRIPTION	"Class string of the group which originated the event."
	::= {eAssociationEvents 5}

a7018EventSystem OBJECT-TYPE
	SYNTAX		INTEGER {
		vStorageController                      	(0),
		vStorageDevice                          	(1),
		vBusPort                                	(2),
		vVolumeSet                              	(3),
		vProtectedSpaceExtent                   	(4),
		vAggregateProtectedSpaceExtent          	(5),
		vPhysicalExtent                         	(6),
		vAggregatePhysicalExtent                	(7),
		vRedundancyGroup                        	(8),
		vCache                                  	(9),
		vSoftwareComponent                      	(10),
		vSoftwareSignature                      	(11)
	}
	ACCESS		read-only
	STATUS		mandatory
	DESCRIPTION	"The association object type which is causing a change."
	::= {eAssociationEvents 6}

a7018EventSubsystem OBJECT-TYPE
	SYNTAX		INTEGER {
		vOther                                  	(1),
		vUnknown                                	(2)
	}
	ACCESS		read-only
	STATUS		mandatory
	DESCRIPTION	"The minor functional aspect of the product causing the fault."
	::= {eAssociationEvents 7}

a7018EventSolution OBJECT-TYPE
	SYNTAX		INTEGER {
		vNotProvided                            	(1)
	}
	ACCESS		read-only
	STATUS		mandatory
	DESCRIPTION	"A solution to the problem that caused the event."
	::= {eAssociationEvents 8}

a7018InstanceDataPresent OBJECT-TYPE
	SYNTAX		INTEGER {
		vFalse                                  	(0),
		vTrue                                   	(1)
	}
	ACCESS		read-only
	STATUS		mandatory
	DESCRIPTION	"Indicates whether second event block contains instance-specific
data."
	::= {eAssociationEvents 9}

a7018EventMessage OBJECT-TYPE
	SYNTAX		DmiDisplaystring
	ACCESS		read-only
	STATUS		mandatory
	DESCRIPTION	"Auxiliary information related to the event."
	::= {eAssociationEvents 10}

a7018VendorSpecificData OBJECT-TYPE
	SYNTAX		DmiOctetstring
	ACCESS		read-only
	STATUS		mandatory
	DESCRIPTION	"Auxiliary information related to the event."
	::= {eAssociationEvents 11}

SBusPortAssociation ::= SEQUENCE {
	a7019BusPortAssociationIndex            	DmiInteger,
	a7019NegotiatedSpeed                    	DmiInteger,
	a7019NegotiatedWidth                    	DmiInteger
}

tBusPortAssociation OBJECT-TYPE
	SYNTAX		SEQUENCE OF SBusPortAssociation
	ACCESS		not-accessible
	STATUS		mandatory
	DESCRIPTION	"Bus Port Association "
	::= {dmtfGroups 7019}

eBusPortAssociation OBJECT-TYPE
	SYNTAX		SBusPortAssociation
	ACCESS		not-accessible
	STATUS		mandatory
	DESCRIPTION	""
	INDEX		{DmiComponentIndex, a7019BusPortAssociationIndex}
	::= {tBusPortAssociation 1}

a7019BusPortAssociationIndex OBJECT-TYPE
	SYNTAX		DmiInteger
	ACCESS		read-only
	STATUS		mandatory
	DESCRIPTION	"An index into the Bus Port Association table.  This index
is the same as the index in the Association group that defines the bus port
association."
	::= {eBusPortAssociation 1}

a7019NegotiatedSpeed OBJECT-TYPE
	SYNTAX		DmiInteger
	ACCESS		read-only
	STATUS		mandatory
	DESCRIPTION	"The maximum burst transfer rate, in millions of bytes, which
was negotiated between the two associated bus ports."
	::= {eBusPortAssociation 2}

a7019NegotiatedWidth OBJECT-TYPE
	SYNTAX		DmiInteger
	ACCESS		read-only
	STATUS		mandatory
	DESCRIPTION	"The width, in bits, of the bus ports data path which was
negotiated between the two associated bus ports."
	::= {eBusPortAssociation 3}

SComponentSpareAssociation ::= SEQUENCE {
	a7020ComponentSpareIndex                	DmiInteger,
	a7020SpareFunctioningState              	DmiInteger
}

tComponentSpareAssociation OBJECT-TYPE
	SYNTAX		SEQUENCE OF SComponentSpareAssociation
	ACCESS		not-accessible
	STATUS		mandatory
	DESCRIPTION	"Component Spare Association"
	::= {dmtfGroups 7020}

eComponentSpareAssociation OBJECT-TYPE
	SYNTAX		SComponentSpareAssociation
	ACCESS		not-accessible
	STATUS		mandatory
	DESCRIPTION	""
	INDEX		{DmiComponentIndex, a7020ComponentSpareIndex}
	::= {tComponentSpareAssociation 1}

a7020ComponentSpareIndex OBJECT-TYPE
	SYNTAX		DmiInteger
	ACCESS		read-only
	STATUS		mandatory
	DESCRIPTION	"An index into the Component Spare table.  This index is the
same as the index in the Association group which defines the spare association."
	::= {eComponentSpareAssociation 1}

a7020SpareFunctioningState OBJECT-TYPE
	SYNTAX		INTEGER {
		vOther                                  	(1),
		vUnknown                                	(2),
		vInactivestandby                        	(3),
		vActivestandby                          	(4),
		vActivestandbyThatInAdditionLoadBalances	(5)
	}
	ACCESS		read-only
	STATUS		mandatory
	DESCRIPTION	"This field specifies the functioning state of the spare."
	::= {eComponentSpareAssociation 2}

SWorldwideIdentifer ::= SEQUENCE {
	a7021WorldwideIdentifierIndex           	DmiInteger,
	a7021WorldwideIdentifierType            	DmiInteger,
	a7021WorldwideIdentifier                	DmiDisplaystring
}

tWorldwideIdentifer OBJECT-TYPE
	SYNTAX		SEQUENCE OF SWorldwideIdentifer
	ACCESS		not-accessible
	STATUS		mandatory
	DESCRIPTION	"The Worldwide Identifer"
	::= {dmtfGroups 7021}

eWorldwideIdentifer OBJECT-TYPE
	SYNTAX		SWorldwideIdentifer
	ACCESS		not-accessible
	STATUS		mandatory
	DESCRIPTION	""
	INDEX		{DmiComponentIndex, a7021WorldwideIdentifierIndex}
	::= {tWorldwideIdentifer 1}

a7021WorldwideIdentifierIndex OBJECT-TYPE
	SYNTAX		DmiInteger
	ACCESS		read-only
	STATUS		mandatory
	DESCRIPTION	"An index into the Worldwide Identifier table."
	::= {eWorldwideIdentifer 1}

a7021WorldwideIdentifierType OBJECT-TYPE
	SYNTAX		INTEGER {
		vOther                                  	(1),
		vUnknown                                	(2),
		vNone                                   	(3),
		vVendorIdProductIdSerialNumber          	(4),
		vIeeeExtendedUniqueIdentifier64-bit     	(5),
		vFc-ph64-bitName-identifier             	(6),
		vBinary                                 	(7),
		vUnicode                                	(8),
		vLanMacAddress                          	(9),
		vWanAccessAddress                       	(10)
	}
	ACCESS		read-only
	STATUS		mandatory
	DESCRIPTION	"The type of identifier displayed by the Worldwide Identifier
attribute."
	::= {eWorldwideIdentifer 2}

a7021WorldwideIdentifier OBJECT-TYPE
	SYNTAX		DmiDisplaystring
	ACCESS		read-only
	STATUS		mandatory
	DESCRIPTION	"The Worldwide identifier for this device."
	::= {eWorldwideIdentifer 3}

SMassStorageStatistics ::= SEQUENCE {
	a7022StatisticsIndex                    	DmiInteger,
	a7022BlocksRead                         	DmiCounter,
	a7022BlocksWritten                      	DmiCounter,
	a7022ReadCommandsIssued                 	DmiCounter,
	a7022WriteCommandsIssued                	DmiCounter,
	a7022IoRange0Read                       	DmiCounter,
	a7022IoRange1Read                       	DmiCounter,
	a7022IoRange2Read                       	DmiCounter,
	a7022IoRange3Read                       	DmiCounter,
	a7022IoRange4Read                       	DmiCounter,
	a7022IoRange5Read                       	DmiCounter,
	a7022IoRange6Read                       	DmiCounter,
	a7022IoRange7Read                       	DmiCounter,
	a7022IoRange8Read                       	DmiCounter,
	a7022IoRange9Read                       	DmiCounter,
	a7022IoRange10Read                      	DmiCounter,
	a7022IoRange11Read                      	DmiCounter,
	a7022IoRange12Read                      	DmiCounter,
	a7022IoRange0Written                    	DmiCounter,
	a7022IoRange1Written                    	DmiCounter,
	a7022IoRange2Written                    	DmiCounter,
	a7022IoRange3Written                    	DmiCounter,
	a7022IoRange4Written                    	DmiCounter,
	a7022IoRange5Written                    	DmiCounter,
	a7022IoRange6Written                    	DmiCounter,
	a7022IoRange7Written                    	DmiCounter,
	a7022IoRange8Written                    	DmiCounter,
	a7022IoRange9Written                    	DmiCounter,
	a7022IoRange10Written                   	DmiCounter,
	a7022IoRange11Written                   	DmiCounter,
	a7022IoRange12Written                   	DmiCounter
}

tMassStorageStatistics OBJECT-TYPE
	SYNTAX		SEQUENCE OF SMassStorageStatistics
	ACCESS		not-accessible
	STATUS		mandatory
	DESCRIPTION	"This group defines statistics that may be used by any other
group."
	::= {dmtfGroups 7022}

eMassStorageStatistics OBJECT-TYPE
	SYNTAX		SMassStorageStatistics
	ACCESS		not-accessible
	STATUS		mandatory
	DESCRIPTION	""
	INDEX		{DmiComponentIndex, a7022StatisticsIndex}
	::= {tMassStorageStatistics 1}

a7022StatisticsIndex OBJECT-TYPE
	SYNTAX		DmiInteger
	ACCESS		read-only
	STATUS		mandatory
	DESCRIPTION	"An index into the Statistics table."
	::= {eMassStorageStatistics 1}

a7022BlocksRead OBJECT-TYPE
	SYNTAX		DmiCounter
	ACCESS		read-only
	STATUS		mandatory
	DESCRIPTION	"The accumulated count of 512 byte blocks of data read."
	::= {eMassStorageStatistics 2}

a7022BlocksWritten OBJECT-TYPE
	SYNTAX		DmiCounter
	ACCESS		read-only
	STATUS		mandatory
	DESCRIPTION	"The accumulated count of 512 byte blocks of data written."
	::= {eMassStorageStatistics 3}

a7022ReadCommandsIssued OBJECT-TYPE
	SYNTAX		DmiCounter
	ACCESS		read-only
	STATUS		mandatory
	DESCRIPTION	"The accumulated count of the number of read commands issued."
	::= {eMassStorageStatistics 4}

a7022WriteCommandsIssued OBJECT-TYPE
	SYNTAX		DmiCounter
	ACCESS		read-only
	STATUS		mandatory
	DESCRIPTION	"The accumulated count of the number of write commands issued."
	::= {eMassStorageStatistics 5}

a7022IoRange0Read OBJECT-TYPE
	SYNTAX		DmiCounter
	ACCESS		read-only
	STATUS		mandatory
	DESCRIPTION	"The number of read commands issued, size < 512 bytes."
	::= {eMassStorageStatistics 6}

a7022IoRange1Read OBJECT-TYPE
	SYNTAX		DmiCounter
	ACCESS		read-only
	STATUS		mandatory
	DESCRIPTION	"The number of read commands issued, 512 bytes <= size < 1K
bytes."
	::= {eMassStorageStatistics 7}

a7022IoRange2Read OBJECT-TYPE
	SYNTAX		DmiCounter
	ACCESS		read-only
	STATUS		mandatory
	DESCRIPTION	"The number of read commands issued, 1K bytes <= size < 2K
bytes."
	::= {eMassStorageStatistics 8}

a7022IoRange3Read OBJECT-TYPE
	SYNTAX		DmiCounter
	ACCESS		read-only
	STATUS		mandatory
	DESCRIPTION	"The number of read commands issued, 2K bytes <= size < 4K
bytes."
	::= {eMassStorageStatistics 9}

a7022IoRange4Read OBJECT-TYPE
	SYNTAX		DmiCounter
	ACCESS		read-only
	STATUS		mandatory
	DESCRIPTION	"The number of read commands issued, 4K bytes <= size < 8K
bytes."
	::= {eMassStorageStatistics 10}

a7022IoRange5Read OBJECT-TYPE
	SYNTAX		DmiCounter
	ACCESS		read-only
	STATUS		mandatory
	DESCRIPTION	"The number of read commands issued, 8K bytes <= size < 16K
bytes."
	::= {eMassStorageStatistics 11}

a7022IoRange6Read OBJECT-TYPE
	SYNTAX		DmiCounter
	ACCESS		read-only
	STATUS		mandatory
	DESCRIPTION	"The number of read commands issued, 16K bytes <= size < 32K
bytes."
	::= {eMassStorageStatistics 12}

a7022IoRange7Read OBJECT-TYPE
	SYNTAX		DmiCounter
	ACCESS		read-only
	STATUS		mandatory
	DESCRIPTION	"The number of read commands issued, 32K bytes <= size < 64K
bytes."
	::= {eMassStorageStatistics 13}

a7022IoRange8Read OBJECT-TYPE
	SYNTAX		DmiCounter
	ACCESS		read-only
	STATUS		mandatory
	DESCRIPTION	"The number of read commands issued, 64K bytes <= size < 128K
bytes."
	::= {eMassStorageStatistics 14}

a7022IoRange9Read OBJECT-TYPE
	SYNTAX		DmiCounter
	ACCESS		read-only
	STATUS		mandatory
	DESCRIPTION	"The number of read commands issued, 128K bytes <= size <
256K bytes."
	::= {eMassStorageStatistics 15}

a7022IoRange10Read OBJECT-TYPE
	SYNTAX		DmiCounter
	ACCESS		read-only
	STATUS		mandatory
	DESCRIPTION	"The number of read commands issued, 256K bytes <= size <
512K bytes."
	::= {eMassStorageStatistics 16}

a7022IoRange11Read OBJECT-TYPE
	SYNTAX		DmiCounter
	ACCESS		read-only
	STATUS		mandatory
	DESCRIPTION	"The number of read commands issued, 512K bytes <= size <
1M bytes."
	::= {eMassStorageStatistics 17}

a7022IoRange12Read OBJECT-TYPE
	SYNTAX		DmiCounter
	ACCESS		read-only
	STATUS		mandatory
	DESCRIPTION	"The number of read commands issued, size >= 1M bytes."
	::= {eMassStorageStatistics 18}

a7022IoRange0Written OBJECT-TYPE
	SYNTAX		DmiCounter
	ACCESS		read-only
	STATUS		mandatory
	DESCRIPTION	"The number of write commands issued, size < 512 bytes."
	::= {eMassStorageStatistics 19}

a7022IoRange1Written OBJECT-TYPE
	SYNTAX		DmiCounter
	ACCESS		read-only
	STATUS		mandatory
	DESCRIPTION	"The number of write commands issued, 512 bytes <= size <
1K bytes."
	::= {eMassStorageStatistics 20}

a7022IoRange2Written OBJECT-TYPE
	SYNTAX		DmiCounter
	ACCESS		read-only
	STATUS		mandatory
	DESCRIPTION	"The number of write commands issued, 1K bytes <= size < 2K
bytes."
	::= {eMassStorageStatistics 21}

a7022IoRange3Written OBJECT-TYPE
	SYNTAX		DmiCounter
	ACCESS		read-only
	STATUS		mandatory
	DESCRIPTION	"The number of write commands issued, 2K bytes <= size < 4K
bytes."
	::= {eMassStorageStatistics 22}

a7022IoRange4Written OBJECT-TYPE
	SYNTAX		DmiCounter
	ACCESS		read-only
	STATUS		mandatory
	DESCRIPTION	"The number of write commands issued, 4K bytes <= size < 8K
bytes."
	::= {eMassStorageStatistics 23}

a7022IoRange5Written OBJECT-TYPE
	SYNTAX		DmiCounter
	ACCESS		read-only
	STATUS		mandatory
	DESCRIPTION	"The number of write commands issued, 8K bytes <= size < 16K
bytes."
	::= {eMassStorageStatistics 24}

a7022IoRange6Written OBJECT-TYPE
	SYNTAX		DmiCounter
	ACCESS		read-only
	STATUS		mandatory
	DESCRIPTION	"The number of write commands issued, 16K bytes <= size <
32K bytes."
	::= {eMassStorageStatistics 25}

a7022IoRange7Written OBJECT-TYPE
	SYNTAX		DmiCounter
	ACCESS		read-only
	STATUS		mandatory
	DESCRIPTION	"The number of write commands issued, 32K bytes <= size <
64K bytes."
	::= {eMassStorageStatistics 26}

a7022IoRange8Written OBJECT-TYPE
	SYNTAX		DmiCounter
	ACCESS		read-only
	STATUS		mandatory
	DESCRIPTION	"The number of write commands issued, 64K bytes <= size <
128K bytes."
	::= {eMassStorageStatistics 27}

a7022IoRange9Written OBJECT-TYPE
	SYNTAX		DmiCounter
	ACCESS		read-only
	STATUS		mandatory
	DESCRIPTION	"The number of write commands issued, 128K bytes <= size <
256K bytes."
	::= {eMassStorageStatistics 28}

a7022IoRange10Written OBJECT-TYPE
	SYNTAX		DmiCounter
	ACCESS		read-only
	STATUS		mandatory
	DESCRIPTION	"The number of write commands issued, 256K bytes <= size <
512K bytes."
	::= {eMassStorageStatistics 29}

a7022IoRange11Written OBJECT-TYPE
	SYNTAX		DmiCounter
	ACCESS		read-only
	STATUS		mandatory
	DESCRIPTION	"The number of write commands issued, 512K bytes <= size <
1M bytes."
	::= {eMassStorageStatistics 30}

a7022IoRange12Written OBJECT-TYPE
	SYNTAX		DmiCounter
	ACCESS		read-only
	STATUS		mandatory
	DESCRIPTION	"The number of write commands issued, size >= 1M bytes."
	::= {eMassStorageStatistics 31}

SOverallStatus ::= SEQUENCE {
	a7023OverallStatus                      	DmiInteger
}

tOverallStatus OBJECT-TYPE
	SYNTAX		SEQUENCE OF SOverallStatus
	ACCESS		not-accessible
	STATUS		mandatory
	DESCRIPTION	"This group provides the overall status of the Adaptec CI/O
MIF objects."
	::= {dmtfGroups 7023}

eOverallStatus OBJECT-TYPE
	SYNTAX		SOverallStatus
	ACCESS		not-accessible
	STATUS		mandatory
	DESCRIPTION	""
	INDEX		{DmiComponentIndex}
	::= {tOverallStatus 1}

a7023OverallStatus OBJECT-TYPE
	SYNTAX		INTEGER {
		vOk                                     	(1),
		vWarning                                	(2),
		vFailure                                	(3),
		vUnknown                                	(4),
		vOther                                  	(5)
	}
	ACCESS		read-only
	STATUS		mandatory
	DESCRIPTION	"The overall status of the Adaptec CI/O MIF objects."
	::= {eOverallStatus 1}

SOperationalState ::= SEQUENCE {
	a7024OperationalStateIndex              	DmiInteger,
	a7024DeviceGroupIndex                   	DmiInteger,
	a7024OperationalStatus                  	DmiInteger,
	a7024UsageState                         	DmiInteger,
	a7024AvailabilityStatus                 	DmiInteger,
	a7024AdministrativeState                	DmiInteger,
	a7024FatalErrorCount                    	DmiCounter,
	a7024MajorErrorCount                    	DmiCounter,
	a7024WarningErrorCount                  	DmiCounter,
	a7024CurrentErrorStatus                 	DmiInteger,
	a7024DevicePredictedFailureStatus       	DmiInteger
}

tOperationalState OBJECT-TYPE
	SYNTAX		SEQUENCE OF SOperationalState
	ACCESS		not-accessible
	STATUS		mandatory
	DESCRIPTION	"This group provides the operational state, usage, and availabili
y status, and administrative state indicators for specific Device Group instance
."
	::= {dmtfGroups 7024}

eOperationalState OBJECT-TYPE
	SYNTAX		SOperationalState
	ACCESS		not-accessible
	STATUS		mandatory
	DESCRIPTION	""
	INDEX		{DmiComponentIndex, a7024OperationalStateIndex}
	::= {tOperationalState 1}

a7024OperationalStateIndex OBJECT-TYPE
	SYNTAX		DmiInteger
	ACCESS		read-only
	STATUS		mandatory
	DESCRIPTION	"The Index into the Operational State table."
	::= {eOperationalState 1}

a7024DeviceGroupIndex OBJECT-TYPE
	SYNTAX		DmiInteger
	ACCESS		read-only
	STATUS		mandatory
	DESCRIPTION	"The group ID of the group referencing this instance."
	::= {eOperationalState 2}

a7024OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device Group instance."
	::= {eOperationalState 3}

a7024UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalState 4}

a7024AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalState 5}

a7024AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalState 6}

a7024FatalErrorCount OBJECT-TYPE
	SYNTAX		DmiCounter
	ACCESS		read-only
	STATUS		mandatory
	DESCRIPTION	"The accumulated Fatal or Non-recoverable error count for
this Device Group instance."
	::= {eOperationalState 7}

a7024MajorErrorCount OBJECT-TYPE
	SYNTAX		DmiCounter
	ACCESS		read-only
	STATUS		mandatory
	DESCRIPTION	"The accumulated Major or Critical error count for this Device
Group instance."
	::= {eOperationalState 8}

a7024WarningErrorCount OBJECT-TYPE
	SYNTAX		DmiCounter
	ACCESS		read-only
	STATUS		mandatory
	DESCRIPTION	"The accumulated Warning or Non-Critical error count for this
Device Group instance."
	::= {eOperationalState 9}

a7024CurrentErrorStatus OBJECT-TYPE
	SYNTAX		INTEGER {
		vOther                                  	(1),
		vUnknown                                	(2),
		vOk                                     	(3),
		vNon-critical1                          	(4),
		vCritical                               	(5),
		vNon-recoverable1                       	(6)
	}
	ACCESS		read-only
	STATUS		mandatory
	DESCRIPTION	"This attribute presents the current error status for this
Device Group instance. The most critical error status in effect should be
presented. I.e. if a part of the Device Group instance is 'Critical', while
other status is 'Non-critical' then the status 'Critical' should be reported."
	::= {eOperationalState 10}

a7024DevicePredictedFailureStatus OBJECT-TYPE
	SYNTAX		INTEGER {
		vOther                                  	(1),
		vUnknown                                	(2),
		vNotSupportedByThisDevice               	(3),
		vNoFailurePredictedByTheDevice          	(4),
		vDeviceFailurePredictedByTheDevice      	(5),
		vMediaFailurePredictedByTheDevice       	(6)
	}
	ACCESS		read-only
	STATUS		mandatory
	DESCRIPTION	"Enumeration describing the current Device Predicted Failure
Status (e.g.: the S.M.A.R.T. status of the device)."
	::= {eOperationalState 11}

SEventLogCount ::= SEQUENCE {
	a7025EventLogCount                      	DmiInteger
}

tEventLogCount OBJECT-TYPE
	SYNTAX		SEQUENCE OF SEventLogCount
	ACCESS		not-accessible
	STATUS		mandatory
	DESCRIPTION	"Count of the number of entries in the event log table."
	::= {dmtfGroups 7025}

eEventLogCount OBJECT-TYPE
	SYNTAX		SEventLogCount
	ACCESS		not-accessible
	STATUS		mandatory
	DESCRIPTION	""
	INDEX		{DmiComponentIndex}
	::= {tEventLogCount 1}

a7025EventLogCount OBJECT-TYPE
	SYNTAX		DmiInteger
	ACCESS		read-only
	STATUS		mandatory
	DESCRIPTION	"Count of the number of entries in the event log table."
	::= {eEventLogCount 1}

SEventLog ::= SEQUENCE {
	a7026EventLogIndex                      	DmiInteger,
	a7026EventLogEntry                      	DmiDisplaystring,
	a7026EventLogTimestamp                  	DmiInteger
}

tEventLog OBJECT-TYPE
	SYNTAX		SEQUENCE OF SEventLog
	ACCESS		not-accessible
	STATUS		mandatory
	DESCRIPTION	"This group provides a log of previous events."
	::= {dmtfGroups 7026}

eEventLog OBJECT-TYPE
	SYNTAX		SEventLog
	ACCESS		not-accessible
	STATUS		mandatory
	DESCRIPTION	""
	INDEX		{DmiComponentIndex, a7026EventLogIndex}
	::= {tEventLog 1}

a7026EventLogIndex OBJECT-TYPE
	SYNTAX		DmiInteger
	ACCESS		read-only
	STATUS		mandatory
	DESCRIPTION	"The Index into the Event Log table."
	::= {eEventLog 1}

a7026EventLogEntry OBJECT-TYPE
	SYNTAX		DmiDisplaystring
	ACCESS		read-only
	STATUS		mandatory
	DESCRIPTION	"An event log entry."
	::= {eEventLog 2}

a7026EventLogTimestamp OBJECT-TYPE
	SYNTAX		DmiInteger
	ACCESS		read-only
	STATUS		mandatory
	DESCRIPTION	"The number of seconds that have elapsed between powerup and
the event."
	::= {eEventLog 3}

SEventState ::= SEQUENCE {
	a7027EventStateIndex                    	DmiInteger,
	a7027EventGenerationGroupClass          	DmiDisplaystring,
	a7027EventType                          	DmiInteger,
	a7027CurrentState                       	DmiInteger,
	a7027AssociatedGroupObject              	DmiDisplaystring
}

tEventState OBJECT-TYPE
	SYNTAX		SEQUENCE OF SEventState
	ACCESS		not-accessible
	STATUS		mandatory
	DESCRIPTION	"This group holds the current state for state-based events."
	::= {dmtfGroups 7027}

eEventState OBJECT-TYPE
	SYNTAX		SEventState
	ACCESS		not-accessible
	STATUS		mandatory
	DESCRIPTION	""
	INDEX		{DmiComponentIndex, a7027EventStateIndex}
	::= {tEventState 1}

a7027EventStateIndex OBJECT-TYPE
	SYNTAX		DmiInteger
	ACCESS		read-only
	STATUS		mandatory
	DESCRIPTION	"The Index into the Event State table."
	::= {eEventState 1}

a7027EventGenerationGroupClass OBJECT-TYPE
	SYNTAX		DmiDisplaystring
	ACCESS		read-only
	STATUS		mandatory
	DESCRIPTION	"The Class String of the event generator group."
	::= {eEventState 2}

a7027EventType OBJECT-TYPE
	SYNTAX		DmiInteger
	ACCESS		read-only
	STATUS		mandatory
	DESCRIPTION	"Type of the event (same as Event Type attribute in event
template)."
	::= {eEventState 3}

a7027CurrentState OBJECT-TYPE
	SYNTAX		INTEGER {
		vOk                                     	(4),
		vNon-critical                           	(8),
		vCritical                               	(10),
		vNon-recoverable                        	(12)
	}
	ACCESS		read-only
	STATUS		mandatory
	DESCRIPTION	"Current state of the event type identified by the Event Type
attribute."
	::= {eEventState 4}

a7027AssociatedGroupObject OBJECT-TYPE
	SYNTAX		DmiDisplaystring
	ACCESS		read-only
	STATUS		mandatory
	DESCRIPTION	"Object reference to spare causing event.  The references
shall use the format of 'x-dmi//<locator>/dmi/row; cid=<>; gid=<>; key=<>'."
	::= {eEventState 5}

trap1ForDevices TRAP-TYPE
   ENTERPRISE eStorageDevicesEvents 
   VARIABLES {
	a7002StorageDevicesEventType,
	a7002EventSeverity,
	a7002EventIsStateBased,
	a7002EventStateKey,
	a7002AssociatedGroup,
	a7002EventSystem,
	a7002EventSubsystem,
	a7002EventSolution,
	a7002InstanceDataPresent,
	a7002EventMessage,
	a7002VendorSpecificData,
	a7001StorageDeviceIndex
}

DESCRIPTION "RebuildInProgress"

::=1

trap2ForDevices TRAP-TYPE
   ENTERPRISE eStorageDevicesEvents 
   VARIABLES {
	a7002StorageDevicesEventType,
	a7002EventSeverity,
	a7002EventIsStateBased,
	a7002EventStateKey,
	a7002AssociatedGroup,
	a7002EventSystem,
	a7002EventSubsystem,
	a7002EventSolution,
	a7002InstanceDataPresent,
	a7002EventMessage,
	a7002VendorSpecificData,
	a7001StorageDeviceIndex
}

DESCRIPTION "StorageDeviceReadying"

::=2

trap3ForDevices TRAP-TYPE
   ENTERPRISE eStorageDevicesEvents 
   VARIABLES {
	a7002StorageDevicesEventType,
	a7002EventSeverity,
	a7002EventIsStateBased,
	a7002EventStateKey,
	a7002AssociatedGroup,
	a7002EventSystem,
	a7002EventSubsystem,
	a7002EventSolution,
	a7002InstanceDataPresent,
	a7002EventMessage,
	a7002VendorSpecificData,
	a7001StorageDeviceIndex
}

DESCRIPTION "StorageDeviceError"

::=3

trap4ForDevices TRAP-TYPE
   ENTERPRISE eStorageDevicesEvents 
   VARIABLES {
	a7002StorageDevicesEventType,
	a7002EventSeverity,
	a7002EventIsStateBased,
	a7002EventStateKey,
	a7002AssociatedGroup,
	a7002EventSystem,
	a7002EventSubsystem,
	a7002EventSolution,
	a7002InstanceDataPresent,
	a7002EventMessage,
	a7002VendorSpecificData,
	a7001StorageDeviceIndex
}

DESCRIPTION "Self-monitoringWarning"

::=4

trap5ForDevices TRAP-TYPE
   ENTERPRISE eStorageDevicesEvents 
   VARIABLES {
	a7002StorageDevicesEventType,
	a7002EventSeverity,
	a7002EventIsStateBased,
	a7002EventStateKey,
	a7002AssociatedGroup,
	a7002EventSystem,
	a7002EventSubsystem,
	a7002EventSolution,
	a7002InstanceDataPresent,
	a7002EventMessage,
	a7002VendorSpecificData,
	a7001StorageDeviceIndex
}

DESCRIPTION "CioEvent"

::=5

trap1ForController TRAP-TYPE
   ENTERPRISE eStorageControllerEvents 
   VARIABLES {

	a7004StorageControllerEventType,
	a7004EventSeverity,
	a7004EventIsStateBased,
	a7004EventStateKey,
	a7004AssociatedGroup,
	a7004EventSystem,
	a7004EventSubsystem,
	a7004EventSolution,
	a7004InstanceDataPresent,
	a7004EventMessage,
	a7004VendorSpecificData,
	a7003ControllerIndex
}

DESCRIPTION "StorageControllerError"

::=1

trap2ForController TRAP-TYPE
   ENTERPRISE eStorageControllerEvents 
   VARIABLES {

	a7004StorageControllerEventType,
	a7004EventSeverity,
	a7004EventIsStateBased,
	a7004EventStateKey,
	a7004AssociatedGroup,
	a7004EventSystem,
	a7004EventSubsystem,
	a7004EventSolution,
	a7004InstanceDataPresent,
	a7004EventMessage,
	a7004VendorSpecificData,
	a7003ControllerIndex
}

DESCRIPTION "Self-monitoringWarning1"

::=2

trap3ForController TRAP-TYPE
   ENTERPRISE eStorageControllerEvents 
   VARIABLES {

	a7004StorageControllerEventType,
	a7004EventSeverity,
	a7004EventIsStateBased,
	a7004EventStateKey,
	a7004AssociatedGroup,
	a7004EventSystem,
	a7004EventSubsystem,
	a7004EventSolution,
	a7004InstanceDataPresent,
	a7004EventMessage,
	a7004VendorSpecificData,
	a7003ControllerIndex
}

DESCRIPTION "CioEvent"

::=3


trap1ForEnclosure TRAP-TYPE
   ENTERPRISE eEnclosureEvents 
   VARIABLES {

	a7006EnclosureEventType ,
	a7006EventSeverity,
	a7006EventIsStateBased,
	a7006EventStateKey,
	a7006AssociatedGroup,
	a7006EventSystem,
	a7006EventSubsystem,
	a7006EventSolution,
	a7006InstanceDataPresentr,
	a7006EventMessage,
	a7006VendorSpecificData,
	a7005EnclosureIndex
}

DESCRIPTION "CioEvent"

::=1


trap1ForBusPort TRAP-TYPE
   ENTERPRISE eBusPortEvents 
   VARIABLES {

	a7008BusPortEventType,
	a7008EventSeverity,
	a7008EventIsStateBased,
	a7008EventStateKey,
	a7008AssociatedGroup,
	a7008EventSystem,
	a7008EventSubsystem,
	a7008EventSolution,
	a7008InstanceDataPresent,
	a7008EventMessage,
	a7008VendorSpecificData,
	a7007BusPortIndex
}

DESCRIPTION "BusPortError"

::=1

trap1ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "VolumeSetExposed"

::=1

trap2ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "RebuildInProgress"

::=2

trap3ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "ProtectionDisabled"

::=3

trap4ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "VolumeSetReadying"

::=4

trap5ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "RecalculateActive"

::=5

trap6ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "SpareInUse"

::=6

trap7ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "VerifyInProgress"

::=7

trap8ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "VolumeSetBroken"

::=8

trap9ForVolumeSet TRAP-TYPE
   ENTERPRISE eVolumeSetEvents 
   VARIABLES {

	a7012VolumeSetEventType,
	a7012EventSeverity,
	a7012EventIsStateBased,
	a7012EventStateKey,
	a7012AssociatedGroup,
	a7012EventSystem,
	a7012EventSubsystem,
	a7012EventSolution,
	a7012InstanceDataPresent,
	a7012EventMessage,
	a7012VendorSpecificData,
	a7011VolumeSetIndex

}

DESCRIPTION "CioEvent"

::=9



trap1ForSetActivity TRAP-TYPE
   ENTERPRISE eVolumeSetActivityEvents 
   VARIABLES {

	a7013VolumeSetEventType,
	a7013EventSeverity,
	a7013EventIsStateBased,
	a7013EventStateKey,
	a7013AssociatedGroup,
	a7013EventSystem,
	a7013EventSubsystem,
	a7013EventSolution,
	a7013InstanceDataPresent,
	a7013EventMessage,
	a7013VendorSpecificData, 
	a7011VolumeSetIndex

}

DESCRIPTION "CioEvent"

::=1

trap1ForRedundancyGroup TRAP-TYPE
   ENTERPRISE eRedundancyGroupEvents 
   VARIABLES {

	a7015RedundancyGroupEventType,
	a7015EventSeverity,
	a7015EventIsStateBased,
	a7015EventStateKey,
	a7015AssociatedGroup,
	a7015EventSystem,
	a7015EventSubsystem,
	a7015EventSolution,
	a7015InstanceDataPresent,
	a7015EventMessage,
	a7015VendorSpecificData,
	a7014RedundancyGroupIndex

}

DESCRIPTION "RedundancyGroupExposed"

::=1

trap2ForRedundancyGroup TRAP-TYPE
   ENTERPRISE eRedundancyGroupEvents 
   VARIABLES {

	a7015RedundancyGroupEventType,
	a7015EventSeverity,
	a7015EventIsStateBased,
	a7015EventStateKey,
	a7015AssociatedGroup,
	a7015EventSystem,
	a7015EventSubsystem,
	a7015EventSolution,
	a7015InstanceDataPresent,
	a7015EventMessage,
	a7015VendorSpecificData,
	a7014RedundancyGroupIndex

}

DESCRIPTION "RebuildInProgress"

::=2

trap3ForRedundancyGroup TRAP-TYPE
   ENTERPRISE eRedundancyGroupEvents 
   VARIABLES {

	a7015RedundancyGroupEventType,
	a7015EventSeverity,
	a7015EventIsStateBased,
	a7015EventStateKey,
	a7015AssociatedGroup,
	a7015EventSystem,
	a7015EventSubsystem,
	a7015EventSolution,
	a7015InstanceDataPresent,
	a7015EventMessage,
	a7015VendorSpecificData,
	a7014RedundancyGroupIndex

}

DESCRIPTION "ProtectionDisabled"

::=3

trap4ForRedundancyGroup TRAP-TYPE
   ENTERPRISE eRedundancyGroupEvents 
   VARIABLES {

	a7015RedundancyGroupEventType,
	a7015EventSeverity,
	a7015EventIsStateBased,
	a7015EventStateKey,
	a7015AssociatedGroup,
	a7015EventSystem,
	a7015EventSubsystem,
	a7015EventSolution,
	a7015InstanceDataPresent,
	a7015EventMessage,
	a7015VendorSpecificData,
	a7014RedundancyGroupIndex

}

DESCRIPTION "RecalculationActive"

::=4

trap5ForRedundancyGroup TRAP-TYPE
   ENTERPRISE eRedundancyGroupEvents 
   VARIABLES {

	a7015RedundancyGroupEventType,
	a7015EventSeverity,
	a7015EventIsStateBased,
	a7015EventStateKey,
	a7015AssociatedGroup,
	a7015EventSystem,
	a7015EventSubsystem,
	a7015EventSolution,
	a7015InstanceDataPresent,
	a7015EventMessage,
	a7015VendorSpecificData,
	a7014RedundancyGroupIndex

}

DESCRIPTION "VerifyInProgress"

::=5


trap1ForSpareEvents TRAP-TYPE
   ENTERPRISE eSpareEvents 
   VARIABLES {

	a7016SpareEventType,
	a7016EventSeverity,
	a7016EventIsStateBased,
	a7016EventStateKey,
	a7016AssociatedGroup,
	a7016EventSystem,
	a7016EventSubsystem,
	a7016EventSolution,
	a7016InstanceDataPresent,
	a7016EventMessage,
	a7016VendorSpecificData,
	a7020ComponentSpareIndex
}

DESCRIPTION "ComponentSpareBroken"

::=1


trap2ForSpareEvents TRAP-TYPE
   ENTERPRISE eSpareEvents 
   VARIABLES {

	a7016SpareEventType,
	a7016EventSeverity,
	a7016EventIsStateBased,
	a7016EventStateKey,
	a7016AssociatedGroup,
	a7016EventSystem,
	a7016EventSubsystem,
	a7016EventSolution,
	a7016InstanceDataPresent,
	a7016EventMessage,
	a7016VendorSpecificData,
	a7020ComponentSpareIndex
}

DESCRIPTION "ComponentSpareInUse"

::=2


trap3ForSpareEvents TRAP-TYPE
   ENTERPRISE eSpareEvents 
   VARIABLES {

	a7016SpareEventType,
	a7016EventSeverity,
	a7016EventIsStateBased,
	a7016EventStateKey,
	a7016AssociatedGroup,
	a7016EventSystem,
	a7016EventSubsystem,
	a7016EventSolution,
	a7016InstanceDataPresent,
	a7016EventMessage,
	a7016VendorSpecificData,
	a7020ComponentSpareIndex
}

DESCRIPTION "ComponentSpareReadying"

::=3


trap4ForSpareEvents TRAP-TYPE
   ENTERPRISE eSpareEvents 
   VARIABLES {

	a7016SpareEventType,
	a7016EventSeverity,
	a7016EventIsStateBased,
	a7016EventStateKey,
	a7016AssociatedGroup,
	a7016EventSystem,
	a7016EventSubsystem,
	a7016EventSolution,
	a7016InstanceDataPresent,
	a7016EventMessage,
	a7016VendorSpecificData,
	a7020ComponentSpareIndex
}

DESCRIPTION "CioEvent"

::=4



trap1ForAssociation TRAP-TYPE
   ENTERPRISE eAssociationEvents 
   VARIABLES {

	a7018AssociationEventType,
	a7018EventSeverity,
	a7018EventIsStateBased,
	a7018EventStateKey,
	a7018AssociatedGroup,
	a7018EventSystem,
	a7018EventSubsystem,
	a7018EventSolution,
	a7018InstanceDataPresent,
	a7018EventMessage,
	a7018VendorSpecificData,
	a7017AssociationIndex
}

DESCRIPTION "NewObjectDetected"

::=1

trap2ForAssociation TRAP-TYPE
   ENTERPRISE eAssociationEvents 
   VARIABLES {

	a7018AssociationEventType,
	a7018EventSeverity,
	a7018EventIsStateBased,
	a7018EventStateKey,
	a7018AssociatedGroup,
	a7018EventSystem,
	a7018EventSubsystem,
	a7018EventSolution,
	a7018InstanceDataPresent,
	a7018EventMessage,
	a7018VendorSpecificData,
	a7017AssociationIndex
}

DESCRIPTION "ExistingObjectReplaced"

::=2

trap3ForAssociation TRAP-TYPE
   ENTERPRISE eAssociationEvents 
   VARIABLES {

	a7018AssociationEventType,
	a7018EventSeverity,
	a7018EventIsStateBased,
	a7018EventStateKey,
	a7018AssociatedGroup,
	a7018EventSystem,
	a7018EventSubsystem,
	a7018EventSolution,
	a7018InstanceDataPresent,
	a7018EventMessage,
	a7018VendorSpecificData,
	a7017AssociationIndex
}

DESCRIPTION "ExistingObjectIsGone"

::=3

END
