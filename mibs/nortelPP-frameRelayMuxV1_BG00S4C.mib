Nortel-Magellan-Passport-FrameRelayMuxMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      NonReplicated,
      Link
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayMux Enterprise MIB."

frameRelayMuxMIB OBJECT IDENTIFIER ::= { passportMIBs 38 }










-- FrMux/n
-- This component defines an instance of the Frame Relay 
-- Multiplexer/Demultiplexer used by the DpnGateway as a frame 
-- relay transport mechanism. The component instance value n is a 
-- unique positive integer within a module.

frMux OBJECT IDENTIFIER ::= { components 112 }



frMuxRowStatusTable OBJECT-TYPE
   SYNTAX     SEQUENCE OF FrMuxRowStatusEntry
   ACCESS     not-accessible
   STATUS     mandatory
   DESCRIPTION
     "This entry controls the addition and deletion of 
      frMux components."
::= { frMux 1 }

frMuxRowStatusEntry OBJECT-TYPE
   SYNTAX     FrMuxRowStatusEntry
   ACCESS     not-accessible
   STATUS     mandatory
   DESCRIPTION
     "A single entry in the table represents a single 
      frMux component."
   INDEX {
      frMuxIndex }
::= { frMuxRowStatusTable 1 }

FrMuxRowStatusEntry ::= SEQUENCE {
   frMuxRowStatus
      RowStatus,
   frMuxComponentName
      DisplayString,
   frMuxStorageType
      StorageType,
   frMuxIndex
      Integer32 }

frMuxRowStatus OBJECT-TYPE
   SYNTAX     RowStatus 
   ACCESS     read-write
   STATUS     mandatory
   DESCRIPTION
     "This variable is used as the basis for SNMP naming of
      frMux components.
      These components can be added and deleted."
::= { frMuxRowStatusEntry 1 }

frMuxComponentName OBJECT-TYPE
   SYNTAX     DisplayString 
   ACCESS     read-only
   STATUS     mandatory
   DESCRIPTION
     "This variable provides the component's string name for
      use with the ASCII Console Interface"
::= { frMuxRowStatusEntry 2 }

frMuxStorageType OBJECT-TYPE
   SYNTAX     StorageType 
   ACCESS     read-only
   STATUS     mandatory
   DESCRIPTION
     "This variable represents the storage type value for the
      frMux tables."
::= { frMuxRowStatusEntry 4 }

frMuxIndex OBJECT-TYPE
   SYNTAX     Integer32 (1..65535)
   ACCESS     not-accessible
   STATUS     mandatory
   DESCRIPTION
     "This variable represents the index for the frMux tables."
::= { frMuxRowStatusEntry 10 }

frMuxOperStatusTable OBJECT-TYPE
   SYNTAX     SEQUENCE OF FrMuxOperStatusEntry
   ACCESS     not-accessible
   STATUS     mandatory
   DESCRIPTION
     "This group includes the Operational Status attribute. This attribute 
      defines the current operational state of this component."
::= { frMux 8 }

frMuxOperStatusEntry OBJECT-TYPE
   SYNTAX     FrMuxOperStatusEntry
   ACCESS     not-accessible
   STATUS     mandatory
   DESCRIPTION
     "An entry in the frMuxOperStatusTable."
   INDEX {
      frMuxIndex }
::= { frMuxOperStatusTable 1 }

FrMuxOperStatusEntry ::= SEQUENCE {
   frMuxSnmpOperStatus
      INTEGER }

frMuxSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { frMuxOperStatusEntry 1 }

frMuxIfEntryTable OBJECT-TYPE
   SYNTAX     SEQUENCE OF FrMuxIfEntryEntry
   ACCESS     not-accessible
   STATUS     mandatory
   DESCRIPTION
     "This group contains the provisionable attributes for the ifEntry."
::= { frMux 9 }

frMuxIfEntryEntry OBJECT-TYPE
   SYNTAX     FrMuxIfEntryEntry
   ACCESS     not-accessible
   STATUS     mandatory
   DESCRIPTION
     "An entry in the frMuxIfEntryTable."
   INDEX {
      frMuxIndex }
::= { frMuxIfEntryTable 1 }

FrMuxIfEntryEntry ::= SEQUENCE {
   frMuxIfAdminStatus
      INTEGER,
   frMuxIfIndex
      InterfaceIndex }

frMuxIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { frMuxIfEntryEntry 1 }

frMuxIfIndex OBJECT-TYPE
   SYNTAX     InterfaceIndex (1..65535)
   ACCESS     read-only
   STATUS     mandatory
   DESCRIPTION
     "This is the index for the IfEntry. Its value is automatically initialized 
      during the provisioning process."
::= { frMuxIfEntryEntry 2 }

frMuxCidDataTable OBJECT-TYPE
   SYNTAX     SEQUENCE OF FrMuxCidDataEntry
   ACCESS     not-accessible
   STATUS     mandatory
   DESCRIPTION
     "This group contains the attribute for a component's Customer 
      Identifier (CID). Refer to the attribute description for a detailed 
      explanation of CIDs."
::= { frMux 10 }

frMuxCidDataEntry OBJECT-TYPE
   SYNTAX     FrMuxCidDataEntry
   ACCESS     not-accessible
   STATUS     mandatory
   DESCRIPTION
     "An entry in the frMuxCidDataTable."
   INDEX {
      frMuxIndex }
::= { frMuxCidDataTable 1 }

FrMuxCidDataEntry ::= SEQUENCE {
   frMuxCustomerIdentifier
      Unsigned32 }

frMuxCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { frMuxCidDataEntry 1 }

frMuxStateTable OBJECT-TYPE
   SYNTAX     SEQUENCE OF FrMuxStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { frMux 11 }

frMuxStateEntry OBJECT-TYPE
   SYNTAX     FrMuxStateEntry
   ACCESS     not-accessible
   STATUS     mandatory
   DESCRIPTION
     "An entry in the frMuxStateTable."
   INDEX {
      frMuxIndex }
::= { frMuxStateTable 1 }

FrMuxStateEntry ::= SEQUENCE {
   frMuxAdminState
      INTEGER,
   frMuxOperationalState
      INTEGER,
   frMuxUsageState
      INTEGER,
   frMuxAvailabilityStatus
      OCTET STRING,
   frMuxProceduralStatus
      OCTET STRING,
   frMuxControlStatus
      OCTET STRING,
   frMuxAlarmStatus
      OCTET STRING,
   frMuxStandbyStatus
      INTEGER,
   frMuxUnknownStatus
      INTEGER }

frMuxAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { frMuxStateEntry 1 }

frMuxOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { frMuxStateEntry 2 }

frMuxUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { frMuxStateEntry 3 }

frMuxAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { frMuxStateEntry 4 }

frMuxProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { frMuxStateEntry 5 }

frMuxControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { frMuxStateEntry 6 }

frMuxAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { frMuxStateEntry 7 }

frMuxStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { frMuxStateEntry 8 }

frMuxUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { frMuxStateEntry 9 }

frMuxStatsTable OBJECT-TYPE
   SYNTAX     SEQUENCE OF FrMuxStatsEntry
   ACCESS     not-accessible
   STATUS     mandatory
   DESCRIPTION
     "This group contains the statistics about the operational behavior of 
      the FrMux at the interface level."
::= { frMux 12 }

frMuxStatsEntry OBJECT-TYPE
   SYNTAX     FrMuxStatsEntry
   ACCESS     not-accessible
   STATUS     mandatory
   DESCRIPTION
     "An entry in the frMuxStatsTable."
   INDEX {
      frMuxIndex }
::= { frMuxStatsTable 1 }

FrMuxStatsEntry ::= SEQUENCE {
   frMuxLastUnknownDlci
      Unsigned32,
   frMuxUnknownDlciFramesFromIf
      Counter32,
   frMuxInvalidHeaderFramesFromIf
      Counter32,
   frMuxTimeFramerCongested
      Counter32 }

frMuxLastUnknownDlci OBJECT-TYPE
   SYNTAX     Unsigned32 (0..1023)
   ACCESS     read-only
   STATUS     mandatory
   DESCRIPTION
     "This attribute identifies the most recent DLCI which user frames 
      were received on, for which a Dlci has not been provisioned on the 
      interface."
   DEFVAL     { 0 }
::= { frMuxStatsEntry 1 }

frMuxUnknownDlciFramesFromIf OBJECT-TYPE
   SYNTAX     Counter32 
   ACCESS     read-only
   STATUS     mandatory
   DESCRIPTION
     "This attribute counts frames received from the interface with an 
      unknown DLCI (Dlci which is not provisioned). When the 
      maximum is reached the count wraps to zero."
::= { frMuxStatsEntry 2 }

frMuxInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { frMuxStatsEntry 3 }

frMuxTimeFramerCongested OBJECT-TYPE
   SYNTAX     Counter32 
   ACCESS     read-only
   STATUS     mandatory
   DESCRIPTION
     "This attribute accumulates the time (in msec) during which Framer 
      congestion has been observed in the direction towards the interface. 
      The overload causing this statistic to increase may be caused by 
      oversubscription. When this count reaches maximum, it wraps to 
      zero."
::= { frMuxStatsEntry 4 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

frMuxFramer OBJECT IDENTIFIER ::= { frMux 2 }



frMuxFramerRowStatusTable OBJECT-TYPE
   SYNTAX     SEQUENCE OF FrMuxFramerRowStatusEntry
   ACCESS     not-accessible
   STATUS     mandatory
   DESCRIPTION
     "This entry controls the addition and deletion of 
      frMuxFramer components."
::= { frMuxFramer 1 }

frMuxFramerRowStatusEntry OBJECT-TYPE
   SYNTAX     FrMuxFramerRowStatusEntry
   ACCESS     not-accessible
   STATUS     mandatory
   DESCRIPTION
     "A single entry in the table represents a single 
      frMuxFramer component."
   INDEX {
      frMuxIndex,
      frMuxFramerIndex }
::= { frMuxFramerRowStatusTable 1 }

FrMuxFramerRowStatusEntry ::= SEQUENCE {
   frMuxFramerRowStatus
      RowStatus,
   frMuxFramerComponentName
      DisplayString,
   frMuxFramerStorageType
      StorageType,
   frMuxFramerIndex
      NonReplicated }

frMuxFramerRowStatus OBJECT-TYPE
   SYNTAX     RowStatus 
   ACCESS     read-only
   STATUS     mandatory
   DESCRIPTION
     "This variable is used as the basis for SNMP naming of
      frMuxFramer components.
      These components cannot be added nor deleted."
::= { frMuxFramerRowStatusEntry 1 }

frMuxFramerComponentName OBJECT-TYPE
   SYNTAX     DisplayString 
   ACCESS     read-only
   STATUS     mandatory
   DESCRIPTION
     "This variable provides the component's string name for
      use with the ASCII Console Interface"
::= { frMuxFramerRowStatusEntry 2 }

frMuxFramerStorageType OBJECT-TYPE
   SYNTAX     StorageType 
   ACCESS     read-only
   STATUS     mandatory
   DESCRIPTION
     "This variable represents the storage type value for the
      frMuxFramer tables."
::= { frMuxFramerRowStatusEntry 4 }

frMuxFramerIndex OBJECT-TYPE
   SYNTAX     NonReplicated 
   ACCESS     not-accessible
   STATUS     mandatory
   DESCRIPTION
     "This variable represents the index for the frMuxFramer tables."
::= { frMuxFramerRowStatusEntry 10 }

frMuxFramerProvTable OBJECT-TYPE
   SYNTAX     SEQUENCE OF FrMuxFramerProvEntry
   ACCESS     not-accessible
   STATUS     mandatory
   DESCRIPTION
     "This group contains the base provisioning data for the Framer 
      component. Application or hardware interface specific provisioning 
      data is contained in other provisionable Framer groups."
::= { frMuxFramer 10 }

frMuxFramerProvEntry OBJECT-TYPE
   SYNTAX     FrMuxFramerProvEntry
   ACCESS     not-accessible
   STATUS     mandatory
   DESCRIPTION
     "An entry in the frMuxFramerProvTable."
   INDEX {
      frMuxIndex,
      frMuxFramerIndex }
::= { frMuxFramerProvTable 1 }

FrMuxFramerProvEntry ::= SEQUENCE {
   frMuxFramerInterfaceName
      Link }

frMuxFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { frMuxFramerProvEntry 1 }

frMuxFramerLinkTable OBJECT-TYPE
   SYNTAX     SEQUENCE OF FrMuxFramerLinkEntry
   ACCESS     not-accessible
   STATUS     mandatory
   DESCRIPTION
     "This group contains attributes defining the framing of data on the 
      link interface."
::= { frMuxFramer 11 }

frMuxFramerLinkEntry OBJECT-TYPE
   SYNTAX     FrMuxFramerLinkEntry
   ACCESS     not-accessible
   STATUS     mandatory
   DESCRIPTION
     "An entry in the frMuxFramerLinkTable."
   INDEX {
      frMuxIndex,
      frMuxFramerIndex }
::= { frMuxFramerLinkTable 1 }

FrMuxFramerLinkEntry ::= SEQUENCE {
   frMuxFramerFlagsBetweenFrames
      Unsigned32 }

frMuxFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { frMuxFramerLinkEntry 4 }

frMuxFramerStateTable OBJECT-TYPE
   SYNTAX     SEQUENCE OF FrMuxFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frMuxFramer 12 }

frMuxFramerStateEntry OBJECT-TYPE
   SYNTAX     FrMuxFramerStateEntry
   ACCESS     not-accessible
   STATUS     mandatory
   DESCRIPTION
     "An entry in the frMuxFramerStateTable."
   INDEX {
      frMuxIndex,
      frMuxFramerIndex }
::= { frMuxFramerStateTable 1 }

FrMuxFramerStateEntry ::= SEQUENCE {
   frMuxFramerAdminState
      INTEGER,
   frMuxFramerOperationalState
      INTEGER,
   frMuxFramerUsageState
      INTEGER }

frMuxFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frMuxFramerStateEntry 1 }

frMuxFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frMuxFramerStateEntry 2 }

frMuxFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frMuxFramerStateEntry 3 }

frMuxFramerStatsTable OBJECT-TYPE
   SYNTAX     SEQUENCE OF FrMuxFramerStatsEntry
   ACCESS     not-accessible
   STATUS     mandatory
   DESCRIPTION
     "This group contains the operational statistics data for a Framer 
      component."
::= { frMuxFramer 13 }

frMuxFramerStatsEntry OBJECT-TYPE
   SYNTAX     FrMuxFramerStatsEntry
   ACCESS     not-accessible
   STATUS     mandatory
   DESCRIPTION
     "An entry in the frMuxFramerStatsTable."
   INDEX {
      frMuxIndex,
      frMuxFramerIndex }
::= { frMuxFramerStatsTable 1 }

FrMuxFramerStatsEntry ::= SEQUENCE {
   frMuxFramerFrmToIf
      Counter32,
   frMuxFramerFrmFromIf
      Counter32,
   frMuxFramerOctetFromIf
      Counter32,
   frMuxFramerAborts
      Counter32,
   frMuxFramerCrcErrors
      Counter32,
   frMuxFramerLrcErrors
      Counter32,
   frMuxFramerNonOctetErrors
      Counter32,
   frMuxFramerOverruns
      Counter32,
   frMuxFramerUnderruns
      Counter32,
   frMuxFramerLargeFrmErrors
      Counter32,
   frMuxFramerFrmModeErrors
      Counter32 }

frMuxFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { frMuxFramerStatsEntry 1 }

frMuxFramerFrmFromIf OBJECT-TYPE
   SYNTAX     Counter32 
   ACCESS     read-only
   STATUS     mandatory
   DESCRIPTION
     "The number of frames received from the link interface by Framer."
::= { frMuxFramerStatsEntry 2 }

frMuxFramerOctetFromIf OBJECT-TYPE
   SYNTAX     Counter32 
   ACCESS     read-only
   STATUS     mandatory
   DESCRIPTION
     "The number of bytes received from the link interface by Framer."
::= { frMuxFramerStatsEntry 3 }

frMuxFramerAborts OBJECT-TYPE
   SYNTAX     Counter32 
   ACCESS     read-only
   STATUS     mandatory
   DESCRIPTION
     "This attribute is the total number of aborts received."
::= { frMuxFramerStatsEntry 4 }

frMuxFramerCrcErrors OBJECT-TYPE
   SYNTAX     Counter32 
   ACCESS     read-only
   STATUS     mandatory
   DESCRIPTION
     "This attribute is the total number of frames with CRC errors, 
      occurring in the receive direction from the link."
::= { frMuxFramerStatsEntry 5 }

frMuxFramerLrcErrors OBJECT-TYPE
   SYNTAX     Counter32 
   ACCESS     read-only
   STATUS     mandatory
   DESCRIPTION
     "This attribute is the total number of frames with LRC errors, 
      occurring in the Tx link prior to transmission onto the link."
::= { frMuxFramerStatsEntry 6 }

frMuxFramerNonOctetErrors OBJECT-TYPE
   SYNTAX     Counter32 
   ACCESS     read-only
   STATUS     mandatory
   DESCRIPTION
     "This attribute is the total number of frames that were non octet 
      aligned."
::= { frMuxFramerStatsEntry 7 }

frMuxFramerOverruns OBJECT-TYPE
   SYNTAX     Counter32 
   ACCESS     read-only
   STATUS     mandatory
   DESCRIPTION
     "This attribute is the total number of frames received from the link 
      for which overruns occurred."
::= { frMuxFramerStatsEntry 8 }

frMuxFramerUnderruns OBJECT-TYPE
   SYNTAX     Counter32 
   ACCESS     read-only
   STATUS     mandatory
   DESCRIPTION
     "This attribute is the total number of frames transmitted to the link 
      for which underruns occurred."
::= { frMuxFramerStatsEntry 9 }

frMuxFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { frMuxFramerStatsEntry 10 }

frMuxFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { frMuxFramerStatsEntry 11 }

frMuxFramerUtilTable OBJECT-TYPE
   SYNTAX     SEQUENCE OF FrMuxFramerUtilEntry
   ACCESS     not-accessible
   STATUS     mandatory
   DESCRIPTION
     "This group contains the link utilizaiton operational data for a 
      Framer component."
::= { frMuxFramer 14 }

frMuxFramerUtilEntry OBJECT-TYPE
   SYNTAX     FrMuxFramerUtilEntry
   ACCESS     not-accessible
   STATUS     mandatory
   DESCRIPTION
     "An entry in the frMuxFramerUtilTable."
   INDEX {
      frMuxIndex,
      frMuxFramerIndex }
::= { frMuxFramerUtilTable 1 }

FrMuxFramerUtilEntry ::= SEQUENCE {
   frMuxFramerNormPrioLinkUtilToIf
      Gauge32,
   frMuxFramerNormPrioLinkUtilFromIf
      Gauge32 }

frMuxFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { frMuxFramerUtilEntry 1 }

frMuxFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { frMuxFramerUtilEntry 3 }


-- FrMux/n Lmi
-- This component defines the parameters for implementing the Local 
-- Management Interface protocol.

frMuxLmi OBJECT IDENTIFIER ::= { frMux 3 }



frMuxLmiRowStatusTable OBJECT-TYPE
   SYNTAX     SEQUENCE OF FrMuxLmiRowStatusEntry
   ACCESS     not-accessible
   STATUS     mandatory
   DESCRIPTION
     "This entry controls the addition and deletion of 
      frMuxLmi components."
::= { frMuxLmi 1 }

frMuxLmiRowStatusEntry OBJECT-TYPE
   SYNTAX     FrMuxLmiRowStatusEntry
   ACCESS     not-accessible
   STATUS     mandatory
   DESCRIPTION
     "A single entry in the table represents a single 
      frMuxLmi component."
   INDEX {
      frMuxIndex,
      frMuxLmiIndex }
::= { frMuxLmiRowStatusTable 1 }

FrMuxLmiRowStatusEntry ::= SEQUENCE {
   frMuxLmiRowStatus
      RowStatus,
   frMuxLmiComponentName
      DisplayString,
   frMuxLmiStorageType
      StorageType,
   frMuxLmiIndex
      NonReplicated }

frMuxLmiRowStatus OBJECT-TYPE
   SYNTAX     RowStatus 
   ACCESS     read-only
   STATUS     mandatory
   DESCRIPTION
     "This variable is used as the basis for SNMP naming of
      frMuxLmi components.
      These components cannot be added nor deleted."
::= { frMuxLmiRowStatusEntry 1 }

frMuxLmiComponentName OBJECT-TYPE
   SYNTAX     DisplayString 
   ACCESS     read-only
   STATUS     mandatory
   DESCRIPTION
     "This variable provides the component's string name for
      use with the ASCII Console Interface"
::= { frMuxLmiRowStatusEntry 2 }

frMuxLmiStorageType OBJECT-TYPE
   SYNTAX     StorageType 
   ACCESS     read-only
   STATUS     mandatory
   DESCRIPTION
     "This variable represents the storage type value for the
      frMuxLmi tables."
::= { frMuxLmiRowStatusEntry 4 }

frMuxLmiIndex OBJECT-TYPE
   SYNTAX     NonReplicated 
   ACCESS     not-accessible
   STATUS     mandatory
   DESCRIPTION
     "This variable represents the index for the frMuxLmi tables."
::= { frMuxLmiRowStatusEntry 10 }

frMuxLmiProvTable OBJECT-TYPE
   SYNTAX     SEQUENCE OF FrMuxLmiProvEntry
   ACCESS     not-accessible
   STATUS     mandatory
   DESCRIPTION
     "This group contains the provisionable attributes of the Local 
      Management Interface component of the FrMux. The Local 
      Management Interface of the FrMux is always User Side Procedure 
      of the User Network Interface (USP-UNI)."
::= { frMuxLmi 10 }

frMuxLmiProvEntry OBJECT-TYPE
   SYNTAX     FrMuxLmiProvEntry
   ACCESS     not-accessible
   STATUS     mandatory
   DESCRIPTION
     "An entry in the frMuxLmiProvTable."
   INDEX {
      frMuxIndex,
      frMuxLmiIndex }
::= { frMuxLmiProvTable 1 }

FrMuxLmiProvEntry ::= SEQUENCE {
   frMuxLmiProcedures
      INTEGER,
   frMuxLmiLinkVerificationTimer
      Unsigned32,
   frMuxLmiFullStatusPollingCycles
      Unsigned32,
   frMuxLmiErrorEventThreshold
      Unsigned32,
   frMuxLmiEventCount
      Unsigned32 }

frMuxLmiProcedures OBJECT-TYPE
   SYNTAX     INTEGER  {
                 none(0),
                 vendorForum(1),
                 ansi(2),
                 ccitt(3) }
   ACCESS     read-write
   STATUS     mandatory
   DESCRIPTION
     "This attribute selects the procedures to be used for the Local 
      Management Interface. The following are the supported procedures:
      none	:	 No Local Management Interface procedure is active. 
      vendorForum	:	Local Management Interface procedure according to 
      the Vendor Forum specification is active. DLCI 1023 is used for the 
      LMI protocol.
      ansi: 	Local Management Interface procedure according to the 
      ANSI specification is active. DLCI 0 is used for the LMI protocol.
      ccitt: Local Management Interface procedure according to the 
      CCITT specification is active. DLCI 0 is used for the LMI protocol."
   DEFVAL     { ccitt }
::= { frMuxLmiProvEntry 1 }

frMuxLmiLinkVerificationTimer OBJECT-TYPE
   SYNTAX     Unsigned32 (5 | 10 | 15 | 20 | 25 | 30)
   ACCESS     read-write
   STATUS     mandatory
   DESCRIPTION
     "This attribute specifies the time interval (in seconds) at which the 
      FrMux sends Status Enquiry messages to the interface. Exchange of 
      Status Enquiry and Status Report messages constitutes a polling 
      cycle, so this attribute may also be interpreted as time interval at 
      which the FrMux initiates polling cycles. It must be less than 
      checkPointTimer (t392) configured at the other end of the Frame 
      Relay interface.
      
      This attribute corresponds to t391 of the ANSI and CCITT 
      specifications, and nT1 of the Vendor Forum specification."
   DEFVAL     { 10 }
::= { frMuxLmiProvEntry 2 }

frMuxLmiFullStatusPollingCycles OBJECT-TYPE
   SYNTAX     Unsigned32 (1..255)
   ACCESS     read-write
   STATUS     mandatory
   DESCRIPTION
     "This attribute specifies every which polling cycle the FrMux sends a 
      full STATUS ENQUIRY to the interface. Every 
      fullStatusPollingCycles polling cycles the FrMux sends a full 
      STATUS ENQUIRY. In all other cycles of a sequence of 
      fullStatusPollingCycles polling cycles the FrMux sends a keep alive 
      STATUS ENQUIRY. 
      
      This attribute corresponds to n391 of the ANSI and CCITT 
      specifications and nN1 of the Vendor Forum specification."
   DEFVAL     { 6 }
::= { frMuxLmiProvEntry 3 }

frMuxLmiErrorEventThreshold OBJECT-TYPE
   SYNTAX     Unsigned32 (1..10)
   ACCESS     read-write
   STATUS     mandatory
   DESCRIPTION
     "This attribute specifies the number of error events which, if they 
      occur within eventCount events, will cause a protocol error 
      condition (protocolStatus = errorCondition). The error condition is 
      cleared after eventCount sequential correct events occur 
      (protocolStatus = normalCondition). 
      
      An event is one of the following: (1) expiry of the 
      linkVerificationTimer (t391), (2) reception of a STATUS message. 
      An error event is one of the following: (1)non-receipt of the 
      STATUS message in t391 seconds, (2)invalid STATUS message, (3) 
      invalid sequence number. 
      
      This attribute corresponds to n392 of the ANSI and CCITT 
      specifications and nN2 of the Vendor Forum Specification. 
      
      This attribute must be less than or equal to eventCount."
   DEFVAL     { 3 }
::= { frMuxLmiProvEntry 4 }

frMuxLmiEventCount OBJECT-TYPE
   SYNTAX     Unsigned32 (1..10)
   ACCESS     read-write
   STATUS     mandatory
   DESCRIPTION
     "This attribute specifies the number of contiguous events within 
      which no more than eventErrorThreshold error events are allowed.
      
      This attribute corresponds to n392 of the ANSI and CCITT 
      specifications and nN3 of the Vendor Forum Specification. 
      
      This attribute must be greater than or equal to errorEventThreshold."
   DEFVAL     { 4 }
::= { frMuxLmiProvEntry 5 }

frMuxLmiStateTable OBJECT-TYPE
   SYNTAX     SEQUENCE OF FrMuxLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frMuxLmi 11 }

frMuxLmiStateEntry OBJECT-TYPE
   SYNTAX     FrMuxLmiStateEntry
   ACCESS     not-accessible
   STATUS     mandatory
   DESCRIPTION
     "An entry in the frMuxLmiStateTable."
   INDEX {
      frMuxIndex,
      frMuxLmiIndex }
::= { frMuxLmiStateTable 1 }

FrMuxLmiStateEntry ::= SEQUENCE {
   frMuxLmiAdminState
      INTEGER,
   frMuxLmiOperationalState
      INTEGER,
   frMuxLmiUsageState
      INTEGER }

frMuxLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frMuxLmiStateEntry 1 }

frMuxLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frMuxLmiStateEntry 2 }

frMuxLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frMuxLmiStateEntry 3 }

frMuxLmiPsiTable OBJECT-TYPE
   SYNTAX     SEQUENCE OF FrMuxLmiPsiEntry
   ACCESS     not-accessible
   STATUS     mandatory
   DESCRIPTION
     "This group provides the protocol status of the Local Management 
      Interface of this FrMux."
::= { frMuxLmi 12 }

frMuxLmiPsiEntry OBJECT-TYPE
   SYNTAX     FrMuxLmiPsiEntry
   ACCESS     not-accessible
   STATUS     mandatory
   DESCRIPTION
     "An entry in the frMuxLmiPsiTable."
   INDEX {
      frMuxIndex,
      frMuxLmiIndex }
::= { frMuxLmiPsiTable 1 }

FrMuxLmiPsiEntry ::= SEQUENCE {
   frMuxLmiProtocolStatus
      INTEGER }

frMuxLmiProtocolStatus OBJECT-TYPE
   SYNTAX     INTEGER  {
                 errorCondition(0),
                 normalCondition(1) }
   ACCESS     read-only
   STATUS     mandatory
   DESCRIPTION
     "This attribute indicates whether the Lmi is in an error condition or 
      whether the protocol is behaving normally. When operating with no 
      LMI protocol (procedures = none), this attribute will always be set 
      to normalCondition. When operating with an LMI protocol 
      (procedures set to one of venforForum, ansi, ccitt), this attribute is 
      set to errorCondition when errorEventThreshold of the last 
      eventCount events are in error. 
      The error condition is cleared when eventCount consecutive good 
      events take place.
      The consequence of an error condition is that all Dlci's on this 
      interface become disabled and there is no data flow in either 
      direction."
   DEFVAL     { normalCondition }
::= { frMuxLmiPsiEntry 1 }

frMuxLmiStatsTable OBJECT-TYPE
   SYNTAX     SEQUENCE OF FrMuxLmiStatsEntry
   ACCESS     not-accessible
   STATUS     mandatory
   DESCRIPTION
     "This group contains the operational statistics for the FrMux Local 
      Management Interface."
::= { frMuxLmi 13 }

frMuxLmiStatsEntry OBJECT-TYPE
   SYNTAX     FrMuxLmiStatsEntry
   ACCESS     not-accessible
   STATUS     mandatory
   DESCRIPTION
     "An entry in the frMuxLmiStatsTable."
   INDEX {
      frMuxIndex,
      frMuxLmiIndex }
::= { frMuxLmiStatsTable 1 }

FrMuxLmiStatsEntry ::= SEQUENCE {
   frMuxLmiKeepAliveStatusEnqToIf
      Counter32,
   frMuxLmiFullStatusEnqToIf
      Counter32,
   frMuxLmiProtocolErrors
      Counter32,
   frMuxLmiUnexpectedIes
      Counter32,
   frMuxLmiSequenceErrors
      Counter32,
   frMuxLmiUnexpectedReports
      Counter32,
   frMuxLmiNoStatusReportCount
      Counter32 }

frMuxLmiKeepAliveStatusEnqToIf OBJECT-TYPE
   SYNTAX     Counter32 
   ACCESS     read-only
   STATUS     mandatory
   DESCRIPTION
     "This attribute counts the number of keep alive STATUS ENQUIRY 
      messages sent to the interface. When the maximum count is reached 
      it wraps to zero."
::= { frMuxLmiStatsEntry 1 }

frMuxLmiFullStatusEnqToIf OBJECT-TYPE
   SYNTAX     Counter32 
   ACCESS     read-only
   STATUS     mandatory
   DESCRIPTION
     "This attribute counts the number of full STATUS ENQUIRY 
      messages sent to the interface. When the maximum count is reached 
      it wraps to zero."
::= { frMuxLmiStatsEntry 2 }

frMuxLmiProtocolErrors OBJECT-TYPE
   SYNTAX     Counter32 
   ACCESS     read-only
   STATUS     mandatory
   DESCRIPTION
     "This attribute counts the number of Local Management Interface 
      protocol errors. Protocol errors include (1) protocol message format 
      errors, (2) protocol timer expiry errors, and (3) sequence errors. 
      When the maximum count is reached it wraps to zero."
::= { frMuxLmiStatsEntry 3 }

frMuxLmiUnexpectedIes OBJECT-TYPE
   SYNTAX     Counter32 
   ACCESS     read-only
   STATUS     mandatory
   DESCRIPTION
     "This attribute counts the number of frames received with an 
      Information Element identifier that is unknown or unexpected. 
      When the maximum count is reached, this counter wraps to zero."
::= { frMuxLmiStatsEntry 4 }

frMuxLmiSequenceErrors OBJECT-TYPE
   SYNTAX     Counter32 
   ACCESS     read-only
   STATUS     mandatory
   DESCRIPTION
     "This attribute counts the number of Local Management Interface 
      sequence errors. A sequence error is receipt of an LMI message 
      with a receive sequence number not equal to the last send sequence 
      number. When the maximum count is reached the counter wraps to 
      zero."
::= { frMuxLmiStatsEntry 5 }

frMuxLmiUnexpectedReports OBJECT-TYPE
   SYNTAX     Counter32 
   ACCESS     read-only
   STATUS     mandatory
   DESCRIPTION
     "This attribute counts the number of frames received on the Local 
      Management Interface with an unknown or unexpected report type. 
      When the maximum count is reached the counter wraps to zero."
::= { frMuxLmiStatsEntry 6 }

frMuxLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and t391 timer expires without 
      having a status report received.
      ii) an invalid status report is received.
      When the maximum count is reached it wraps to zero."
::= { frMuxLmiStatsEntry 7 }


-- FrMux/n Dlci/n
-- This component is responsible for the Frame Relay U-plane (User-
-- plane) protocol for the specified instance. The instance value is used 
-- to identify the logical connection, multiplexed within the physical 
-- channel, with which a frame is associated. All frames carried within 
-- a particular physical channel and having the same DLCI value are 
-- associated with the same logical connection.

frMuxDlci OBJECT IDENTIFIER ::= { frMux 4 }



frMuxDlciRowStatusTable OBJECT-TYPE
   SYNTAX     SEQUENCE OF FrMuxDlciRowStatusEntry
   ACCESS     not-accessible
   STATUS     mandatory
   DESCRIPTION
     "This entry controls the addition and deletion of 
      frMuxDlci components."
::= { frMuxDlci 1 }

frMuxDlciRowStatusEntry OBJECT-TYPE
   SYNTAX     FrMuxDlciRowStatusEntry
   ACCESS     not-accessible
   STATUS     mandatory
   DESCRIPTION
     "A single entry in the table represents a single 
      frMuxDlci component."
   INDEX {
      frMuxIndex,
      frMuxDlciIndex }
::= { frMuxDlciRowStatusTable 1 }

FrMuxDlciRowStatusEntry ::= SEQUENCE {
   frMuxDlciRowStatus
      RowStatus,
   frMuxDlciComponentName
      DisplayString,
   frMuxDlciStorageType
      StorageType,
   frMuxDlciIndex
      Integer32 }

frMuxDlciRowStatus OBJECT-TYPE
   SYNTAX     RowStatus 
   ACCESS     read-write
   STATUS     mandatory
   DESCRIPTION
     "This variable is used as the basis for SNMP naming of
      frMuxDlci components.
      These components can be added and deleted."
::= { frMuxDlciRowStatusEntry 1 }

frMuxDlciComponentName OBJECT-TYPE
   SYNTAX     DisplayString 
   ACCESS     read-only
   STATUS     mandatory
   DESCRIPTION
     "This variable provides the component's string name for
      use with the ASCII Console Interface"
::= { frMuxDlciRowStatusEntry 2 }

frMuxDlciStorageType OBJECT-TYPE
   SYNTAX     StorageType 
   ACCESS     read-only
   STATUS     mandatory
   DESCRIPTION
     "This variable represents the storage type value for the
      frMuxDlci tables."
::= { frMuxDlciRowStatusEntry 4 }

frMuxDlciIndex OBJECT-TYPE
   SYNTAX     Integer32 (16..1007)
   ACCESS     not-accessible
   STATUS     mandatory
   DESCRIPTION
     "This variable represents the index for the frMuxDlci tables."
::= { frMuxDlciRowStatusEntry 10 }

frMuxDlciOperTable OBJECT-TYPE
   SYNTAX     SEQUENCE OF FrMuxDlciOperEntry
   ACCESS     not-accessible
   STATUS     mandatory
   DESCRIPTION
     "This group contains the name of the application associated with this 
      Dlci."
::= { frMuxDlci 10 }

frMuxDlciOperEntry OBJECT-TYPE
   SYNTAX     FrMuxDlciOperEntry
   ACCESS     not-accessible
   STATUS     mandatory
   DESCRIPTION
     "An entry in the frMuxDlciOperTable."
   INDEX {
      frMuxIndex,
      frMuxDlciIndex }
::= { frMuxDlciOperTable 1 }

FrMuxDlciOperEntry ::= SEQUENCE {
   frMuxDlciApplicationName
      RowPointer }

frMuxDlciApplicationName OBJECT-TYPE
   SYNTAX     RowPointer 
   ACCESS     read-only
   STATUS     mandatory
   DESCRIPTION
     "This attribute contains the name of the application associated with 
      this Dlci."
::= { frMuxDlciOperEntry 1 }

frMuxDlciStateTable OBJECT-TYPE
   SYNTAX     SEQUENCE OF FrMuxDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { frMuxDlci 11 }

frMuxDlciStateEntry OBJECT-TYPE
   SYNTAX     FrMuxDlciStateEntry
   ACCESS     not-accessible
   STATUS     mandatory
   DESCRIPTION
     "An entry in the frMuxDlciStateTable."
   INDEX {
      frMuxIndex,
      frMuxDlciIndex }
::= { frMuxDlciStateTable 1 }

FrMuxDlciStateEntry ::= SEQUENCE {
   frMuxDlciAdminState
      INTEGER,
   frMuxDlciOperationalState
      INTEGER,
   frMuxDlciUsageState
      INTEGER }

frMuxDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { frMuxDlciStateEntry 1 }

frMuxDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { frMuxDlciStateEntry 2 }

frMuxDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { frMuxDlciStateEntry 3 }

frMuxDlciAbitTable OBJECT-TYPE
   SYNTAX     SEQUENCE OF FrMuxDlciAbitEntry
   ACCESS     not-accessible
   STATUS     mandatory
   DESCRIPTION
     "This group contains the A-Bit status information for this Dlci."
::= { frMuxDlci 12 }

frMuxDlciAbitEntry OBJECT-TYPE
   SYNTAX     FrMuxDlciAbitEntry
   ACCESS     not-accessible
   STATUS     mandatory
   DESCRIPTION
     "An entry in the frMuxDlciAbitTable."
   INDEX {
      frMuxIndex,
      frMuxDlciIndex }
::= { frMuxDlciAbitTable 1 }

FrMuxDlciAbitEntry ::= SEQUENCE {
   frMuxDlciABitStatusFromIf
      INTEGER }

frMuxDlciABitStatusFromIf OBJECT-TYPE
   SYNTAX     INTEGER  {
                 inactive(0),
                 active(1) }
   ACCESS     read-only
   STATUS     mandatory
   DESCRIPTION
     "This attribute is the most recent A-Bit status received from the 
      interface."
   DEFVAL     { inactive }
::= { frMuxDlciAbitEntry 1 }

frMuxDlciStatsTable OBJECT-TYPE
   SYNTAX     SEQUENCE OF FrMuxDlciStatsEntry
   ACCESS     not-accessible
   STATUS     mandatory
   DESCRIPTION
     "This group contains the operational statistics for the FrMux Dlci."
::= { frMuxDlci 13 }

frMuxDlciStatsEntry OBJECT-TYPE
   SYNTAX     FrMuxDlciStatsEntry
   ACCESS     not-accessible
   STATUS     mandatory
   DESCRIPTION
     "An entry in the frMuxDlciStatsTable."
   INDEX {
      frMuxIndex,
      frMuxDlciIndex }
::= { frMuxDlciStatsTable 1 }

FrMuxDlciStatsEntry ::= SEQUENCE {
   frMuxDlciFrmToIf
      Counter32,
   frMuxDlciBytesToIf
      PassportCounter64,
   frMuxDlciFrmFromIf
      Counter32,
   frMuxDlciDeFrmFromIf
      Counter32,
   frMuxDlciBytesFromIf
      PassportCounter64,
   frMuxDlciDeBytesFromIf
      PassportCounter64,
   frMuxDlciFecnFrmToIf
      Counter32,
   frMuxDlciFecnFrmFromIf
      Counter32,
   frMuxDlciBecnFrmToIf
      Counter32,
   frMuxDlciBecnFrmFromIf
      Counter32,
   frMuxDlciDiscCongestedFromIf
      Counter32,
   frMuxDlciDiscCongestedFromIfBytes
      Counter32,
   frMuxDlciDiscDeCongestedFromIf
      Counter32,
   frMuxDlciDiscDeCongestedFromIfBytes
      Counter32,
   frMuxDlciErrorShortFrmFromIf
      Counter32,
   frMuxDlciErrorLongFrmFromIf
      Counter32 }

frMuxDlciFrmToIf OBJECT-TYPE
   SYNTAX     Counter32 
   ACCESS     read-only
   STATUS     mandatory
   DESCRIPTION
     "This attribute counts the frames sent to the interface. When the 
      maximum count is reached the count wraps to zero."
::= { frMuxDlciStatsEntry 1 }

frMuxDlciBytesToIf OBJECT-TYPE
   SYNTAX     PassportCounter64 
   ACCESS     read-only
   STATUS     mandatory
   DESCRIPTION
     "This attribute counts the bytes sent to the interface. When the 
      maximum count is reached the count wraps to zero."
::= { frMuxDlciStatsEntry 2 }

frMuxDlciFrmFromIf OBJECT-TYPE
   SYNTAX     Counter32 
   ACCESS     read-only
   STATUS     mandatory
   DESCRIPTION
     "This attribute counts the frames received from the interface. Frames 
      that are discarded are not included in this count. When the 
      maximum count is reached the count wraps to zero."
::= { frMuxDlciStatsEntry 3 }

frMuxDlciDeFrmFromIf OBJECT-TYPE
   SYNTAX     Counter32 
   ACCESS     read-only
   STATUS     mandatory
   DESCRIPTION
     "This attribute counts the frames received from the interface with the 
      Discard Eligibility (DE) bit set. When the count reaches maximum 
      it wraps to zero."
::= { frMuxDlciStatsEntry 4 }

frMuxDlciBytesFromIf OBJECT-TYPE
   SYNTAX     PassportCounter64 
   ACCESS     read-only
   STATUS     mandatory
   DESCRIPTION
     "This attribute counts the bytes received from the interface. Frames 
      that are discarded are not included in this count. When the 
      maximum count is reached the count wraps to zero."
::= { frMuxDlciStatsEntry 5 }

frMuxDlciDeBytesFromIf OBJECT-TYPE
   SYNTAX     PassportCounter64 
   ACCESS     read-only
   STATUS     mandatory
   DESCRIPTION
     "This attribute counts the bytes received from the interface with the 
      Discard Eligibility (DE) bit set. When the count reaches maximum 
      it wraps to zero."
::= { frMuxDlciStatsEntry 6 }

frMuxDlciFecnFrmToIf OBJECT-TYPE
   SYNTAX     Counter32 
   ACCESS     read-only
   STATUS     mandatory
   DESCRIPTION
     "This attribute counts the frames sent to the interface with the 
      Forward Explicit Congestion Notification (FECN) bit set. When the 
      count reaches maximum it wraps to zero."
::= { frMuxDlciStatsEntry 7 }

frMuxDlciFecnFrmFromIf OBJECT-TYPE
   SYNTAX     Counter32 
   ACCESS     read-only
   STATUS     mandatory
   DESCRIPTION
     "This attribute counts the frames received from the interface with the 
      Forward Explicit Congestion Notification (FECN) bit set. When the 
      count reaches maximum it wraps to zero."
::= { frMuxDlciStatsEntry 8 }

frMuxDlciBecnFrmToIf OBJECT-TYPE
   SYNTAX     Counter32 
   ACCESS     read-only
   STATUS     mandatory
   DESCRIPTION
     "This attribute counts the frames sent to the interface with the 
      Backward Explicit Congestion Notification (BECN) bit set. When 
      the count reaches maximum it wraps to zero."
::= { frMuxDlciStatsEntry 9 }

frMuxDlciBecnFrmFromIf OBJECT-TYPE
   SYNTAX     Counter32 
   ACCESS     read-only
   STATUS     mandatory
   DESCRIPTION
     "This attribute counts the frames received from the interface with the 
      Backward Explicit Congestion Notification (BECN) bit set. When 
      the count reaches maximum it wraps to zero."
::= { frMuxDlciStatsEntry 10 }

frMuxDlciDiscCongestedFromIf OBJECT-TYPE
   SYNTAX     Counter32 
   ACCESS     read-only
   STATUS     mandatory
   DESCRIPTION
     "This attribute counts the number of frames discarded in the receive 
      direction due to local congestion. When this count reaches 
      maximum, it wraps to zero."
::= { frMuxDlciStatsEntry 11 }

frMuxDlciDiscCongestedFromIfBytes OBJECT-TYPE
   SYNTAX     Counter32 
   ACCESS     read-only
   STATUS     mandatory
   DESCRIPTION
     "This attribute counts the number of bytes discarded in the receive 
      direction due to local congestion. When this count reaches 
      maximum, it wraps to zero."
::= { frMuxDlciStatsEntry 12 }

frMuxDlciDiscDeCongestedFromIf OBJECT-TYPE
   SYNTAX     Counter32 
   ACCESS     read-only
   STATUS     mandatory
   DESCRIPTION
     "This attribute counts the number of discard eligible (DE=1) frames 
      discarded in the receive direction due to local congestion. When this 
      count reaches maximum, it wraps to zero."
::= { frMuxDlciStatsEntry 13 }

frMuxDlciDiscDeCongestedFromIfBytes OBJECT-TYPE
   SYNTAX     Counter32 
   ACCESS     read-only
   STATUS     mandatory
   DESCRIPTION
     "This attribute counts the number of bytes of discard eligible (DE=1) 
      traffic discarded in the receive direction due to local congestion. 
      When the maximum count is reached the count wraps to zero."
::= { frMuxDlciStatsEntry 14 }

frMuxDlciErrorShortFrmFromIf OBJECT-TYPE
   SYNTAX     Counter32 
   ACCESS     read-only
   STATUS     mandatory
   DESCRIPTION
     "This attribute counts the frames received with 0 octets in the 
      information field. When the count reaches maximum it wraps to 
      zero."
::= { frMuxDlciStatsEntry 15 }

frMuxDlciErrorLongFrmFromIf OBJECT-TYPE
   SYNTAX     Counter32 
   ACCESS     read-only
   STATUS     mandatory
   DESCRIPTION
     "This attribute counts the frames received with number of octets in 
      the information field greater than the maximum frame size 
      provisioned in the component pointed to by the applicationName. 
      When the count reaches maximum it wraps to zero. Frames whose 
      lengths are greater than the hardware receive buffer are discarded by 
      the Framer and are therefore not included in this count."
::= { frMuxDlciStatsEntry 16 }


-- FrMux/n Dlci/n ApplicationInfo
-- This component contains provisionable attributes of this Dlci.

frMuxDlciApplInfo OBJECT IDENTIFIER ::= { frMuxDlci 2 }



frMuxDlciApplInfoRowStatusTable OBJECT-TYPE
   SYNTAX     SEQUENCE OF FrMuxDlciApplInfoRowStatusEntry
   ACCESS     not-accessible
   STATUS     mandatory
   DESCRIPTION
     "This entry controls the addition and deletion of 
      frMuxDlciApplInfo components."
::= { frMuxDlciApplInfo 1 }

frMuxDlciApplInfoRowStatusEntry OBJECT-TYPE
   SYNTAX     FrMuxDlciApplInfoRowStatusEntry
   ACCESS     not-accessible
   STATUS     mandatory
   DESCRIPTION
     "A single entry in the table represents a single 
      frMuxDlciApplInfo component."
   INDEX {
      frMuxIndex,
      frMuxDlciIndex,
      frMuxDlciApplInfoIndex }
::= { frMuxDlciApplInfoRowStatusTable 1 }

FrMuxDlciApplInfoRowStatusEntry ::= SEQUENCE {
   frMuxDlciApplInfoRowStatus
      RowStatus,
   frMuxDlciApplInfoComponentName
      DisplayString,
   frMuxDlciApplInfoStorageType
      StorageType,
   frMuxDlciApplInfoIndex
      NonReplicated }

frMuxDlciApplInfoRowStatus OBJECT-TYPE
   SYNTAX     RowStatus 
   ACCESS     read-only
   STATUS     mandatory
   DESCRIPTION
     "This variable is used as the basis for SNMP naming of
      frMuxDlciApplInfo components.
      These components cannot be added nor deleted."
::= { frMuxDlciApplInfoRowStatusEntry 1 }

frMuxDlciApplInfoComponentName OBJECT-TYPE
   SYNTAX     DisplayString 
   ACCESS     read-only
   STATUS     mandatory
   DESCRIPTION
     "This variable provides the component's string name for
      use with the ASCII Console Interface"
::= { frMuxDlciApplInfoRowStatusEntry 2 }

frMuxDlciApplInfoStorageType OBJECT-TYPE
   SYNTAX     StorageType 
   ACCESS     read-only
   STATUS     mandatory
   DESCRIPTION
     "This variable represents the storage type value for the
      frMuxDlciApplInfo tables."
::= { frMuxDlciApplInfoRowStatusEntry 4 }

frMuxDlciApplInfoIndex OBJECT-TYPE
   SYNTAX     NonReplicated 
   ACCESS     not-accessible
   STATUS     mandatory
   DESCRIPTION
     "This variable represents the index for the frMuxDlciApplInfo tables."
::= { frMuxDlciApplInfoRowStatusEntry 10 }

frMuxDlciApplInfoProvTable OBJECT-TYPE
   SYNTAX     SEQUENCE OF FrMuxDlciApplInfoProvEntry
   ACCESS     not-accessible
   STATUS     mandatory
   DESCRIPTION
     "This group contains provisionable attributes of this Dlci."
::= { frMuxDlciApplInfo 11 }

frMuxDlciApplInfoProvEntry OBJECT-TYPE
   SYNTAX     FrMuxDlciApplInfoProvEntry
   ACCESS     not-accessible
   STATUS     mandatory
   DESCRIPTION
     "An entry in the frMuxDlciApplInfoProvTable."
   INDEX {
      frMuxIndex,
      frMuxDlciIndex,
      frMuxDlciApplInfoIndex }
::= { frMuxDlciApplInfoProvTable 1 }

FrMuxDlciApplInfoProvEntry ::= SEQUENCE {
   frMuxDlciApplInfoApplicationName
      Link }

frMuxDlciApplInfoApplicationName OBJECT-TYPE
   SYNTAX     Link 
   ACCESS     read-write
   STATUS     mandatory
   DESCRIPTION
     "This attribute is the link to the application associated with this Dlci."
::= { frMuxDlciApplInfoProvEntry 1 }




-- 
-- Version and Compliance statements
-- 



-- Object-Group Statement:
-- A list of all current accessible leaf objects.

-- OBJECTS { frMuxLmiProtocolStatus,
--           frMuxSnmpOperStatus,
--           frMuxDlciOperationalState,
--           frMuxUnknownStatus,
--           frMuxLmiAdminState,
--           frMuxInvalidHeaderFramesFromIf,
--           frMuxLmiProtocolErrors,
--           frMuxFramerLrcErrors,
--           frMuxDlciFecnFrmFromIf,
--           frMuxLmiKeepAliveStatusEnqToIf,
--           frMuxLmiFullStatusPollingCycles,
--           frMuxLmiFullStatusEnqToIf,
--           frMuxLmiRowStatus,
--           frMuxTimeFramerCongested,
--           frMuxLmiEventCount,
--           frMuxDlciFrmToIf,
--           frMuxDlciBytesFromIf,
--           frMuxDlciBecnFrmToIf,
--           frMuxAvailabilityStatus,
--           frMuxDlciFrmFromIf,
--           frMuxFramerNormPrioLinkUtilToIf,
--           frMuxDlciStorageType,
--           frMuxLmiUsageState,
--           frMuxIfIndex,
--           frMuxDlciDiscDeCongestedFromIf,
--           frMuxAlarmStatus,
--           frMuxLmiComponentName,
--           frMuxLmiErrorEventThreshold,
--           frMuxLastUnknownDlci,
--           frMuxFramerFrmFromIf,
--           frMuxDlciApplInfoApplicationName,
--           frMuxFramerStorageType,
--           frMuxStandbyStatus,
--           frMuxLmiProcedures,
--           frMuxDlciDeFrmFromIf,
--           frMuxDlciErrorShortFrmFromIf,
--           frMuxFramerCrcErrors,
--           frMuxStorageType,
--           frMuxDlciAdminState,
--           frMuxLmiOperationalState,
--           frMuxLmiUnexpectedReports,
--           frMuxFramerFlagsBetweenFrames,
--           frMuxFramerFrmToIf,
--           frMuxFramerOctetFromIf,
--           frMuxDlciApplInfoComponentName,
--           frMuxDlciBecnFrmFromIf,
--           frMuxDlciRowStatus,
--           frMuxDlciApplInfoStorageType,
--           frMuxFramerAdminState,
--           frMuxDlciApplicationName,
--           frMuxDlciDeBytesFromIf,
--           frMuxDlciDiscDeCongestedFromIfBytes,
--           frMuxControlStatus,
--           frMuxAdminState,
--           frMuxDlciFecnFrmToIf,
--           frMuxProceduralStatus,
--           frMuxFramerRowStatus,
--           frMuxDlciErrorLongFrmFromIf,
--           frMuxDlciABitStatusFromIf,
--           frMuxLmiNoStatusReportCount,
--           frMuxFramerAborts,
--           frMuxDlciUsageState,
--           frMuxDlciApplInfoRowStatus,
--           frMuxIfAdminStatus,
--           frMuxFramerOverruns,
--           frMuxDlciComponentName,
--           frMuxCustomerIdentifier,
--           frMuxFramerNonOctetErrors,
--           frMuxLmiUnexpectedIes,
--           frMuxFramerUsageState,
--           frMuxLmiSequenceErrors,
--           frMuxFramerNormPrioLinkUtilFromIf,
--           frMuxFramerComponentName,
--           frMuxUsageState,
--           frMuxFramerLargeFrmErrors,
--           frMuxDlciDiscCongestedFromIfBytes,
--           frMuxFramerInterfaceName,
--           frMuxComponentName,
--           frMuxLmiStorageType,
--           frMuxDlciDiscCongestedFromIf,
--           frMuxFramerUnderruns,
--           frMuxUnknownDlciFramesFromIf,
--           frMuxDlciBytesToIf,
--           frMuxFramerOperationalState,
--           frMuxLmiLinkVerificationTimer,
--           frMuxOperationalState,
--           frMuxFramerFrmModeErrors,
--           frMuxRowStatus }
-- STATUS  mandatory
-- DESCRIPTION
--   "A list of all current accessible leaf objects."

frameRelayMuxGroup OBJECT IDENTIFIER ::= { frameRelayMuxMIB 1 }
frameRelayMuxGroupBE OBJECT IDENTIFIER ::= { frameRelayMuxGroup 5 }
frameRelayMuxGroupBE00 OBJECT IDENTIFIER ::= { frameRelayMuxGroupBE 1 }
frameRelayMuxGroupBE00A OBJECT IDENTIFIER ::= { frameRelayMuxGroupBE00 2 }



-- Agent-Capabilities Statement:

-- PRODUCT-RELEASE "Passport Release 7.0 FrameRelayMux."
-- STATUS          mandatory
-- DESCRIPTION     "FrameRelayMux MIB: MIB Version BE00A,
--                  Software Version BG00S4C."
-- SUPPORTS        Nortel-Magellan-Passport-FrameRelayMuxMIB
--    INCLUDES     { frameRelayMuxGroupBE00A }

frameRelayMuxCapabilities OBJECT IDENTIFIER ::= { frameRelayMuxMIB 3 }
frameRelayMuxCapabilitiesBE OBJECT IDENTIFIER ::= { frameRelayMuxCapabilities 5 }
frameRelayMuxCapabilitiesBE00 OBJECT IDENTIFIER ::= { frameRelayMuxCapabilitiesBE 1 }
frameRelayMuxCapabilitiesBE00A OBJECT IDENTIFIER ::= { frameRelayMuxCapabilitiesBE00 2 }





END
