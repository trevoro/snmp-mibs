RC-ERROR-MIB DEFINITIONS ::= BEGIN

IMPORTS
    MODULE-IDENTITY, OBJECT-TYPE, Integer32
        FROM SNMPv2-SMI
    DisplayString, TruthValue
        FROM SNMPv2-TC
    rcError
        FROM RAPID-CITY;

rcErrorMib MODULE-IDENTITY
       LAST-UPDATED     "200903161100Z" 
       ORGANIZATION     "Bay Networks, Rapid-City Group"
       CONTACT-INFO     "Yu-Ten Lee
                     	 Postal:    Nortel Networks, Inc. 
                           	    4655 Great America Parkway 
                     		    Santa Clara, CA 95052-8185 

                   	 Tel: 	408-495-2560
                   	 Fax: 	408-495-6680
                	 E-mail:	ylee@nortelnetworks.com"

       DESCRIPTION 	"Enterprise MIB for the Accelar product family."
 
       REVISION "200903161100Z" -- 16 March 2009
       DESCRIPTION "Version 234: Added error codes 10458"


       REVISION "200903101200Z" -- 10 March 2009
       DESCRIPTION "Version 233: Added error codes 1227-1230, 2565, 6525, 7146-7155, 8371, 
				 9536-9539, 10127-10129, 10454-10457, 10641, 11224-11225, 11418.
				 Modified error codes: 11218-11223"

       REVISION "200903091200Z" -- 09 March 2009
       DESCRIPTION "Version 232: Added error code 10363"

       REVISION "200903061200Z" -- 06 March 2009
       DESCRIPTION "Version 231: Updated entry for 1181"

       REVISION "200903060000Z" -- 06 March 2009
       DESCRIPTION "Version 230: Added error code 1181."

       REVISION "200903020000Z" -- 02 March 2009
       DESCRIPTION "Version 229: Added error code 4818."

       REVISION "200902170000Z" -- 17 February 2009
       DESCRIPTION "Version 228: Added error codes 9435 and 9436."

       REVISION "200902160000Z" -- 16 February 2009
       DESCRIPTION "Version 227: Added error codes 2329 - 2330."
       
       REVISION "200902100000Z" -- 10 February 2009
       DESCRIPTION "Version 226: Added error codes 3627."

       REVISION "200902060000Z" -- 06 February 2009
       DESCRIPTION "Version 225: Added error codes 11701-11707."

       REVISION "200901090000Z" -- 09 January 2009
       DESCRIPTION "Version 224: Modify error codes 11101, 11102, 11104 and 11108."

       REVISION "200901080000Z" -- 08 January 2009
       DESCRIPTION "Version 223: Added error codes 8119-8121, 8439-8441, 1178-1180, 1538-1539."

       REVISION "200812110000Z" -- 11 December 2008
       DESCRIPTION "Version 222: Added error codes 11414-11417."


       REVISION "200812050000Z" -- 05 December 2008
       DESCRIPTION "Version 221: Added error codes 12601-12606."

       REVISION "200812030000Z" -- 03 December 2008
       DESCRIPTION "Version 220: Added error code 11106-11119."

       REVISION "200811290000Z" -- 29 November 2008
       DESCRIPTION "Version 219: Added error code 3405."

       REVISION "200811280000Z" -- 28 November 2008
       DESCRIPTION "Version 218: Modified label of error code 10248."

       REVISION "200811260000Z" -- 26 November 2008
       DESCRIPTION "Version 217: Added error codes 6522-6524, 7937, 10519, 11219-11223, 
                                 11405-11411, 11616."

       REVISION "200811030000Z" -- 03 November 2008
       DESCRIPTION "Version 216: Added error code 10248."

       REVISION "200810311000Z" -- 31 October 2008
       DESCRIPTION "Version 215: Added error codes 1224-1226, 6519-6521, 7133-7145, 8697-8699,
				 9321, 9531-9535, 10049-10057, 10346-10362, 10447-10453, 10640, 
				 10715-10716, 11214-11218, 11601-11615."

       REVISION "200810310000Z" -- 31 October 2008
       DESCRIPTION "Version 214: Added error code 5510"

       REVISION "200810130000Z" -- 13 October 2008
       DESCRIPTION "Version 213: Added error codes 11201-11213, 11301-11315,
				11401-11404, 11501."

       REVISION "200809150000Z" -- 15 September 2008
       DESCRIPTION "Version 212: Added error codes 1220-1223, 7228-7233, 
				 7933-7936, 8208-8209, 8370, 8683-8696, 
				 10123-10126, 10344-10345, 10444-10446, 
				 10511-10518, 10713-10714, 10845-10847, 
				 10964-10973, 11019"

       REVISION "200808280000Z" -- 28 August 2008
       DESCRIPTION "Version 211: Added error codes 12501-12504."

       REVISION "200808070000Z" -- 07 August 2008
       DESCRIPTION "Version 210: Added error codes 11101-11105."

       REVISION "200807170000Z" -- 17 July 2008
       DESCRIPTION "Version 209: Added error codes 2328 and 6518."

       REVISION "200807080000Z" -- 08 July 2008
       DESCRIPTION "Version 208: Added error code 8367-8369, 8682, 10341-10343, 10442-10443, 
                                 10962-10963, 11001-11018.
                                 Modified error codes 10928-10929, 10936."

       REVISION "200806270000Z" -- 27 June 2008
       DESCRIPTION "Version 207: Added error code 10844."

       REVISION "200806170000Z" -- 17 June 2008
       DESCRIPTION "Version 206: Added error codes 1177, 1219, 9432, 9434, 9529-9530, 
				 10433-10441, 10639, 10937-10961."

       REVISION "200806060000Z" -- 06 June 2008
       DESCRIPTION "Version 205: Added error codes 2493 and 9111."

       REVISION "200805170000Z" -- 17 May 2008
       DESCRIPTION "Version 204: Modified mplsTunnelNoAltPath(10041) to match
				the codestream mplsTunnelNoALtPath. Add error 
				code 5103."

       REVISION "200805140000Z" -- 14 May 2008
       DESCRIPTION "Version 203: Updated the chronology of version updates. 
				 Reduced the string length of enums 10121, 10122."

       REVISION "200805130000Z" -- 13 May 2008
       DESCRIPTION "Version 202: Moved 10841-10844 to 10840-10843."

       REVISION "200805100000Z" -- 10 May 2008
       DESCRIPTION "Version 201: Added error code 6711 and modified 10047-10048."

       REVISION "200805060000Z" -- 06 May 2008
       DESCRIPTION "Version 200: Added error codes 1206-1218, 8363-8366, 8678-8681, 
                                 9428, 10047-10048, 10631-10638, 10712, 10917-10936."
       
       REVISION "200804110000Z" -- 11 Apr 2008
       DESCRIPTION "Version 199: Added error codes 10335-10338."

       REVISION "200804091000Z" -- 09 Apr 2008
       DESCRIPTION "Version 198: Added error codes 8932-8933, 10247.
                                 Modified error codes 1537, 10817-10844."

       REVISION "200804090000Z" -- 09 Apr 2008
       DESCRIPTION "Version 197: Added error codes 7509, 8362, 8672-8677, 
                                 10625-10630, 10711, 10901-10916"

       REVISION "200803250000Z" -- 25 Mar 2008
       DESCRIPTION "Version 196: Added error codes 2489 - 2492.
                                 Removed error code 10422."

       REVISION  "200802260000Z" -- 26 Feb 2008
       DESCRIPTION "Version 195: Added error codes 1537, 2564, 7508, 
				 8359-8361, 8437-8438, 8670-8671, 9427,
				 10241-10246, 10330-10334, 10431-10432, 
				 10510, 10710, 10841-10844.
				 Modified 4902-4906, 8662, 10709"

       REVISION  "200802140000Z" -- 14 Feb 2008
       DESCRIPTION "Version 194: Added error code 8356-8358, 8664-8669, 10426-1027, 
				 10429-10430, 10709"
       
       REVISION  "200802110000Z" -- 11 Feb 2008
       DESCRIPTION "Version 193: Added error code 8661,8663,10424,10428,7761,7507,7762,10623,10624,10425,10324-10329,
				 Modified error code 8782-8789"

       REVISION  "200802010000Z" -- 01 Feb 2008
       DESCRIPTION "Version 192: Added error code 9110,8931"

       REVISION "200801280000Z" -- 28 Jan 2008
       DESCRIPTION "Version 191: Added error codes for DDM 1801-04. Revise the version number."       

       REVISION "200801140000Z" -- 14 Jan 2008
       DESCRIPTION "Version 188: Added error codes for MLT 2561-63"

       REVISION "200801110000Z" -- 11 January 2008
       DESCRIPTION "Version 187: Added error codes 4902-4906, 7759-7760, 7929-7932, 8354-8355, 
		    8659-8660, 10238-10240, 10508-10509, 10622, 10708, 10801-10840. 
		    Modify 10421, 10621"

       REVISION "200801040000Z" -- 4 January 2008
       DESCRIPTION "Version 186: Added error codes 6516,6517."

       REVISION "200712280000Z" -- 28 December 2007
       DESCRIPTION "Version 185: Added error codes 10238-10240, 10508, 10509."

       REVISION "200712260000Z" -- 26 December 2007
       DESCRIPTION "Version 184: Added error codes 9527, 9425, 9426"

       REVISION  "200712200000Z" -- 20 December 2007
       DESCRIPTION "Version 183: Added error code 9109"

       REVISION  "200712180000Z" -- 18 December 2007
       DESCRIPTION "Version 182: Added error codes 8654-8658, 10320-10323, 10422, 10621"

       REVISION  "200712120000Z" -- 12 December 2007
       DESCRIPTION "Version 181: Added error code 8929, 8930"

       REVISION  "200712040000Z" -- 04 December 2007
       DESCRIPTION "Version 180: Added error code 10701-10707, 10423, 7927-7928,
	                         8653, 10619-10620"

       REVISION  "200711200000Z" -- 22 November 2007
       DESCRIPTION "Version 179: Added error code 1536, 7801, 8432-8436"

       REVISION  "200711010000Z" -- 01 November 2007
       DESCRIPTION "Version 178: Added error code 2327, 7499, 7925-7926, 8652, 10042-10046, 
				 10319, 10419-10421, 10504-10507, 10618."

       REVISION  "200710180000Z" -- 18 October 2007
       DESCRIPTION "Version 177: Added error code 1176, 8651, 7926, 10121-10122"	
   
       REVISION  "200710100000Z" -- 10 October 2007
       DESCRIPTION "Version 176: Added error code 8928"

       REVISION  "200710020000Z" -- 02 October 2007
       DESCRIPTION "Version 175: Removed error code 10601 and re-numbered 10602-10618 to 10601-10617."

       REVISION  "200709280000Z" -- 28 September 2007
       DESCRIPTION "Version 174: Added error codes 10601-10618."

       REVISION  "200709260000Z" -- 26 September 2007
       DESCRIPTION "Version 173: Modified error codes 10315-10317, Added error code 8650."

       REVISION  "200709250000Z" -- 25 September 2007
       DESCRIPTION "Version 172: Added error codes 10118-10120, 10503"

       REVISION  "200709190000Z" -- 19 September 2007
       DESCRIPTION "Version 171: Added error codes 5299, 7925, 8335-8353, 10235-10237, 10415-10418, 10501-10502"

       REVISION  "200709100000Z" -- 10 September 2007
       DESCRIPTION "Version 170: Added error codes 8649, 8729, 8774-8799, 10113-10117, 10315-10318, 10401-10413"

       REVISION  "200708290000Z" -- 29 August 2007
       DESCRIPTION "Version 169: Added error codes 7658"

       REVISION  "200708220000Z" -- 22 August 2007
       DESCRIPTION "Version 168: Added error codes 8708-8725" 

       REVISION  "200708140000Z" -- 14 August 2007
       DESCRIPTION "Version 167: Added error codes 9526" 
       
       REVISION  "200708020000Z" -- 02 August 2007
       DESCRIPTION "Version 166: Added error codes 5709-5710, 8774-8781, 10037-10041" 

       REVISION  "200707300000Z" -- 30 July 2007
       DESCRIPTION "Version 165: Added error codes 10035-10036, 10313-10314" 

       REVISION  "200707260000Z" -- 26 July 2007
       DESCRIPTION "Version 164: Added error codes 2321-2326" 
       
       REVISION  "200707200000Z" -- 20 July 2007
       DESCRIPTION "Version 163: Added error codes 1175, 7758, 8771-8773, 
				 9108, 9525, 10109-10112, 10235"

       REVISION  "200707160000Z" -- 16 July 2007
       DESCRIPTION "Version 162: Added NSNA error code 8431"

       REVISION "200707130000Z" -- 13 July 2007
       DESCRIPTION "Version 161: Added error codes 10306-10311"

       REVISION "200707120000Z" -- 12 July 2007
       DESCRIPTION "Version 160: Move lldpMedCapabilityTlvMandatory to 10312"

       REVISION "200707111000Z" -- 11 July 2007
       DESCRIPTION "Version 159: Deleted error codes 9526&9527 duplicate as 9504&9505"

       REVISION "200707110900Z" -- 11 July 2007
       DESCRIPTION "Version 158: Added 1174 (under VLAN module)"

       REVISION "200707110000Z" -- 11 July 2007
       DESCRIPTION "Version 157: Added error codes 9526 & 9527"

       REVISION "200706260000Z" -- 26 June 2007
       DESCRIPTION "Version 156: Added error code 3404 and change 3403."

       REVISION "200706200000Z" -- 20 June 2007
       DESCRIPTION "Version 155: Added error code 7923-7924, 10031-10034."

       REVISION "200706160000Z" -- 16 June 2007
       DESCRIPTION "Version 154: Added error code 3622 and 3626."

       REVISION "200706150000Z" -- 15 June 2007
       DESCRIPTION "Version 153: Added error code 7917."

       REVISION "200706140000Z" -- 14 June 2007
       DESCRIPTION "Version 152: Added error codes 2484-2488 and 3625."

       REVISION "200706130000Z" -- 13 June 2007
       DESCRIPTION "Version 151: Change a typo of error code 8430."

       REVISION "200706080000Z" -- 08 June 2007
       DESCRIPTION "Version 150: Added error code 3403 and 10306."

       REVISION "200706070000Z" -- 07 June 2007
       DESCRIPTION "Version 149: Added error code 10030."

       REVISION "200706060000Z" -- 06 June 2007
       DESCRIPTION "Version 148: Added error code 2802."

       REVISION "200706041000Z" -- 04 June 2007
       DESCRIPTION "Version 147: Added error code 8334."

       REVISION "200706040000Z" -- 04 June 2007
       DESCRIPTION "Version 146: Added error code 10027-10029."

       REVISION "200706011000Z" -- 01 June 2007
       DESCRIPTION "Version 145: Added error code 8769-8770."

       REVISION "200706010000Z" -- 01 June 2007
       DESCRIPTION "Version 144: Added error code 8768."

       REVISION "200705280000Z" -- 28 May 2007
       DESCRIPTION "Version 143: Added error codes 2607 and 2608."

       REVISION "200705240000Z" -- 24 May 2007
       DESCRIPTION "Version 142: Added error codes 10024-10026."

       REVISION "200705220000Z" -- 22 May 2007
       DESCRIPTION "Version 141: Added error codes 2606, 5293-5298, 8646-8648, 8767,
			9424, 10233-10234, 10303-10305."

       REVISION "200705180000Z" -- 18 May 2007
       DESCRIPTION "Version 140: Added error codes 10019-10023."

       REVISION "200705170000Z" -- 17 May 2007
       DESCRIPTION "Version 139: Added error codes 8924-8926."

       REVISION "200705150000Z" -- 15 May 2007
       DESCRIPTION "Version 138: Added error codes 10017-10018."

       REVISION "200705101000Z" -- 10 May 2007
       DESCRIPTION "Version 137: Added error code 10232."

       REVISION "200705100000Z" -- 10 May 2007
       DESCRIPTION "Version 136: Added error code 10231."

       REVISION "200705070000Z" -- 07 May 2007
       DESCRIPTION "Version 135: Added error codes 1172-1173, 2605, 8645, 
				 8764-8766, 10016, 10230."

       REVISION "200704251000Z" -- 25 Apr 2007
       DESCRIPTION "Version 134: Added error codes 8763 and 10229."

       REVISION "200704250000Z" -- 25 Apr 2007
       DESCRIPTION "Version 133: Added error codes 8920-8923 and 10228. Reassigned 8907."

       REVISION "200704241000Z" -- 24 Apr 2007
       DESCRIPTION "Version 132: Added error codes 7916 and 8762."

       REVISION "200704240000Z" -- 24 Apr 2007
       DESCRIPTION "Version 131: Added error codes 10014, 10015, 10301, 10302."

       REVISION "200704220000Z" -- 22 Apr 2007
       DESCRIPTION "Version 130: Added error codes 10223-10227."

       REVISION "200704170000Z" -- 17 Apr 2007
       DESCRIPTION "Version 129: Added error codes 7922, 8760, 8761 and 10222.  
		Removed error codes 7916 and 7917."

       REVISION "200704041000Z" -- 04 Apr 2007
       DESCRIPTION "Version 128: Converted error code 3625 to 3621 and removed 3622"

       REVISION "200704040000Z" -- 04 Apr 2007
       DESCRIPTION "Version 127: Add error codes 1171, 3621-3625, 7754-7757, 
				 7920-7921, 8643-8644, 10001, 10013"

       REVISION "200703300000Z" -- 30 Mar 2007
       DESCRIPTION "Version 126: Change 8429 and add 8430"

       REVISION "200703270000Z" -- 27 Mar 2007
       DESCRIPTION "Version 125: Add error codes 3621 and 8429"

       REVISION "200703140000Z" -- 14 Mar 2007
       DESCRIPTION "Version 124: Add error codes 5289-5292, 10217-10221"

       REVISION "200703100000Z" -- 10 Mar 2007
       DESCRIPTION "Version 123: Add error codes 10215-10216"

       REVISION "200702270000Z" -- 27 Feb 2007
       DESCRIPTION "Version 122: Add error codes 1165-1170, 7722-7753, 7918-7919, 
				 8637-8642, 8758-8759, 10201-10214"

       REVISION "200702250000Z" -- 25 Feb 2007
       DESCRIPTION "Version 121: Updated error codes 2558-2560"

       REVISION "200702080000Z" -- 09 Feb 2007
       DESCRIPTION "Version 120: Added error code 2558; removed error code 10001"

       REVISION "200701300000Z" -- 30 Jan 2007
       DESCRIPTION "Version 119: Added error codes 6996-6998, 7095-7099, 
				 7916-7917, 8632-8636, 8756-8757, 8821-8830, 
				 10011-10012, 10101-10108."

       REVISION "200701260000Z" -- 26 Jan 2007
       DESCRIPTION "Version 118: Added error code 1164."

       REVISION "200701180000Z" -- 18 Jan 2007
       DESCRIPTION "Version 117: Added error code 3402."

       REVISION "200701141000Z" -- 14 Jan 2007
       DESCRIPTION "Version 116: Added error code 7915."

       REVISION "200701140000Z" -- 14 Jan 2007
       DESCRIPTION "Version 115: Added error codes 1163 and 8622-8631."

       REVISION "200701120000Z" -- 12 Jan 2007
       DESCRIPTION "Version 114: Added error code 9399."

       REVISION "200701100000Z" -- 10 Jan 2007
       DESCRIPTION "Version 113: Added error codes 7914, 9521-9524, 10010."

       REVISION "200612150000Z" -- 15 Dec 2006
       DESCRIPTION "Version 112: Added error codes 6710, 7908-7913, 8914-8919, 9421-9423, 10009."

       REVISION "200612130000Z" -- 13 Dec 2006
       DESCRIPTION "Version 111: Added error code 9398"

       REVISION "200612010000Z" -- 01 Dec 2006
       DESCRIPTION "Version 110: Added error code 2483, 4817"

       REVISION "200611290000Z" -- 29 Nov 2006
       DESCRIPTION "Version 109: Added error codes 8617-8621, 9395-9397."

       REVISION "200611220000Z" -- 22 Nov 2006
       DESCRIPTION "Version 108: Added error codes 10006-10008, 8613-8616, 
				 6993-6995, 8753-8755
				 8727 brought back to its original name."

       REVISION "200611150000Z" -- 15 Nov 2006
       DESCRIPTION "Version 107: Added error code 9394"
       
       REVISION "200611140000Z" -- 14 Nov 2006
       DESCRIPTION "Version 106: Added error codes 8602-8612, 8752 and rename 8727"

       REVISION "200611070000Z" -- 07 Nov 2006
       DESCRIPTION "Version 105: Added error codes 8599, 8601, 8748-8751, 9389-9393, 10003-10005"

       REVISION "200610190000Z" -- 19 Oct 2006
       DESCRIPTION "Version 104: Added error codes 2557 and 8747"

       REVISION "200610100000Z" -- 10 Oct 2006
       DESCRIPTION "Version 103: Added error codes 9419-9420"

       REVISION "200610060000Z" -- 06 Oct 2006
       DESCRIPTION "Version 102: Added error codes 6978-6992"

       REVISION "200610050000Z" -- 05 Oct 2006
       DESCRIPTION "Version 101: Added error code 8746 and 10001-10002"

       REVISION "200609291000Z" -- 29 Sep 2006
       DESCRIPTION "Version 100: Added error code 8744-8745"

       REVISION "200609290000Z" -- 29 Sep 2006
       DESCRIPTION "Version 99: Added back original error codes 6101-6199 and 7301-7309 used
		                    for MPLS by an obsoleted product (OM8k)"

       REVISION "200609280000Z" -- 28 Sep 2006
       DESCRIPTION "Version 98: Added error codes 6101-6102 for MPLS and 8737-8743.
			Removed existing 61xx and 73xx blocks currently being
			used for MPLS by an obsoleted product (OM8k)"

       REVISION "200609251000Z" -- 25 Sep 2006
       DESCRIPTION "Version 97: Added error code 8731-8936"

       REVISION "200609250000Z" -- 25 Sep 2006
       DESCRIPTION "Version 96: Added error code 8908-8913"

       REVISION "200609150000Z" -- 15 Sep 2006
       DESCRIPTION "Version 95:  Added error codes 8729-8730.  
			Removed error codes 8601-8603 as VRF/MVR has been assigned 89xx block.
			Added error codes 8560-8598"

       REVISION "200609131000Z" -- 13 Sep 2006
       DESCRIPTION "Version 94: Added error code 8728"

       REVISION "200609130000Z" -- 13 Sep 2006
       DESCRIPTION "Version 93: Added error code 1162"

       REVISION "200609110000Z" -- 11 Sep 2006
       DESCRIPTION "Version 92: Added error codes 2555-2556, 8726-8727, 8901-8907"

       REVISION "200608100000Z" -- 10 Aug 2006
       DESCRIPTION "Version 91: Added error codes 1535"

       REVISION "200608030000Z" -- 03 Aug 2006
       DESCRIPTION "Version 90: Added error codes 3401, 8206-8207"

       REVISION "200607200000Z" -- 20 Jul 2006
       DESCRIPTION "Version 89: Added error codes 1533-1534, 8427-8428, 9388"

       REVISION "200607130000Z" -- 13 Jul 2006
       DESCRIPTION "Version 88: Added error codes 1160,1161 for Pcap"
       
       REVISION "200606140000Z" -- 14 Jun 2006
       DESCRIPTION "Version 87: Added error code 2482 for ACE"

       REVISION "200605110000Z" -- 11 May 2006
       DESCRIPTION "Version 86: Added error codes 9606, 9607 for ospf"

       REVISION "200605050000Z" -- 05 May 2006
       DESCRIPTION "Version 85: Added error codes 1159, 8816-8820"

       REVISION "200604210000Z" -- 21 Apr 2006
       DESCRIPTION "Version 84: Added error codes 8707"

       REVISION "200604070000Z" -- 7 Apr 2006
       DESCRIPTION "Version 83: Added error codes 5508-5509, 7496-7498, & 9908"

       REVISION "200603300000Z" -- 30 Mar 2006
       DESCRIPTION "Version 82: Added error code 8815"

       REVISION "200603241200Z" -- 24 Mar 2006
       DESCRIPTION "Version 81: Added error code 7496"

       REVISION "200603240000Z" -- 24 Mar 2006
       DESCRIPTION "Version 80: Added error codes 7131, 7132"

       REVISION "200603211200Z" -- 21 Mar 2006
       DESCRIPTION "Version 79: Added error codes 1150, 1152-1157"

       REVISION "200603210000Z" -- 21 Mar 2006
       DESCRIPTION "Version 78: Added new error codes 8801-8814" 

       REVISION "200603171000Z" -- 17 Mar 2006
       DESCRIPTION "Version 77: Modify error code 1532, Added error codes 1158, 2544-2554, 8701-8706" 

       REVISION "200603170000Z" -- 17 Mar 2006
       DESCRIPTION "Version 76: Added error code 6977,8559" 

       REVISION "200603150000Z" -- 15 Mar 2006
       DESCRIPTION "Version 75: Added error code 1532" 

       REVISION "200603010000Z" -- 01 Mar 2006
       DESCRIPTION "Version 74: Added error code 8555-8558 " 

       REVISION "200602200000Z" -- 20 Feb 2006
       DESCRIPTION "Version 73: Added error code 2543" 

       REVISION "200602110000Z" -- 11 Feb 2006
       DESCRIPTION "Version 72: Added error codes 7494-7495" 

       REVISION "200602080000Z" -- 08 Feb 2006
       DESCRIPTION "Version 71: Added error codes 6509, 6515, 7487-7493"

       REVISION "200602030000Z" -- 03 Feb 2006
       DESCRIPTION "Version 70: Added error code 6974,6975,7078-7094,7129,7130"

       REVISION "200602020000Z" -- 02 Feb 2006
       DESCRIPTION "Version 69: Added error code 6976"

       REVISION "200601190000Z" -- 19 Jan 2006
       DESCRIPTION "Version 68: Added error codes 2540,2541,2542 for MLT"

       REVISION "200601180000Z" -- 18 Jan 2006
       DESCRIPTION "Version 67: Added error codes 9382-9387"

       REVISION "200601090000Z" -- 09 Jan 2006
       DESCRIPTION "Version 66: Added error codes 1151,6514,7491,9418,9906,9907"

       REVISION "200512080000Z" -- 08 Dec 2005
       DESCRIPTION "Version 65: Added error codes 6971-6973, 8554"

       REVISION "200511220000Z" -- 22 Nov 2005
       DESCRIPTION "Version 64: Added more ipv6 error codes; up to 7486"

       REVISION "200511090000Z" -- 09 Nov 2005
       DESCRIPTION "Version 63: Added 5708"

       REVISION "200511020000Z" -- 02 Nov 2005
       DESCRIPTION "Version 62: Added 8552 - 8553"

       REVISION "200510250000Z" -- 25 Oct 2005
       DESCRIPTION "Version 61: Added 8549 - 8551"

       REVISION "200510180000Z" -- 18 Oct 2005
       DESCRIPTION "Version 60: Added 8546 - 8548 and modified 8513 and 8525"

       REVISION "200510130000Z" -- 13 Oct 2005
       DESCRIPTION "Version 59: Added 8534 - 8545"

       REVISION "200510070000Z" -- 07 Oct 2005
       DESCRIPTION "Version 58: Added 6709"

       REVISION "200510050000Z" -- 05 Oct 2005
       DESCRIPTION "Version 57: Added 6706-6708"

       REVISION "200509300000Z" -- 30 Sep 2005
       DESCRIPTION "Version 56: Removed 631-635, Added 1148-1149, 1530-1531, 6705, 7467-7476, 9380-9381, 9107, 9417"

       REVISION "200509280000Z" -- 28 Sep 2005
       DESCRIPTION "Version 55: Add error code 635."

       REVISION "200509260000Z" -- 26 Sep 2005
       DESCRIPTION "Version 54: Added error codes 633-634 for ECMP 8-path"

       REVISION "200509230000Z" -- 23 Sep 2005
       DESCRIPTION "Version 53: Modify error codes 1147, 6967, and 6969.  Add new error code 6970."

       REVISION "200509210000Z" -- 21 Sep 2005
       DESCRIPTION "Version 52: Added error code 6969"

       REVISION "200509080000Z" -- 08 Sep 2005
       DESCRIPTION "Version 51: Added error codes for IPv6 & SLPP & NSNA"

       REVISION "200509071200Z" -- 07 Sep 2005
       DESCRIPTION "Version 50: Added error codes 6961-6968, 8529-8533"

       REVISION "200508311200Z" -- 31 Aug 2005
       DESCRIPTION "Version 49: Added error codes 9605, 8526-8528, and initial error codes for VRF 8601-8603"

       REVISION "200508261200Z" -- 26 Aug 2005
       DESCRIPTION "Version 48: Added initial error codes for IPv6 - 74xx"

       REVISION "200508260000Z" -- 26 August 2005
       DESCRIPTION "Version 47: Added new error codes 1146-1147 and 8501-8525."

       REVISION "200508250000Z" -- 25 Aug 2005
       DESCRIPTION "Version 46: Added error codes 8424, 8425"

       REVISION "200508100000Z" -- 10 Aug 2005
       DESCRIPTION "Version 45: Added error codes 2539, 4110"

       REVISION "200508030000Z" -- 03 Aug 2005
       DESCRIPTION "Version 44: Added error codes 1145, 6513"

       REVISION "200507250000Z" -- 25 July 2005
       DESCRIPTION "Version 43: Added error codes 3618-3620, 8422-8423, 9379"

       REVISION "200507140000Z" -- 14 July 2005
       DESCRIPTION "Version 42: Added error codes 1141-1144."

       REVISION "200507060000Z" -- 06 July 2005
       DESCRIPTION "Version 41: Added NSNA error codes 8401-8421.  Also, added 1140."

       REVISION "200506011200Z" -- 01 June 2005
       DESCRIPTION "Version 40: Added new error code 1529."

       REVISION "200505241200Z" -- 24 May 2005
       DESCRIPTION "Version 39: Added new error codes for NSNA.  Reorganized existing error codes so that they appear in ascending order."

       REVISION "200505240000Z" -- 24 May 2005
       DESCRIPTION "Version 38: Added new error codes 8332 and 8333."

       REVISION "200505230000Z" -- 23 May 2005
       DESCRIPTION "Version 37: Added new error code 8205."

       REVISION "200505170000Z" -- 17 May 2005
       DESCRIPTION "Version 36: Added new error code 2604."

       REVISION "200505160000Z" -- 16 May 2005
       DESCRIPTION "Version 35: Renamed error codes 8311-8312 and 8325-8329."

       REVISION "200505131200Z" -- 13 May 2005
       DESCRIPTION "Version 34: Added error code 8331"

       REVISION "200505130000Z" -- 13 May 2005
       DESCRIPTION "Version 33: Added error code 9604"

       REVISION "200505060000Z" -- 06 May 2005
       DESCRIPTION "Version 32: Added error code 8004.  Updated 8002."

       REVISION "200504221200Z" -- 22 April 2005
       DESCRIPTION "Version 31: Added new error code 8330.
			Also sync up the error codes with the Master Copy:
			- Add 2533 - 2537
			- Add 7064 - 7077
			- Add 7127-7128
			- 8108-8119 incorrectly numbered - should be 8107-8118"

       REVISION "200504131200Z" -- 13 April 2005
       DESCRIPTION "Version 30: Added error codes 8319-8329"

       REVISION "200503241200Z" -- 24 March 2005
       DESCRIPTION "Version 29: Added error code 8003 - eapInvalidMaxNonEapValue"

       REVISION "200502231200Z" -- 23 February 2005
       DESCRIPTION "Version 28: Added error codes 9375-9378"

       REVISION "200502180000Z" -- 18 February 2005
       DESCRIPTION "Version 27: Sync-up with Master Copy and introduced ISIS @ 83xx"

       REVISION "200502110000Z" -- 11 February 2005
       DESCRIPTION "Version 26: Added error codes for 4109 & 5507.  Introduced Tacacs @ 82xx"

       REVISION "200502100000Z" -- 10 February 2005
       DESCRIPTION "Version 25: Added intial error codes for IPFIX @ 81xx"

       REVISION "200502011800Z" -- 01 February 2005
       DESCRIPTION "Version 24: Added error code 2419"

       REVISION "200501241200Z" -- 24 January 2005
       DESCRIPTION "Version 23: Added error codes 6511-6512, 8002"

       REVISION "200501201200Z" -- 20 January 2005
       DESCRIPTION "Version 22: Added error codes 1134-1135"       

       REVISION "200501171200Z" -- 17 January 2005
       DESCRIPTION "Version 21: Updated 7613"

       REVISION "200501141800Z" -- 14 January 2005
       DESCRIPTION "Version 20: Added message 9373"

       REVISION "200412200000Z" -- 20 December 2004
       DESCRIPTION "Version 19: Updated messages (7059,6958)
				Added new messages (6956,6957,7057,7058) "
       
       REVISION "200412171800Z" -- 17 December 2004
       DESCRIPTION "Version 18: Added new messages (6958,7059, 7648-7653,7505,7506)."
       
       REVISION "200412071400Z" -- 12 December 2004
       DESCRIPTION "Version 17: Added new messages (1132-1133)."

       REVISION "200411301700Z" -- 30 November 2004
       DESCRIPTION "Version 16: Added new messages for Launch Pad(1129-1131)."

       REVISION "200411110000Z" -- 11 November 2004
       DESCRIPTION "Version 15: Cleaned up REVISIONs and fixed typos."

       REVISION "200411040000Z" -- 04 November 2004
       DESCRIPTION "Version 14: Modify PowerRanger related Error
                                messages(9363,64,65,69,71,72, 7501-04,
                                7601-47,7701-17)"

       REVISION "200410271700Z" -- 27 October 2004
       DESCRIPTION "Version 13: Add error message
                                communityListModificationNotAllowed(5288)"

       REVISION "200410200000Z" -- 20 October 2004
       DESCRIPTION "Version 12: Add error message 6948-6955 and 7052-7054,
                                7056, 7904-7905"

       REVISION "200410110000Z" -- 11 October 2004
       DESCRIPTION "Version 11: Add error message 1127, 1128 And Correct
                                the 7042,7045."

       REVISION "200410080000Z" -- 08 October 2004
       DESCRIPTION "Version 10: Add error message (1126)."

       REVISION "200410050000Z" -- 05 October 2004
       DESCRIPTION "Version 9: Add missing error message (2532, 7035-7051)."

       REVISION "200409300000Z" -- 30 September 2004
       DESCRIPTION "Version 8: Add missing error message (9338-9344)."

       REVISION "200409290000Z" -- 29 September 2004
       DESCRIPTION "Version 7: Add error message eapGuestAndMultiMac ."

       REVISION "200409280000Z" -- 28 September 2004
       DESCRIPTION "Version 6: Fixing typo and remove duplicate entry."

       REVISION "200409230000Z" -- 23 September 2004
       DESCRIPTION "Version 5: Added back unsubmitted error message."

       REVISION "200409130000Z" -- 13 September 2004
       DESCRIPTION "Version 4: Added radiusInvalidCliCommandCount(4107)"  

       REVISION "200407200000Z" -- 20 July 2004
       DESCRIPTION "Version 3: Added version info"  

       ::= { rcError 0 }
 
rcErrorLevel OBJECT-TYPE
        SYNTAX        Integer32
        MAX-ACCESS    read-only
        STATUS        current
        DESCRIPTION   "Error level indicator for the last error
                      reported in the system.  The meaning of
		      this value are :

			0 = Informative Information
			1 = Warning Condition
			2 = Error Condition
			3 = Manufacturing Information
			4 = Fatal Condition
		      "
        ::= { rcError 1 } 
 
rcErrorCode OBJECT-TYPE
        SYNTAX        Integer32
        MAX-ACCESS    read-only
        STATUS        current
        DESCRIPTION   "Error code indicator for the last error
                      reported in the system.  This is an encoded
		      value that identifies the software module
		      that generated the error message as well as
                      a specific error condition within that module.
		      This value is transparent to the user.  This
		      value is intended to help Accelar support and
		      development staff to isolate system problems."
        ::= { rcError 2 }

rcErrorText OBJECT-TYPE
        SYNTAX        DisplayString
        MAX-ACCESS    read-only
        STATUS        current
        DESCRIPTION   "Error string of the last error reported 
                      in the system."
        ::= { rcError 3 }

-- 
-- *** THIS SECTION IS GENERATED FROM ../mib_tools/error.mib ***

-- This is generated by str2c.py -mib
-- Do not edit this file
-- Instead, edit $(TOPDIR)/mib/mib_tools/error_input.txt

rcErrorReturnCode OBJECT-TYPE
    SYNTAX INTEGER {
		none(100),
		resourceNotAvailable(101),
		operationNotAllowed(102),
		operationInProgress(103),
		invalidPortNumber(104),
		invalidSubnetAddress(105),
		invalidSubnetMask(106),
		invalidVlanId(107),
		invalidVlanName(108),
		invalidVlanType(109),
		invalidStgId(110),
		invalidProtocolId(111),
		invalidPortMembers(112),
		invalidStaticMembers(113),
		invalidNotAllowedMembers(114),
		destinationNotReachable(115),
		tableIsFull(116),
		nondualConnectorGigPort(117),
		testIdNotPresent(118),
		invalidTestId(119),
		invalidStatusChange(120),
		invalidCpuCard(121),
		invalidSrcPortChoice(122),
		dstPortUnspecified(123),
		srcPortOneUnspecified(124),
		srcPortTwoUnspecified(125),
		notSupported(126),
		userNameIsNonUnique(127),
		invalidName(128),
		unknownErrorCode1(129),
		cannotModifyThisField(130),
		invalidUserPasswordLength(131),
		thisUsernameExists(132),
		invalidIpAddress(133),
		invalidMacAddress(134),
		nosuchEntry(135),
		anotherLoopBackTestAlreadyRunning(136),
		protocolIdNotRoutable(137),
 		autoNegotiateIsOn(138),
		noActionSpecified(139),
		invalidActionSpecified(140),
		cannotModifyAutoNegotiateIsOn(141),
		cannotModifyAutoPortIsFiber(142),
		autoNegotiationNotSupported(143),
		cannotSetAdminSpeed(144),
		cannotSetAdminDuplex(145),
		ospfRtrDeadIntIsnotMultOfHelloInt(146),
		ospfRtrDeadIntLessThan4TimesHelloInt(147),
		notUsed1(148),
		ospfBadAuthValue(149),
		ospfEnabled(150),
		ospfAreaNotFound(151),
		ospfBackboneArea(152),
		notInTestMode(153),
		ospfInvalidAreaRangeMask(154),
		ospfDuplicateEntry(155),
		ospfRangeNotAllocated(156),
		ospfAreaRangeNotFound(157),
		testRunning(158),
		nvramLimitExceeded(159),
		flowAlreadyExist(160),
		flowNotFound(161),
		invalidOspfAreaRangeNet(162),
		duplicateIpAddress(163),
		conflictingIpAddress(164),
		invalidRouteCost(165),
		invalidNextHop(166),
		duplicateRoute(167),
		cannotFindRoute(168),
		cannotDeleteLocalRoute(169),
		badDhcpMinSec(170),
		badDhcpMaxHop(171),
		badDhcpMode(172),
		badAgentAddress(173),
		dhcpNotEnabled(174),
		dhcpForwardNotFound(175),
		dhcpDuplicateForward(176),
		dhcpMaxForward(177),
		dhcpBadEnable(178),
		invalidDeviceFileNumber(179),
		notExecutableDeviceFile(180),
		deletedDeviceFile(181),
		pcmciaNotPresent(182),
		pcmciaWriteProtected(183),
		discontiguousSubnetMask(184),
		invalidOspfMetric(185),
		ospfHostRouteNotFound(186),
		invalidMltId(187),
		invalidMltName(188),
		onlyOnePortInMlt(189),
		moreThan4PortsInMlt(190),
		portsInDifferentQuid(191),
		portAlreadyInAnotherMlt(192),
		invalidVlan(193),
		nonExistIpMcastAddriess(194),
		invalidIpMulticastAddress(195),
		portIsLocked(196),
		accessRestriction(197),
		invalidDeviceFileLength(198),
		duplicateAccessPolicyId(199),
		noDesiredAccessPolicyItem(200),
		ipfFilterNonExist(201),
		ipfInvalidVlanPriority(202),
		ipfInvalidDestinationAddress(203),
		ipfInvalidSourceAddress(204),
		ipfFilterDuplicate(205),
		ipfGlobalListDuplicate(206),
		ipfGlobalListNonExist(207),
		ipfBaseListDuplicate(208),
		ipfBaseListNonExist(209),
		ipfPortDuplicate(210),
		ipfPortNonExist(211),
		ipfListNonExist(212),
		snmpSnoopDisabled(213),
		invalidHostIpAddress(214),
		snoopStaticGroupExist(215),
		ripAnnouncePolicyNotFound(216),
		duplicateRipAnnouncePolicy(217),
		ospfAnnouncePolicyNotFound(218),
		duplicateOspfAnnouncePolicy(219),
		policyMatchNetEntryNotFound(220),
		duplicatePolicyNetEntry(221),
		policyAddrListEntryNotFound(222),
		duplicatePolicyAddrListEntry(223),
		policyAddrListIdNotFound(224),
		policyExactNetListNotFound(225),
		policyRangeNetListNotFound(226),
		policyRipGatewayListNotFound(227),
		policyRipInterfaceListNotFound(228),
		policyOspfRtrIdListNotFound(229),
		policyAnnounceInterfaceListNotFound(230),
		policyAdvertiseNetListNotFound(231),
		policyInjectNetListNotFound(232),
		invalidPolicyListIdListSize(233),
		policyAddrEntryNotFound(234),
		duplicatePolicyAddrEntry(235),
		disableThisPortFirst(236),
		mutinettingNotSupported(237),
		addingGlobalFilterToNonGlobalList(238),
		addingNonGlobalFilterToGlobalList(239),
		setFilteredPortMode(240),
		setFilteredPortEnableValue(241),
		invalidModeType(242),
		duplicateRipAcceptPolicy(243),
		ripAccepPolicyNotFound(244),
		duplicateOspfAcceptPolicy(245),
		ospfAccepPolicyNotFound(246),
		invalidAccessPolicyName(247),
		invalidAccessPolicyPolicyEnable(248),
		invalidAccessPolicyMode(249),
		invalidAccessPolicyService(250),
		invalidAccessPolicyPrecedence(251),
		invalidAccessPolicyNetAddress(252),
		invalidAccessPolicyTrustedHostAddress(253),
		invalidAccessPolicyTrustedHostUserName(254),
		invalidAccessPolicyAccessLevel(255),
		invalidAccessPolicyLogSetting(256),
		invalidAccessPolicyPolicyId(257),
		invalidAreaOptions(258),
		cannotDeleteAreaIfCountIsNotZero(259),
		ospfInterfaceNotFound(260),
		ospfIfAreaIdConflictsWithConfiguredAreaRange(261),
		applyingDuplicateGlobalFilterToPort(262),
		differentMltPortTypes(263),
		addPortToMltFailed(264),
		removePortFromMltFailed(265),
		mirrorPortInMlt(266),
		invalidDhcpAlwaysBroadcast(267),
		interfaceIsSetToTransmitRipV1(268),
		ripInterfaceDoesnotExist(269),
		interfaceIsNotRunningRip(270),
		cannotCreateVirtLinksThroughStubArea(271),
		invalidSyslogEnableSetting(272),
		invalidSyslogMaxHostsSettings(273),
		invalidSyslogHostIpAddr(274),
		invalidSyslogHostUdpPort(275),
		invalidSyslogHostFacility(276),
		invalidSyslogModuleId(277),
		invalidSyslogSeverity(278),
		invalidSyslogMapInfoSeverity(279),
		invalidSyslogMapWarningSeverity(280),
		invalidSyslogMapErrorSeverity(281),
		invalidSyslogMapMfgSeverity(282),
		invalidSyslogMapFatalSeverity(283),
		invalidSyslogMapTraceMsgSetting(284),
		invalidSyslogMapTrapMsgSetting(285),
		invalidSyslogLogTraceMsgSetting(286),
		invalidSyslogLogTrapMsgSetting(287),
		invalidSyslogEntryEnableSetting(288),
		invalidSyslogMaxHostSetting(289),
		invalidSyslogHostId(290),
		duplicateSyslogEntry(291),
		syslogHostTableIsFull(292),
		noDesiredSyslogHostEntryFound(293),
		invalidHoldDownTime(294),
		incompatibleAruHardware(295),
		invalidVrid(296),
		duplicateVrrpEntry(297),
		noVrrpIpAddressSpecified(298),
		invalidVrrpControlValue(299),
		invalidVrrpPriority(300),
		invalidVrrpAdvertisementInterval(301),
		maxNumOfVrrpsEntriesExceeded(302),
		policyNetListEntryNotFound(303),
		duplicatePolicyNetListEntry(304),
		policyNetListIdNotFound(305),
		filterOnAnEnabledPort(306),
		listOnAnEnabledPort(307),
		invalidIpFilterSrcOption(308),
		invalidIpFilterDstOption(309),
		invalidOspfAreaImportextOption(310),
		invalidOspfInterfaceMd5KeyIdLength(311),
		invalidOspfInterfaceMd5KeyLength(312),
		invalidIPXNetworkNumber(313),
		ipxCircuitAlreadyExists(314),
		ipxCircuitDoesNotExist(315),
		encapsulationIsNotAllowedOnSameSegment(316),
		encapsulationDoesNotMatchProtocolBasedVLAN(317),
		invalidDvmrpIfTblEnableValue(318),
		invalidDvmrpIfTblMetricValue(319),
		ipHostPartForSubnetAddrIsNonZero(320),
		globalMulticastNotEnabled(321),
		metricFieldIsCreatedButModified(322),
		invalidIpMRouteInterfaceTblTtlValue(323),
		invalidUdpPortNumber(324),
		invalidUdpProtocolNameLength(325),
		cannotModifyUdpProtocolName(326),
		udpProtocolEntryDoesnotexists(327),
		duplicateUdpProtocolEntry(328),
		cannotDelUdpProtocolEntryFwdEntriesExists(329),
		udpBroadcastIntfEntryDoesnotExists(330),
		duplicateUdpBroadcastIntfEntry(331),
		invalidUdpConfBroacastInterface(332),
		updConfIntfEntryNotEnabledForUdpBcastForwarding(333),
		udpPortFwdEntryDoesnotExists(334),
		duplicateUdpPortFwdEntryDoesnotExists(335),
		udpPortFwdEntryUdpPortInterfaceDoesnotExists(336),
		udpPortFwdListEntryDoesnotExists(337),
		duplicateUdpPortFwdListEntryDoesnotExists(338),
		udpPortFwdListEntryPortFwdIdDoesnotExists(339),
		udpPortFwdListEntryinvalidFwdIdListSize(340),
		cannotDeleteUdpPortFwdListEntryInterfaceUsingThisList(341),
		invalidIgmpSnoopDestAddress(342),
		invalidIgmpSnoopHostAddress(343),
		cannotDeleteDefaultUdpProtocolTblEntry(344),
		nextHopRouteIsStaticRoute(345),
		invalidUpdateIntervalValueInDVMRPGlobalTable(346),
		invalidTriggeredUpdateIntervalValueInDVMRPGlobalTable(347),
		invalidLeafTimeoutValueInDVMRPGlobalTable(348),
		invalidNbrTimeoutValueInDVMRPGlobalTable(349),
		invalidNbrProbeIntervalValueInDVMRPGlobalTable(350),
		invalidQueryIntervalValueInIgmpInterfaceTable(351),
		invalidVersionValueInIgmpInterfaceTable(352),
		invalidQueryMaxResponseTimeValueInIgmpInterfaceTable(353),
		invalidRobustnessValueInIgmpInterfaceTable(354),
		invalidLastMembQueryIntvlValueInIgmpInterfaceTable(355),
		invalidANDMaskInRcIpTosRuleGroup(356),
		invalidORRule1InRcIpTosRuleGroup(357),
		invalidORRule2InRcIpTosRuleGroup(358),
		invalidORRule3InRcIpTosRuleGroup(359),
		deleteStaticPortNotValid(360),
		maxEntriesForIgmpAccTbl(361),
		maxMaskNumberOfHostIgmpAccTbl(362),
		dvmrpIgmpExclusive(363),
		theSpecifiedAreaRangeMaskIsInvalid(364),
		invalidLengthOf2kBootConfigImageSource(365),
		invalidLengthOf2kBootConfigSource(366),
		preferenceOfStaticRouteIsInvalid(367),
		copyFileOutOfSpace(368),
		copyFileFileNotFound(369),
		copyFileInvalidDestination(370),
		copyFileInvalidSource(371),
		copyFileFail(372),
		invalidLinkFlapDetectAutoPortDown(373),
		invalidLinkFlapDetectFrequency(374),
		invalidLinkFlapDetectInterval(375),
		invalidLinkFlapDetectSendTrap(376),
		invalidQosLevel(377),
		invalidQosWeight(378),
		invalidQosThreshold(379),
		invalidTagToQosTableIeee1pValue(380),
		invalidTagToQosTableQosLevel(381),
		invalidDsFieldToQosTableDsField(382),
		invalidDsFieldToQosTableQosLevel(383),
		invalidQosToTagTableQosLevel(384),
		invalidQosToTagTableIeee1pValue(385),
		invalidQosLevelValue(386),
		invalidQosToDsFieldTableDsFieldValue(387),
		invalidQosToDsFieldTableQosLevel(388),
		invalidDiffServEnable(389),
		invalidDiffServType(390),
		invalidIeeeOverride(391),
		invalidVlanQosValue(392),
		invalidVlanTosValue(393),
		operationNotAllowedOnAccessPort(394),
		operationNotAllowedOnTaggingPort(395),
		invalidFileName(396),
		invalidDiaglogueDuplicateMirroredPort(397),
 		invalidDiaglogueEnableValue(398),
		invalidDiaglogueEnableSetting(399),
		invalidDiaglogueModeSetting(400),
		invalidDiaglogueEntryId(401),
		srcMacVlanIsNotYetEnabled(402),
		srcMacVlanIsNotYetDisabled(403),
		invalidDiaglogueOperation(404),
		invalidMacAddressSpecied(405),
		maxResponseTimeGreaterThanQueryInterval(406),
		noModifyDsFltrAllowedOnDiffSrvCorePort(407),
		mltMoreThan4PortsInMgMlt(408),
		protocolRulesForThePortHasExceeded16(409),
		routeDoesNotExistsInTheRroutingTable(410),
		diagMirrorByPortTableAccessError(411),
		diagMirrorByPortInvalidMirroringPortSetting(412),
		igmpAdminVersionConfiguredLessThanOperatingVersion(413),
		canOnlyConfigureViaMltTable(414),
		dvmrpInterfaceTableIsFull(415),
		invalidDscpField(416),
		invalidDscpReservedField(417),
		disablePortPriorToChangingDiffServPortType(418),
		ipFilterInvalidId(419),
		rateLimitingExceeded(420),
		diagEntryMaxExceeded(421),
		onlyOneMirroringPortAllow(422),
		radiusServerExist(423),
		radiusServerNotExist(424),
		radiusServerInUse(425),
		radiusMaxServerNumExceeded(426),
		radiusInvalidAttribute(427),
		canNotChangeLocking(428),
		activationDisabled(429),
		zeroMac(430),
		atmBadVpi(431),
		atmBadVci(432),
		atmBadFramingMode(433),
		atmDestroyPvcFailed(434),
		atmBadName(435),
		atmBadEnable(436),
		atmBadpvcEncapsulation(437),
		atmBadPvdServiceType(438),
		atmBadPeakCellRate(439),
		atmBadSustainedCellRate(440),
		atmBadMaxBurstSize(441),
		atmBadMaxMtuSize(442),
		atmBadElanId(443),
		atmUnknownOperation(444),
		atmDestroy1483ElanFailed(445),
		atmBadPerformTagging(446),
		atmIlleagalElanDefinition(447),
		atmCreate1483ElanFailed(448),
		atmBadSnmpMessage(449),
		atmBadScrambleEnable(450),
		atmBadSignalingEnable(451),
		atmBadClockSource(452),
		atmBadLoopback(453),
		badRowStatus(454),
		atmBadLaneConfigMode(455),
		atmLecCreationFailed(456),
		atmBad1438Inarp(457),
		atmF5StartFailed(458),
		atmBadPvcId(459),
		atmBadConnectType(460),
		atmBadIpxEncapMethod(461),
		atmBadUniVersion(462),
		atmCreatePvcFailed(463),
		invalidLoginPromptLength(464),
		invalidPasswordPromptLength(465),
		invalidCliBannerLength(466),
		invalidCliBannerSize(467),
		invalidCliMotdLength(468),
		invalidCliMotdSize(469),
		invalidPortNameLength(470),
		invalidPortName(471),
		invalidMaxAdvertiseInterval(472),
		invalidMinAdvertiseInterval(473),
		invalidMaxInitialAdvertiseInterval(474),
		invalidMaxInitalAdvertments(475),
		invalidNeigborDeadInterval(476),
		invalidUserSetTimeYearValue(477),
		invalidUserSetTimeMonthValue(478),
		invalidUserSetTimeDateValue(479),
		invalidUserSetTimeHourValue(480),
		invalidUserSetTimeMinuteValue(481),
		invalidUserSetTimeSecondValue(482),
		rtcIsNotPresent(483),
		rtcIsNotRunning(484),
		maxMacCount(485),
		maxAdvertiseIntLessThanMinAdvertiseInt(486),
		minAdvertiseIntGreaterThanMaxAdvertiseInt(487),
		dvmrpNotEnabledGlobally(488),
		vrrpCriticalIpAddrNotEnable(489),
		vrrpInvalidCriticalIpAddr(490),
		metricConfigNotAllowed(491),
		posActiveNonBcpEnabledPort(492),
		posVlanNoMorePorts(493),
		posPortCanBeAdded(494),
		posNonBcpCanNotBeEnabled(495),
		posImageFilenameTooLong(496),
		posNoIpcpEnableOnMltPorts(497),
		posNoIpcpEnableOnTagPort(498),
		posNoIpxcpEnableOnMltPort(499),
		posNoIpxcpEnableOnTagPort(500),
		posDisableTagBeforeBcpDisable(501),
		posAssignIpBeforeIpcpEnable(502),
		posAssignIpxBeforeIpxcpEnable(503),
		posAssignIpBeforeRemoteIp(504),
		posKeepRemoteIpInSameSubnet(505),
		staticRouteEnabled(506),
		cannotChangeAutoLearnState(507),
		invalidVirtualIpAddr(508),
		virtualAndPhysicalIpNotInSameSubnet(509),
		vidNotAvailable(510),
		mgidNotAvailable(511),
		posNoIpcpEnableOnPolicyVlanPort(512),
		posNoIpxcpEnableOnPolicyVlanPort(513),
		posVrrpNotAllowed(514),
		webInvalidHttpPort(515),
		cannotAddMulticastStaticMac(516),
		posNoStpEnableWithBCPClosed(517),
		posAtmNoRip1(518),
		ipfFilterNumOverFilterSetLimit(519),
		ipfQosTrafficAverageRateOverLimit(520),
		ipfQosTrafficProfileNotExist(521),
		atmNoIpIpxConfigOnVlan(522),
		atmPvcIsInUse(523),
		globalFilterNotDisabled(524),
		dhcpNotOnByIpSubnetVlan(525),
		cannotConfigureDefaultGateway(526),
		routeExists(527),
		gatewayNotOnMgmtInterfaceSubnet(528),
		mgmtRouteTableFull(529),
		routeNotExists(530),
		invalidMacOffsetRangeForBW(531),
		invalidMacOffsetRangeForMG(532),
		atmPvcBadPeakCellRate(533),
		atmPvcBadSustainedCellRate(534),
		qosReservedQosLevel(535),
		dvmrpGlobInvalidFwdCacheTimeOut(536),
		dvmrpGlobInvalidRouteExpireTimeOut(537),
		dvmrpGlobInvalidRouteDiscardTimeOut(538),
		dvmrpGlobInvalidRouteSwitchTimeOut(539),
		pimCondRPGroupExists(540),
		pimCandRPAddressInvalid(541),
		pimGroupAddressInvalid(542),
		pimNotEnabled(543),
		pimInvalidJPInterval(544),
		pimInvalidMode(545),
		pimInvalidHelloInt(546),
		pimInvalidCBSRPRef(547),
		pimInvalidEnable(548),
		pimAlreadyEnabled(549),
		ipDvmrpAlreadyEnabled(550),
		ospfIntfChangeNotAllowedWhenEnabled(551),
		ospfIntfChangeFromNBMANotAllowed(552),
		ospfPollIntIsnotMultOfHelloInt(553),
		ospfNeigNoCircuit(554),
		ospfNeigSameIp(555),
		ospfCircNotNBMA(556),
		ospfCircPriZero(557),
		ospfNBMANeigExist(558),
		ospfNBMANeigNotFound(559),
		ospfDynNeigExist(560),
		pgmInvalidSessionLifetime(561),
		pgmInvalidMaxRetxStates(562),
		pgmInvalidMaxSessions(563),
		pgmInvalidIfNakRetxInterval(564),
		pgmInvalidIfMaxNakRetxCnt(565),
		pgmInvalidIfNakRdataInt(566),
		pgmInvalidIfNakElimInt(567),
		maxOfMirroringPortAllowedExceed(568),
		duplicatedRoutePolicyEntry(569),
		specifiedRoutePolicyEntryNotFound(570),
		specifiedPrefixListNotFound(571),
		routePolicyListNotSpecify(572),
		routePolicyPrefixListOverLimit(573),
		ipPrefixListDuplicate(574),
		ipPrefixListDuplicateEntry(575),
		ipPrefixListEntryNotFound(576),
		ipPrefixListInvalidName(577),
		ipRedistributeDuplicateEntry(578),
		ipRedistributeEntryNotFound(579),
		ipOspfInFilterDuplicateEntry(580),
		ipOspfInFilterEntryNotFound(581),
		ipEcmpNotDisabled(582),
		ipEcmpMaxExceeded(583),
		ipfQosTrafficAvgRateZeroProfileEnable(584),
		ipmTimePruneEntryInvalidGroup(585),
		ipmTimePruneEntryDuplicate(586),
		ipmTimePruneEntryNotExist(587),
		ipmTimePruneEntryInvalidExpireTime(588),
		smltIstExist(589),
		smltSmltIdExist(590),
		smltIstNotExist(591),
		smltSmltIsEnabled(592),
		smltSmltLocalIpNotExist(593),
		smltInvalidPortTypeForIstMlt(594),
		ntpServerAlreadyExist(595),
		ntpServerDoesNotExist(596),
		ntpKeyAlreadyExists(597),
		ntpKeyDoesNotExist(598),
		ntpMaxKeyExceeded(599),
		ntpServerAlreadyEnabled(600),
		ntpServerAlreadyDisabled(601),
		ntpNoServerConfigured(602),
		ntpMaxServerNumExceeded(603),
		ntpInvalidIntervalValue(604),
		ecmpNotEnabled(605),
		ipfInvalidProtocolType(606),
		assignIpToPortInRouteVlan(607),
		assignIpToVlanWithRoutePortMember(608),
		ipfIstPort(609),
		smltMltIpfExist(610),
		smltMltPortIpfExist(611),
		smltL2fIstPort(612),
		smltMltL2fExist(613),
		smltMltPortL2fExist(614),
		portMirroringEgressNotSupportFullDuplexMode(615),
		pimGlobInvalidRegSupprTimeOut(616),
		smltNotAvailableIn8100(617),
		mltNoPort(618),
		mltInvalidPortType(619),
		inUsedByATM1483Elan(620),
		smltIstStpEnableNotAllowed(621),
		invalidHighestVrrpPrio(622),
		dynamicPortMemberIn8100IsNotAllowed(623),
		ipfGlobalNextHopModeNotSupported(624),
		smltPeerIpNotExist(625),
		smltMltNoThisVlan(626),
		smltNotANormalMlt(627),
		validStaticRtExist(628),
		validBlkHolRtExist(629),
		pimOrIgmpAlreadyEnabled(630),
		readWriteAccessReadOnly(900),
		readWriteAccessLevelOne(901),
		readWriteAccessLevelTwo(902),
		readWriteAccessLevelThree(903),
		readWriteAccessReadWrite(904),
		readWriteAccessReadWriteAll(905),
		readWriteAccessUnknownLevel(906),
		vlanWithIPXEnabledCannotAdd10GEPortOrMlt(1101),
		addRemDsapSsapNotAllowed(1102),
		maxDsapSsapExceeded(1103),
		vlanInvalidEncap(1104),
		cannotDeleteVlanWithTlsEndpointMember(1105),
		vlanCannotAddMoreThanOneServerPort(1106),
		vlanSupportsOneAssociatedPortOrOneMlt(1107),
		vlanCannotRemoveVpnPortWhileInService(1108),
		vlanEnforcementNotAllowed(1109),
		vlanNaapVlanPortMustBeTagged(1110),
		vlanRegPortNotAllowedInNaapVlan(1111),
		vlanFwPortNotAllowedInRegVlan(1112),
		invalidVlanIdSpecified(1113),
		exceedMaxNumPolicyVlan(1114),
		retrieve10GEInfoFailure(1115),
		minMacGreaterThanMaxMac(1116),
		maxMacLessThanMinMac(1117),
		duplicateProtocolVlan(1118),
		macAddressDoesNotExist(1119),
		vlanTooManyPids(1120),
		prPortNotForStackedVlan(1121),
		prPortNotForIPXVlan(1122),
		vlanAgingTimeNotAppToStaticVlan(1123),
		cannotDeleteVlanWithTlsUniCustIpVlanAssociation(1124),
		vlanNotExists(1125),
		naapInvalidVlanId(1126),
		cannotDeleteRingIbtVlan(1127),
		cannotRemoveRingPortOrIbtPortFromIbtVlan(1128),
		clusterIsdAlreadyUsed(1129),
		regularPortsNotAllowedInPeeringVlan(1130),
                		regularPortsNotAllowedInClusterSyncVlan(1131),
                		mltSdmPortNotAllowed(1132),
                		clusterIdNotAllowedForNormalVlan(1133),
                		clusterTypeNotSupported(1134),
                		clusterMgmtSyncVlanCannotBeSame(1135),
		vlanIsBeingUsedAsARepeaterVlan(1136),
		ageTimeIsOnlyApplicableToDynamicVlan(1137),
		nsnaPortNotConfigurable(1138),
		nsnaUplinkOperationNotAllowed(1139),
		vlanNotRoutable(1140),
		exceededMaxFdbFilterMacEntries (1141),
		exceededMaxFdbStaticMacEntries (1142),
		exceededMaxStaticMcastEntries (1143),
		exceededMaxArpEntries (1144),
		clusterTpsSizeExceeded(1145),
		cannotEnableUnknownDestMacDiscard(1146),
		cannotDeletePbtVlanInUseByTrunk(1147),
		clusterNotFwIsd(1148),
		clusterNotTpsIsd(1149),
		vlanDeleteIstNotAllowed(1150),
                		vlanFwPortDelNotAllowedInRegVlan(1151),
		fwPortNotAlwdForClusterTypeIs(1152),
		syncVlanNotAlwdForClusterTypeIs(1153),
		portMemberNotAlwdForNonIsCluster(1154),
		portMemberOfIsClusterCannotBeSdmPort(1155),
		portHasPcapEnabled(1156),
		portInSameOctapidAsIsCluster(1157),
		cannotDeleteVlanWhenIncludedWithMltBvid(1158),
		invalidCustIpVlanForEsuUni(1159),
                		pcapInvalidTypeForAclFilter(1160),
	        	rmodOnlyOnePcapPortPerLane(1161),
		vlanCannotRemoveIbtMltPortMembers(1162),
                		cannotDeletePbtVlanInUseByLoopbackTrunkGroup(1163),
		anotherNLBModeAlreadyEnabled(1164),
		staticFdbNotAllowedOnSmltPortWhenAllSmltPortsDown(1165),
		staticFdbNotAllowedOnSltPortWhenSltDown(1166),
		staticFdbOnIstPortsNotAllowed(1167),
		ipTblszRmodLevel(1168),
		ipTblWtrMkRmodLevel(1169),
		ipAgeTimerRmodLevel(1170),
		custipvlanNotSupportedOnESM(1171),
		fdbEntryNotFound(1172),
		fdbStatusMismatch(1173),
                		rstpOnlyDefaultInstanceAllowed(1174),
		rwaAccessOnlyForMgmtVlan(1175),
                vlanCannotRemovePortAssociatedWithMep(1176),
		vlanNotMemberOfSlpp(1177),
		vlanNLBIsEnabled(1178),
		vlanStaticMcastMacArpExist(1179),
		vlanNotInVrfZero(1180),
		vlanNoPortsInFwdState(1181),
		dynModMaxModule(1201),
		dynModUnknown(1202),
		dynModAlreadyLoaded(1203),
		dynModCantOpenFile(1204),
		dynModNotEnoughSpace(1205),
		sysGrpInvalidSingleMgmtIp(1206),
		ipAddressUsedasSingleMgmtIp(1207),
		mandatoryImagesRequired(1208),
		bimgUnreachableOrCorrupt(1209),
		aimgUnreachableOrCorrupt(1210),
		mimgUnreachableOrCorrupt(1211),
		jdldUnreachableOrCorrupt(1212),
		kdldUnreachableOrCorrupt(1213),
		odldUnreachableOrCorrupt(1214),
		fallBackImageUnreachableOrCorrupt(1215),
		configFileUnreachableOrCorrupt(1216),
		fallBackVersionIncorrect(1217),
		upgradeImagesNotSameVersion(1218),
		fallbackVersionNotSameAsaimage(1219),
		fallbackVersionNotSame(1220),
		fallbackaImgUnreachableOrCorrupt(1221),
		fallbackmImgUnreachableOrCorrupt(1222),
		bootcfgFileNotFound(1223),
		manualCommitModeIsValidOnlyWithCsuModeAsFullAuto(1224),
		setSaveToStandbyFlagToTrue(1225),
		csuModeCannotBeNoneWithModeAsManualCommit(1226),
		thisFilenameIsUsedToAutosaveTheConfigurations(1227),
		cannotChangeTheAutosaveFilenameIfAutosaveStateIsEnabled(1228),
		cannotChangeTheAutosaveIntervalIfAutosaveStateIsEnabled(1229),
		autosaveStateIsAlreadyEnabled(1230),
		circuitlestInvalidIpInterfaceId(1501),
		circuitlessMaxNumberIpInterfacesReached(1502),
		circuitDoesNotExist(1503),
		circuitAlreadyExists(1504),
		circuitlessIpInterfacesOperationNotAllowed(1505),
		priority255SpecialForPhyIpSameAsVrIp(1506),
		icmpRdiscInvalidPreferenceLevel(1507),
		icmpRdiscAdvAddrIsNotBroadcastOrMulticastAddr(1508),
		icmpRdiscInvalidMaxAdvInt(1509),
		icmpRdiscMinAdvIntvGreaterThanMaxAdvIntvOrLessThan3Secs(1510),
		icmpRdiscLifeTimeLessThanMaxAdvIntvOrGreaterThan9000Secs(1511),
		vrrpInvalidFasterAdvertInterval(1512),
		vrrpFasterAdvEnabled(1513),
		vrrpFasterAdvDisabled(1514),
		vrrpInvalidFastAdvEnableValue(1515),
		globalFiltersNotSupportFwdingNextHopMode(1516),
		vrrpPreemptActionNotAllowed(1517),
		rcPimModeIgmpVersionIncompatible(1518),
		invalidOrInconsistentBroadCastMaskValue(1519),
		invalidRipTimeoutInterval(1520),
		rsmltNoCirc(1521),
		rsmltInvalidHoldUpTimer(1522),
		rsmltNoBrouter(1523),
		rsmltNoIst(1524),
		staticRoutesMaxLimitExceeded(1525),
		vrrpSetWithRsmltEnable(1527),
		rsmltSetWithVrrpEnable(1528),
		rsmltMaxSmltCreated(1529),
		ipEcmpMaxPathExceeded(1530),
		ipEcmpPathListNotAllowedInRmode(1531),
		featureAppliesToRmodulePortsOnly(1532),
		invalidVrrpEntry(1533),
		invalidIpOwnerVrrpPrio(1534),
                		invalidNetMgmtRouteAddr(1535),
        	                    rsmltInvalidHoldDownTimer(1536),
		circuitlessIpUsedByIpvpnRD(1537),
		ipAddrUsedByStaticRoute(1538),
		ipAddrUsedByStaticMcastMacArp(1539),
		invalidDdmMonitorInterval(1801),
		invalidDdmMonitor(1802),
		invalidDdmTrapsSend(1803),
		invalidDdmAlarmPortdown(1804),        	                    
		igmpOutOfSsmRange(2301),
		igmpDuplicateSsmTblEntry(2302),
		igmpSsmEntryDoesNotExist(2303),
		igmpSsmTblNotEmpty(2304),
		igmpRpSetExistsInSsmRange(2305),
		igmpCandidateRpExistsInSsmRange(2306),
		igmpIfInvalidQIntervalMrt(2307),
		igmpAlreadyEnabled(2308),
		igmpMaxStreamExceeded(2309),
		igmpStreamLimitAlreadyEnabled(2310),
		igmpStreamLimitNotEnabled(2311),
		igmpPimEnabledInSSMMode(2312),
		igmpDisableV3First(2313),
		igmpSSmConflictsWithSsgEntry(2314),
		igmpSsmCanNotDisableDynamicEntry(2315),
		invalidIpMulticastRange(2316),
		igmpStaticGroupCountExceeded(2317),
		igmpL2DenyTxInvalidHost(2318),
		igmpOverlappingStaticRangeNotAllowed(2319),
		igmpCannotEditStaticRecMcastDisabledGloballyOrOnVlan(2320),
		igmpMulticastRoutingEnabled(2321),
		igmpMVREnabled(2322),
		igmpMVRVlanIsMvrVlan(2323),
		igmpMVRVlanIsReceiverVlan(2324),
		igmpMVRVlanCanNotBeDeleted(2325),
		igmpMVRVlanReachMaximum(2326),
		igmpPortMaxStreamExceedsIntfMaxStream(2327),
		igmpQueryMaxResponseUnsupportedOnV1(2328),
		igmpSsmEntryUsedByStaticMember(2329),
		igmpStaticGroupExceededMax(2330),
		ipfStreamAlreadyExists(2401),
		ipfStreamDoesNotExists(2402),
 		ipfStreamInvalidStreamType(2403),
		ipfStreamInvalidPortOption(2404),
		ipfStreamNameTooLong(2405),
		ipfStreamInvalidProtocol(2406),
		ipfStreamInvalidDscp(2407),
		ipfDeviceAlreadyExists(2408),
		ipfDeviceUnknownPlatform(2409),
		ipfDeviceUnknownDevice(2410),
		ipfDeviceDoesNotExists(2411),
		ipfDeviceNameTooLong(2412),
		ipfOneZeroIpDestFilterIsAllowed(2413),
		ipfGlobalFilterMaxPerOctapid(2414),
		ipfDeviceMaxPerPort(2415),
		ipfDeviceMaxPerBox(2416),
		ipfDeviceMaxFilterList(2417),
		ipfInvalidRmodPort (2418),
		ipfSourceNextHopModeNotSupported(2419),
		actErrIpIllegal(2421),
		actErrIdInvalid(2422),
		actErrNotExist(2423),
		actErrInUse(2424),
		actErrExists(2425),
		actErrFieldTooMany(2426),
		actErrNameInvalid(2427),
		aclErrIdInvalid(2428),
		aclErrNameInvalid(2429),
		aclErrTypeInvalid(2430),
		aclErrNotExist(2431),
		aclErrInUse(2432),
		aclErrExists(2433),
		aclErrActIdInvalid(2434),
		aclErrInvalidCounterMode(2435),
		aceErrAclIdInvalid(2436),
		aceErrAclNotExist(2437),
		aceErrAceNotExist(2438),
		aceErrAceInUse(2439),
		aceErrAceDefault(2440),
		aceErrAceExists(2441),
		aceErrPrecedenceInvalid(2442),
		aceErrTrafficIllegal(2443),
		aceErrModeIllegal(2444),
		aceErrSupportUnavailable(2445),
		aceErrDscpIllegal(2446),
		aceErrDot1PIllegal(2447),
		aceErrUnreachIllegal(2448),
		aceErrPoliceIllegal(2449),
		aceErrInvalidCountMode(2450),
		aceErrFieldIllegal(2451),
		acgErrIdInvalid(2452),
		acgErrNotExist(2453),
		acgErrInUse(2454),
		acgErrExists(2455),
		acgErrAclNotExist(2456),
		acgErrNameInvalid(2457),
		aclIfIndexErrNotExist(2458),
		aclIfIndexErrExists(2459),
		aclIfIndexErrAcgNotExist(2460),
		acgErrActIllegal(2461),
		acgErrAclIdDuplicate(2462),
		acgErrAclTypeDuplicate(2463),
		actErrDefaultAct(2464),
		aceErrAceNameInvalid(2465),
		aceErrFragmentOptionInvalid(2466),
		aceErrSpecifyTaggedUntagged(2467),
		aceErrPolicyEntryInvalid(2469),
		acgErrEmptyAcg(2470),
		acgErrAclLimitMax(2471),
		aceErrNeedTrafficType(2472),
		aceErrTrustDscpEnabled(2473),
		aceErrMaxExceeded(2474),
		aceErrSpecifyL4Protocol(2475),
		actPartialFieldInvalid(2476),
		aceErrMatchingUserPriorityNotSupported(2477),
		aceErrMatchingL4NotSupportedForFragmentedPackets(2478),
		aceErrSelectTagAct(2479),
		aceErrIfindexHwActInsuf(2480),
		acgErrUplinkCannotBeModified (2481),
                aceInvalidMode (2482),
		aceEgressqEgressqnnscInvalid(2483),
		aceInvalidPolicyId(2484),
		actNoSuchPatternName(2485),
		flowclsPolicingNotAllowedFor8021p(2486),
		flowclsInvalidPolicyId(2487),
		flowclsPolicingNotAllowedForDropAction(2488),
        	actFieldsOverlap(2489),
	        actPatternInUse(2490),
	        actPatternAlreadyExists(2491),
	        actPatternDoesNotExist(2492),
		userDefErrDepthExceeded(2493),
		cannotDeleteIntMltId(2501),
		mltNoThisVlan(2502),
		mltPortsDifferentFramingMode(2503),
		moreThan2PortsInMlt(2504),
		portCannotBeAddedToDefualtVLANWithIPXEnabled(2505),
		portMemberNotSupportSMLT(2506),
		tenGEMltPortOrMltCannotBeAddedToVlanWithSmltMember(2507),
		tenGEMltPortCannotRunTogetherWithSMLT(2508),
		portCannotBeAddedToDefualtVLANWithSMLT(2509),
		tenGEPortOrMltCannotBeAddedToVlanWithSmltMember(2510),
		tenGEPortOrMltCannotRunTogetherWithSMLT(2511),
		tenGEPortNotSupportMcastDistribution(2512),
		tenGEPortNotSupportMLT(2513),
		mltSmltIdAlreadyExists(2514),
		mltInvalidSmltId(2515),
		mltSmltNotConfigured(2516),
		mltSmltAlreadyConfigured(2517),
		mltPortIsMemberOfMlt(2518),
		mltPortIsMemberOfSmlt(2519),
		mltSmltIpAddrNotAllowedOnSltPort (2520),
		mltUsedForLacp(2521),
		mltPortUsedForLacp(2522),
		mltUsedForMlt(2523),
		commandOnlySupportedIn10GMlt (2524),
		mltWithLacp10gBackupEnableSupports10GPortMemebersOnly (2525),
		removeIpOnVplsPortToAddToMltGroup (2526),
		mltIdAlreadyExists(2527),
		mltPartOfMoreThanOneVlan(2528),
		operationNotAllowedOnMltPort(2529),
		mltInvalidMltIdForFastEther(2530),
		mltPartOfMoreThanOneStg(2531),
		mltDoesNotExist(2532),
		mltCannotBeAddedToMultpleVlansWhilePerformTagIsDisabled(2533),
		performTagCannotBeDisabledWhileMltBelongsToMultipleVlans(2534),
		mltPerformTaggingIsAlreadyEnabledOrDisabled(2535),
		smltPeerIpCannotBeSameAsLocalIp(2536),
		mltCannotDeletedBeforeDeletingSmltOrSetMltTypeToNormal(2537),
		mltNsnaUplinkMismatch(2538),
		mltIdInvalidInNonRmode(2539),
		mltNaapVlanCannotBeAddedToIst(2540),
		mltIstCannotBeCreatedOverMltWithNaapVlan(2541),
                mltNaapCannotBeAddedToMltWithActiveIst(2542),
		cannotRemPriSecBvidPort(2543),
		invalidUniAggrMacIdxRange(2544),
		uniAggrMacIdxInUse(2545),
		performTaggingDisabled(2546),
		cannotChangeMltWhenSetToUniOrIsid(2547),
		mltBelongsToActiveUniOrIsid(2548),
		vlanDoesNotExist(2549),
		bvidNodeAlreadyExists(2550),
		bvidInvalid(2551),
		cannotSetSamePriSecPortForBvid(2552),
		portNotInMlt(2553),
		uniAggrMacIdxSet(2554),
		mltBvidBothPrimaryAndSecondaryPortsNeeded(2555),
		mltTypeNotSetToSplitMlt(2556),
		mltInTlsServiceCannotHaveMoreThanTwoNpus(2557),
		mltMax2kBvidNodesSupported(2558),
		cosProfileSupportedOnlyOnEsmPorts(2559),
		mltIncompatibleSmltIst(2560),
                mltWithSilentPortCannotBeAddedToVlan(2561),
                differentInterfaceTypePortCannotBeAddedToMlt(2562),
                mltVrfVlanAndLegacyPortCannotBeMembers(2563),
		mltPortUsedForVlacp(2564),
		mltLacpCannotBeEnabledWithInterfaceTypeSilent(2565),
		asListOverLimit(2601),
		communityListOverLimit(2602),
		mltSmltLacpInvalidKey(2603),
		ipRedistributeNotEnabled(2604),
		lacpAndBvidCannotCoexist(2605),
		extCommunityListOverLimit(2606),
		extCommunityInvalidListId(2607),
		extCommunityListIdExceedsRange(2608),
		mcastMltNotEnabled(2701),
		mcastMltInvalidSrcMask(2702),
		mcastMltInvalidGrpMask(2703),
		mcastMltRedistrNotEnabled(2704),
		mcastMltDiscontiguousSrcMaskValue(2705),
		mcastMltDiscontiguousGrpMaskValue(2706),
 		mcastMltNotEnabledOnMlt(2707),
		mcastMltPortOnNonEtkt(2708),
		mcastMltConfMaskDisableMcastMlt(2709),
		ipmcTimePruneConflictsWithSsmEntry(2710),
		invalidPortServiceType (2711),
		rcSnmpSyslogDisableSyslogFirst(2801),
		rcSnmpInvalidSyslogHeader(2802),
		dvmrpMBRNotAllowed(2901),
		dvmrpInvalidIntfTypeChange(2902),
		dvmrpMbrNotAllowed (2903),
		dvmrpInvalidIntfTypeChangeWhenIntfIsEnabled (2904),
		ipxPolicyNetEntryNotFound(3101),
		ipxPolicyNetDuplicateEntry(3102),
		ipxPolicyNetListEntryNotFound(3103),
		ipxPolicyNetListDuplicateEntry(3104),
		ipxPolicyServEntryNotFound(3105),
		ipxPolicyServDuplicateEntry(3106),
		ipxPolicyServeListEntryNotFound(3107),
		ipxPolicyServListDuplicateEntry(3108),
		ipxPolicyPolicyEntryNotFound(3109),
		ipxPlicyPolicyDuplicateEntry(3110),
		ipxRoutePolicyNetListOverLimit(3111),
		ipxRoutePolicyServListOverLimit(3112),
		ipxPolicyRipOutFilterEntryNotFound(3113),
		ipxPolicySapOutFilterEntryNotFound(3114),
		ipxPolicyRipInFilterEntryNotFound(3115),
		ipxPolicySapInFilterEntryNotFound(3116),
		ipxPolicyIpxNetEntryInvalidName(3117),
		ipxPolicyIpxServEntryInvalidName(3118),
		ipxPolicyPolicyEntryInvalidName(3119),
		vlanHas10GEMemberWhichNotSupportIPX(3120),
		vlanContainUnSupportedPrPort (3121),
		invalidLengthOf2kBootConfigLicenseSource(3401),
		licenseFileDoesNotExist(3402),
		masterAndStandbyIPNotSameSubnet(3403),
		managementIPSameAsVirtuaIP(3404),
		licenseFileIsAlreadyLoaded(3405),
		qosNumTxQueueOutOfRange(3601),
		qosTxQueueSizeOutOfRange(3602),
		qosEntryExist(3603),
		qosEntryNotExist(3604),
		qosEntryInUse(3605),
		qosInvalidPort(3606),
		qosNotAllowToModify(3607),
		qosPirSmallerThanCir(3608),
		qosShapingRateOutOfRange(3609),
		qosEgressCntrExceed(3610),
		qosPolicyRmkUsrOrDpNoEffect(3611),
		qosEgressCntrVlanNotExist(3612),
		qosEgressCntrPortLinkDown(3613),
		qosEgressCntrVlanInUsed(3614),
		qosPortBasedVlan(3615),
		qosPolicyRmkDpNoEffect (3617),
		qosVbEgressCounterNoVlan(3618),
		qosVbTrustDscp(3619),
		qosVbTxConfigAppliedPortsCascadingGrp(3620),
		qosTwistDNotSupported(3621),
		qosWrongSchedulerSetting(3622),
		octapidNotPresent(3623),
		qosThresholdNotSupportedOnEsmPort(3624),
		qosPbsSmallerThanCbs(3625),
		qosDuplicateConfiguration(3626),
		qosVbPortLevelEgressCounterInvalid(3627),
		invalidModeForAtmMDAType(3901),
		atmInvalidPVCEncapTypeForElan(3902),
		atmInvalidPVCPCRRange(3903),
		unsupportedVPI(3904),
		radiusAuthAcctAttrSame(4101),
		radiusAuthAcctPortSame(4102),
		radiusAuthAcctNoServerConfig(4103),
		radiusReAuthTimerFailed(4104),
		radiusAbortSesionTimerFailed(4105),
		radiusInvalidSnmpUserLength(4106),
		radiusInvalidCliCommandCount(4107),
		radiusNotEnabled(4108),
		radiusTacacsEnabled(4109),
		radiusInvalidSecretKey(4110),
		pimGlobInvalidUniRouteChangeTimeOut(4801),
		pimGlobInvalidDiscDataTimeOut(4802),
		pimGlobInvalidCRPADVTimeOut(4803),
		pimGlobInvalidBootStrapPeriod(4804),
		pimStaticRpEnabled(4805),
		pimStaticRpNotEnabled(4806),
		pimStaticRpEntryExists(4807),
		pimStaticRpNoRoute(4808),
		pimAddressInSsmRange(4809),
		pimInvalidModeChange(4810),
		pimStaticRpNotAllowed(4811),
		pimMBRNotAllowed(4812),
		pimGlobInvalidActChkInterval(4813),
		pimGlobActChkIntervalNotAllowed(4814),
		pimMbrNotAllowed (4815),
		pimGlobNotSuppActChkInterval(4817),
                pimVirtualNbrInvalidIfIndex(4818),
		rpsMcastMaskLenToNotAllowed(4901),
		rpsExtendedAclListNameInvalid(4902),
		rpsExtendedAclDuplicateEntry(4903),
		rpsExtendedAclListNotFound(4904),
		rpsExtendedAclEntryNotFound(4905),
		rpsExtendedAclDuplicateListFound(4906),
		tcpConnectionNotFound(5101),
		tcpInvalidState(5102),
		tcpSessionsInUse(5103),
		bgpPeerNotFound(5201),
		bgpInvalidPeerEnable(5202),
		bgpInvalidPeerRemoteas(5203),
		bgpInvalidPeerGroupName(5204),
		bgpInvalidPeerDefaultOriginate(5205),
		bgpInvalidPeerEbgpMultiNop(5206),
		bgpInvalidPeerAdvertisementInterval(5207),
		bgpInvalidPeerPassword(5208),
		bgpInvalidPeerWeight(5209),
		bgpInvalidPeerNextHopSelf(5210),
		bgpInvalidPeerRoutePolicyIn(5211),
		bgpInvalidPeerRoutePolicyOut(5212),
		bgpInvalidPeerRouteReflectorClient(5213),
		bgpInvalidPeerSoftReconfigurationIn(5214),
		bgpInvalidPeerSoftReconfiguration(5215),
		bgpInvalidPeerRemovePrivateAs(5216),
		bgpInvalidPeerRowStatus(5217),
		bgpNetworkNotFound(5218),
		bgpPeerGroupNotFound(5219),
		bgpInvalidPeerGroupEnable(5220),
		bgpInvalidPeerGroupRemoteAs(5221),
		bgpInvalidPeerGroupDefaultOriginate(5222),
		bgpInvalidPeerGroupUpdateSource(5223),
		bgpInvalidPeerGroupEbgpMultiHop(5224),
		bgpInvalidPeerGroupAdvertisementInterval(5225),
		bgpInvalidPeerGroupPassword(5226),
		bgpInvalidPeerGroupWeight(5227),
		bgpInvalidPeerGroupNextHopSelf(5228),
		bgpInvalidPeerGroupRoutePolicyIn(5229),
		bgpInvalidPeerGroupRoutePolicyOut(5230),
		bgpInvalidPeerGroupRouteReflectorClient(5231),
		bgpInvalidPeerGroupSoftReconfigurationIn(5232),
		bgpInvalidPeerGroupSoftReconfiguration(5233),
		bgpInvalidPeerGroupRemovePrivateAs(5234),
		bgpInvalidPeerGroupHoldTime(5235),
		bgpInvalidPeerGroupKeepAlive(5236),
		bgpInvalidPeerGroupRowStatus(5237),
		bgpInvalidPeerGroupGroupName(5238),
		bgpAggregateNotFound(5239),
		bgpInvalidAggregateAsSetGenerate(5240),
		bgpInvalidAggregateSummaryOnly(5241),
		bgpInvalidAggregateSuppressPolicy(5242),
		bgpInvalidAggregateAdvertisePolicy(5243),
		bgpInvalidAggregateAttributePolicy(5244),
		bgpOperationNotAllowedWhenBgpIsEnabled(5245),
		bgpInvalidPeerHoldTime(5246),
		bgpInvalidPeerKeepAlive(5247),
		bgpInvalidPeerMaxPrefix(5248),
		bgpInvalidPeerGroupMaxPrefix(5249),
		bgpInvalidPeerMD5Authentication(5250),
		bgpInvalidPeerGroupMD5Authentication(5251),
		bgpInvalidPeerGroupIndex(5252),
		bgpInvalidConfederationIdentifier(5253),
		bgpInvalidConfederationPeerAsNumber(5254),
		bgpInvalidConfederationPeerNotFound(5255),
		bgpInvalidConfederationPeerAlreadyExist(5256),
		bgpOperationNotAllowedWhenSoftReconfigInIsDisabled(5257),
		bgpNotAllowedSoftRecfgInIsDisabledForTheGrpOrAnyPeerInGrp(5258),
		bgpCanNotEnablePeerWithoutCfgRemoteAsForThePeer(5259),
		bgpCanNotEnablePeerGrpWoCfgRemoteASPeerGrpOrAnyPeerInGrp(5260),
		bgpOperationNotAllowedWhenPeerIsBGPON(5261),
		bgpOperationNotAllowedWhenPeerGrpOrAnyPeerInGrpIsBGPON(5262),
		bgpOperationNotAllowedExternalPeer(5263),
		bgpOperationNotAllowedInternalPeer(5264),
		asListNotFound(5265),
		asListDuplicate(5266),
		asListAsPathEntryNotFound(5267),
		asListAsPathEntryDuplicate(5268),
		asListInvalidModeOfAsPathEntry(5269),
		asListInvalidAsRegularExpressionOfAsPathEntry(5270),
		asListInvalidRowStatusOfAsPathEntry(5271),
		communityListNotFound(5272),
		communityListDuplicate(5273),
 		communityListCommunityPathEntryNotFound(5274),
		communityListCommunityPathEntryDuplicate(5275),
		communityListInvalidModeOfCommunityPathEntry(5276),
		communityListInvalidValueOfCommunityEntry(5277),
		communityListInvalidRowStatusOfCommunityEntry(5278),
		bgpFeatureNotSupport(5279),
		bgpMd5EnabledWithoutPasswd(5280),
		bgpEnabledWithoutLocalAs(5281),
		bgpAggregateAdvertisePolicyWithoutAsSet(5282),
		bgpPeerHoldTimeLessThanKeepAliveTime(5283),
		bgpCommListCommunityStringUsed(5284),
		bgpNotFoundRowStatus (5285),
		bgpCannotConfigSystemLocalInterfaceAsPeer (5286),
		bgpDuplicateRowStatus (5287),
		communityListModificationNotAllowed(5288),
		bgpInvalidPeerGroupAsOverride(5289),
		bgpInvalidPeerGroupAllowAsIn(5290),
		bgpInvalidPeerAllowAsIn(5291),
		bgpInvalidPeerAsOverride(5292),	
		extCommunityListNotFound(5293),
		extCommunityListModificationNotAllowed(5294),
		extCommunityListInvalidEntry(5295),
		extCommunityListDuplicateMemberId(5296),
		extCommunityListInfoAlreadyExists(5297),
		extCommunityMemberNotFound(5298),
		bgpPeerLimitExceeded(5299),
		sshEnableTrue(5501),
		rsaKeyNotExist(5502),
		dsaKeyNotExist(5503),
		rsaKeyGenMiss(5504),
		dsaKeyGenMiss(5505),
		sshShutDownInProcess(5506),
		sshInvalidPort(5507),
		sshPortAlreadyInUse(5508),
		sshPortReserved(5509),
		sshAuthenticationNotEnabled(5510),
		invalidOperationOnWsmOrSamStg(5601),
		invalidOperationOnWsmOrSamVlan(5602),
		invalidOperationOnWsmOrSamPort(5603),
		invalidOperationOnSamPort(5604),
		opmImageFilenameTooLong (5701),
		serverSupportedOnOpmPortOnly (5702),
		commandValidOnlyIfMezzCardIsPresent (5703),
		serverPortAlreadyEnabled (5704),
		serverPortCannotBeDisabledWhileInService (5705),
		serverPortAlreadyDisabled (5706),
		serverPortSomeOtherServiceEnabled(5708),
		opmResetNotAllowedWhileFPGAUpgradeInProgress(5709),
		opmResetNotAllowedWhileBootMonitorUpgradeInProgress(5710),
		mplsInvalidRowStatus (6101),
		mplsNoIpInterface (6102),
		mplsInvalidSetWhenMplsIsEnabled (6103),
		mplsNotAnMplsInterface (6104),
		mplsInvalidSetWhenMplsInterfaceIsEnabled (6105),
		mplsInvalidSetWhenLdpIsEnabled (6106),
		mplsNotAnLdpInterface (6107),
		mplsInvalidGlobalAdminStatus (6108),
		mplsInvalidRouterId (6109),
		mplsInvalidTtl (6110),
		mplsInterfaceInvalidAdminStatus (6111),
		mplsInterfaceInvalidLabelDistMode (6112),
		mplsInterfaceInvalidLabelRetenMode (6113),
		mplsInterfaceInvalidLabelUseMode (6114),
		mplsInterfaceInvalidLabelReqMode (6115),
		mplsInterfaceInvalidLabelAdvMode (6116),
		mplsInterfaceInvalidMtu (6117),
		mplsInterfaceInvalidLabelProtocol (6118),
		mplsInterfaceInvalidIpAddr (6119),
		mplsInvalidLdpAdminStatus (6120),
		mplsInvalidLdpHoldTime (6121),
		mplsInvalidLdpHelloHoldTime (6122),
		mplsInvalidLdpHelloInterval (6123),
		mplsInvalidLdpMaxHops (6124),
		mplsInvalidLdpPathVectorLimit (6125),
		mplsInvalidLdpTargettedHelloHoldTime (6126),
		mplsLdpInterfaceInvalidTargetAddr (6127),
		mplsInvalidRsvpAdminStatus (6128),
		mplsInvalidRsvpPathUpdateTime (6129),
		mplsInvalidRsvpResvUpdateTime (6130),
		mplsInvalidRsvpHelloTime (6131),		
		mplsInvalidRsvpBlockStateAgingTime (6132),
		mplsInvalidRsvpMaxBundleMsgSize (6133),
		mplsInvalidRsvpMaxBundleMsgTime (6134),
		mplsInvalidRsvpMaxAckMsgTime (6135),
		mplsInvalidRsvpMaxAckMsgs (6136),
		mplsInvalidRsvpMaxMsgIdListSize (6137),
		mplsInvalidRsvpMaxMsgIdListTime (6138),
		mplsInvalidRsvpMaxPiggybackAckMsgs (6139),
		mplsInvalidRsvpPathAgingTimeMultiplier (6140),
		mplsInvalidRsvpResvAgingTimeMultiplier (6141),
		mplsInvalidRsvpHelloAgingTimeMultiplier (6142),
		mplsInvalidRsvpPathVectorLimit (6143),
		mplsInvalidRsvpMaxHops (6144),
		mplsInvalidRsvpRapidRetransmissionTime (6145),
		mplsInvalidRsvpRapidRetransmissionIncrement (6146),
		mplsInvalidRsvpRapidRetransmissionLimit (6147),
		mplsInvalidTunnelName (6148),
		mplsInvalidTunnelDescr (6149),
		mplsInvalidTunnelIsif (6150),
		mplsInvalidTunnelSignalProto (6151),
		mplsInvalidTunnelSetupPrio (6152),
		mplsInvalidTunnelHoldingPrio (6153),
		mplsInvalidTunnelSessionAttr (6154),
		mplsInvalidTunnelOwner (6155),
		mplsInvalidTunnelLocalProtectInuse (6156),
		mplsInvalidTunnelHopTblIndex (6157),
		mplsInvalidTunnelAdminStatus (6158),
		mplsInvalidTunnelRowStatus (6159),
		mplsInvalidTunnelStorageType (6160),
		mplsInvalidTunnelBandwidth (6161),
		mplsInvalidTunnelHopAddrType (6162),
		mplsInvalidTunnelHopIpv4Addr (6163),
		mplsInvalidTunnelHopIpv4PrefixLen (6164),
		mplsInvalidTunnelHopIpv6Addr (6165),
		mplsInvalidTunnelHopIpv6PrefixLen (6166),
		mplsInvalidTunnelHopASNum (6167),
		mplsInvalidTunnelHopLspid (6168),
		mplsInvalidTunnelHopType (6169),
		mplsInvalidTunnelIncludeExclude (6170),
		mplsInvalidTunnePathOptionName (6171),
		mplsInvalidTunnePathComp (6172),
		mplsInvalidTunnelHopRowStatus (6173),
		mplsInvalidTunnelHopStorageType (6174),
		mplsInvalidFtnRowStatus (6175),
		mplsInvalidFtnMask (6176),
		mplsInvalidFtnSourceIpAddr (6177),
		mplsInvalidFtnSourceIpMask (6178),
		mplsInvalidFtnDestIpAddr (6179),
		mplsInvalidFtnDestIpMask (6180),
		mplsIpCircuitNotUp (6181),
		mplsInvalidTunnelGrpId (6182),
		mplsTunnelGrpNoDestAddr (6183),
		mplsTunnelGrpExists (6184),
		mplsTunnelGrpNonExists (6185),
		mplsTunnelGrpInvalidRowStatus (6186),
		mplsTunnelGrpInvalidTunnelId (6187),
		mplsTunnelGrpTunnelNonExists (6188),
		mplsTunnelGrpInvalidPersistentFlag (6189),
		mplsTunnelGrpInvalidOperation (6190),
		mplsTunnelGrpOperationNotEntered (6191),
		mplsTunnelGrpMemberExist (6192),
		mplsTunnelGrpBackupTunnelExists (6193),
		mplsTunnelGrpNoPrimaryTunnel (6194),
		mplsTunnelMemberOfAnothergroup (6195),
		mplsInvalidTunnelListFormat (6196),
		mplsInvalidTunnelPriority (6197),
		mplsTunnelHopCreateNotEnoughParameters (6198),
		mplsTunnelGroupInvalidTunnelOperation (6199),
		vpnPortModeNotConfigurable (6201),
		vpnIncompatiblePortServiceTypeAndMode (6202),
		vpnPortInvalidMember (6203),
		vpnPortInvalidQtag (6204),
		vpnPortServiceTypeModificationNotAllowed (6205),
		vpnLocalSwitchingNotEnabled (6206),
		vpnDuplicateEntry (6207),
		vpnEntryNotFound (6208),
		vpnCannotCreateBrouterIncompatiblePortServiceType (6209),
		vpnAddVpnMemberNotAllowed (6210),
		vpnCannotEnableVpnNoMemberExists (6211),
		vpnCannotEnableVpnSwitchModeNoQtag (6212),
		vpnCannotEnableVpnNoTunnelGrpExists (6213),
		vpnCannotEnableVpnNoRemotePeerExits (6214),
		vpnTunnelExpPolicyIdDoesNotExists (6215),
		vpnIncompatibleTunnelExpPolicyTypeAndTunnelExpPolicyId(6216),
		vpnInvalidTunnelExpPolicyType (6217),
		vpnInvalidTunnelExpPolicyId (6218),
		vpnTunnelGroupIdDoesnotExists (6219),
		vpnVcGrpIdEntryDoesnotExists (6220),
		vpnTransparentPortCannotHaveQtagSpecified (6221),
		vpnPortAlreadyConfiguredForASpecificService (6222),
		vpnPortTransAlreadyBeAVpnMember (6223),
		vpnPortCannotChangePeerIdWhileEnabled (6224),
		vpnInvalidRcGrpId (6225),
		vpnLowerBwCannotBeGreaterThanUpperBw (6226),
		vpnUpperBwCannotBeLessThanLowerBw (6227),
		vpnLocalSwitchingNotSupported (6228),
		vpnTunnelGrpIdCannotChangeWhenVPNOperational (6229),
		vpnPortIsNotVpnMember (6230),
		vpnServiceCtypeLowerBwCannotBeConfigured (6231),
		vpnLowerBwCannotBeZeroForServiceAB (6232),
		vpnInvlidQtagNumOrRange (6233),
		vpnEntryNoMemActionSet (6234),
		vpnNotL2uniPort (6235),
		vpnAddQtagNotAllowed (6236),
		vpnEntryInvalidMemActionSet (6237),
		vpnCannotAddMoreThan128Qtags (6238),
		vpnQtagExistInOtherVpn (6239),
		vlanNotCreatedOrNotAssocitaedWithServerPort (6240),
		vlanPortNotServerPort (6241),
		invalidPortOrMltId (6242),
		tunnelGroupIdInTlsVpn (6243),
		tunnelGroupIdInP2pVpn (6244),
		oeAdmInvalidValue (6301),
		oeAdmInvalidKpalvIntVal (6302),
		oeAdmInvalidUDPPort (6303),
		vpnTlsRemotePeerDoesNotExist (6304),
		vpnTlsRemotePeerEntryExists (6305),
		vpnTlsTdidoesNotExist (6306),
		tlsVpnTunnelGrpShouldBeSpecified (6307),
		tlsVpnRemotePeerEntryNotFound (6308),
		tlsVpnDoesNotExists (6309),
		tlsVpnTdiCannotBeUnset (6310),
		tlsVpnTdiHasBeenUsed (6311),
		tlsVpnInvalidRemotePeerId (6312),
		vpnAddRemoveMemberNotAllowedWhileEnabled (6313),
		portServiceTypeNotconfiured (6314),
		vplsIncompatiblePortServiceType (6315),
		tlsVpnSetValidOnlyOnAddRemotePeer (6316),
		tlsVpnTunnelGrpOrLdpFecShouldBeSpecified (6317),
		tlsvpnBothTunnelGrpAndLdpFecCannotBeSpecified (6318),
		tlsVpnTunnelIdCannotBespecified (6319),		
		portIsAssociatedWithOtherTranparentUni (6401),
		portCanBeOnlyAssignedToSwitchedServiceTypeUni (6402),
		portCanBeOnlyAssignedToIpmcUniServiceTypeUni (6403),
		portCanBeOnlyAssignedToIpmcBiServiceTypeUni (6404),
		cannotSetIpMcastServiceTypeForEndPointUni (6405),
		portCanBeOnlyAssignedToQnq1ServiceTypeUni (6406),
		portCanBeOnlyAssignedToQnq2ServiceTypeUni (6407),
		portInOtherUniWithDifferentServiceType (6408),
		incompleteStandaloneRbsUni (6409),
		tlsUniCannotSetPortForRbs (6410),
		tlsUniCannotChangeParam (6411),
		tlsUniCannotChangeUniServiceType (6412),
		tlsUniCannotAddNonOpmPort (6413),
		tlsMappedVlanDoesNotExist (6414),
		tlsUniCanNotEnableWithoutPort (6415),
		tlsQtagAlreadyInUse (6416),
		tlsUniAlreadyExist (6417),
		tlsUniDoesNotExist (6418),
		tlsUniNotFound (6419),
		tlsTdiAlreadyExist (6420),
		tlsTdiDoesNotExist (6421),
		tlsTdiNotFound (6422),
		tlsTdiEndpointAlreadyExist (6423),
		tlsTdiEndpointDoesNotExist (6424),
		tlsTdiEndpointNotFound (6425),
		tlsTdiUserMacAlreadyExist (6426),
		tlsTdiUserMacDoesNotExist (6427),
		tlsTdiUserMacNotFound (6428),
		tlsRemoteUniAlreadyExist (6429),
		tlsRemoteUniDoesNotExist (6430),
		tlsRemoteUniNotFound (6431),
		tlsUniCannotStandaloneforrbs (6432),
		tlsTdiEndpointExist (6433),
		tlsTdiCannotChangeParam (6434),
		tlsTdiAdmAlreadyEnable (6345),
		tlsTdiAdmAlreadyDisable (6346),
		tlsTdiEndpointCannotChangeParam (6437),
		tlsTdiEndpointCosProfileNotFound (6438),
		tlsTdiEndpointSpokeOrP2p (6439),
		tlsUniOtherUniEnabled (6440),
		portIsInTlsService (6441),
		portPerformTaggingIsDisabled (6442),
		tlsUniPortdoesnotexist (6443),
		tlsSwitchEndpointCannotInEnableStateWithoutQtag (6444),
		tlsQnqEndpointCannotInEnableStateWithoutOuterQtag (6445),
		portHasDiffEtherTypeWithOtherEnabledUni (6446),
		tlsEnableQnqForUniToAddOuterQtag (6447),
		tlsTransparentEndpointCannotSetQtag (6448),
		tlsTransparentUniCannotAddedToManyToOneTdi (6449),
		tlsOneToOneEndPointCannotSetMultiQtag (6450),
		tlsTdiCannotSetManyToOneWithTransparentUni (6451),
		tlsCannotAddSameTransparentEndpointToTwoDifferentTdis (6452),
		tlsMappedNniVlanCannotHaveIpAddress (6453),
		tlsVlanWithIpAddressCannotBeUsedAsMappedNniVlan (6454),
		tlsMappedNniVlanMustBePortBased (6455),
		tlsMacTableWaterMarkIsIngoredWhenThereIsNoMacTableSize(6456),
		tlsTdiCanOnlyHaveOneTypeOfEndPoints (6457),
		tlsTdiCannotHaveMoreThanTwoP2PEndPoints (6458),
		tlsTdiCannotHaveMoreThanOneHubEndPoints (6459),
		tlsExpedTrafCanOnlyTrueForTransEpOrSwEpWithQtag4096 (6460),
		tlsExpediteTrafficNotApplyToEndpointOnQinqPort (6461),
		tlsTdiEndpointRemoteUni (6462),
		tlsQnq1EptCannotHaveInnerQtag (6463),
		tlsQnqOnlyApplyToLocalTlsPOrt (6464),
		tlsUniCannotAssignRbsRingAndStandAlone (6465),
		tlsSwitchedEndPointQtagInvalid (6466),
		tlsQnqEndPointQtagInvalid (6467),
		tlsSwitchedEptOnSamePortNeedDiffInnerQtag (6468),
		tlsQnq1EptOnSamePortNeedDiffInnerQtag (6469),
		tlsQnq2EptOnSamePortNeedDiffQtag (6470),
		tlsUniInvalidNonOpmPortType (6471),
		tlsUniCannotEnableWithoutServerPort (6472),
		tlsUniOpmServerCannotBeAccess (6473),
		tlsUniCannotSetServerPortWithoutUniPort (6474),
		tlsUniCannotAssignNonServerPort (6475),
		tlsUniAnotherServerportAlreadyAssigned (6476),
		tlsEptSetPortForUniBeforeConfigEpt (6477),
		tlsEptMacTableSizeExceedLimit (6478),
		tlsMacTableSizeExceedLimitForPort (6479),
		tlsOverridePbitNotSupportedForQnq1 (6480),
		tlsPriorityOverrideNotSupportedForOpmPort (6481),
		tlsPriorityOverrideCannotBeEnabledOnMultiVlansPort (6482),
		tlsTdiCannotChangeMuxModeWithActiveEpt (6483),
		tlsDestUniIsNotInGlobalUniMacTable (6484),
		tlsCannotSetMulticastMacAddrToRemoteUni (6485),
		tlsManyToOneEptDoesNotSupportQtag4096 (6486),
		tlsRemoteUniNotSupportedForA2AEpt (6487),
		tlsUniCannotBeAssignedPortAndRbsRing (6488),
		tlsUniPortIsNotStandaloneRbsPort (6489),
		cannotAssignRbsRingOrStandaloneRbsToQnqServiceUni (6490),
		tlsUniFailsToRemoveRbsRing (6491),
		tlsUniFailsToRemoveServerPort (6492),
		tlsUniFailsToRemoveRbsStandalone (6493),
		ringIdAndRbsIdAndPortAllMustBeZero (6494),
		standaloneRbsIdAndPortAllMustBeZero (6495),
		tlsTdiOnlySpokesOnSameServerPort (6496),
		tlsGsmPortHasOverLimitNubmerOfSwitchedUni (6497),
		tlsGsmPortHasOverLimitNubmerOfQnq2OuterTag (6498),
		tlsRsmPortHasOverLimitNubmerOfQnq2OuterTag (6499),
		lacpInvalidAggrsysPrio(6501),
		lacpInvalidAggrActorAdminKey(6502),
		lacpInvalidAggrColMaxDelay(6503),
		lacpInconsistentKey(6504),
		lacpInvalidVal(6505),
		lacpOutOfRangeKey(6506),
		lacpPortNotAggregatable(6507),
		lacpKeyModificationNotAllowedOnSltPort(6508),
		vlacpTimeoutScaleRangeBetween3To10(6509), 
		lacpOtherPortsWithSameKey(6510),
		vlacpOneofPortorMLTIdIsRequired(6511),
		vlacpDuplicatePeerMacAddress(6512),
		vlacpOutOfRangeMac(6513),
		lacpSmltSysIdSyncIncomplete(6514),
		vlacpOperationReqPortVlacpDis(6515),
		lacpNotAllowedForSmlt(6516),
		lacpCantCreateSmlt(6517),
		vlacpCannotModifyMacAddressVlacpEnable(6518),
		portBelongsToLacpEnabledMLT(6519),
		mltIsLacpEnabled(6520),
		lacpKeyAndVlanDonotMatch(6521),
		onlyStaticPortsCanBeAddedAsPrimaryOrSecondaryPortForBvid(6522),
		operationNotAllowedOnStaticPorts(6523),
		operationNotAllowedOnDynamicPorts(6524),
		togglingMltLacpNotAllowedIfConfiguredPortsPresentInMlt(6525),
		poeInvalidAdminState(6601),
		poeInvalidDetecCtrlState(6602),
		poeInvalidPriorityState(6603),
		poeInvalidType(6604),
		poeInvalidPwrPairState(6605),
		poeInvalidUsageThreshold(6606),
		poeInvalidBackupDCPower(6607),
		poeInvalidNotificationControl(6608),
		diagVctPortNotCapable(6701),
		diagVctPortNotEnabled(6702),
		diagVctPortNotFound(6703),
		diagVctUnknownSet(6704),
		esmPortMirrorParameter(6705),
		modeNotCorrectForGranularity(6706),
		filterNotSupportedOnThisHardware(6707),
		esmPortNotSuppAsMirroringPort(6708),
		mirroredPortNotSuppAsServerPort (6709),
		esmOrRmodPortMirrorParameter(6710),
		mirrorByPortNonExistingEntry(6711),
		targetAddressMissing(6801),
		testAlreadyRunning(6802),
		invalidTargetAddress(6803),
		invalidSourceAddress(6804),
		controlEntryAlreadyExists(6805),
		invalidIpAddressFormat(6806),
		invalidDataRange(6807),
		invalidIndex(6808),
		entryDoesNotExist(6809),
		controlEntryMaxLimitReached(6810),
		maxRowOutOfRange(6811),
		oeAdmPEEdgeOutgoingInterfaceNotConfigured (6901),
		oeAdmPEEdgeNotAllowedWhenAdmEnabled (6902),
		tlsServerPortForUniOnLegacyPortBeforeConfigEpt (6903),
		tlsEndptInvalidPriorityMapping (6904),
		tlsVlanBasedUniEndPtInvalidQtag (6905),
		tlsUniUnsupportedServiceType (6906),
		portIsNotEsmServerPort (6907),
		cannotSetOneToOneWithMultipleQtagsEndpoint (6908),
		tdiMgmtAlreadyEnabled (6909),
		tdiMgmtAlreadyDisabled (6910),
		mappedNniVlanDoesNotHaveIp (6911),
		cannotDeleteVlanWithTlsTdiAssociation (6912),
		cannotCreateIpWhileVlanTdiEnabled (6913),
		cannotDeleteIpWhileVlanTdiEnabled (6914),
		tlsTdiMappedVlanCannotHaveIp (6915),
		netMgmtTdiMappedVlanDoesNotHaveIp (6916),
		tlsUniInvalidNonOpmPortVlanType (6917),
		tlsAtmEndptsShareSameServerPort (6918),
		oeAdmPEEdgeSecOutgoingInterfaceNotConfigured (6919),
		oeAdmPEEdgeDhPriPortNotConfigured (6920),
		oeAdmPEEdgeDhSecPortNotConfigured (6921),
		oeAdmPEEdgePortIsUsedAsDhPriPort (6922),
		oeAdmPEEdgePortIsUsedAsDhSecPort (6923),
		oeAdmPEEdgeDhPortCanNotBeOpmPort (6924),
		oeAdmPEEdgeIpAddIsUsedAsPriInterface (6925),
		oeAdmPEEdgeIpAddIsUsedAsSecInterface (6926),
		tlsUniIsNotCreatedYet (6927),
		tlsUniCustIpVlanAlreadyCreated (6928),
		tlsUniCustIpVlanIsNotCreatedYet (6929),
		custIpVlanCannotBeDeletedWhileIsEnabled (6930),
		tlsUniSPIpVlanCannotBeEmptyForCreation (6931),
		custIpVlanIsMappedToDifferentLocalIpVlan (6932),
		serviceProvideVlanIsMappedToADifferentLocalIpVlan (6933),
		oeAdmPEEdgeDhPriMltNotConfigured (6934),
		oeAdmPEEdgeDhSecMltNotConfigured (6935),
		oeAdmPEEdgePortIsUsedAsDhPriMlt (6936),
		oeAdmPEEdgePortIsUsedAsDhSecMlt (6937),
		custIpVlanCannotModifyParamWhileInEnableState (6938),
		custIpVlanIpTblWaterMarkIsIngoredWhenZeroIpTblSize (6939),
		tlsSetPortForUniBeforeConfigCustIpVlan (6940),
		uniIpTableSizeExceedLimitForPort (6941),
		transparentUniNotSupportCustIpVlan (6942),
		serviceProviderIpVlanNotExist (6943),
		qnqUniSupportsCustIpVlanOnlyIfIs8100EtherType (6944),
		uniEtherTypeOnlyCanBe8100IfWithCustIpVlan (6945),
		custIpVlanUniServiceTypeCannotBeQnqIfNot8100Type (6946),
		tdiCannotUseAccessPortDefaultVlanAsMappedVlan (6947),
		custIpVlanIpTblArpTimerIsLessThanGlobalArpTimer (6948),
		cannotSetArpTimerIfCustIpVlanUniOperUp (6949), 
		cannotSetPriMappedVlanIfAdmNotInDualHomingMode (6950),
		cannotSetSecMappedVlanIfAdmNotInDualHomingMode (6951),
		oeAdmPEEdgeDhPriAndSecMappedVlansCannotBeTheSame(6952),
		tdiCannotHaveSameValueForPriAndSecMappedVlan (6953),								tdiSecMappedVlanCannotBeConfiguredWhenAdmIsNotDualHomed (6954),
		ipAddressBeingUsedAsAdmPriOrSecInterface (6955),
		tlsUniCustIpVlanInvalidPriorityMapping (6956),
		tlsUniCustIpVlanCosProfileNotFound (6957),
		cannotEnableAdmInDhModeWithoutSecOutgoingInterface(6958),
		cannotDeleteIpWhileVlanTdiMgmtEnabled (6959),
		standaloneUniCannotBeEnabledWithNonStandalonePort (6960),
		custIpVlanParamValueRemainsSame(6961),
		uniWithAtmPortSupportsTlsSwitchServiceOnly(6962),
		atmPortOnlyCanBeAssignedToTlsSwitchedServiceUni(6963),
		portIsAssociatedWithOtherServiceTypeUni(6964),
		etherTypeOnlyCanBe8100IfItsUniAssociatedWithCustIpVlan(6965),
		cannotModifyEtherTypeWhileItsEndptOperationUp(6966),
		tdiCannotSupportPbtAndMappedVlan(6967),
		tdiCannotSupportMimAndMappedVlan(6968),
		tdiMappedVlanIsAlreadyUsedForPbt(6969),
		pbtHasToBeEnabledForTdiMimEncap(6970),
		commandIsSupportedOnEsmPortOnly(6971),
		canNotEnableTdiWithMimEncapWhenMimEtherTypeIsNotSet(6972),
		canNotEnablePbtTdiWhenMezzCardIsNotPresent(6973),
		tlsPriorityOverrideNotSupportedOnRModule(6974),
		serviceProviderVlanMustBeSameAsLocalIpVlan(6975),
		tlsUniCustIpVlanInvalid(6976),
     		tlsOnlyConnectionModeOfP2pIsValidForPbt(6977),
		isidSupportedOnlyOnRmodule(6978),
		tlsQnqEndpointCannotBeEnabledWithoutSvlan(6979),
		tlsBvlanDoesNotExist(6980),
		tlsQnqEndPointCvlanOutOfRange(6981),
		tlsQnqEndPointSvlanOutOfRange(6982),
		tlsTransparentEndpointCannotSetCvlan(6983),
		setEndpointServiceTypeToQnqBeforeSettingSvlan(6984), 
		onlyOneEndpointPerTdiAllowedOnRmodPort(6985),
		tlsCannotSetManyToOneWithQnq1ServiceType(6986),
		tlsQnq1EndptCannotHaveCVlan(6987),
		tlsQnq1EndptOnSamePortNeedDiffSVlan(6988),
		isidHubAndSpokeNotSupportedInThisRelease(6989),
		tlsCustIpVlanSpVlanPvidCannotCoexist(6990),
		tlsPbtCanOnlyHaveOneEnabledEndPoints(6991),
		tlsTdiCannotChangeEvpnModeWithActiveEpt(6992),
		tlsSupportedOnlyOnRModule(6993),
		tlsColorRemarkNotAllowedIfPolicerIsDisabled(6994),
		tlsPolicerDisableNotAllowedWhenColorBasedRemarkIsEnabled(6995),
		tlsTransparentOrQnq1EndptMustHaveCvidConfigured(6996),
		tlsCvidMustBeIncludedInQtags(6997),
		tlsClientMepsNotOnTheSameMa(6998),
		onlyOpmPortCanBeAssignedToRbsRing (7001),
		portIsAlreadyConfiguredInTheRbsRing (7002),
		portIsBeingUsedAsSecondaryPortInThisRbsRing (7003),
		portIsBeingUsedAsPrimaryPortInThisRbsRing (7004),
		portIsBeingUsedInOtherRbsRing (7005),
		portCannotBeUsedAsPrimaryAndSecondaryInRbsRing (7006),
		standaloneRbsPortCanBeAssignedToOnlyOneUni (7007),
		standaloneRbsPortAlreadyCreated (7008),
		portCannotBeModfiedWhenRingEnable (7009),
		portCannotBeModifiedWhileTheRbdRingUniIsEnabled (7010),
		rbsRingAlreadyExist (7011),
		rbsRingDoesNotExist (7012),
		rbsRingNotFound (7013),
		rbsRingCanNotEnableWithoutPort (7014),
		standaloneRbsPortDoesNotExist (7015),
		onlyOpmPortCanBeAssignedToStandalone (7016),
		rbsRingUniIsEnable (7017),
		rbsStandaloneUniIsEnable (7018),
		rbsRingCannotChangeParam (7019),
		rbsStandaloneCannotChangeParam (7020),
		rbsRingInvalidPortId (7021),
		rbsStandaloneInvalidPortId (7022),
		rbsRingTableSizeExceedLimit (7023),
		rbsPortCanOnlyAssignedOneUni (7024),
		rbsRingInvalidRbsId (7025),
		rbsRingHasOverLimitNubmerOfSwitchedUni (7026),
		vlanContainsRingPortAssociatedWithOtherIpmcEnabledVlan (7027),
		cannotAddSameRingPortToMoreThanOneIpmcEnabledVlan (7028),
		cannotEnableIpmcOnTlsIpmcDisabledRingVlan (7029),
		cannotDisableTlsIpmcOnIpmcEnabledRingVlan (7030),
		cannotAddRingPortToIpmcEnabledTlsIpmcDisabledVlan (7031),
		cannotAddRingToIpmcEnabledTlsIpmcDisabledVlan (7032),
		cannotAddSameRingToMoreThanOneIpmcEnabledVlan (7033),
		vlanContainsRingAssociatedWithOtherIpmcEnabledVlan (7034),
		esuDhRingCannotChangeParam (7035),               
		esuDhRingCannotBeDeletedUniIsEnable (7036),
		onlyOpmPortCanBeAssignedToDhRingPort(7037),
		portCannotBeModfiedWhenDhRingEnable (7038),
		paramCannotBeModifiedWhileTheDhRingUniIsEnabled (7039),
		opmPortCannotBeAssignedToIbtPort (7040),
		esuDhRingCanNotEnableWithoutPort (7041), 
		ibtPortNotPresent (7042),
		ringIdAlreadyUsedForOtherType (7043),
		esuDhRingIbtPortOrMltNotConfig (7044),
		ringPortNotPresent (7045),
		ringOnlyCanBeConfigEitherIbtPortOrIbtMlt (7046), 
		ibtVidCannotBeDefaultVlan (7047), 
		ringCannotBeEnabledWithoutIbtVid (7048),
		ringCannotBeEnableddWhileIbtMltHasNoPort (7049),
		mltPerformTaggingIsDisabled (7050),
		ringCannotBeEnabledWithoutPartnerPortMac (7051),
		ringOrIbtPortMustBePerformTaggingEnabled (7052),
		ringPortMustBePerformTaggingEnabled (7053),
		cannotDisableIbtPortPerformTagging (7054),
		cannotDeleteIbtMlt (7056), 
		uniMacCannotBeDeleteWhileIsInUse (7057),
		destUniIdIsRequiredForUserMacCreation (7058),
		standaloneCannotCreateUnisOnBothGigPorts (7059),
		removeVlanIdFromThisRingVlanListBeforeAssignItAsIbtVid (7060),
		vlanIsBeingUsedAsIbtVlanForThisRing (7061), 
		esuRingDoesNotHavePrimaryOrSecondaryPortsAssigned (7062), 
		esuDhRingDoesNotHavePrimaryOrSecondaryPortsAssigned(7063),
		primaryPortNotPresent(7064),
		secondaryPortNotPresent(7065),
		esuStandalonePortNotPresent(7066),
		cannotDirectlyAssignMltPortAsIbtPort(7067),
		vlanWithoutIpCannotBeAssignedToMgmtEnabledTdi(7068),
		uniCannotBeSetToTransparentWhilePortIsAssociatedWithOtherUni(7069),
		cannotSetPt2PtOrSpokeTypeWithoutRemoteUniWhileEndptIsEnabled(7070),
		remoteUniCannotBeResetInPt2PtOrSpokeEndptWhileItIsEnabled(7071),
		muxModeCannotBeManyToOneWhileTdiEndpointWithQtag4096(7072),
		custIpVlanCannotChangeParam(7073),
		custIpVlanIsBeingUsedAsEndptQtagInThisSubnet(7074),
		qtagIsBeingUsedAsCustIpVlanInThisSubnet(7075),
		ringCannotBeDeletedWhileItsUniAssociateWithEndpt(7076),
		cannotRemoveAllQtagsWhileEndptAdminStateEnabled(7077),
		rrpIntervalValueMustBeAMultipleOf1000(7078),
		standaloneEsuCannotBeDeletedWhileItsUniAssociateWithEndpt(7079),
		remoteUniAndEndPointUniCannotBeSame(7080),
		cannotSetOuterQtagZeroWhileQnqEndPointStateEnabled(7081),
		paramValueRemainsSame(7082),
		cannotAddRingToTlsServerServiceVlan(7083),
		vlanReservedForTlsServerService(7084),
		serverPortIsAssociatedWithLocalSwitchOrTransparentUni(7085),
		serverPortIsAssociatedWithQinQUni(7086),
		outerQtagIsBeingUsedInOtherEndpointOnSamePort(7087),
		qtagIsBeingUsedInOtherEndpointOnSamePort(7088),
		custIpVlanIsBeingUsedInOtherUniOnSamePort(7089),
		spIpVlanIsBeingUsedInOtherUniOnSamePort(7090),
		portCannotBeRemovedWhileUniOnRing(7091),
		qnqUniDoesNotSupportCustIpVlan(7092),
		outerQtagIsBeingUsedAsCustIpVlanInOtherUniOnTheSame(7093),
		custIpVlanIsBeingUsedAsInnerOrOuterQtagInOtherEndptOnSamePort(7094),
		cannotSetSVlanZeroWhileQnqEndptStateEnable(7095),
		sVlanIsBeingUsedAsCustIpVlanInOtherUniOnTheSame(7096),
		sVlanIsBeingUsedInOtherEndptOnSamePort(7097),
		cannotConfigPrimaryPortOnLaneWithSecondaryPort(7098),
		cannotConfigSecondaryPortOnLaneWithPrimaryPort(7099),
		cosProfileTableIndexAlreadyExist (7101),
		cosProfileTableIndexNotFound (7102),
		cosProfilePremiumUnitError (7103),
		cosProfilePremiumCirError (7104),
		cosProfileGoldUnitError (7105),
		cosProfileGoldCirError (7106),
		cosProfileSilverUnitError (7107),
		cosProfileSilverCirError (7108),
		cosProfileStandardUnitError (7109),
		cosProfileStandardPirError (7110),
		cosProfileTableNameAlreadyExist (7111),
		cosProfileDeleteTableNameIndexError (7112),
		cosProfileNameFieldCannotBeEmpty (7113),
		cosProfilePremiumCirRateOutOfRange (7114),
		cosProfileGoldCirRateOutOfRange (7115),
		cosProfileSilverCirRateOutOfRange (7116),
		cosProfileStandardPirRateOutOfRange (7117),
		changingPremCirUnitOrRateCauseTotalCirExceedStndPir (7118),
		changingGoldCirUnitOrRateCauseTotalCirExceedStndPir (7119),
		changingSilverCirUnitOrRateCauseTotalCirExceedStndPir (7120),
		changingStandardPirUnitOrRateCauseStndPirLessThanTotalCir(7121),
		premTbMaxKbCannotBeModifiedWhileItsCtlIsAutomatic (7122),
		goldTbMaxKbCannotBeModifiedWhileItsCtlIsAutomatic (7123),
		silverTbMaxKbCannotBeModifiedWhileItsCtlIsAutomatic (7124),
		stndTbMaxKbCannotBeModifiedWhileItsCtlisAutomatic (7125),
		cannotDeleteCosProfileWhileIsUsedInCustIpVlanOrTdiEndpt (7126),
		mcastRateCannotBeMoreThan15WhileMcastUnitIs64k(7127),
		cannotSetMcastUnitTo64kWhileMcastRateIsMoreThan15(7128),
		mcastTbMaxCannotBeModifiedWhileItsCtlIsAutomatic(7129),
		cannotDeleteCosProfileWhileIsUsedInCustIpVlanOrEndptOrEsmPort(7130),
		onlyEsmOrRModulePortCanBeAssignedToEsuRing(7131),
 		primaryAndSecondaryPortCanNotBeOnTheSameLaneInEsuRing(7132),
		cosProfileStandardCirOutOfRange(7133),
		changingStandardCirUnitOrRateCauseTotalCirExceedStndPir(7134),
		cosProfilePremiumEirOutOfRange(7135),
		cosProfileGoldEirOutOfRange(7136),
		cosProfileSilverEirOutOfRange(7137),
		cosProfileStandardEirOutOfRange(7138),
		cosProfileBcastUUcastRateOutOfRange(7139),
		premEirTbMaxKbCannotBeModifiedWhileItsCtlIsAutomatic(7140),
		goldEirTbMaxKbCannotBeModifiedWhileItsCtlIsAutomatic(7141),
		silverEirTbMaxKbCannotBeModifiedWhileItsCtlIsAutomatic(7142),
		stndCirTbMaxKbCannotBeModifiedWhileItsCtlisAutomatic(7143),
		stndEirTbMaxKbCannotBeModifiedWhileItsCtlisAutomatic(7144),
		bcastUucastTbMaxCannotBeModifiedWhileItsCtlIsAutomatic(7145),
		premCirEirSumCannotExceedPir(7146),
		goldCirEirSumCannotExceedPir(7147),
		silverCirEirSumCannotExceedPir(7148),
		stndCirEirSumCannotExceedPir(7149),
		premEirUnitOrRateChangeCauseTotalCirEirExceedPir(7150),
		goldEirUnitOrRateChangeCauseTotalCirEirExceedPir(7151),
		silvEirUnitOrRateChangeCauseTotalCirEirExceedPir(7152),
		stndEirUnitOrRateChangeCauseStndCirEirExceedPir(7153),
		cosProfileInvalidCosMap(7154),
		cosProfileCannotEnableCouplingIfEirDisable(7155),
		tdcontTestEntryAlreadyExists (7201), 
		tdcontTestEntryDoesNotExist (7202),
		testInProgress (7203),
		tdiHasBeenSet (7204),
		sourceUniDoesNotExist (7205),
		tdcTdiDoesNotExist (7206),
		tdiOrSrcUniDoesNotAssociateWithTheValidEndpoint (7207),
		tdiEndpointIsDisabled (7208),
		tdcOutofHistoryRange (7209),
		testNotInProgress (7210),
		srcUniHasBeenSet (7211),
		dstUniHasBeenSet (7212),
		nameExist (7213),
		tdcConfigNotDone (7214),
		mcastUcastBothZero (7215),
		uniIsNotOnPort (7216),
		noQtagForTdiInMappedUni (7217),
		priorityNeeded (7218),
		tdiIsDown (7219),
		testIsNotPeriodicRun (7220),
		periodicRateCannotBeZero (7221),
		dstUniHasNotBeenConfigured (7222),
		tdcTdiHasNotBeenConfigured (7223),
		unicastTestIsNotAllowedWithDestPortSet (7224),
		tdcTestDstPortOutOfRange (7225),
		dstPortCannotBeSetInUnicastTest (7226), 
		dstPortHasBeenSet (7227),
		tdcSrcUniIsDisabled(7228),
		tdcSrcEndptIsDisabled(7229),
		tdcSrcEndptDoesNotExist(7230),
		totalTdcHistoryCountExceedsMaxLimit(7231), 
		totalTdcHistoryCountAlreadyReachedMaxLimit(7232),
		tdcSrcUniAndDstUniCannotBeSame(7233),
		mplsTunnelExists (7301),
		mplsInvalidTunnelGrpTunnelDestnNoMatch (7302),
		mplsInvalidLabelRecordFlagSet (7303),
		mplsInvalidSetWhenRsvpEnabled (7304),
		mplsTunnelGrpInvalidHelloInterval (7305),
		mplsTunnelHopToIpMapInvalidPrefixLen (7306),
		mplsTunnelHopToIpMapHopNameExists  (7307),
		mplsTunnelHopToIpMapInvalidHopName (7308),
		mplsTunnelHopToIpMapIpAddressExists (7309),
		ipv6VlanDoesnotExist (7401),
		ipv6InvalidInstance(7402),
		ipv6InvalidParameter(7403),
		ipv6AttrNotImplemented(7404),
		ipv6EntryDuplicate(7405),
		ipv6EntryNotExist(7406),
		ipv6InvalidIdentifierLength(7407),
		ipv6CircuitDoesNotExist(7408),
		ipv6PortNotPowerRanger(7409),
		ipv6InvalidInterfaceIdentifier(7410),
		ipv6CannotChangeWhenAdminEnable(7411),
		ipv6InvalidReasmMaxSize(7412),
		ipv6InvalidReachableTime(7413),
		ipv6InvalidPrefixLength(7414),
		ipv6InvalidSendAdverts(7415),
		ipv6InvalidMaxInterval(7416),
		ipv6InvalidMinInterval(7417),
		ipv6InvalidRetransmitTimer(7418),
		ipv6InvalidDefaultLifeTime(7419),
		ipv6InvalidCurHopLimit(7420),
		ipv6InvalidManagedFlag(7421),
		ipv6InvalidOtherConfigFlag(7422),
		ipv6InvalidDadNsNum(7423),
		ipv6InvalidPhysicalAddress(7424),
		ipv6InvalidNetToPhysicalType(7425),
		ipv6NeighborDuplicate(7426),
		ipv6NeighborDoesNotExist(7427),
		ipv6InvalidInvalidIpv6Addr(7428),
		ipv6PrefixDuplicate(7429),
		ipv6InvalidPrefix(7430),
		ipv6InvalidInterfaceType(7431),
		ipv6NexthopOrIndexReq(7432),
		ipv6NexthopIsLinklocBothIndexHopReq(7433),
		ipv6StaticRouteDistanceReq(7434),
		ipv6StaticRouteDuplicate(7435),
		ipv6StaticRouteInvalid(7436),
		ipv6OspfInvalidRouterId(7437),
		ipv6OspfNotSupported(7438),
		ipv6OspfAreaDoesNotExist(7439),
		ipv6OspfAlreadyExist(7440),
		ipv6OspfInterfaceInvalid(7441),
		ipv6OspfInterfaceExists(7442),
		ipv6OspfInterfaceNotExists(7443),
		ipv6OspfAreaAggregateEntryExists(7444),
		ipv6OspfAreaAggregateEntryDoesNotExist(7445),
		ipv6OspfInvalidAreaRangeMask(7446),
		ipv6OspfAreaCannotModifyBackbone(7447),
		tcpConnectTblPermittedStateIsDelete(7448),
		ipv6InterfaceVlanNotFound(7449),
		ipv6TunnelInterfaceDoesnotExist(7450),
		ipv6TunnelNotImplemented(7451),
		ipv6TunnelInvalidOperation(7452),
		ipv6TunnelInvalidType(7453),
		ipv6TunnelInterfaceAlreadyExist(7454),
		ipv6TunnelRemAddrShldBeZero(7455),
		ipv6VlanDoesNotMatchPreviousVlanid(7456),
		ipv6UvifDoesNotExist(7457),
		ipv6MldNotEnabled(7458),
		ipv6MldInterfaceExists(7459),
		ipv6MldInterfaceDoesNotExist(7460),
		ipv6MldInvalidQueryInterval(7461),
		ipv6MldInvalidVersion(7462),
		ipv6MldInvalidMaxRespdelay(7463),
		ipv6MldInvalidRobvar(7464),
		ipv6MldInvalidLlqi(7465),
		ipv6RedistributionInvalidOperation(7466),
		ipv6InvalidMaxRouterAdvertInterval(7467),
		ipv6InvalidMinRouterAdvertInterval(7468),
		ipv6CannotSetSummaryAsFalseIfNotStubArea(7469),
		ipv6CannotModifyStubMetricIfNotStubArea(7470),
		ipv6GatewayMustBeOnMgmtInterface(7471),
		ipv6OspfNbmaNbrAlreadyExist(7472),
		ipv6OspfInterfaceNotNbma(7473),
		ipv6OspfNbmaTunnelNot624(7474),
		ipv6OspfNbmaNbrNotExist(7475),
		cannotConfigureAddrWhichIsLinkLocal(7476),
		addrEntryDoesNotExist(7477),
		ipv6TunnelCannotHaveMoreThanOneAddr(7478),
		cannotChangeAddressType(7479),
		cannotConfigureNetAddr(7480),
		invalidInetNetworkAndMask(7481), 
		cannotConfigureHostAddr(7482),
		ipv6InterfaceIdCannotBeChanged(7483),
		ipv6TunnelLocalAndRemoteIpAddressCannotBeSame(7484),
		ipv6StaticRouteWrongNexthop(7485),
		ipv6EuiInterfacePrefixCannotBeGreaterThan64(7486),
		ipv6CircuitMcastFlagNotSet(7487),
		ipv6MldProxyUnsupported(7488),
		ipv6MtuChangeWhenIntfDisable(7489),
		ipv6OspfNbmaNbrInvalidAddress(7490),
		ipv6AddressAndPrefixSame(7491),
		ipv6IncompatibleAddressTypeAndAddress(7492),
		ipv6DadInProgressTryLater(7493),
		ipv6InterfaceMismatch(7494),
		ipv6StaticNeighborInterfaceNotPresent(7495),
		ipv6RequiresSuperMezz(7496),
		ipv6StaticRouteOnlyIfindexCannotConfigPref(7497),
		ipv6StaticRouteRecursiveRouteNotSupported(7498),
		ipv6TunnelLocalRemoteAddrPairAlreadyExists(7499),
		idInvalid(7501),
		notExist(7502),
		duplicate(7503),
		nameInvalid(7504),
		notenablemixedmlt(7505),
		portconflictmixedmlt(7506),
		clockSourceAvailableOnWanModeInterfaceOnly(7507),
		mtuSettableOnlyOnUni(7508),
		mtuSetOnPortCannotSetInterface(7509),
		actInUse(7601),
		actFieldTooMany(7602),
		actPatternNotExist(7603),
		actErrApplyStateTrue(7604),
		actMaxPatternExceeded(7605),
		aclActNotExist(7606),
		aclTypeInvalid(7607),
		aclDefActionInvalid(7608),
		aclGlobActionInvalid(7609),
		vlanInvalid(7610),
		portInvalid(7611),
		aclMltInvalid(7612),
		aclInUse(7613),
		aclInvalidState(7614),
		aclActNotApplied(7615),
		aclActVlanAttrSpecified(7616),
		aclActPortAttrSpecified(7617),
		aclPortBased(7618),
		aclVlanBased(7619),
		actNoAttributesConfigured(7620),
		aclErrPortAlreadyInAcl(7621),
		aclErrVlanAlreadyInAcl(7622),
		aceAclIdInvalid(7623),
		aceAclNotExist(7624),
		aceInUse(7625),
		aceMax(7626),
		aceModeIllegal(7627),
		aceDscpIllegal(7628),
		aceDot1pIllegal(7629),
		aceUnreachIllegal(7630),
		acePoliceIllegal(7631),
		aceAclInvlanPoliceNotAllLanes(7632),
		aceInvalidAdminState(7633),
		aceEgressQueueInvalid(7634),
		aceEgressQueue1gInvalid(7635),
		aceEgressQueue10gInvalid(7636),
		aceEgressNNSCInvalid(7637),
		acePoliceInvalidMode(7638),
		aceAttrNotExistInAct(7639),
		aceInsuffActionAttr(7640),
		maxAceForSystem(7641),
		aceValMoreThanActPatternLen(7642),
		aceMltIndexIllegal(7643),
		aceModeNotPermit(7644),
		aceNotPermitIngress(7645),
		aceParmNotDefault(7646),
		aceAttrConflict(7647),
		defaultIdnoCreate(7648),
		defaultIdnoDelete(7649),
		defaultIdnoModify(7650),
		mltPortAclConflict(7651),
		aceNoModeModify(7652),
		aclNoAccept(7653),
		aceDebugMirrorDisableToRemoveDest(7658),
		qosPolicyLaneExist(7701),
		qosPolicyLaneNotExist(7702),
		qosPolicyPkRateInvalid(7703),
		qosPolicySvcRateInvalid(7704),
		qosPolicyLaneInvalid(7705),
		qosPolicyValidAcesPresent(7706),
		qosTxQSetQmaxInvalid(7707),
		qosTxQSetQmaxChangeNotAllowed(7708),
		qosTxQSetBalQInvalid(7709),
		qosTxQSetHipriQInvalid(7710),
		qosTxQSetLopriQInvalid(7711),
		qosTxQSetMaxQExceed(7712),
		qosTxQSetPortNotRMod(7713),
		qosTxQSetQInvalid(7714),
		qosTxQSetQNotAssign(7715),
		qosTxQSetMinRateGtMaxrate(7716),
		qosTxQSetQMaxAfter8Adjust(7717),
		qosTxQSetPortFeIncompatibleQset64(7718),
		qosTxQSetPortGbIncompatibleQset8(7719),
		qosTxQSetModificationNotAllowed(7720),
		qosTxQSetQLengthWredModNotAllowed(7721),
		qosWredDropThresholdQminShouldBeLessThanQmax(7722),
		qosSubportQueueProfileIndexAlreadyExists(7723),
		qosSubportQueueProfileNameCannotBeEmpty(7724),
		qosSubportQueueProfileNameAlreadyExists(7725),
		qosSubportQueueProfileInvalidIndex(7726),
		qosSubportQueueProfileInvalidNumberOfBalancedQueues(7727),
		qosSubportQueueProfileInvalidNumberOfHiPriQueues(7728),
		qosSubportQueueProfileInvalidNumberOfLowPriQueues(7729),
		qosSubportQueueProfileInvalidTotalQueues(7730),
		qosSubportQueueProfileDeleteDefaultProfileNotAllowed(7731),
		qosSubportQueueProfileDoesNotExist(7732),
		qosSubportQueueProfileInvalidQIndex(7733),
		qosSubportQueueProfileQMinRateGreaterThanMaxrate(7734),
		qosSubportQueueProfileInvalidQMaxLength(7735),
		qosSubportQueueProfileInvalidQWredCurveSet(7736),
		qosSubportQueueSetAlreadyExists(7737),
		qosSubportQueueSetSupportedOnlyOnRModule(7738),
		qosSubportQueueSetCreateOn48PortCardNotAllowed(7739),
		qosSubportQueueSetInvalidIndex(7740),
		qosSubportQueueSetDoesNotExist(7741),
		qosSubportQueueSetDeleteNotAllowedInUseByEnabledTrunk(7742),
		qosSubportQueueSetDeleteDefaultQSetNotAllowed(7743),
		qosSubportQueueSetRateExceededLineRate(7744),
		qosSubportQueueSetMinRateGreaterThanMaxRate(7745),
		qosSubportQueueSetTotalMinRatesExceededLineRate(7746),
		qosSubportQueuesetChangeMinRateNotAllowedIfAnyQsetIsModifed(7747),
		qosSubportQueueSetInvalidMaxRate(7748),
		qosSubportQueuesetApplyNotAllowedIfAnyQsetIsModifed(7749),
		qosIsidRateLimiterForThisSlotDoesNotExist(7750),
		qosIsidRateLimiterIsidEntryAlreadyExists(7751),
		qosIsidRateLimiterMaxAllowedIsidEntriesReached(7752),
		qosIsidRateLimiterIsidEntryDoesNotExist(7753),
		qosCannotDeleteSubportProfileWhileInUse(7754),
		qosSubportQSetProfileWithDiffQueueCombinationsNotAllowed(7755),
		qosSubportQProfileMinRateInvalidOnThisQType(7756),
		qosSubportQProfileOverSubscriptionNotAllowed(7757),
		qosSubportQSetReservedForInternalUse(7758),
		qosCombineOperationInvalidWhenDeCodingIs8p0DOrDei(7759),
		qosSplitOperationInvalidWhenDeCodingIsM5P3D(7760),
		qosInvalidDeCodingWhenUseCfiAsDeiIsTrue(7761),
		qosCannotConfigureUseCfiAsDeiWhenDeCodingIsNotDei(7762),
		maxIpv6AddressesOnMgmtPort(7801),
		tlsTdiCannotDisableUniWithActiveEndpoints (7901),
		tlsTdiCannotDisableTdiWithActiveEndpoints (7902),
		tlsUniMultipleAccessPortNotSupported (7903),
		cannotDisableUniWithActiveCustIpVlan (7904),
		cannotDeleteUniWhileCustIpVlanExists (7905),
		mstpStpCannotBeEnabledOnOpmPort (7906),
		rstpStpCannotBeEnabledOnOpmPort (7907),
		tlsPbtNotEnabled(7908),
		tlsEndPointDefaultTdiIsidNotAllowQtag(7909),
		tlsEndPointDefaultTdiIsidAlreadyExists(7910),
		tlsEndPointDefaultTdiIsidAllowTlsSwitched(7911),
		tlsEndPointDefaultTdiIsidAllowManyToOne(7912),
		tlsEndPointDefaultTdiIsidNotDefault(7913),
		tlsEndPointDefaultTdiPortNotRmodulePort (7914),
		tlsEndptShouldBeQnQForMacSwap(7915),
		removeSvlanAndCvlanBeforeServiceTypeChange(7916),
		tlsNoRcmoduleTrunkOnEsm(7917),
		tlsOverrideTypeSupportedOnlyOnRModule(7918),
		tlsEndPointMacSwapQinQ2InnerQtagNotFound(7919),
		tlsSwitchEndpointCannotInEnableStateWithoutCVlan(7920),
		isidCannotSupportPbtAndMappedVlan(7921),
		tlsEndPointDefaultIsidMepNotAllowed(7922),
		isidCannotSupportPlsbAndMappedVlan(7923),
		isidCannotSupportPbtAndPlsb(7924),
		tlsPbtTGDualHomePartnerTrunkDHOnly(7925),
		tlsPbtTrunkCannotHaveLocalPortAndDHPartnerEnabled(7926),
		tlsPbtDHPartnerTrunkCannotHaveMepConfigured(7927),
		tlsPbtDHPartnerTrunkMissingVlan(7928),
		tlsEndptInvalidDEDecodeScheme(7929),
		tlsEndptInvalidPcpDecodeMap(7930),
		tlsEndptCannotConfigPcpDecodeMapWhenSchemeIsNotCustom(7931),
		tlsEndptInvalidSchemeWhenCoreSchemeIsAD8P0D(7932),
		tlsMappedVlanIsAlreadyUsedForPlsb(7933),
		tlsUniCannotReplaceOldSaPort(7934),
		isidBVlanIsBeingUsedAsSpIpVlanOnEnhancedDualHomeRing(7935),
		spIpVlanIsBeingUsedAsIsidBVlanOnEnhancedDualHomeRing(7936),
		tlsPlsbIsidCannotSupportMltEndpoint(7937),
		eapGuestAndMultiMac(8001),
		eapCannotModifyMaxNonEapClients(8002),
		eapInvalidMaxNonEapValue(8003),
		eapUnknownMacAndEap(8004),
		ipfixStateAlreadyEnabled(8101),
		ipfixStateAlreadyDisabled(8102),
		ipfixInvalidSlotNumber(8103),
		ipfixNotADPMSlot(8104),
		ipfixInvalidActiveTimeout(8105),
		ipfixInvalidAgingInterval(8106),
		ipfixInvalidExportInterval(8107),
		ipfixInvalidTemplateRefIntervalSec(8108),
		ipfixInvalidTemplateRefIntervalPkts(8109),
		ipfixCollectorNotConfigured(8110),
		ipfixTwoCollectorAlreadyConfigured(8111),
		ipfixOnlyUdpProtocolSupported(8112),
		ipfixInvalidCollectorDestPort(8113),
		ipfixInvalidHashPolynomialCoeff(8114),
		ipfixInvalidHashPolynomialSeed(8115),
		ipfixInvalidHashKeyId(8116),
		ipfixInvalidSamplingRate(8117),
		aceIpfixStateIllegal(8118),
		ipfixMirrorPortNoIpfixSupport(8119),
		ipfixOnlyPreipfixv9VersionSupported(8120),
		ipfixPortNoMirrorSupport(8121),
		tacacsIllegalIpAddress(8201),
		tacacsIllegalPriority(8202),
		tacacsMaxServersReached(8203),
		tacacsRadiusEnabled(8204),
		tacacsNoKeyGiven(8205),
		tacacsInvalidSecretKey(8206),
		tacacsSourceIpDisabled(8207),
		tacacsInvalidPort(8208),
		tacacsServerNotConfigured(8209),
		isisPwdInvalid (8301),
		isisKeyIdInvalid (8302),
		isisPwdExists (8303),
		isisNoKeyId (8304),
		isisInvalidAuthType (8305),
		isisCsnpIntInvalid (8306),
		isisRxmtLspIntInvalid (8307),
		isisRtrTypeInvalid (8308),
		isisNetLenInvalid (8309),
		isisSysidError (8310),
		isisManAreaAddrToomany(8311),
		isisManAreaError(8312),
		isisNetEntryExists (8313),
		isisSummAddrExists (8314),
		isisSummAddrError (8315),
		isisInvalidSubnetMask (8316),
		isisEnabledOnInterface (8317),
		isisCannotChangeMetricTypeFromWideToNarrow (8318),
		isisInvalidCircType(8319),
		isisSysIdInvalid(8320),
		isisSysIdRuntimeChange(8321),
		isisInvalidCircuitId(8322),
		isisCircuitAlreadyExists(8323),
		isisCircuitDoesNotExist(8324),
		isisInvalidIntfIndex(8325),
		isisLevelRouterDoesNotSupp(8326),
		isisManAreaNotConfigured(8327),
		isisL2OnlyNotSupported(8328),
		isisPriorityOnlyForBcastType(8329),
		isisMetricValueInvalidForNarrowType(8330),
		isisL2onlyCircuitExists(8331),
		isisMinLspIntGreaterThanMaxLspInt(8332),
		isisMaxLspIntLessThanMinLspInt(8333),
		isisPlsbNodeNicknameInvalid(8334),
		isisPlsbInstanceAlreadyExists(8335), 
		isisOnePlsbInstanceAllowed(8336),
		isisPlsbInstanceDoesNotExist(8337),
		isisCannotDeletePlsbInstanceWithIsid(8338),
		isisCannotDeletePlsbInstanceWithIsisInterface(8339),
		isisOneVlanPerPlsbInstance(8340),
		isisVlanDoesNotExist(8341),
		isisVlanIsNotPlsb(8342),
		isisInterfaceCannotConfigPlsb(8343),
		isisPlsbInstanceNotExistOnInterface(8344),
		isisPlsbInstancePt2ptOnly(8345),
		isisPlsbL1Only(8346),
		isisCannotDeleteVlanWithPlsb(8347),
		isisPlsbNniPortCannotBeAccess(8348),
		isisCannotEnableInterfaceWithoutPlsbInstance(8349),
		isisSystemIdIsnotBasemac(8350),
		isisPlsbInstanceNotConfigured(8351),
		isisNicknameNotConfiguredForPlsbInstance(8352),
		isisBvidNotConfiguredForPlsbInstance(8353),
		isisSpfDelayInvalid(8354),
		isisControlVlanDoesNotExist(8355),
                cannotAddPortToMltWithIsisInterfaceOnBothPortAndMlt(8356),
                cannotCreateIsisIntfOnPortWhichIsMemberOfMltWithIsisIntf(8357),
                cannotCreateIsisIntfOnMltWhichHasPortMemberWithIsisIntf(8358),
		isisSysidCannotBeMulticastAddress(8359),
		deleteIsisInterfaceBeforeDeleteMlt(8360),
		onlyFirst10PortOfLaneCanBeIsisInterface(8361),
		narrowMetricNotSupportedInPlsbMode(8362),
		isisCannotChangeSysIdDueToIsidEpIsEnable(8363),
		isisCannotChangeNickNameDueToIsidEpIsEnable(8364),
		isisCannotChangePlsbVlanDueToIsidEpIsEnable(8365),
		isisBcastNotSupportedOverMlt(8366),
		isisPortIsNotMemberOfPlsbVlan(8367),
		isisMltIsNotMemberOfPlsbVlan(8368),
		isisPlsbVlanDifferentFromDataVlan(8369),
		isisOverloadOnStartUpOutOfRange(8370),
		isisCannotChangeSysIdWhenNodalMepMipAssociatedToPlsbVlan(8371),
		nsnaNoRedVlan(8401),
    		nsnaRedVlanExists(8402),
		nsnaGlobalEnabled(8403),
		nsnaNoVlanColor(8404),
		nsnaVlanHasColor(8405),
		nsnaVlanNonEmpty(8406),
		nsnaNoFilterForNsnaVlan(8407),
		nsnaPortHasFilter(8408),
		nsnaNoUplinkDhcpFilter(8409),
		nsnaYellowSubnetNotSpecified(8410),
		nsnaNoNsnasSubnet(8411),
		nsnaMaxNsnasSubnet(8412),
		nsnaNoSshDaemon(8413),
		nsnaIncorrectGreenVlan(8414),
		nsnaIncorrectUplinkVlan(8415),
		nsnaIncorrectVoipVlan(8416),
		nsnaPortIsEap(8417),
		nsnaPortOperationNotAllowed(8418),
		nsnaUnknownMac(8419),
		nsnaExceedMaxNumEntry(8420),
		nsnaStaticEntryExists(8421),
		nsnaOperationNotAllowedOnMirroredPort(8422),
		nsnaInvalidHelloInact(8423),
		nsnaVlanFlushNotAllowed(8424),
		nsnaNoUplinkVlans(8425),
		nsnaVlanFilterRemapInProgress(8426),
		nsnaVlansCannotBeDeleted(8427),
		nsnaVlanCannotBeMadeGuestVlan(8428),
		nsnaPortCannotBeConfiguredOnNonPrPorts(8429),
		nsnaGuestVlanCannotBeMadeNsnaVlan(8430),
                		nsnaNotAllowedOnSmltPort(8431),
                                        nsnaVlanNotColoredVlan(8432),
                                        nsnaFailOpenVlanNotExist(8433),
                                        nsnaFailOpenFilterVlanNotEqualFailOpenVlan(8434),
                                        nsnaCfgNotAllowedAfterFailOpenAction(8435),
                                        nsnaFailOpenActionInProgress(8436),
		nsnaFailOpenEabled(8437),
		nsnaNonNsnaPortInNsnaVlan(8438),
		nsnaEnableFailedOnDhcpSnVlan(8439),
		nsnaEnableFailedOnDaiVlan(8440),
		nsnaEnableFailedOnIpsgPort(8441),
		cfmNoParamChange(8501),
		cfmDomainExists(8502),
		cfmDomainDoesNotExists(8503),
		cfmMaintenanceAssociationExists(8504),
		cfmMaintenanceAssociationDoesNotExists(8505),
		cfmChangeNotAllowedWhenEnabled(8506),
		cfmMepExists(8507),
		cfmMepDoesNotExists(8508),
		cfmTrunkExists(8509),
		cfmTrunkDoesNotExists(8510),
		cfmOperationNotAllowedWhenMepsExist(8511),
		cfmVlanDoesNotExist(8512),
		cfmVlanIsNotPbt(8513),
		cfmVlanPortNotMember(8514),
		cfmOneTrunkPerAssociation(8515),
		cfmTrunkAlreadySpecifiedState(8516),
		cfmTrunkMissingFields(8517),
		cfmTrunkMissingRemMac (8518),
		cfmTrunkGrpExists(8519),
		cfmTrunkGrpDoesNotExists (8520),
		cfmTrunkGrpCannotReplaceTrunk(8521),
		cfmServiceGrpExists(8522),
		cfmServiceGrpDoesNotExists(8523),
		cfmDiscardUnkMacNotSet(8524),
		cfmInvalidPbtVlan(8525),
		cfmInvalidPortType(8526),
		cfmSGMissingFields(8527),
		cfmSGMissingRemMac(8528),
		cfmSgingAndPortNotAllowed(8529),
		cfmSgDualHomeRingNotSupported(8530),
		cfmMepInUse(8531),
		cfmSgPortInvalid(8532),
		cfmEndPtMissingFields(8533),
		cfmPbtVlanInUse(8534),
		cfmMaDomainNameFieldCannotBeEmptyForCreation(8535),
		indexIsBeingUsedByOtherDomain(8536),
		cfmAssnIndexCantBeZeroForCreation(8537),
		indexIsBeingUsedByOtherMaAssn(8538),
		cfmOperationNotAllowedWhenMasExistUnderMd(8539),
		cfmDomainIndexCantBeZeroForCreation(8540),
		cfmAssnDoesNotExist(8541),
		cfmMepIdCannotBeNullForCreation(8542),
		cfmMaAssnNameFieldCannotBeEmptyForCreation(8543),
		cfmMepDeleteNotAllowedWhenAlreadyAssignedToTdi(8544),
		cfmCannotDeleteRemoteMep(8545),
		cfmMdDeleteNotAllowedWhenAlreadyAssignedToTrunk(8546),
		cfmMdDeleteNotAllowedWhenAlreadyAssignedToSg(8547),
		cfmMdDeleteNotAllowedWhenAlreadyAssignedToEp(8548),
		cfmCannotDeleteIfPortInUseByPbt(8549),
		cfmCannotRemovePortFromPbtStg(8550),
		pbtVlanMustUsePbtStg(8551),
		pbtVlanCannotReassign(8552),
		pbtVlanCannotRemoveFromMlt(8553),
		cfmMepCanNotEnableWhenCfmEtherTypeIsNotSet(8554),
		vplsBroadcastOptimizationMuxModeOnlyOneToOne(8555),
		vplsBroadcastOptimizationEndPtMustHaveSameQtag(8556),
		vplsBroadcastOptimizationServiceTypeMustBeSwitched(8557),
		vplsBroadcastOptimizationTdiMustHaveUniqueQtag(8558),
		normalVlanCannotUsePbtStg(8559), 
		cfmMepChangeNotAllowedWhenCurrentMepIsEnabled(8560),
		cfmMepChangeNotAllowedWhenNewMepIsEnabled(8561),
		invalidMepListInputFormat(8562),
		invalidDmOrMaNameLength(8563),
		mepIdMustBeANumber(8564),
		maxNumOfMepEntriesExceeded(8565), 
		noMepToBeRemovedOrAdded(8566),
		domainAlreadyAssociatedWithOtherTypeOfService(8567),
		cfmOneServiceInstancePerMa(8568),
		cfmOneMaPerServiceInstance(8569),
		cfmRemoteMepDoesExists(8570),
		cfmRemoteMepDoesNotExists(8571),
		cfmSgCannotAssignBothRingIdAndPort(8572),
		cfmPbtCanHaveOnlyOneStg(8573),
		cfmCannotDeleteBeforeRemoveAssociation(8574),
		cfmMipExists(8575),
		cfmMipDoesNotExist(8576),
		cfmOperationNotAllowedWhenMipsExistUnderMd(8577),
		cfmSgMissingMep(8578),
		maxNumOfMipEntriesExceeded(8579),
		noMipToBeRemovedOrAdded(8580),
		cfmMipInUse(8581),
		invalidMipListInputFormat(8582),
		invalidDmNameLength(8583), 
		mipIdMustBeANumber(8584), 
		mipDeleteNotAllowedWhileAssignedToService(8585),
		cannotDeleteVlanWithMepAssociation(8586),
		cannotDeleteIsidEndptWithMepAssociation(8587),
		exceedMinCcmInterval(8588),
		exceedMinCcmIntervalForPbtTrunk(8589), 
		tlsTransparentEndpointCannotAddClientMep(8590), 
		cfmOperationNotAllowedWhenRevertiveIsEnabled(8591), 
		canOnlyAssignOneTypeOfMepToIsidEndpt(8592),
		pbtBaseAddressError(8593),
		cfmCannotDeleteTrunkInGroup(8594),
		cfmCannotDeleteTrunkGroupInUse(8595),
		cfmActiveTrunkMustBeUp(8596),
		cfmTrunkNotTrunkGroupMember(8597),
		cfmCannotRevertFromSecondary(8598),
		multicastccmOnPbtTrunkNotAllowed(8599),
		unicastCcmOnVlanIsidOrClientNotAllowed(8601),
		cfmFlrNameCannotBeEmpty(8602),
		cfmFlrProfileAlreadyExists(8603),
		cfmFlrIndexInUse(8604),
		cfmFlrDoesNotExist(8605),
		cfmFlrThresholdMisconfig(8606),
		cfmFdNameCannotBeEmpty(8607),
		cfmFdProfileAlreadyExists(8608),
		cfmFdIndexInUse(8609),
		cfmFdDoesNotExist(8610),
		cfmFdThresholdMisconfig(8611),
		cfmFdvThresholdMisconfig(8612),
		cfmFlrCannotDeleteIfRefByPm(8613),
		cfmFlrCannotChangePriIfRefByPm(8614),
		cfmFdCannotDeleteIfRefByPm(8615),
 		cfmFdCannotChangePriIfRefByPm(8616),
		cfmPmRowNotModified(8617),
		cfmPmEntryNotFound(8618),
		cfmPmColumnNotSpecified(8619),
		cfmPmEntryExists(8620),
		cfmPmPriorityInUse(8621),
		cfmCannotAssignTrunkToLoopbackTrunkGroup(8622),
		cfmRevertiveInvalidForLoopbackTrunkGroup(8623),
		cfmOnlyOneLoopbackTrunkGroupAllowed(8624), 
		cfmCannotAssignLoopbackVlanToNonLoopbackTrunkGroup(8625),
		cfmPbtVlanInUseByTrunk(8626),
		cfmCannotAssignLoopbackVlanToTrunk(8627), 
		cfmMustUseLoopbackTrunkGroup(8628),
		cfmCannotUseLoopbackTrunkGroup(8629),
		cfmNoMoreThanTwoPbtLocalSwitchingEndpt(8630),
		cfmLoopbackVlanMustBePbtVlan(8631),
		cfmPmSampleRateHigh(8632),
		cfmPmConfigNotAllowed(8633),
		cfmPmFlrNotAllowed(8634),
		cfmPmDisableAndModify(8635),
		cfmPortInUseByOtherService(8636),
		cfmSubportQueueSetDoesNotExist(8637),
		cfmSubportQueueSetIsInUse(8638),
		cfmCannotConfigureSubportQueueSetWithoutConfiguringPort(8639),
		cfmSubportQueueSetNotInAppliedState(8640),
		cfmOneMdMaPerEndPt(8641),
		cfmLbmExceedMaxDataSizeLimit(8642),
		cfmPortNotInPbtStg(8643),
		cfmThreeCVlanPerEndPt(8644),
		cfmVlanMepNotAllowedOnPortMlt(8645),
		plsbVlanMustUsePlsbStg(8646),
		normalVlanCannotUsePlsbStg(8647),
		cfmPlsbCanHaveOnlyOneStg(8648),
		cfmInvalidName(8649),
		cfmCannotRemovePortFromPbtVlan(8650),
                noRMepToBeCreatedForTrunkOrPortWithAutoDetectEnabled(8651),
		cfmPortNotMemberOfCfmvid(8652),
		cfmCannotRemovePrimaryTrunkWhenRevertive(8653),
		cfmIfTlvOnClientMepOnly(8654),
		cfmIfTlvNotOnRingOrStandalone(8655),
		cfmIfTlvNotOnLacpEnabledMlt(8656),
		cfmFLRAllowP2PConnectType(8657),
		cfmAisAllowedOnP2pPortAndMlt(8658),
		cfmPmPortVlanMltRingSAConfigNotAllowed(8659),
		cfmPbtPortInterfaceTypeCannotbeUni(8660),
		cfmOneMdPerEndPtForMip(8661),
		cfmMipMdLevelHigherThanClientMep(8662),
		cfmAisNotAllowedForOFClientMEP(8663),
		cfmCannotEnableCfmControlWithEmptyMepList(8664),
                cfmCannotEnableCfmControlWithMepDisabled(8665),
                cfmCannotEnableCfmControlWithMultipleMeps(8666),
                cfmMepNotInMepList(8667),
                cfmCannotRemoveMepUsedForCfmControl(8668),
                cannotChangeVlanForLoopbackTgWithEp(8669),
		sameLevelMepAlreadyAssignedToVlanOnSamePort(8670),
		sameLevelMipAlreadyAssignedToVlanOnSamePort(8671),
		cfmIfTlvNotOnOutwardFacingClientMeps(8672),
		cfmOFClientMepNotSupportedOnRingOrSA(8673),
		cfmClientMipNotSupportedOnRingOrSA(8674),
		cfmMepMdLevelLowerThanClientMip(8675),
		cfmCannotDeleteAutoLearnedRemoteMepInUpState(8676),
		cfmCannotDeleteStaticallyConfiguredRemoteMep(8677),
		cfmCannotDeleteDisabledStaticallyConfiguredRMEP(8678),
		cfmIfTlvNotMoreThanOneHundredPerPortOrMlt(8679),
		cfmCannotAddMoreThanOneRmepToTrunkPort(8680),
		cfmRemoteMacAddrShouldBeConfiguredForUnicast(8681),
		cfmMepCannotBeAssociatedWith10GUntaggedEndpoint(8682),
		cfmPmPortVlanRingSAConfigNotAllowed(8683),
		cfmPmMltLoadDistributionShouldBeIsid(8684),
		cfmNoMoreThanTwoMltPortsAreSupported(8685),
		cfmExceedMinCcmIntervalForVlan(8686),
		cfmNodalMepOnPbtVlanNotAllowed(8687),
		cfmCannotAddOrRemoveNodalMepsWhenMepListIsEmptyOrInvalid(8688),
		cfmExceedMinCcmIntervalForNodalVlan(8689),
		cfmMepAlreadyInUseWithOtherNodalVlan(8690),
		cfmMepAlreadyInUseWithOtherServiceType(8691),
		cfmNodalMipLevelOnPbtVlanNotAllowed(8692),
		cfmCannotAddOrRemoveNodalMipsWhenMipListIsEmptyOrInvalid(8693),
		cfmExceedMinCcmIntervalForClient(8694),
		cfmIfTlvOnClientAndVlanMepTypeOfPortOrMltOnly(8695),
		mepWithUnicastCcmOnIsidOrClientNotAllowed(8696),
		cfmLbmCannotSpecifyBothDataAndFrameSize(8697),
		cfmFrameSizeTooLargeForRmod(8698),
		cfmFrameSizeTooLargeForRCmod(8699),
		portInMltService(8701),
		mltPortShouldBeOpmOrRmod(8702),
		uniAlreadyConfiguredWithEsuRing(8703),
		cannotAddMltIfPerformTaggingDisabled(8704),
		cannotAddMltIfUniAggrMacIdxValueIsNotSet(8705),
		noPortsConfiguredForMlt(8706),
		onlyP2pConnectionTypeAllowedForMlt(8707),
	        	remoteMacAddressNotSpecifiedForMltEndpt(8708),
		entryCannotBeCreatedWithoutMep(8709),
		mepListEntryNotExist(8710),
		mepListEntryAlreadyExists(8711),
		entryCannotBeCreatedWithoutMip(8712),
		mipListEntryNotExist(8713),
		mipListEntryAlreadyExists(8714),
		portNumCannotBeChanged(8715),
		cfmExceedMinCcmIntervalOnMezz(8716),
		cfmExceedMinCcmIntervalForPbtTrunkOnMezz(8717),
		cfmExceedMinCcmIntervalOnCp(8718),
		cfmExceedMinCcmIntervalForPortOnCp(8719),
		cfmNoServiceAssociatedWithMepOrMip(8720),
		cfmMepNotReadyToSetLbm(8721),
		cfmMepNotOkToSetReady(8722),
		cfmMepNotReadyToSetLtm(8723),
		cfmMaCannotBeDeletedWhileRmepsExist(8724),
		saDaVlanHaveAlreadyBeenUsedByOtherTrunk(8725),
		cfmLbmExceedMaxMessagesLimit(8726),
		cfmCannotDoLtmOnNonVlanMep(8727),
		cfmExceedMaxCcmThroughPut (8728),
		sameLevelMepAlreadyAssignedToPortOrTrunkOnSamePort(8729),
		sameLevelMepAlreadyAssignedToVlanOrIsidEndptOnSamePort(8730),
		tlsRmodEndPtLimitExceededForPort(8731),
		tlsRmodEndPtLimitExceededForPorts1To10(8732),
		tlsRmodEndPtLimitExceededForPorts11To20(8733),
		tlsRmodEndPtLimitExceededForPorts21To30(8734),
		tlsRmodEndPtLimitExceededForPorts1To24(8735),
		tlsRmodEndPtLimitExceededForPorts25To48(8736),
		tlsRmodMacTableSizeOutOfRange(8737),
		tlsRmodMacTableLimitExceededForPort(8738),
		tlsRmodMacTableLimitExceededForPorts1To10(8739),
		tlsRmodMacTableLimitExceededForPorts11To20(8740),
		tlsRmodMacTableLimitExceededForPorts21To30(8741),
		tlsRmodMacTableLimitExceededForPorts1To24(8742),
		tlsRmodMacTableLimitExceededForPorts25To48(8743),
		tlsTdiMuxModeOnly16QtagsAreSupported(8744),
		noMepToBeAddedForMlt(8745),
		cfmOneMdPerServiceInstance(8746),
		tlsRmodMacTableOversubscribed(8747),
		cfmLbmTestPatternSizeError(8748),
		tlsEndptPolicingOptionSupportedOnlyOnRmod(8749),
		cfmMaxAllowedTrunkGroupsAlreadyCreated(8750),
		cfmPerLaneMaxTrunksAlreadyCreated(8751),
		canNotConfigPbtVlanForCfm(8752),
		cfmCannotDoLtmOnNonVlanPbtIsidClientMep(8753),
		mepListCannotHaveTwoMepsWithSameMdLevel(8754),
		mipListCannotHaveTwoMipsWithSameMdLevel(8755),
		noMepToBeAddedForRing(8756),
		noMepToBeAddedForDhRing(8757),
		tlsCannotHaveCvidClientMepWithOneToOneAndSwitchedService(8758),
		tlsCannotChangeToTransparentServiceWhenClientMepExist(8759),
		rttModeCannotHaveInterFrameInterval(8760),
		mltUniAggrMacWithMipModifyNotAllowed(8761),
		tlsTdiEndPtMacTableSizeNotSupportedOnRmodPort(8762), 
		noRMepToBeAddedForTrunkOrPort(8763),
		tlsTdiEndPtMacTableWaterMarkNotSupportedOnRmodPort(8764),
		tlsTdiEndPtLocalMacAgeTimerNotSupportedOnRmodPort(8765),
		tlsTdiEndPtRemoteMacAgeTimerNotSupportedOnRmodPort(8766),
		canNotConfigPlsbVlanForCfm(8767),
		cfmExceedMinCcmIntervalForClientVlan(8768),
		cannotCreateMipWithMepOnPort(8769),
		cannotCreateMepWithMipOnPort(8770),
		pbtPortCannotBeAddedToMltPerformTaggingDisabled(8771),
		cfmCannotDoLtmOnInactiveMeps(8772),
		cfmCannotDoLbmOnInactiveMeps(8773),
		cannotEnableDMcastWithoutDestBmac(8774),
		cannotDeleteAllDestBmacsWithDMcastEnableOnIsid(8775),
		noDestBMacsConfiguredForIsid(8776),
		cannotEnableMacSwapOnDMcastIsid(8777),
		cannotEnableDMcastOnEPWithoutIsidDMcastEnable(8778),
		noParameterChange(8779),
		cannotEnableDMcastOnP2PIsid(8780),
		cannotConfigureAnyMoreDestBmacs(8781),
		onlyTenEndpointsPerTdiAllowedOnRmodPortOrMlt(8782),
		cannotCreateMultipleEndptOnSamePortOnManyToOneIsid(8783),
		cannotCreateMultipleEndptOnPortWithServiceTypeTransparent(8784), 
		cannotCreateMultipleEndptOnSamePortOnManyToOneTdi(8785),
		lastSixBitsOfUniShouldBeUniqueForTdiEndptOnSamePortOrMlt(8786),
		endptIdZeroToNineForRmodulePortOrMlt(8787),
		cannotSetManyToOneWithLocalUniSwitchedEndptOnTdiOrIsid(8788),
		endptOnThisTdiOnThisPortAlreadyExists (8789),
		tlsRCmodEndPtLimitExceededForPorts1To2(8790),
		tlsRCmodEndPtLimitExceededForPorts3To4(8791),
		tlsRCmodEndPtLimitExceededForPorts5To6(8792),
		tlsRCmodEndPtLimitExceededForPorts25To26(8793),
		tlsRCmodMacTableLimitExceededForPorts1To2(8794),
		tlsRCmodMacTableLimitExceededForPorts3To4(8795),
		tlsRCmodMacTableLimitExceededForPorts5To6(8796),
		tlsRCmodMacTableLimitExceededForPorts25To26(8797),
		cannotEnableDMcastOnIsidWithMacSwapEnabledEndpt(8798),
		cannotEnableDMcastOnEndptWithMacSwapEnabled(8799),
		pwDoesNotExist(8801),
		pwExists(8802),
		pwChangedNotAllowedWhenEnable(8803),
		pwParamValueRemainsSame(8804),
		pwAttachmentPwDoesNotExist(8805),
		pwMissingPwId(8806),
		pwMissingGroupId(8807),
		pwMissingGroupAttachmentId(8808),
		pwMissingTAII(8809),
		pwEndPointExist(8810),
		pwEndpointVcLabelExists(8811),
		pwEndpointMissingInVcLabel(8812),
		pwEndpointMissingNextHopMac(8813),
		pwEndpointAlreadyConfigured(8814),
		pwEndpointCannotChangeSTMissingFields(8815),
		pwPwIdInUse(8816),
		pwEndpointQtagConflict(8817),
		pwMissingFields(8818),
		pwEndpointMuxModeConflict(8819),
		pwLabelExists(8820),
		pwEndpointVcLabelSvlanConflict(8821),
		pwEndpointMissingTrunkGroupName(8822),
		vcLabelOnlyAllowedConfigInMplsEndpt(8823),
		pwEndpointSupportedOnlyOnRmodule(8824),
		pwMplsEndpointCvlanOutOfRange(8825),
		pwEndpoint4096CvlanAndUntaggedMplsOnSamePortNotAllowed(8826),
		pwCannotSetVcLabelToZeroWhileMplsEndptStateEnable(8827),
		pwCannotSetNextHopMacToZeroWhileMplsEndptStateEnable(8828),
		pwEndpointMissingVcLabel(8829),
		pwMustUseSameLabel(8830),
		vrfDoesNotExist(8901),
		vrfAlreadyExists(8902),
		vrfMaxRoutesCouldNotBeSet(8903),
		vrfPortDoesNotBelongToSpecifiedVrf(8904),
		vrfVlanDoesNotBelongToSpecifiedVrf(8905),
		vrfLegacyPortCannotBeAddedToVlanAssociatedWithVrf(8906),
		vrfCannotChangeAssociationInterfaceExists(8907),
		vrfInvalidVrfId(8908),
		vrfOperationProhibitedForGrt(8909),
		vrfOspfLimitExceeded(8910),
		vrfRipLimitExceeded(8911),
		vrfDhcpLimitExceeded(8912),
		vrfVrrpLimitExceeded(8913),
		vrfRipDoesNotExist(8914),
		vrfOspfDoesNotExist(8915),
		vrfNameInvalid(8916),
		vrfNameDuplicate(8917),
		vrfRipAlreadyExists(8918),
		vrfOspfAlreadyExists(8919),
		vrfCannotAssociatePortInVlan(8920),
		vrfCannotAddAssociatedPortToVlan(8921),
		vrfCannotAssociateToVlanWithLegacyPorts(8922),
		vrfCannotAssociateToLegacyPortForBrouter(8923),
		vrfBgpDoesNotExist(8924),
		vrfBgpAlreadyExists(8925),
		vrfBgpLimitExceeded(8926),
		vrfConfigNeedsMezz(8927),
		invalidNextHopVrfName(8928),
		vrfCannotCreateVrfForNonTiger(8929),
		vrfCannotAssociateToIstVlan(8930),
                vrfOperationNotAllowed(8931),
		vrfPimLimitExceeded(8932),
		vrfPimDoesNotExist(8933),
		communityAlreadyExists(9101),
		communityDoesnotExist(9102),
		communityStorageTypePermanent(9103),
		defaultEntryNotDeletable(9104),
		invalidAccessPolicyStrict(9105),
		targetAddressNotExist(9106),
		cannotChangeCurrentAndDeprecatedMib(9107),
		invalidPath(9108),
                entryIsQuoted(9109),
		duplicateTargetAddress(9110),
		accessPolicyIsUsed(9111),
		portMirroringTxNotSupportForThisHardwareRevision(9301),
		cannotSetMode(9302),
		cannotSetFraming(9303),
		cannotModifyInLaneMode(9304),
		stpIsNotAllowedToBeEnabledOnIstPort(9305),
		mirroredPortSupportRXModeOnly(9306),
		secondaryCpuNotActive(9307),
		commandNotAllowedInPrimaryCpu(9308),
		pcapUserDefinedDataInConsistency(9309),
		pcapFilterTblEntryNotFound(9310),
		pcapFilterTblDuplicateEntry(9311),
		pcapBufferSizeExceedsMaximumRamLimit(9312),
		portPcapIsActive(9313),
		pcapCommandNotAllowedWhenPcapIsEnabled(9314),
		invalidNumberOfHexDigits(9315),
		commandNotAllowedInHaCpuMode(9316),
		pcapCommandNotAllowedIn3SlotChassis(9317),
		pcapNoMemoryAllocatedForPcap(9318),
		pcapCannotBeEnabledWhenAutosaveInProgress(9319),
		pcapInvalidTimerRangeValue(9320),
		commandNotAllowedOnSlave(9321),
		cannotSetPortAdminRouting(9322),
		smltNotAllowedObBrouterPort(9323),
		pcapOctapidNotInitialized(9324),
		pcapNoPackets(9325),
		pcapInsufficientDiskSpace(9326),
		pcapAutoSaveOrCopyCommandInProgress(9327),
		rmCommandNotAllowedWhenRemoteMirroringIsEnabled(9328),
		rmVlanNotPortBasedVlan(9329),
		rmPortNotMemberOfVlan(9330),
		rmSrcMacAddressNotSet(9331),
		rmRemoteMirroringActiveInOctapd(9332),
		rmRmtExceedsMaxLimit(9333),
		rmVlanIdNotSetForRmtPort(9334),
		rmDstMacNotSet(9335),
		rmPortDuplicateEntry(9336),
		rmPortEntryNotCreated(9337),
		invalidRxMirroringPort (9338),
		invalidTxMirroringPort (9339),
		invalidBothMirroringPort (9340),
		portIsBeingUsedForOtherSer (9341),
		portIsAlreadyConfigured (9342),
		commandNotSupport (9343),
		maxEgressMirroredPort (9344),
		portEapAuthorized(9345),
		invalidAdminDuplexSpeedCombo(9346),
		vplsMgmtVlanApplyToVplsPort (9347),
		repeaterDoesNotExist (9348),
		repeaterAlreadyExists (9349),
		repeaterIdOutOfRange (9350),
		repeaterPortNotPresent (9351),
		brouterPortCannotBeUsedAsRepeater (9352),
		portIsBeingUsedAsRepeaterPort (9353),
		vlanIsBeingUsed (9354),
		quoteNotAllowedInsideTheString (9355),
		duplicateName (9356),
		repeaterFirstAndSecondPortCannotBeSame (9357),
		repeaterPortCannotbeAssignedIp (9358),
		mltPortCannotBeRepeaterPort (9359),
		portIsRepeaterPort (9360),
		portIsNot8GELegacyPort (9361),
		portEapEnabled(9362),
		rateLimitingrmodPort(9363),
		bandwidthLimitingNonrmodPort(9364),
		egressRateLimitingNotAppToNonRModPort(9365),
		cannotSetAutoNegAd(9366),
		invalidAutoNegAdSpecified(9367),
		featureNotApplyToMixedMlt(9368),
		rateLimitingExistsForMlt(9369),
		differentPortConfigurationForMlt(9370),
		rModuleOnlyOneMirroredPortPerLane(9371),
		ieee8021pOverrideNotAppToNonRModPort(9372),
		portMirroringTxFilterNotSupportForThisHardwareRevision(9373),
		portIsDownOperationNotAllowed(9374),
		portSffdEnableError(9375),
		portTxFlowControlNotSupportedForThisHW(9376),
		portFcPause0NotSupportedForThisHW(9377),
		portFcPauseTimeNotSupportedForThisHW(9378),
		portEgressMirroringCountExceededOnCard(9379),
		slppInvalidTxInterval(9380),
		slppInvalidRxThreshold(9381),
		rmRemoteMirroringActiveInRspLane(9382),
		portEsmPortNotSupportedAsOutport(9383),
		portMandatoryParametersMissing(9384),
		portMirroredPortMissing(9385),
		portMirroringPortMissing(9386),
		portServerPortNotSupportedAsMirroredPort(9387),
		portIsNotMemberVoiceVlan(9388),
		repeaterPortCannotBeConfiguredWithoutVlan(9389),
		canConfigureMltPortQnqEtherTypeOnlyViaMltTable(9390),
		pvidFeatureIsSupportedOnRModuleOrEsmPortOnly(9391),
		topologyFeatureIsSupportedOnRModuleOrEsmPortOnly(9392),
		portShapeLimitExceededLineRate(9393),
	        cannotSetClockSource(9394),
		ingressPoliceNonRsPort(9395),
		customAutoNegAdvertNotSupported(9396),
		autoNegotiateIsDisable(9397),
		slppInvalidEtherType(9398),
 		canConfigureMltPortEgressCosProfileOnlyViaMltTable(9399), 
		recordReserveTypeInvalid(9401),
		recordReserveOutOfRange(9402),
		recordReserveExceedPhyLim(9403),
		cannotUpNonEticketCard(9404),
		cannotUpNon128KCard(9405),
		naapVlanNotConfigured(9406),
		lpMiniSlotNotPresent(9407),
		lpSlotDisabled(9408),
		lpSlotEnabled(9409),
		cannotUpNonEmmodeCard (9410),
		cannotUpNonRmodeCard (9411),
		cannotUpNonRspCard (9412),
		dnsDuplicateEntry(9413),
		dnsEntryNotFound(9414),
		dnsEntryNotCreated(9415),
		smartCpldNotSupported(9416),
		dnsEntryCantHaveBothIpv4AndIpv6Addr(9417),
                slotNotPresent(9418),
		rmodeRequired(9419),
		maxVlanDisallow(9420),
		extendedPingBypassChangeNotAllowedWhenEnabled(9421),
		extendedPingBypassAlreadyEnabled(9422),
		extendedPingBypassCannotEnableWithoutOUI(9423),
		snmpSetNotAllowedDuringControlledSoftwareUpgrade(9424),
                softwareLicenseViolation(9425),
                cpuActionNotAllowed(9426),
		resetOperNotAllowed(9427),
		cpuActionNotAllowedPwrPrio(9428),
		slotDualPortModeValidOnlyOnMambaCards(9429),
		slotModeInvalidIfPort26IsConfigured(9430),
		slotAlreadyRunningInThisMode(9431),
		operationAllowedOnlyFor8011coChassis(9432),
		operationNotAllowedFor8011coChassis(9433),
		switchFabricRedundancyDisabled(9434),
                ntpIncorrectKeyValue(9435),
                accessPolicyGroupNameInvalid(9436),
		tenGEMltPortCannotBeAddedToStgWithSMLT(9501),
		tenGEPortCannotBeAddedToStgWithSMLT(9502),
		stgCannotRemoveTlsEndPointPortMember (9503),
		rstpInvalidVal (9504),
		mstpInvalidVal (9505),
		invalidMask (9506),
		bpduMacAddressRangeInUse (9507),
		bpduMacAddressRangeNotConfigured (9508),
		bpduMacAddressNotInConfiguredRange (9509),
		priorityValueMustBeAMultipleOf4096 (9510),
		valueMustBeAMultipleOf100 (9511),
		mstpCannotSetPriorityBeforeCreatingMstiBridge (9512),
		commandIsNotSupportedForMltPort (9513),
		switchIsNotInRstpMode (9514),
		switchIsNotInMstpMode (9515),
		portPriorityvalueMustBeAMultipleOf16 (9516),
		portIsNotAMemberOfThisMsti (9517),
		onlyDefaultInstanceSupportedInRstpMode (9518),
		maxAgeMustEqualOrGreatThan2XForwardDelayMinus1Second (9519),
		maxAgeMustEqualOrGreatThan2XPortHelloTimePlus1Second (9520),
		pbtStgCannotEnableStp(9521),
		pbtMstpInstanceAllowedOnlyInMstpMode(9522),
		pbtStgInstanceCannotBeRemovedWhenPbtVlanExists(9523),
		stgInstanceCannotBeSetToPbtType(9524),
		plsbModeStgCannotEnableStp(9525),
		invalidValueGivenToSTG(9526),
                invalidMstpRstpInstance(9527),
		pbtmstiCannotEnableForceportState(9528),
		maxAgeMustEqualOrLessThan2XForwardDelayMinus1Second(9529),
		mstiForceporCannotBeEnabledWhenCistForceportIsDisable(9530),
		protocolMigrationCannotBeSetIfForceportstateIsDisabled(9531),
		protocolMigrationCanBeSetOnlyForForceVersionRstpOrMstp(9532),
		vlanMstiMappingCannotBeChangedAsVlanExistsDeleteVlan(9533),
		mappingExistsForVlanUnmapVlanFirst(9534),
		mappingExistsForInstanceUnmapVlansFirst(9535),
		plsbMstpInstanceAllowedOnlyInMstpMode(9536),
		plsbStgInstanceCannotBeRemovedWhenPlsbVlanExists(9537),
		stgInstanceCannotBeSetToPlsbType(9538),
		plsbMstiCannotEnableForcePortState(9539),
		ospfOverlappingSummarizedRange(9601),
		ospfTeReservableBandwidthCannotBeBiggerThanMaxBandwidth(9602),
		ospfTeMaxBandwidthCannotBeSmallerThanReservBandwidth (9603),
		pcapBufferSetFail (9604),
		ospfHelloIntNotGreatDeadInt(9605),
                		invalidSetTrapValue(9606),
                		invalidRouterId(9607),
		cluserInvalidId (9901),
		clusterDoesNotExist (9902),
		clusterAlreadyExists (9903),
		clusterSizeExceeded (9904),
		invalidMiniSlot (9905),
		clusterIdMandatory (9906),
		brouterOpNotAllowedOnIsdPort (9907),
		removeVlanBeforeDeletingCluster(9908),
		mplsRouterIdLdpRsvpEnabled(10001),
		mplsInvalidDeleteOperation(10002),
		mplsInvalidInterfaceState(10003),
		mplsInterfaceNotExist(10004),
		mplsInvalidInterfaceMtu(10005),
		mplsExplicitPathInUse(10006),
		mplsTunnelInUse(10007),
		mplsTunnelNoDest(10008),
		mplsTunnelResourceInUse(10009),
		mplsMezzCardAbsent(10010),
		mplsLdpNotReady(10011),
		mplsRsvpNotReady(10012),
		mplsRouterIdSetToZero(10013),
		mplsInterfaceVlanNotFound(10014),
		mplsPortNotRModule(10015),
		mplsIpAddrInUse(10016),
		mplsTunnelNotFound(10017),    
		mplsTunnelNotAllLspUp(10018),  
		mplsInvalidIndex(10019),
		mplsExplicitPathExists(10020),
		mplsExplicitPathHopExists(10021),
		mplsExplicitPathIndexExists(10022),
		mplsMaxIndex(10023),
		mplsInvalidPathOptionIndex(10024),
		mplsLspExists(10025),
		mplsInvalidLspInstance(10026),
		mplsLspNoName(10027),
		mplsLspNoEPName(10028),
		mplsLspEPNotFound(10029),
		mplsConfigNeedsMezz(10030),
		mplsExpPathIpv4AddrTypeOnly(10031),
		mplsExpPathNoNameChange(10032),
		mplsLspNoNameChange(10033),
		mplsSrcIpNonLocal(10034),
		mplsLspIndexUsed(10035),
		mplsLspNameUsed(10036),
		mplsLspNotActive(10037),
		mplsTunnelSameSrcDest(10038),
		mplsLspNotSameSrc(10039),
		mplsLspNotSameDest(10040),
		mplsTunnelNoALtPath(10041),
		mplsTunnelCfgIngressOnly(10042),
		mplsTunnelInvalidIndex(10043),
		mplsEPInvalidIndex(10044),
		mplsEPHopInvalidIndex(10045),
		mplsResInvalidIndex(10046),
		mplsInvalidLdpKeepAliveRange(10047),
		mplsInvalidLdpHelloHoldTimeRange(10048),
		mplsRsvpAdminGroupExists(10049),
		mplsRsvpAdminGroupDoesNotExist(10050),
		mplsRsvpAdminGroupNameInUse(10051),
		mplsLdpEntityExists(10052),
		mplsLdpEntityDoesNotExist(10053),
		mplsLdpEntityTargetPeerExists(10054),
		mplsLdpEntityParamRemainsSame(10055),
		mplsLdpEntityTargetPeerInvalid(10056),
		mplsLdpEntityTargetPeerNotConfigured(10057),
		cannotConfigRingPortOnLaneWithNonOePort(10101),
		ringWithRrpHelloEnableExceedLimit(10102),
		ringWithMinimumRrpHelloIntervalExceedLimit(10103),
		cannotConfigRingBetweenPrAndEsmCards(10104),
		canOnlyConfigRingOn8630GBRCardIfPr(10105),
		cannotConfigNonOePortOnLaneWithRingPort(10106),
		cannotConfigRingPortOnLaneWithLocalUniPort(10107),
		canNotConfigLocalUniPortOnLaneWithRingPort(10108),
		esmPortCannotBeNonUni(10109),
		portInEvpnCannotBeNonUni(10110),
		legacyPortCannotBeUni(10111),
		portShouldBeUniForEvpnEndPoint(10112),
		premiumTBSizeTooLargeForRate(10113),
		goldTBSizeTooLargeForRate(10114),
		silverTBSizeTooLargeForRate(10115),
		standardTBSizeTooLargeForRate(10116),
		mcastTBSizeTooLargeForRate(10117),
		ringNot10gRing(10118),
		ringBroadcastMappingNotExist(10119),
		ringBroadcastMappingAlreadyExist(10120),
                cannotRemoveBcastMappingWhenRingWithEndptUnderEvboEnabledIsid(10121),
                cannotRemoveBcastMappingWhenRingWithEndptUnderCustIpVlan(10122),
		stpCannotBeEnabledOnRingPort(10123),
		cannotAddEnhDHRSecondaryPortToVlanWithCustIpVlanOnIt(10124),
		cannotConfigRingOn8648GBRCardIfPr(10125),
		cannotConfigStandaloneOn8648GBRCardIfPr(10126),
		mltInEvpnCannotBeNonUni(10127),
		mltShouldBeSetToUniForEvpnEndPoint(10128),
		invalidCustIpVlanOn10gRing(10129),
		ipvpnCreateFailed(10201),
		ipvpnDeleteFailed(10202),
		ipvpnAlreadyEnabled(10203),
		ipvpnNotEnabled(10204),
		ipvpnNotSupportedOnDefVRF(10205),
		ipvpnSameRDConf(10206),
		ipvpnInvRDConfOnDefVRF(10207),
		ipvpnInvRDTypeNotSupported(10208),
		ipvpnInvRTConfOnDefVRF(10209),
		ipvpnInvRTTypeNotSupported(10210),
		ipvpnSVCAllocFailed(10211),
		ipvpnSVCILMAddFailed(10212),
		ipvpnLiteSupportOnlyType1(10213),
		ipvpnRDTypeNotSupportedWithLite(10214),
		ipvpnSvcLblChngIfIpvpnDisabledInVRF(10215),
		ipvpnSvcLblOptionAlreadySetInIpvpnVRF(10216),
		ipvpnPeerRRLiteModeConflict(10217),
		ipvpnPeerGroupRRLiteModeConflict(10218),
		ipvpnImplicitReflectInMixedLiteMode(10219),
		ipvpnInvalidPeerSetForAccessPeer(10220),
		ipvpnRouterInNonLiteRRMode(10221),
		ipvpnRouteTargetNotFound(10222),
		bgpOperationNotAllowedWhenDefaultBgpIsEnabled(10223),
		bgpOperationNotAllowedWhenVrfBgpIsEnabled(10224), 
		bgpInvalidLocalAsWhenVrfPeerRemoteAs(10225),		
		bgpInvalidVrfPeerRemoteAs(10226),
		bgpInvalidVrfPeerGroupRemoteAs(10227),
		ipvpnLiteRequiresVpnv4(10228),
		ipvpnVpnv4DisableRequiresLiteDisable(10229),
		ipvpnEnabledWithoutLocalAs(10230),
		ipvpnInterVrfRedistEnable(10231),
		bgpOperationNotAllowedWhenIpvpnIsEnabled(10232),
		ipvpnInvalidAssignedNumber(10233),
		ipvpnInvalidAsNumber(10234),
		ipvpnInvalidPeerSetForExternalPeer(10235),
		ipvpnInvalidPeerGroupSetForExternalPeer(10236),
		ipvpnMaxRtPerVrfExceeded(10237),
		ipvpnRdOverlapOperNotAllowed(10238),
		ipvpnNotCreated(10239),
		ipvpnAlreadyCreated(10240),
		ipvpnLiteRequiresValidIpAddressInRd(10241),
		ipvpnLiteOperationNotAllowedSameIpConfiguredAsRdInAnotherVrf(10242), 
		ipvpnRDInvalidCircuitlessIP(10243),
		ipvpnRDIpNotLiteEnabled(10244),
		ipvpnLiteSupportRDWithClipIp(10245),
		ipvpnLiteSupportOnlyLiteEnabledRDIP(10246),
	        ipvpnEnableDisallowedWithoutValidRD(10247),
                ipvpnLiteRDIpConfiguredInMultipleVrf(10248),
		customAutoNegAdvMacPauseNotSupported(10301),
		customAutoNegAdvAsymPauseNotSupported(10302),
		highSecureModeNotAllowedOnRepeaterPort(10303),
		repeaterPortCannotBeSetOnHighSecureModePort(10304),
		featureSupportedOnRModOrLegacyPort(10305),
		mirrorDestinationNotEntered(10306),
		mirrorLegacyCannotSupportPortList(10307),
		mirrorMltShouldHavePortsAssigned(10308),
		mirrorDestinationNotAttached(10309),
		mirrorDisableEntry(10310),
		mirrorDestinationAlreadyAttached(10311),		
		lldpMedCapabilityTlvMandatory(10312),
		mirrorLegacyCannotSupportVlanOrMlt(10313),
		mirrorDestAlreadyAttachedOrDestSpecifiedNotAttached(10314),
		enhancedRingOnlySupportRModule(10315),
		enhancedRingEndpointsShouldBeDeleted(10316),
		enhancedRingEsuHomeNotConfigured(10317),
		oel2NotSupportedForRCModules(10318),
		cannotConfigureIpToPortInVlanZero(10319),
		portInterfaceTypeCannotBeSilent(10320),
		cannotChangePortInterfaceTypeToSilent(10321),
		cannotAddSilentPortToMlt(10322),
		cannotAddNormalPortToUniMlt(10323),
		cannotSetBroutePortInterfaceTypeToUni(10324),
		onlyNormalPortAllowedToBeIbtPort(10325),
		onlyMltWithNormalPortAllowedToBeIbtMlt(10326),
		onlyNormalPortAllowedToBeRctPort(10327),
		onlyMltWithNormalPortAllowedToBeRctMlt(10328),
		ringIbtOrRctPortInterfaceTypeOnlyCanBeSetToNormal(10329),
		noAdminSettingForSpeed1000(10330),
		portAlwaysRunAt10GSpeed(10331),
		rmodOnlyOneMirroredPortPerLaneForEgress(10332),
		mirrorTxFilterModeNotAllowedOnRsmod(10333),
		mirrorModeNotValidForRmodRSmod(10334),
		portMirroringTxNotSupportForDiffservPort(10335),
		invalidDiffServEnableDueToMirroring(10336),
		invalidDiffServTypeDueToMirroring(10337),
		cannotSetAdminSpeed1000AsPerIEEE(10338),
		slppCannotBeEnabledOnIstPorts(10339),
		slppEnabledPortsCannotBePartOfIst(10340),
		rctVidCannotBeSetWithoutRctPort(10341),
		onlyUniPortAllowedToBeRingPort(10342),
		oel2NotSupportedForEnhancedDHRing(10343),
		portWithUniInterfaceTypeCannotBeAssignedIp(10344),
		brouterPortCannotBeUsedAsUniPort(10345),
		controlPktRateLimitSupportedOnlyForRandRCmoduleCards(10346),
		dropRateLimitCannotBeChangedWhenRateLimitStateIsEnabled(10347),
		shutdownRateLimitCannotBeChangedWhenItsStateIsEnabled(10348),
		cannotEnableControlPktRateLimitOnNonUniInterfaceTypes(10349),
		controlPktRateLimitNotSupportedForRingOrSAports(10350),
		shutdownLimitMustBeGreaterThanOrEqualToDropLimit(10351),
		cannotCreateRingOrSAOnPortsWithCtrlPktRateLimitEnabled(10352),
		ctrlPktDropLimitAlreadyEnabled(10353),
		ctrlPktShutdownLimitAlreadyEnabled(10354),
		portTypeMustBeUniForRateLimitEnabledPorts(10355),
		cannotEnShutdownLimitWithoutEnDropLimit(10356),
		dropLimitDisabledWithSameValue(10357),
		dropLimitAlreadyDisabled(10358),
		dropLimitCannotBeDisabledWhenShutdownLimitIsEnabled(10359),
		shutdownLimitDisabledWithSameValue(10360),
		shutdownLimitAlreadyDisabled(10361),
		shutdownLimitCannotBeEnWhenDropLimitIsDisabled(10362),
		canAddClientMepOnlytoEndpointwithEpIdZero(10401),
		canConfigUserMacOnlyOnAnIsidWithAny2AnyEps(10402),
		tlsCannotSetMulticastMacAddrAsDestBmacForIsid(10403),
		tlsVideoMpAclExists(10404),
		tlsCannotChangeIsidVideoType(10405),
		tlsMaxVideoIsidsConfigured(10406),
		tlsMaxTargetIsidsConfigured(10407),
		tlsVideoMpAclNotVideoIsid(10408),
		tlsVideoMpAclNotTargetIsid(10409),
		tlsVideoMpAclAlreadyExists(10410),
		tlsMaxVideoMpAclsConfigured(10411),
		tlsVideoMpAclDoesNotExist(10412),
		cannotSetConnTypeP2POnDMcastIsid(10413),
		cannotEnableDMcastOnIsidWithPvidConfigured(10414),
		tlsAllowedGrpNotMulticastAddress(10415),
		tlsCannotCreateNonZeroEndptIdForIPTV(10416),
		tlsVideoMpAclExistsForTargetIsid(10417),
		tlsCannotConfigVideoAndTargetIsidEpsOnSameLane(10418),
		tlsCannotConfigPvidIfDMcastEnableOnEndpt(10419),
		tlsAllowedGrpsExceedsRange(10420),
		tlsCannotEnableSnoopWhenVboDisabled(10421),
		tlsIptvEvpnBoNotEnabled(10423),
		canAddMipOnlytoEndpointwithEpIdZero(10424),
		endpointIdCanBeZeroToThirtyOneForRcModulePort(10425),
		mipSupportedOnlyOnRmod(10426),
                mepSupportedOnlyOnRmod(10427),
		portMdLevelLowerThanClientOnSamePort(10428),
		tlsCannotEnableDirectedMcastOnRcmodule(10429),
                mltSupportedOnlyOnRmod(10430),
		mepmipSupportedOnlyOnMltwithPort(10431),
		cannotDeleteMltWithMipMep(10432),
		tlsIsidIgmpEvpnBoNotEnabled(10433),
		tlsCannotEnableProxyWhenSnoopDisabled(10434),
		tlsCannotChangeVideoMpAclWhenSnoopEnabled(10435),
		tlsIgmpAclAlreadyExists(10436),
		tlsIgmpstaticEntriesAlreadyExists(10437), 
		tlsCannotDelPrefixListAssociatedWithMPAcl(10438),
		tlsCannotDelPrefixListAssociatedWithIgmpAcl(10439),
		tlsCannotDelPrefixListAssociatedWithIgmpStaticEntries(10440),
		tlsIsidIgmpZeroMrouterBmac(10441),
		cfmCannotAbortWhenNoLtmInProgress(10442),
		esmMltCannotBeNonUni(10443),
		tlsCannotEnableDhcpL2RelayOn10GRingEndPoint(10444),
		cannotCreateAnotherEndptOnPortWithServiceTypeTransparent(10445),
		cfmCannotAbortWhenNoLbmInProgress(10446),
		tlsExceededMrouterBmacLimit(10447),
		cfmIngressRateLimitCannotBeChangedWhenItsStateIsEnabled(10448),
		cfmIngressRateLimitAlreadyEnabled(10449),
		cfmEgressRateLimitCannotBeChangedWhenItsStateIsEnabled(10450),
		cfmEgressRateLimitAlreadyEnabled(10451),
		cfmIngressRateLimitAlreadyDisabled(10452),
		cfmEgressRateLimitAlreadyDisabled(10453),
		cfmRateLimiterCannotBeEnabledOnEndptWithNoClientMepMip(10454),
		dhuCanOnlyBeAssociatedWithPlsbControllerIsid(10455),
		plsbControllerIsidCannotHaveEndpt(10456),
		removeDhuAssociationBeforeDisablePlsbOnIsid(10457),
                cfmOnlyP2pConnTypeAllowedForY17OnMltEp(10458), 
		bgpInvalidPeerSetWhenVpnv4Enabled(10501),
		bgpInvalidPeerGroupSetWhenVpnv4Enabled(10502),
		bgpOverlappingAggregateAddress(10503),
		bgpInvalidLocalAsWhenPeerRemovePrivateAsEnabled(10504),
		bgpInvalidPeerRemovePrivateAsEnableWithoutRemoteAs(10505),
		bgpInvalidPeerGroupRemovePrivateAsEnableWithoutRemoteAs(10506),
		bgpDuplicatePeerNotAllowed(10507),
		bgpPeerDoesNotBelongToPeerGroup(10508),
		bgpOperationNotAllowedWhenRouteReflectorClientIsEnabled(10509),
		bgpInvalidAggregateAdvertisePolicyWithoutAsSetGenerate(10510),
		bgpDuplicatePeerGroupIndex(10511),
		bgpInvalidPeerDefaultOriginateIpv6(10512),
		bgpInvalidPeerGroupDefaultOriginateIpv6(10513),
		bgpInvalidPeerIpv6Capability(10514),
		bgpOperationNotAllowedForIpv6Peer(10515),
		bgpOperationNotAllowedForIpv6PeerGroup(10516),
		bgpOperationNotAllowedWhenOutboundMapsAreDifferent(10517),
		bgpOperationNotAllowedWhenInboundMapsAreDifferent(10518),
		maxPeerEntriesInPeerGroup(10519),
		opmPortCannotBeAssignedToRctPort(10601),
		rctPortNotPresent(10602),
		esuDhRingRctPortOrMltNotConfig(10603),
		ringOnlyCanBeConfigEitherRctPortOrRctMlt(10604),
		rctVidCannotBeDefaultVlan(10605),
		ringCannotBeEnabledWithoutRctVid(10606),
		ringCannotBeEnableddWhileRctMltHasNoPort(10607),
		mltPerformTaggingIsDisabledRct(10608),
		ringOrRctPortMustBePerformTaggingEnabled(10609),
		cannotDisableRctPortPerformTagging(10610),
		cannotDeleteRctMlt(10611),
		removeVlanIdFromThisRingVlanListBeforeAssignItAsRctVid(10612),
		vlanIsBeingUsedAsRctVlanForThisRing(10613),
		cannotDirectlyAssignMltPortAsRctPort(10614),
		cannotDeleteRingRctVlan(10615),
		cannotRemoveRingPortOrRctPortFromRctVlan(10616),
		vlanCannotRemoveRctMltPortMembers(10617),
		ringCanNotEnableWithoutPort(10618),
		macTableSizeTooLargeForRModule(10619),
		macTableSizeExceedsRModuleLimits(10620),
		tlsCopyItagToStagCanBeEnabledOnlyForQnqEndpoint(10621),
		ringPortAndRctPortCannotBeSame(10622),
		copyBtagPbitsStateCannotBeModifiedWhenStateEnable(10623),
		copyBtagPbitsStateCannotBeModifiedWithoutPort(10624),
		localUniSwitchingSupportedOnlyOnRModule(10625),
		cvidToBvidMappingIsNotSupportedOnRCModule(10626),
		ringInvalidEsuModIdOnNon10GRing(10627),
		ringOnly10GDHRingSupportQinQ(10628),
		isidNoOverlappedQtagForIgmpSnooping(10629),
		isidEndpointSameServiceTypeWithVboEnabled(10630),
		ringBroadcastGroupCannotBeSetForBothIsidAndCustIpVlan(10631),
		ringNotAllowedOnDualPortModeCard(10632),
		ringBroadcastMappingNotCreated(10633),
		cardModeCannotChangeWithRing(10634),
		tenGRingOnlySupportedOnRCModule(10635),
		tlsSwitchedEndPointQtagInvalidOn10GWhenIgmpSnoopEnabled(10636),
		isidQinqEndPointSVlanInvalidOn10GWhenIgmpSnoop(10637),
		qinqRingEndPointOnlySupportedOnRCModule(10638),
		commandNotSupportedOn10GRing(10639),
		cannotSetDualPortModeOnLinkOamConfiguredPort(10640),
		custIpVlanNotSupportedOnDualHomeRing(10641),
		plsbDeleteIntfBeforeSetPlsbFlag(10701),
		plsbDeletePlsbInstanceBeforeSetPlsbFlag(10702),
		plsbDeleteManualAreaBeforeSetPlsbFlag(10703),
		plsbDeleteSummaryAddrBeforeSetPlsbFlag(10704),
		plsbDisableIsisBeforeSetPlsbFlag(10705),
		plsbDeletePlsbVlanBeforeSetPlsbFlag(10706),
		plsbCannotConfigPlsbInNonplsbMode(10707),
		commandValidOnlyIfInRmode(10708),
		cannotAssociateMoreThan5000IsidToPlsbInstance(10709),
		globalPlsbAlreadyEnabled(10710),
		cannotEnablePlsbWithMmrpConfiguration(10711),
		cannotHaveSameBvlanAsSpIpVlanRCModPort(10712),
		cannotAddRcModPortsToMltWhenSpIpVlanSameAsBvlan(10713),
		cannotConfigPlsbIsisSmltistIntfOnSameIntf(10714),
		plsbDisableAllIsisEndpointsBeforeTogglePlsbState(10715),
		cannotConfigPortInSmltOrIstForPlsbVlan(10716),
		msdpInconsistentRowStatus(10801),
		msdpInvalidRPAddress(10802),
		msdpRPAddressNotLocalAddress(10803),
		msdpPeerTableInvalidLocalAddress(10804),
		msdpNotLocalAddress(10805),
		msdpLocalAddressPeerEstablished(10806),
		msdpPeerCreated(10807),
		msdpInconsistentPeerRowStatus(10808),
		msdpPeerNotFound(10809),
		msdpInvalidConnectRetryPeriod(10810),
		msdpHoldTimePeerEstablished(10811),
		msdpInvalidHoldtimePeriod(10812),
		msdpKeepAliveTimePeerEstablished(10813),
		msdpPeerKeepAliveInvalid(10814),
		msdpDataTTLInvalid(10815),
		msdpEncapsulationTypeNotSupported(10816),
		msdpPeerSARouteMapNameLenInvalid(10817),
		msdpPeerSAFilterPolicyNotFound(10818),
		msdpInvalidDescriptionLength(10819),
		msdpInvalidSALimit(10820),
		msdpInvalidMD5AuthStatus(10821),
		msdpInvalidPeerSetWhenPeerIsEnabled(10822),
		msdpInvalidPeerAddress(10823),
		msdpInvalidMD5AuthPasswordLength(10824),
		msdpInvalidASnumber(10825),
		msdpPeerNotConfigured(10826),
		msdpInvalidDefaultPeerRouteMapNameLength(10827),
		msdpDefaultPeerRoutePolicyNotFound(10828),
		msdpInvalidRedistributeRouteMapNameLength(10829),
		msdpRedistributeRoutePolicyNotFound(10830),
		msdpInvalidMeshGroupNameLength(10831),
		msdpPeerAlreadyConfiguredInMeshGroup(10832),
		msdpPeerNotFoundInMeshGroup(10833),
		msdpInconsistentPeerAdminStatus(10834),
		msdpInconsistentDefaultPeerStatus(10835),
		msdpInconsistentRedistributeRowStatus(10836),
		msdpInconsistentMeshGroupRowStatus(10837),
		msdpInvalidPeerAddressInMeshGroup(10838),
		msdpDefaultPeerAlreadyCreated(10839),
		msdpPeerSAFilterNotFound(10840),
		msdpGlobalGrpRedistributeNotFound(10841),  
		msdpPeerSAFilterAlreadyCreated(10842),
		msdpGlobalGrpRedistributeAlreadyCreated(10843),
		msdpInterfaceNotUp(10844),
		msdpPeerConfigurePassword(10845),
		msdpPeerControlCharNotAllowed(10846),
		msdpPeerCannotDeleteNonExistingPasswd(10847),
		mmrpCannotCoexistWithPlsb(10901),
		mmrpOnSuperMezzOnly(10902),
		mmrpAndPbtCannotBeOnSameVlan(10903),
		mmrpRequiresMstpMode(10904),
		mmrpNotSupportedOnThisCardType(10905),
		mmrpAlreadyEnabledOnVlan(10906),
		mmrpPortMustBeVlanMember(10907),
		mmrpJoinTimerOutOfRange200to600DivBy10(10908),
		mmrpLeaveTimerOutOfRange500to1400DivBy10(10909),
		mmrpLeaveTimerIs2timesJoinTimerPlus6timesResolutionOf10(10910),
		mmrpLeaveAllIs10xLargerThanLeaveTimer(10911),
		mmrpLeaveAllOutOfRange10000to150000OrNotDivBy10(10912),
		mmrpPeriodicOutOfRange800to1500orNotDivisibleBy10(10913),
		mmrpControlPacketPBitOutOfRange(10914),
		mmrpAlreadyDisabledOnVlan(10915),
		mmrpRequiresMmrpToBeEnabledOnVlan(10916),
		l2cpMacBlockInvalidAddrRange(10917),
		l2cpMacBlockAlreadyExists(10918),
		l2cpMacBlockDoesNotExist(10919),
		l2cpProfileDoesNotExist(10920),
		l2cpProfileAlreadyExists(10921),
		l2cpProfileRuleAlreadyExists(10922),
		l2cpProfileRuleDoesNotExist(10923),
		l2cpProfileRulePriorityValidOnlyForExpediteAction(10924),
		cannotDeleteL2cpMacBlkUsedByProfile(10925),
		endptL2cpProfileRuleNotAssociatedWithMacBlock(10926),
		cannotDeleteL2cpProfileAssociatedToEndpoint(10927),
		cannotAssignL2cpMacBlkAsStartOrEndMacAddrIsZero(10928),
		profileHasNoRuleOrAnyRuleHasNoMacBlkAssociated(10929),
		l2cpMacBlockOnlyMulticastMACAddrAllowed(10930),
		endpointL2cpProfileDoesNotHaveAnyRule(10931),
		cannotChangeOrDeleteDefaultL2cpProfile(10932),
		l2cpProfileNameCannotBeEmpty(10933),
		tlsTdiEndptL2cpProfileNotSupportedOnESMPort(10934),
		bpduTrafficNotSupportedWithL2cpProfile(10935),
		cannotDeleteLastRuleWhenProfileAssociatedWithEndpoint(10936),
		cannotChangeMgmtIsidStateIfEndptStateEnabled(10937),
		cannotConfigureMgmtIsidOnRmod(10938),
		cannotSetZeroMacForMgmtIsid(10939),
		cannotSetZeroIpForMgmtIsid(10940),
		mgmtIsidSupportedOnlyOnQnq1AndTransparentServiceType(10941), 
		mgmtIsidSupportedOnlyOnAnyToAnyConnectionType(10942),
		toEnableMgmtIsidMuxModeMustBeOneToOne(10943),
		cannotChangeSrcMacIfEndPtEnabled(10944),
		cannotSetMulticastMacAddressForMgmtIsid(10945),
		cannotChangeSrcMacIfMgmtIsidStateEnabled(10946),
		cannotChangeSrcIpIfEndPtEnabled(10947),
		cannotSetMulticastIpForMgmtIsid(10948),
		cannotChangeSrcIpIfMgmtIsidStateEnabled(10949),
		cannotChangeMuxModeIfMgmtIsidEnabled(10950),
		cannotDeleteEndPtIfMgmtIsidEnabled(10951),
		cannotChangeOuterQtagIfMgmtIsidEnabledForQnq1(10952),
		cannotChangeServiceTypeIfMgmtIsidEnabled(10953),
		cannotChangeConnectionTypeIfMgmtIsidEnabled(10954),
		localUniSwitchingNotSupportedForNidEpForSameIsidSamePort(10955),
		onlyTwoEndPtCanBeConfiguredOnPortWithMgmtIsidEnabled(10956),
		cannotConfigureMoreThan100MgmtIsidEndPtOnTheSamePort(10957),
		cannotHaveTwoMgmtEndPtOnSamePortForServTypeTransparent(10958),
		cannotHaveTwoMgmtEndPtOnSamePortSameSvlanForServTypeQnq1(10959),
		cannotEnableAnotherIsidEpOnSamePortForServTypeTrans(10960),
		dataIsidEndptAlreadyExistsOnSamePortWithSameSvlan(10961),
		cannotAddRmodPortForMltEpIdGreaterThanNine(10962),
		bpduTrafficSupportedOnESMOnlyOthersUseL2cpProfile(10963),
		invalidL2cpProfileName(10964),
		mgmtSrcMacIsAlreadyConfiguredOnOtherEndpointOnSameIsid(10965),
		olcStatusEnabled(11001),
		olcStatusDisabled(11002),
		olcInvalidModuleId(11003),
		olcInvalidThreshold(11004),
		olcInvalidStatus(11005),
		olcInvalidHoldDownPeriod(11006),
		olcInvalidSamplePeriod(11007),
		olcActionRuleDoesNotExist(11008),
		olcActionRuleEnabled(11009),
		olcActionRuleStatusInvalid(11010),
		olcActionRuleInvalid(11011),
		olcActionRuleInvalidAction(11012),
		olcActionRuleInvalidHoldDownStatus(11013),
		olcMaxActionRule(11014),
		olcActionRuleConditionExists(11015),
		olcActionRuleInvalidCondition(11016),
		olcActionRuleConditionDoesNotExist(11017),
		olcActionRuleMaxCondition(11018),
		olcActionRuleInvalidSuspendProtocol(11019),
		dhcpDhcpSnGlobalDisabled(11101),
		dhcpPortBelongToDhcpSnDisabledVlan(11102),
		dhcpPortBelongToDaiDisabledVlan(11103),
		dhcpPortIsDhcpSnTrusted(11104),
		dhcpPortIsDaiTrusted(11105),
                		dhcpIpsgEnabledOnDaiVlanMember(11106), 
               		 dhcpIpsgEnabledOnDaiUntrustedPort(11107),
                		dhcpMltPortDifferentDhcpSnType(11108),
                		dhcpMltPortDifferentDaiType(11109), 
                		dhcpMltPortDifferentIpSourceGuardType(11110),
                		dhcpMltPortDifferentDhcpSnDaiType(11111),
                		dhcpIpsgEnabledOnSomePorts(11112),
                		dhcpIpsgEnabledOnDhcpSnVlanMember(11113), 
                		dhcpIpsgEnabledOnDhcpSnUntrustedPort(11114), 
                		dhcpFailDhcpSnEnableOnSsaVlan(11115),
                		dhcpFailDaiEnableOnSsaVlan(11116),
                		dhcpFailIpsgEnableOnSsaPort(11117),
                		dhcpNotEnoughIpFilterResource(11118),
                		dhcpNotEnoughNonIpFilterResource(11119), 
		dhuNodeDoesNotExist(11201),
		dhuWrongAdminState(11202),
		dhuWrongRowState(11203),
		dhuShouldBeSetToDisable(11204),
		dhuNodeAlreadyExists(11205),
		dhuPortNotConfigured(11206),
		dhuRctVlanIdNotConfigured(11207),
		dhuPartnerMACNotConfigured(11208),
		dhuOrRingIdAlreadyUsed(11209),
		dhuIsidBVlanDoesNotExist(11210),
		dhuEndPointExist(11211),
		dhuCannotChangeParam(11212),
		dhuServiceTypeCannotBeTransparentForDhuEndpoints(11213),
		dhuNodeInUseByAccessMSTP(11214),
		dhuEndpointSVLANNotDefinedInMSTI(11215),
		dhuEndpointCVLANNotDefinedInMSTI(11216),
		dhuPortOnlyOnRCModule(11217),
		dhuPortNotAvailable(11218),
		dhuControllerMepNotConfigured(11219),
		dhuControllerMepAlreadyConfigured(11220),
		dhuInvalidControllerMepConfigured(11221),
		dhuControllerMepTypeNotSupported(11222),
		dhuNoNeedtoConfigurePortMepAsControllerMep(11223),
		dhuLimitedTo3Meps(11224),
		dhuAssociatedWithPlsbControllerIsid(11225),
		accessMstpDoesNotExist(11301),
		accessMstpAlreadyCreated(11302),
		accessMstpMstiDoesNotExist(11303),
		accessMstpMstiAlreadyCreated(11304),
		accessMstpMstiAlreadyConfigured(11305),
		accessMstpMstiNotConfigured(11306),
		accessMstpMstiVlanAlreadyConfigured(11307),
		accessMstpMstiVlanMustBeConfigured(11308),
		accessMstpMaxCist(11309),
		accessMstpMaxMsti(11310),
		accessMstpMaxDHU(11311),
		accessMstpNoDHU(11312),
		accessMstpNoMsti(11313),
		accessMstpDhuDoesNotExist(11314),
		accessMstpDhuAlreadyCreated(11315),
		cfmLbmFrameTooSmall(11401),
		cfmLbmExceedsChassisMtu(11402),
		cfmLbmExceedsUniPortMtu(11403),
		vlanMepExistsOnDhuPort(11404),
		cfmValidateControllerMepFailed(11405),
		cfmNodalMepAndPortMltMepCannotCoExistOnVlanAtSameLevel(11406),
		cfmNodalMipAndPortMltMipsCannotCoexistOnVlanAtSameLevel(11407),
		cfmNodalMepIsNotSupportedOnESM(11408),
		cfmNodalMipLevelIsNotSupportedOnESM(11409),
		cfmMepCcmTxMustBeEnabledWithController(11410),
		cfmMepStateMustBeEnabledWithController(11411),
		ccmMulticastUnsupportedForVlanMepOnDhuPort(11412),
		cfmIfTlvNotMoreThanOneHundredPerDhu(11413),
		cfmLbmFrameSizeExceedMaxForNodalMep(11414),
		cfmLbmFrameSizeExceedMaxForMlt(11415),
		cannotDeleteVlanWithNodalMipLevelAssociation(11416),
		sameLevelNodalMepAlreadyAssignedToVlan(11417),
		cfmIfTlvNotMoreThanOneHundredPerEsuPort(11418),
		bfdMultiplierInvalidValue(11501),
		efmLinkOamEntryAlreadyExists(11601),
		efmLinkOamCanOnlyBeConfiguredOnRcModPorts(11602),
		efmLinkOamEntryDoesNotExist(11603),
		efmLinkOamDeleteNotAllowedWhenEnabled(11604),
		efmRemoteLbCannotBeInitializedWhenPortIsNotInNoLBState(11605),
		efmPortAlreadyInLbState(11606),
		efmRemoteLbCannotTerminateWhenPortNotInLbState(11607),
		efmRemoteLbCannotTerminateWhilePortInTransmitState(11608),
		efmRemoteLbCannotBeSetInCurrentState(11609),
		efmRemoteLbFrameCountOutOfRange(11610),
		efmRemoteLbFrameSizeOutOfRange(11611),
		efmRemoteLbCannotBeTestedWhenPortIsNotInRemoteLbState(11612),
		efmRemoteLbCannotAbortWhenRemoteLbIsNotInTransmit(11613),
		efmRemoteLbNotOkToSetStatusToReady(11614),
		efmLinkOamNotSupportedOnDualPortMode(11615),
		efmRemoteLbTestAlreadyInProgress(11616),
		multinetVlanDoesNotExist(11701), 
		multinetVlanPortMustBeTagged(11702),
		multinetVlanHasIpSubnetVlanAssociated(11703),
		multinetVlanAssignPortToMultipleIpMultinetVlan(11704), 
		multinetVlanCannotHaveLegacyPort(11705),
		multinetVlanHasMltMember(11706),
		multinetVlanCannotHaveBrouterPort(11707), 
		qosMapExists(12501),
		qosMapNotExist(12502),
		qosMapDeleteUsedByFilter(12503),
		qosMapDeleteDefaultMap(12504),
		standbyIpSubnetNotSameAsMaster(12601),
		standbyIpSubnetNotSameAsVirtual(12602),
		standbyIpSameAsVirtual(12603),
		masterIpSubnetNotSameAsStandby(12604),
		masterIpSubnetNotSameAsVirtual(12605),
		masterIpSameAsVirtual(12606)
	}
	MAX-ACCESS read-only
	STATUS current
	DESCRIPTION "This variable is used primarily as an enumeration
		      to list the proprietary return codes that this
		      device can send to a management station in
		      response to a failed SNMP operation."
	DEFVAL { none }
	::= { rcError 4 }
	
-- *** ABOVE SECTION IS GENERATED FROM ../mib_tools/error.mib ***

rcErrorSendTrap OBJECT-TYPE
        SYNTAX        TruthValue
        MAX-ACCESS    read-write
        STATUS        current
        DESCRIPTION   "Indicates whether to send trap upon receiving an
                      error in the system."
	DEFVAL	      { true }
        ::= { rcError 5 }

END
