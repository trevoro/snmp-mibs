-- automatically generated by mosy 7.1 #1 (elc), do not edit!
-- crmSvcSigTable add object(kameishi 99.4.5)
-- crmSvcIfConfTable add object(kameishi 99.4.5)
-- crmSvcBECNCellSending DEFVAL change(kameishi 99.4.5)
-- crmSvcHeavy/LightCongestionTh DEFVALchange(kameishi 99.4.5)
-- crmSvcIfConfTable MIBname change(kameishi 99.4.5)


CRMSVC-MIB DEFINITIONS ::= BEGIN




IMPORTS
	DisplayString
		FROM RFC1213-MIB
	OBJECT-TYPE
		FROM RFC-1212
	Counter, IpAddress
		FROM RFC1155-SMI
	mib-2, ifIndex
		FROM RFC1213-MIB
	atmVclVci, atmVclVpi, atmVplVpi, atmTrafficDescrParamIndex
		FROM ATM-MIB
	RowStatus, TimeStamp
		FROM SNMPv2-TC;


org OBJECT IDENTIFIER ::= { iso  3 }
dod OBJECT IDENTIFIER ::= { org  6 }
internet OBJECT IDENTIFIER ::= { dod  1 }
private OBJECT IDENTIFIER ::= { internet  4 }
enterprises OBJECT IDENTIFIER ::= { private  1 }
ntt OBJECT IDENTIFIER ::= { enterprises  210 }
mibDoc OBJECT IDENTIFIER ::= { ntt  2 }
ba3000 OBJECT IDENTIFIER ::= { mibDoc  8 }
crmCommon OBJECT IDENTIFIER ::= { ba3000  1 }

-- created from crmSvc (9605221200Z)


crmSvc OBJECT IDENTIFIER ::= { crmCommon  10 }


crmSvcNodeAddress OBJECT-TYPE
    SYNTAX  OCTET STRING(20)
    ACCESS  read-only
    STATUS  mandatory
    DESCRIPTION
           "DUMMY"
    ::= { crmSvc  1 }


crmIfAdminAddrTable OBJECT-TYPE
    SYNTAX  SEQUENCE OF CrmIfAdminAddrEntry
    ACCESS  not-accessible
    STATUS  mandatory
    DESCRIPTION
           "DUMMY"
    ::= { crmSvc  2 }


crmIfAdminAddrEntry OBJECT-TYPE
    SYNTAX  CrmIfAdminAddrEntry
    ACCESS  not-accessible
    STATUS  mandatory
    DESCRIPTION
           "DUMMY"
    INDEX   { ifIndex,  crmIfAdminAddrAddress }
    ::= { crmIfAdminAddrTable  1 }


CrmIfAdminAddrEntry ::=
    SEQUENCE {
        crmIfAdminAddrAddress	OCTET STRING,
        crmIfAdminAddrLength	INTEGER,
        crmIfAdminAddrAddressSource	INTEGER,
        crmIfAdminAddrPriority	INTEGER,
        crmIfAdminAddrRowStatus	INTEGER (-2147483648..2147483647)
    }



crmIfAdminAddrAddress OBJECT-TYPE
    SYNTAX  OCTET STRING
    ACCESS  not-accessible
    STATUS  mandatory
    DESCRIPTION
           "DUMMY"
    ::= { crmIfAdminAddrEntry  1 }


crmIfAdminAddrLength OBJECT-TYPE
    SYNTAX  INTEGER
    ACCESS  read-write
    STATUS  mandatory
    DESCRIPTION
           "DUMMY"
    ::= { crmIfAdminAddrEntry  2 }


crmIfAdminAddrAddressSource OBJECT-TYPE
    SYNTAX  INTEGER {
    other(1),
    static(2),
    dynamic(3)
}
    ACCESS  read-write
    STATUS  mandatory
    DESCRIPTION
           "DUMMY"
    ::= { crmIfAdminAddrEntry  3 }


crmIfAdminAddrPriority OBJECT-TYPE
    SYNTAX  INTEGER
    ACCESS  read-write
    STATUS  mandatory
    DESCRIPTION
           "DUMMY"
    ::= { crmIfAdminAddrEntry  4 }


crmIfAdminAddrRowStatus OBJECT-TYPE
    SYNTAX  INTEGER (-2147483648..2147483647)
    ACCESS  read-write
    STATUS  mandatory
    DESCRIPTION
           "DUMMY"
    ::= { crmIfAdminAddrEntry  5 }


crmSvcCollectionTable OBJECT-TYPE
    SYNTAX  SEQUENCE OF CrmSvcCollectionEntry
    ACCESS  not-accessible
    STATUS  mandatory
    DESCRIPTION
           "DUMMY"
    ::= { crmSvc  3 }


crmSvcCollectionEntry OBJECT-TYPE
    SYNTAX  CrmSvcCollectionEntry
    ACCESS  not-accessible
    STATUS  mandatory
    DESCRIPTION
           "DUMMY"
    INDEX   { ifIndex,  crmSvcCollectionType }
    ::= { crmSvcCollectionTable  1 }


CrmSvcCollectionEntry ::=
    SEQUENCE {
        crmSvcCollectionType		INTEGER,
        crmSvcCollectionFileName	OCTET STRING,
        crmSvcCollectionAdminStatus	INTEGER,
        crmSvcCollectionOperStatus	INTEGER,
        crmSvcCollectionRowStatus    INTEGER (-2147483648..2147483647)
    }


crmSvcCollectionType OBJECT-TYPE
    SYNTAX  INTEGER {
    disconnection(1),
    cellacount(2)
}
    ACCESS  not-accessible
    STATUS  mandatory
    DESCRIPTION
           "DUMMY"
    ::= { crmSvcCollectionEntry  1 }


crmSvcCollectionFileName OBJECT-TYPE
    SYNTAX  OCTET STRING
    ACCESS  read-write
    STATUS  mandatory
    DESCRIPTION
           "DUMMY"
    ::= { crmSvcCollectionEntry  2 }


crmSvcCollectionAdminStatus OBJECT-TYPE
    SYNTAX  INTEGER {
    up(1),
    down(2)
}
    ACCESS  read-write
    STATUS  mandatory
    DESCRIPTION
           "DUMMY"
    DEFVAL {  2  }
    ::= { crmSvcCollectionEntry  3 }


crmSvcCollectionOperStatus OBJECT-TYPE
    SYNTAX  INTEGER {
    up(1),
    down(2),
    unknown(3)
}
    ACCESS  read-only
    STATUS  mandatory
    DESCRIPTION
           "DUMMY"
    ::= { crmSvcCollectionEntry  4 }


crmSvcCollectionRowStatus OBJECT-TYPE
    SYNTAX  INTEGER (-2147483648..2147483647)
    ACCESS  read-write
    STATUS  mandatory
    DESCRIPTION
           "DUMMY"
    ::= { crmSvcCollectionEntry  5 }


crmSvcSigTable OBJECT-TYPE
    SYNTAX  SEQUENCE OF CrmSvcSigEntry
    ACCESS  not-accessible
    STATUS  mandatory
    DESCRIPTION
           "DUMMY"
    ::= { crmSvc  4 }


crmSvcSigEntry OBJECT-TYPE
    SYNTAX  CrmSvcSigEntry
    ACCESS  not-accessible
    STATUS  mandatory
    DESCRIPTION
           "DUMMY"
    INDEX   { ifIndex }
    ::= { crmSvcSigTable  1 }


CrmSvcSigEntry ::=
    SEQUENCE {
        crmSvcSigRole		INTEGER,
        crmSvcSigType		INTEGER,
        crmSvcSigVpi		INTEGER,
        crmSvcSigLineType	INTEGER,
        crmSvcSigAdminStatus	INTEGER,
        crmSvcSigOperStatus	INTEGER,
        crmSvcSigRowStatus	INTEGER (-2147483648..2147483647),
-- add object
	crmSvcSigNativeE164	INTEGER,
        crmSvcSigLoop		INTEGER,
	crmSvcSigAdministrativeWeight	INTEGER,
	crmSvcSigMaxDataSize	INTEGER,
	crmSvcSigFrameLossPriority	INTEGER,
	crmSvcSigPCR		INTEGER,
	crmSvcSigSCR		INTEGER,
	crmSvcSigMCR		INTEGER,
	crmSvcSigMBS		INTEGER,
crmSvcSigRDF		INTEGER,
crmSvcSigRIF		INTEGER
-- END
    }


crmSvcSigRole OBJECT-TYPE
    SYNTAX  INTEGER {
    other(1),
    symmetric(2),
    user(3),
    network(4)
}
    ACCESS  read-write
    STATUS  mandatory
    DESCRIPTION
           "DUMMY"
    ::= { crmSvcSigEntry  1 }


crmSvcSigType OBJECT-TYPE
    SYNTAX  INTEGER {
    other(1),
    ituDss2(2),
    atmfUni3Dot0(3),
    atmfUni3Dot1(4),
    atmfIisp(5),
    atmfuni4Dot0(6),
    atmfIisp4Dot0(7),
    atmfPnni(8)
}
    ACCESS  read-write
    STATUS  mandatory
    DESCRIPTION
           "DUMMY"
    ::= { crmSvcSigEntry  2 }


crmSvcSigVpi OBJECT-TYPE
    SYNTAX  INTEGER
    ACCESS  read-write
    STATUS  mandatory
    DESCRIPTION
           "DUMMY"
    ::= { crmSvcSigEntry  3 }


crmSvcSigLineType OBJECT-TYPE
    SYNTAX  INTEGER {
    activeOpen(1),
    passiveOpen(2)
}
    ACCESS  read-write
    STATUS  mandatory
    DESCRIPTION
           "DUMMY"
    ::= { crmSvcSigEntry  4 }


crmSvcSigAdminStatus OBJECT-TYPE
    SYNTAX  INTEGER {
    up(1),
    down(2)
}
    ACCESS  read-write
    STATUS  mandatory
    DESCRIPTION
           "DUMMY"
    DEFVAL {  2  }
    ::= { crmSvcSigEntry  5 }


crmSvcSigOperStatus OBJECT-TYPE
    SYNTAX  INTEGER {
    up(1),
    down(2),
    unknown(3)
}
    ACCESS  read-only
    STATUS  mandatory
    DESCRIPTION
           "DUMMY"
    ::= { crmSvcSigEntry  6 }


crmSvcSigRowStatus OBJECT-TYPE
    SYNTAX  INTEGER (-2147483648..2147483647)
    ACCESS  read-write
    STATUS  mandatory
    DESCRIPTION
           "DUMMY"
    ::= { crmSvcSigEntry  7 }

-- Add object
crmSvcSigNativeE164 OBJECT-TYPE
    SYNTAX  INTEGER {
	invalid(1),
	valid(2)
}
    ACCESS  read-write
    STATUS  mandatory
    DESCRIPTION
           "DUMMY"
    DEFVAL {  1  }
    ::= { crmSvcSigEntry  8 }

crmSvcSigLoop OBJECT-TYPE
    SYNTAX  INTEGER {
	invalid(1),
	valid(2)
}
    ACCESS  read-write
    STATUS  mandatory
    DESCRIPTION
           "DUMMY"
    DEFVAL {  1  }
    ::= { crmSvcSigEntry  9 }


crmSvcSigAdministrativeWeight OBJECT-TYPE
    SYNTAX  INTEGER
    ACCESS  read-write
    STATUS  mandatory
    DESCRIPTION
           "DUMMY"
    DEFVAL {  5040  }
    ::= { crmSvcSigEntry  10 }


crmSvcSigMaxDataSize OBJECT-TYPE
    SYNTAX  INTEGER
    ACCESS  read-write
    STATUS  mandatory
    DESCRIPTION
           "DUMMY"
    DEFVAL {  4096  }
    ::= { crmSvcSigEntry  11 }


crmSvcSigFrameLossPriority OBJECT-TYPE
    SYNTAX  INTEGER  {
	invalid(1),
	valid(2)
}
    ACCESS  read-write
    STATUS  mandatory
    DESCRIPTION
           "DUMMY"
    DEFVAL {  1  }
    ::= { crmSvcSigEntry  12 }


crmSvcSigPCR OBJECT-TYPE
    SYNTAX  INTEGER
    ACCESS  read-write
    STATUS  mandatory
    DESCRIPTION
           "DUMMY"
    DEFVAL {  64  }
    ::= { crmSvcSigEntry  13 }


crmSvcSigSCR OBJECT-TYPE
    SYNTAX  INTEGER
    ACCESS  read-write
    STATUS  mandatory
    DESCRIPTION
           "DUMMY"
    DEFVAL {  0  }
    ::= { crmSvcSigEntry  14 }


crmSvcSigMCR OBJECT-TYPE
    SYNTAX  INTEGER
    ACCESS  read-write
    STATUS  mandatory
    DESCRIPTION
           "DUMMY"
    DEFVAL {  0  }
    ::= { crmSvcSigEntry  15 }


crmSvcSigMBS OBJECT-TYPE
    SYNTAX  INTEGER
    ACCESS  read-write
    STATUS  mandatory
    DESCRIPTION
           "DUMMY"
    DEFVAL {  86  }
    ::= { crmSvcSigEntry  16 }


crmSvcSigRDF OBJECT-TYPE
    SYNTAX  INTEGER
    ACCESS  read-write
    STATUS  mandatory
    DESCRIPTION
           "DUMMY"
    DEFVAL {  4  }
    ::= { crmSvcSigEntry  17 }

crmSvcSigRIF OBJECT-TYPE
    SYNTAX  INTEGER
    ACCESS  read-write
    STATUS  mandatory
    DESCRIPTION
           "DUMMY"
    DEFVAL {  4  }
    ::= { crmSvcSigEntry  18 }
-- END


crmAddrVclTable OBJECT-TYPE
    SYNTAX  SEQUENCE OF CrmAddrVclEntry
    ACCESS  not-accessible
    STATUS  mandatory
    DESCRIPTION
           "DUMMY"
    ::= { crmSvc  5 }


crmAddrVclEntry OBJECT-TYPE
    SYNTAX  CrmAddrVclEntry
    ACCESS  not-accessible
    STATUS  mandatory
    DESCRIPTION
           "DUMMY"
    INDEX   { crmAddrVclAtmIfIndex,  crmAddrVclAtmAddress,  crmAddrVclVpi,  crmAddrVclVci }
    ::= { crmAddrVclTable  1 }


CrmAddrVclEntry ::=
    SEQUENCE {
        crmAddrVclAtmIfIndex	INTEGER (-2147483648..2147483647),
        crmAddrVclAtmAddress	OCTET STRING,
        crmAddrVclVpi		INTEGER,
        crmAddrVclVci		INTEGER,
        crmAddrVclAddrType	INTEGER
    }


crmAddrVclAtmIfIndex OBJECT-TYPE
    SYNTAX  INTEGER (-2147483648..2147483647)
    ACCESS  not-accessible
    STATUS  mandatory
    DESCRIPTION
           "DUMMY"
    ::= { crmAddrVclEntry  1 }


crmAddrVclAtmAddress OBJECT-TYPE
    SYNTAX  OCTET STRING
    ACCESS  not-accessible
    STATUS  mandatory
    DESCRIPTION
           "DUMMY"
    ::= { crmAddrVclEntry  2 }


crmAddrVclVpi OBJECT-TYPE
    SYNTAX  INTEGER
    ACCESS  not-accessible
    STATUS  mandatory
    DESCRIPTION
           "DUMMY"
    ::= { crmAddrVclEntry  3 }


crmAddrVclVci OBJECT-TYPE
    SYNTAX  INTEGER
    ACCESS  not-accessible
    STATUS  mandatory
    DESCRIPTION
           "DUMMY"
    ::= { crmAddrVclEntry  4 }


crmAddrVclAddrType OBJECT-TYPE
    SYNTAX  INTEGER {
    local(1),
    remote(2)
}
    ACCESS  read-only
    STATUS  mandatory
    DESCRIPTION
           "DUMMY"
    ::= { crmAddrVclEntry  5 }


crmSigChannelBlockingTable OBJECT-TYPE
    SYNTAX  SEQUENCE OF CrmSigChannelBlockingEntry
    ACCESS  not-accessible
    STATUS  mandatory
    DESCRIPTION
           "DUMMY"
    ::= { crmSvc  6 }


crmSigChannelBlockingEntry OBJECT-TYPE
    SYNTAX  CrmSigChannelBlockingEntry
    ACCESS  not-accessible
    STATUS  mandatory
    DESCRIPTION
           "DUMMY"
    INDEX   { ifIndex }
    ::= { crmSigChannelBlockingTable  1 }


CrmSigChannelBlockingEntry ::=
    SEQUENCE {
        crmSigChannelBlocking			INTEGER,
        crmSigChannelBlockingAdminStatus	INTEGER,
        crmSigChannelBlockingOperStatus		INTEGER,
        crmSigChannelBlockingRowStatus
		INTEGER (-2147483648..2147483647)
    }


crmSigChannelBlocking OBJECT-TYPE
    SYNTAX  INTEGER
    ACCESS  read-write
    STATUS  mandatory
    DESCRIPTION
           "DUMMY"
    DEFVAL {  1  }
    ::= { crmSigChannelBlockingEntry  1 }


crmSigChannelBlockingAdminStatus OBJECT-TYPE
    SYNTAX  INTEGER {
    up(1),
    down(2)
}
    ACCESS  read-write
    STATUS  mandatory
    DESCRIPTION
           "DUMMY"
    DEFVAL {  2  }
    ::= { crmSigChannelBlockingEntry  2 }
crmSigChannelBlockingOperStatus OBJECT-TYPE
    SYNTAX  INTEGER {
    other(1),
    preblocking(2),
    blocking(3)
}
    ACCESS  read-only
    STATUS  mandatory
    DESCRIPTION
           "DUMMY"
    ::= { crmSigChannelBlockingEntry  3 }


crmSigChannelBlockingRowStatus OBJECT-TYPE
    SYNTAX  INTEGER (-2147483648..2147483647)
    ACCESS  read-write
    STATUS  mandatory
    DESCRIPTION
           "DUMMY"
    ::= { crmSigChannelBlockingEntry  4 }


crmSvcIfConfTable OBJECT-TYPE
    SYNTAX  SEQUENCE OF CrmSvcIfConfEntry
    ACCESS  not-accessible
    STATUS  mandatory
    DESCRIPTION
           "DUMMY"
    ::= { crmSvc  7 }


crmSvcIfConfEntry OBJECT-TYPE
    SYNTAX  CrmSvcIfConfEntry
    ACCESS  not-accessible
    STATUS  mandatory
    DESCRIPTION
           "DUMMY"
    INDEX   { ifIndex }
    ::= { crmSvcIfConfTable  1 }


CrmSvcIfConfEntry ::=
    SEQUENCE {
        crmSvcIfMinVpi		INTEGER,
        crmSvcIfMaxVpi		INTEGER,
        crmSvcIfMinVci		INTEGER,
        crmSvcIfMaxVci		INTEGER,
        crmSvcIfUpcControl	INTEGER,
        crmSvcIfShapingControl	INTEGER,
-- Add object
	crmSvcIfHeavyCongestionTh	INTEGER,
	crmSvcIfLightCongestionTh	INTEGER,
	crmSvcIfEFCIMarking	INTEGER,
	crmSvcIfNICIMarking	INTEGER,
	crmSvcIfERMarking		INTEGER,
	crmSvcIfBECNCellSending	INTEGER,
	crmSvcIfVSVD		INTEGER,
	crmSvcIfCDF		INTEGER,
	crmSvcIfCbrCellDelayPriority	INTEGER,
	crmSvcIfRtvbrCellDelayPriority	INTEGER,
	crmSvcIfNrtvbrCellDelayPriority	INTEGER,
	crmSvcIfAbrCellDelayPriority	INTEGER,
	crmSvcIfUbrCellDelayPriority	INTEGER,
crmSvcIfCDVT 	INTEGER
-- END
    }


crmSvcIfMinVpi OBJECT-TYPE
    SYNTAX  INTEGER
    ACCESS  read-write
    STATUS  mandatory
    DESCRIPTION
           "DUMMY"
    DEFVAL {  0  }
    ::= { crmSvcIfConfEntry  1 }


crmSvcIfMaxVpi OBJECT-TYPE
    SYNTAX  INTEGER
    ACCESS  read-write
    STATUS  mandatory
    DESCRIPTION
           "DUMMY"
    DEFVAL {  31  }
    ::= { crmSvcIfConfEntry  2 }


crmSvcIfMinVci OBJECT-TYPE
    SYNTAX  INTEGER
    ACCESS  read-write
    STATUS  mandatory
    DESCRIPTION
           "DUMMY"
    DEFVAL {  32  }
    ::= { crmSvcIfConfEntry  3 }


crmSvcIfMaxVci OBJECT-TYPE
    SYNTAX  INTEGER
    ACCESS  read-write
    STATUS  mandatory
    DESCRIPTION
           "DUMMY"
    DEFVAL {  255  }
    ::= { crmSvcIfConfEntry  4 }


crmSvcIfUpcControl OBJECT-TYPE
    SYNTAX  INTEGER {
    upcInvalid(1),
    upcValid(2)
}
    ACCESS  read-write
    STATUS  mandatory
    DESCRIPTION
           "DUMMY"
    DEFVAL {  1  }
    ::= { crmSvcIfConfEntry  5 }


crmSvcIfShapingControl OBJECT-TYPE
    SYNTAX  INTEGER {
    shapingInvalid(1),
    shapingValid(2)
}
    ACCESS  read-write
    STATUS  mandatory
    DESCRIPTION
           "DUMMY"
    DEFVAL {  1  }
    ::= { crmSvcIfConfEntry  6 }

-- Add object
crmSvcIfHeavyCongestionTh OBJECT-TYPE
    SYNTAX  INTEGER
    ACCESS  read-write
    STATUS  mandatory
    DESCRIPTION
           "DUMMY"
    DEFVAL {  80  }
    ::= { crmSvcIfConfEntry  7 }


crmSvcIfLightCongestionTh OBJECT-TYPE
    SYNTAX  INTEGER
    ACCESS  read-write
    STATUS  mandatory
    DESCRIPTION
           "DUMMY"
    DEFVAL {  60  }
    ::= { crmSvcIfConfEntry  8 }


crmSvcIfEFCIMarking OBJECT-TYPE
    SYNTAX  INTEGER {
    invalid(1),
    valid(2)
}
    ACCESS  read-write
    STATUS  mandatory
    DESCRIPTION
           "DUMMY"
    DEFVAL {  2  }
    ::= { crmSvcIfConfEntry  9 }


crmSvcIfNICIMarking OBJECT-TYPE
    SYNTAX  INTEGER {
    invalid(1),
    valid(2)
}
    ACCESS  read-write
    STATUS  mandatory
    DESCRIPTION
           "DUMMY"
    DEFVAL {  2  }
    ::= { crmSvcIfConfEntry  10 }


crmSvcIfERMarking OBJECT-TYPE
    SYNTAX  INTEGER {
    invalid(1),
    valid(2)
}
    ACCESS  read-write
    STATUS  mandatory
    DESCRIPTION
           "DUMMY"
    DEFVAL {  2  }
    ::= { crmSvcIfConfEntry  11 }


crmSvcIfBECNCellSending OBJECT-TYPE
    SYNTAX  INTEGER {
    invalid(1),
    valid(2)
}
    ACCESS  read-write
    STATUS  mandatory
    DESCRIPTION
           "DUMMY"
    DEFVAL {  1  }
    ::= { crmSvcIfConfEntry  12 }


crmSvcIfVSVD OBJECT-TYPE
    SYNTAX  INTEGER {
    invalid(1),
    valid(2)
}
    ACCESS  read-write
    STATUS  mandatory
    DESCRIPTION
           "DUMMY"
    DEFVAL {  1  }
    ::= { crmSvcIfConfEntry  13 }


crmSvcIfCDF OBJECT-TYPE
    SYNTAX  INTEGER
    ACCESS  read-write
    STATUS  mandatory
    DESCRIPTION
           "DUMMY"
    DEFVAL {  4  }
    ::= { crmSvcIfConfEntry  14 }


crmSvcIfCbrCellDelayPriority OBJECT-TYPE
    SYNTAX  INTEGER {
	class1(1),
	class2(2),
	class3(3),
	class6(4),
	class4(5),
	class5(6)
}
    ACCESS  read-write
    STATUS  mandatory
    DESCRIPTION
           "DUMMY"
    DEFVAL {  1  }
    ::= { crmSvcIfConfEntry  15 }


crmSvcIfRtvbrCellDelayPriority OBJECT-TYPE
    SYNTAX  INTEGER {
	class1(1),
	class2(2),
	class3(3),
	class6(4),
	class4(5),
	class5(6)
}
    ACCESS  read-write
    STATUS  mandatory
    DESCRIPTION
           "DUMMY"
    DEFVAL {  2  }
    ::= { crmSvcIfConfEntry  16 }


crmSvcIfNrtvbrCellDelayPriority OBJECT-TYPE
    SYNTAX  INTEGER {
	class1(1),
	class2(2),
	class3(3),
	class6(4),
	class4(5),
	class5(6)
}
    ACCESS  read-write
    STATUS  mandatory
    DESCRIPTION
           "DUMMY"
    DEFVAL {  3  }
    ::= { crmSvcIfConfEntry  17 }


crmSvcIfAbrCellDelayPriority OBJECT-TYPE
    SYNTAX  INTEGER {
	class1(1),
	class2(2),
	class3(3),
	class6(4),
	class4(5),
	class5(6)
}
    ACCESS  read-write
    STATUS  mandatory
    DESCRIPTION
           "DUMMY"
    DEFVAL {  4  }
    ::= { crmSvcIfConfEntry  18 }


crmSvcIfUbrCellDelayPriority OBJECT-TYPE
    SYNTAX  INTEGER {
	class1(1),
	class2(2),
	class3(3),
	class6(4),
	class4(5),
	class5(6)
}
    ACCESS  read-write
    STATUS  mandatory
    DESCRIPTION
           "DUMMY"
    DEFVAL {  6  }
    ::= { crmSvcIfConfEntry  19 }


crmSvcIfCDVT OBJECT-TYPE
    SYNTAX  INTEGER
    ACCESS  read-write
    STATUS  mandatory
    DESCRIPTION
           "DUMMY"
    DEFVAL {  720  }
    ::= { crmSvcIfConfEntry  20 }
-- END

END
