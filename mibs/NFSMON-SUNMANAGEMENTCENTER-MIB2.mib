-------------------------------------------------------
-- Copyright 1999 - Sun Microsystems, Inc. All Rights Reserved.
--
--
-------------------------------------------------------
-- Sun Management Center
-------------------------------------------------------


NFSMON-SUNMANAGEMENTCENTER-MIB2 DEFINITIONS ::= BEGIN

  IMPORTS
        enterprises, MODULE-IDENTITY, OBJECT-TYPE,  Integer32
                FROM SNMPv2-SMI
         OBJECT-GROUP
                FROM SNMPv2-CONF
         DisplayString
               FROM SNMPv2-TC;


nfsmon MODULE-IDENTITY
    LAST-UPDATED "9907201505Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        "The NFS file systems mib allows to monitor key statistics of NFS 
	file systems which are mounted and also specified in agent 
        configuration.
        SNMPv2 uses the term 'context' for the MIBs that can have multiple
        instances running on the Agent. If you are using a SNMPv2 based
        thirdparty management station to communicate with such an agent,
        then make sure that you are using the right context information.
        However, if you are using SNMPv1 based management station, then
        add the context information to the SNMP community as follows
        '<community>:<context>'
        This will enable you to access data from multiple instances of
        the same module running on an agent."

    REVISION  "9907201505Z"
    DESCRIPTION
        "Rev 1.0  20th July 1999 15:05, Initial version Of MIB."
    ::= { modules 27 }

sun       OBJECT IDENTIFIER ::= { enterprises 42 }
prod      OBJECT IDENTIFIER ::= { sun 2 }
sunsymon  OBJECT IDENTIFIER ::= { prod 12 }
agent     OBJECT IDENTIFIER ::= { sunsymon 2 }
modules   OBJECT IDENTIFIER ::= { agent 2 }


nfsmFileSystemGroup OBJECT-GROUP
        OBJECTS {  nfsmFileSystemName, nfsmFileSystemSize, 
		nfsmFileSystemUsedSpace, nfsmFileSystemAvailSpace, 
		nfsmFileSystemPctUsedSpace, nfsmFileSystemPctUsedSpaceRate, 
		nfsmFileSystemMountPoint, nfsmFileSystemEntryIndex }
        STATUS current
        DESCRIPTION
        "NFS Filesystem related statistics."
        ::= { nfsmon 1 }



nfsmFileTable OBJECT-TYPE
    SYNTAX      SEQUENCE OF NfsmFileEntry
    MAX-ACCESS  not-accessible
    STATUS      current
    DESCRIPTION
                "Table of monitoring information of the network file systems 
                 that are mounted and being monitored by the agent."
    ::= { nfsmFileSystemGroup 1 }

NfsmFileEntry ::=
    SEQUENCE {
        nfsmFileSystemName
            DisplayString,
        nfsmFileSystemSize
            Integer32,
        nfsmFileSystemUsedSpace
            Integer32,
        nfsmFileSystemAvailSpace
            Integer32,
        nfsmFileSystemPctUsedSpace
            DisplayString,
        nfsmFileSystemPctUsedSpaceRate
            DisplayString,
        nfsmFileSystemMountPoint
            DisplayString,
        nfsmFileSystemEntryIndex
            DisplayString
    }

nfsmFileEntry OBJECT-TYPE
    SYNTAX      NfsmFileEntry
    MAX-ACCESS  not-accessible
    STATUS      current
    DESCRIPTION
                "Monitoring information about one network file system 
		mounted on the system."
    INDEX  { nfsmFileSystemEntryIndex  }
    ::= { nfsmFileTable 1 }

nfsmFileSystemName OBJECT-TYPE
    SYNTAX      DisplayString
    MAX-ACCESS  read-only
    STATUS      current
    DESCRIPTION
                "The name of the NFS file system. This is the full path 
		name of the NFS file system being monitored, relative to 
		the host."
    ::= { nfsmFileEntry 1 }

nfsmFileSystemSize OBJECT-TYPE
    SYNTAX      Integer32
    UNITS       "KB"
    MAX-ACCESS  read-only
    STATUS      current
    DESCRIPTION
                "The total size of the NFS file system, in Kbytes."
    ::= { nfsmFileEntry 2 }

nfsmFileSystemUsedSpace OBJECT-TYPE
    SYNTAX      Integer32
    UNITS       "KB"
    MAX-ACCESS  read-only
    STATUS      current
    DESCRIPTION
                "Used disk space for the NFS file system, in Kbytes."
    ::= { nfsmFileEntry 3 }

nfsmFileSystemAvailSpace OBJECT-TYPE
    SYNTAX      Integer32
    UNITS       "KB"
    MAX-ACCESS  read-only
    STATUS      current
    DESCRIPTION
                "Available disk space for the NFS file system, in Kbytes."
    ::= { nfsmFileEntry 4 }


nfsmFileSystemPctUsedSpace OBJECT-TYPE
    SYNTAX      DisplayString
    UNITS       "%"
    MAX-ACCESS  read-only
    STATUS      current
    DESCRIPTION
                "Percentage of NFS disk space Used."
    ::= { nfsmFileEntry 5 }

nfsmFileSystemPctUsedSpaceRate OBJECT-TYPE
    SYNTAX      DisplayString
    UNITS       "%/sec"
    MAX-ACCESS  read-only
    STATUS      current
    DESCRIPTION
                "The rate at which the percentage-used value changes per 
		second."
    ::= { nfsmFileEntry 6 }

nfsmFileSystemMountPoint OBJECT-TYPE
    SYNTAX      DisplayString
    MAX-ACCESS  read-only
    STATUS      current
    DESCRIPTION
                "The mount point for the NFS file system. This is the 
		full pathname of the directory on which the NFS file 
		system is mounted."
    ::= { nfsmFileEntry 7 }


nfsmFileSystemEntryIndex OBJECT-TYPE
    SYNTAX      DisplayString
    MAX-ACCESS  read-only
    STATUS      current
    DESCRIPTION
                "Character string value used for indexing in the table."
    ::= { nfsmFileEntry 8 }
END
