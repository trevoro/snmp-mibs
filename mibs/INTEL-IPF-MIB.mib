INTEL-IPF-MIB DEFINITIONS ::= BEGIN

-- Copyright (C) 1998 Intel Corporation. All rights reserved.
--
-- IP filtering MIB for Cork, 1998-06-17, ms.
--
-- This MIB defines the management information for a system functioning
-- as an IP router.
--
-- Change History:
-- 98-06-17 Initial version


	IMPORTS
		IpAddress, Counter, TimeTicks	FROM RFC1155-SMI
		OBJECT-TYPE		FROM RFC-1212
		DisplayString		FROM RFC1213-MIB
		mib2ext			FROM INTEL-GEN-MIB;


	ipf	OBJECT IDENTIFIER ::= { mib2ext 34 }

	ipfUGs	OBJECT IDENTIFIER ::= { ipf 1 }

	ipfL3UGM	OBJECT IDENTIFIER ::= { ipf 2 }

	ipfL4UGM	OBJECT IDENTIFIER ::= { ipf 3 }

	ipfInfo		OBJECT IDENTIFIER ::= { ipf 4 }

	UserGroupSet ::= OCTET STRING
	-- this data type is used to encode sets of user groups.
	-- set membership of usergroup no X is encoded as 1 in bit
	-- position X.


ipfUGsTable OBJECT-TYPE
    SYNTAX SEQUENCE OF IpfUGsEntry
    ACCESS not-accessible
    STATUS mandatory
    DESCRIPTION "Numbers and Names of UserGroups"
    ::= { ipfUGs 1 }

ipfUGsEntry OBJECT-TYPE
    SYNTAX IpfUGsEntry
    ACCESS not-accessible
    STATUS mandatory
    DESCRIPTION ""
    INDEX { ipfUGsNumber }
    ::= { ipfUGsTable 1 }

IpfUGsEntry ::= SEQUENCE {
                        ipfUGsNumber
                           INTEGER,
                        ipfUGsName
                           OCTET STRING
                        }

ipfUGsNumber OBJECT-TYPE
    SYNTAX INTEGER
    ACCESS read-only
    STATUS mandatory
    DESCRIPTION ""
    ::= { ipfUGsEntry 1 }

ipfUGsName OBJECT-TYPE
    SYNTAX DisplayString (SIZE(20))
    ACCESS read-write
    STATUS mandatory
    DESCRIPTION ""
    ::= { ipfUGsEntry 2 }

ipfL3UGMTable OBJECT-TYPE
    SYNTAX SEQUENCE OF IpfL3UGMEntry
    ACCESS not-accessible
    STATUS mandatory
    DESCRIPTION "UserGroup membership for prefices of IP-addresses"
    ::= { ipfL3UGM 1 }

ipfL3UGMEntry OBJECT-TYPE
    SYNTAX IpfL3UGMEntry
    ACCESS not-accessible
    STATUS mandatory
    DESCRIPTION ""
    INDEX { ipfL3UGMIpAddress }
    ::= { ipfL3UGMTable 1 }

IpfL3UGMEntry ::= SEQUENCE {
                        ipfL3UGMIpAddress
                           IpAddress,
                        ipfL3UGMSubnetMask
                           IpAddress,
                        ipfL3UGMUserGroups
                           UserGroupSet
                        }

ipfL3UGMIpAddress OBJECT-TYPE
    SYNTAX IpAddress
    ACCESS read-only
    STATUS mandatory
    DESCRIPTION ""
    ::= { ipfL3UGMEntry 1 }

ipfL3UGMSubnetMask OBJECT-TYPE
    SYNTAX IpAddress
    ACCESS read-write
    STATUS mandatory
    DESCRIPTION ""
    ::= { ipfL3UGMEntry 2 }

ipfL3UGMUserGroups OBJECT-TYPE
    SYNTAX UserGroupSet
    ACCESS read-write
    STATUS mandatory
    DESCRIPTION "Group membership assigned to packets matching IpAddress AND SubnetMask"
    ::= { ipfL3UGMEntry 3 }

ipfL4UGMTable OBJECT-TYPE
    SYNTAX SEQUENCE OF IpfL4UGMEntry
    ACCESS not-accessible
    STATUS mandatory
    DESCRIPTION "UserGroup membership for layer-4 port numbers"
    ::= { ipfL4UGM 1 }

ipfL4UGMEntry OBJECT-TYPE
    SYNTAX IpfL4UGMEntry
    ACCESS not-accessible
    STATUS mandatory
    DESCRIPTION ""
    INDEX { ipfL4UGMPortNumber }
    ::= { ipfL4UGMTable 1 }

IpfL4UGMEntry ::= SEQUENCE {
                        ipfL4UGMPortNumber
                           INTEGER,
                        ipfL4UGMUserGroups
                           UserGroupSet
                        }

ipfL4UGMPortNumber OBJECT-TYPE
    SYNTAX INTEGER
    ACCESS read-only
    STATUS mandatory
    DESCRIPTION ""
    ::= { ipfL4UGMEntry 1 }

ipfL4UGMUserGroups OBJECT-TYPE
    SYNTAX UserGroupSet
    ACCESS read-write
    STATUS mandatory
    DESCRIPTION "Group membership assigned to packets matching PortNumber"
    ::= { ipfL4UGMEntry 2 }

ipfInfoL3Rejects OBJECT-TYPE
    SYNTAX Counter
    ACCESS read-only
    STATUS mandatory
    DESCRIPTION "Packets rejected when exposed to L3 filter"
    ::= { ipfInfo 1 }

ipfInfoL4Rejects OBJECT-TYPE
    SYNTAX Counter
    ACCESS read-only
    STATUS mandatory
    DESCRIPTION "Packets rejected when exposed to L3 filter"
    ::= { ipfInfo 2 }

ipfInfoMostRecentChange OBJECT-TYPE
    SYNTAX TimeTicks
    ACCESS read-only
    STATUS mandatory
    DESCRIPTION ""
    ::= { ipfInfo 3 }

ipfInfoOnOffSwitch OBJECT-TYPE
    SYNTAX INTEGER { on(1), off(2) }
    ACCESS read-write
    STATUS mandatory
    DESCRIPTION ""
    ::= { ipfInfo 4 }

ipfInfoDeleteUserGroup OBJECT-TYPE
    SYNTAX INTEGER
    ACCESS read-write
    STATUS mandatory
    DESCRIPTION "Write the number of the UG to delete here."
    ::= { ipfInfo 5 }

ipfInfoDeleteL3UGM OBJECT-TYPE
    SYNTAX IpAddress
    ACCESS read-write
    STATUS mandatory
    DESCRIPTION "Write the IP-address of the L3-entry to delete here."
    ::= { ipfInfo 6 }

ipfInfoDeleteL4UGM OBJECT-TYPE
    SYNTAX INTEGER
    ACCESS read-write
    STATUS mandatory
    DESCRIPTION "Write the port number of theL4-entry to delete here."
    ::= { ipfInfo 7 }

ipfInfoCreateDeleteStatus OBJECT-TYPE    
    SYNTAX INTEGER { ok(1), createTableFull(2), deleteNotFound(3) }
    ACCESS read-only
    STATUS mandatory
    DESCRIPTION "Completion status of most recent create/delete operation."
    ::= { ipfInfo 8 }

END
