USR-PPTP-MIB DEFINITIONS ::= BEGIN
	 IMPORTS
         Counter32, Integer32, IpAddress, 
         OBJECT-IDENTITY, OBJECT-TYPE, MODULE-IDENTITY
                FROM SNMPv2-SMI
    	 RowStatus, TruthValue, TEXTUAL-CONVENTION, DisplayString
                FROM SNMPv2-TC
         common, UsrConfigStatus, DisplayString
         	FROM USR-DEFINITIONS-MIB;
 usrPptp MODULE-IDENTITY
         LAST-UPDATED "200204011700Z"
         ORGANIZATION "CommWorks Corporation, a 3Com Company"
         CONTACT-INFO "Customer Support"
         DESCRIPTION
                 "The commWorks enterprise defined MIB objects
                   for point-to-point tunneling."
         ::= { common 56 }
   MilliSeconds ::=  TEXTUAL-CONVENTION
          DISPLAY-HINT    "d-3"
          STATUS          current
          DESCRIPTION     
              " A period of time measured in units of .001 of seconds
              when used in conjunction with the DISPLAY-HINT will
              show seconds and fractions of second with a resolution
              of .001 of a second."
       SYNTAX          INTEGER (0..2147483646)      
   usrPPTPGlobal  OBJECT-IDENTITY
           STATUS          current
           DESCRIPTION
              "The root of the PPTP global Object-Identifiers."
           ::= { usrPptp 1 }
   usrPPTPConfigTable OBJECT-TYPE
           SYNTAX          SEQUENCE OF UsrPPTPConfigEntry
           MAX-ACCESS      not-accessible
           STATUS          current
           DESCRIPTION
              ""
           ::= { usrPPTPGlobal 1 }
   usrPptpConfigEntry OBJECT-TYPE
           SYNTAX          UsrPPTPConfigEntry
           MAX-ACCESS      not-accessible
           STATUS          current
           DESCRIPTION
              "."
           INDEX           { usrPptpConfigIndex }
           ::= { usrPPTPConfigTable 1 }
   UsrPPTPConfigEntry ::= SEQUENCE {
           usrPptpConfigIndex
                   Integer32,
           usrPptpMaxNumberOfSessions
                   Integer32,
           usrPptpMaxNumberOfTunnels
                   Integer32,
           usrPptpControlTunnelSeekDescriptors
                   Integer32,
           usrPptpUseDataTunnelFlowControl
                   TruthValue,
           usrPptpDataTunnelDelayedAckTimeout
                   MilliSeconds,
           usrPptpDataTunnelReassemblyTimeout
                   MilliSeconds,
           usrPptpDataChannelRecvPacketWindow
                   Integer32,
           usrPptpHelloInactivityHoldTime
                   Integer32,
           usrPptpEchoReplyTimeoutSeconds
                   Integer32,
           usrPptpLoggingLevel
                   INTEGER,
           usrPptpLoadBalancing
                   TruthValue,
           usrPptpDialOut
                    DisplayString,
    	   usrPptpPnsFlag 
                    INTEGER 
       }
   usrPptpConfigIndex     OBJECT-TYPE
           SYNTAX          Integer32
           MAX-ACCESS      read-only
           STATUS          current
           DESCRIPTION
              " A unique value for each pptp protocol stack. "
           ::= { usrPptpConfigEntry 1 }
   usrPptpMaxNumberOfSessions OBJECT-TYPE
           SYNTAX          Integer32
           MAX-ACCESS      read-write
           STATUS          current
           DESCRIPTION
               "Defines the number of simultaneous active sessions
               that the PPTP stack will support."
           DEFVAL          { 0 }
              --CONFIGURABLE
           ::= { usrPptpConfigEntry 2 }
   usrPptpMaxNumberOfTunnels OBJECT-TYPE
           SYNTAX          Integer32
           MAX-ACCESS      read-write
           STATUS          current
           DESCRIPTION
               "Defines the number of simultaneous active tunnels
               that the PPTP stack will support. Remember that sessions
               are multiplexed within a single tunnel, therefore this
               object contains the number of active PPTP tunnel
               sessions which are to be supported per tunnel."
           DEFVAL          { 0 }
               --CONFIGURABLE
           ::= { usrPptpConfigEntry 3 }
   usrPptpControlTunnelSeekDescriptors  OBJECT-TYPE
           SYNTAX          Integer32
           MAX-ACCESS      read-write
           STATUS          current
           DESCRIPTION
              "Defines the number of tunnel terminators which the PPTP
              stack is to be able to simultaneous connect to. Once a
              tunnel is in the established state, the seek descriptor
              is no longer used."
           DEFVAL          { 8 }
              --CONFIGURABLE
           ::= { usrPptpConfigEntry 4 }
    usrPptpUseDataTunnelFlowControl  OBJECT-TYPE
           SYNTAX          TruthValue
           MAX-ACCESS      read-write
           STATUS          current
           DESCRIPTION
              "This object determines whether or not the PPTP stack is
              to use flow control on the data tunnel."
           DEFVAL          { false }
              --CONFIGURABLE
           ::= { usrPptpConfigEntry 5 }
    usrPptpDataTunnelDelayedAckTimeout  OBJECT-TYPE
           SYNTAX          MilliSeconds
           MAX-ACCESS      read-write
           STATUS          current
           DESCRIPTION
              "This object defines the number of milliseconds which the
              PPTP stack will wait  to send and ACK to it's peer in the
              case where there are no data or control packets to piggy-
              back the ACK to.  The default value for this object is 0
              which results in immediate acknowledgment when there are
              no data or control packets pending."
             DEFVAL          { 0 }
            --CONFIGURABLE
           ::= { usrPptpConfigEntry 6 }
     usrPptpDataTunnelReassemblyTimeout  OBJECT-TYPE
           SYNTAX          MilliSeconds
           MAX-ACCESS      read-write
           STATUS          current
           DESCRIPTION
              "This object defines the number of milliseconds that the
              PPTP stack will use to determine the window to use before
              reassembling out of order packets. A low value increases
              the chance of out-of-sequence packets to be lost (which
              MAY causes the PPP decompression engine to reset), a high
              value increases the time period where the PPTP stack
              processes packets which were received out of order
              (especially in the case of a packet which was lost within
              the network).  The default value for this object is zero
              (0) which may result in all out of sequence packets being
              lost."
           DEFVAL          { 0 }
           --CONFIGURABLE
           ::= { usrPptpConfigEntry 7 }
   usrPptpDataChannelRecvPacketWindow  OBJECT-TYPE
           SYNTAX          Integer32
           MAX-ACCESS      read-write
           STATUS          current
           DESCRIPTION
              "This object defines the Data Channel receive window
              size which is transmitted to the PPTP peers."
           DEFVAL          { 7 }
           --CONFIGURABLE
           ::= { usrPptpConfigEntry 8 }
    usrPptpHelloInactivityHoldTime    OBJECT-TYPE
           SYNTAX          Integer32
           MAX-ACCESS      read-write
           STATUS          current
           DESCRIPTION
              "This object defines the length of the inactivity timer
              in seconds which causes the PPTP stack to transmit a
              keep-alive packet (known as Hello)."
           DEFVAL          { 0 }
            --CONFIGURABLE
           ::= { usrPptpConfigEntry 9 }
    usrPptpEchoReplyTimeoutSeconds  OBJECT-TYPE
           SYNTAX          Integer32
           MAX-ACCESS      read-write
           STATUS          current
           DESCRIPTION
              "This object defines the number of seconds which the PPTP
              stack must wait until a time-out occurs in receiving a
              response to the Hello  message."
           DEFVAL          { 0 }
              --CONFIGURABLE
           ::= { usrPptpConfigEntry 10 }
     usrPptpLoggingLevel  OBJECT-TYPE
           SYNTAX          INTEGER {
               logDisabled(1),
               logControlPackets(2),
               logControlAndDataPacketHeaders(3),
               logControlAndDataPackets(4)
           }
           MAX-ACCESS      read-write
           STATUS          current
           DESCRIPTION
              "This object defines the logging level which the PPTP
              protocol stack will use."
           DEFVAL          { logDisabled }
                --CONFIGURABLE
           ::= { usrPptpConfigEntry 11 }
   usrPptpLoadBalancing  OBJECT-TYPE
           SYNTAX          TruthValue
           MAX-ACCESS      read-write
           STATUS          current
           DESCRIPTION
              "Defines If Load Balancing is enabled or not."
           DEFVAL          { true }
             --CONFIGURABLE 
           ::= { usrPptpConfigEntry 12 }
usrPptpDialOut OBJECT-TYPE
        SYNTAX  DisplayString (SIZE(0..32))
        MAX-ACCESS  read-write
        STATUS  current
        DESCRIPTION
                "This variable is set through the CLI when the user
                 manually issues a PPTP dial-out."
        ::= { usrPptpConfigEntry 13 }
 usrPptpPnsFlag OBJECT-TYPE
      SYNTAX   INTEGER { enabled(1), disabled(2) }
      MAX-ACCESS   read-write 
      STATUS   current
      DESCRIPTION
             "Setting this object to a value of enabled(1) will enable      
              the PPTP pns enable feature. Setting this object to
              disabled(2) will disable the PPTP PNS feature."
     --CONFIGURABLE 
 ::= { usrPptpConfigEntry 14 }
usrPPTPStatsTable OBJECT-TYPE
           SYNTAX          SEQUENCE OF UsrPPTPStatsEntry 
           MAX-ACCESS      not-accessible
           STATUS          current
           DESCRIPTION
              ""
           ::= { usrPPTPGlobal 2 }
usrPptpStatsEntry OBJECT-TYPE
           SYNTAX          UsrPPTPStatsEntry 
           MAX-ACCESS      not-accessible
           STATUS          current
           DESCRIPTION
              "."
           INDEX           { usrPptpStatsIndex }
           ::= {usrPPTPStatsTable 1 }
UsrPPTPStatsEntry ::= SEQUENCE {
           usrPptpStatsIndex
                   Integer32,
           usrPptpNumActiveTunnels
                   Integer32,
           usrPptpStatsNumActiveSessions
                   Integer32,
           usrPptpStatsMalformedPackets
                   Counter32,
           usrPptpStatsControlTunnelRecvPackets
                   Counter32,
           usrPptpStatsProcessedControlTunnelRecvPackets
                   Counter32,
           usrPptpStatsControlTunnelSendPackets
                   Counter32,
           usrPptpStatsDataTunnelRecvPackets
                   Counter32,
           usrPptpStatsDataTunnelWithdataRecvPackets
                   Counter32,
           usrPptpStatsDataTunnelWithoutdataRecvPackets
                   Counter32,
           usrPptpStatsProcessedDataTunnelRecvPackets
                   Counter32,
           usrPptpStatsInSequenceDataTunnelRecvPackets
                   Counter32,
           usrPptpStatsOutSequenceDataTunnelRecvPackets
                   Counter32,
           usrPptpStatsInOrderDataTunnelRecvPackets
                   Counter32,
           usrPptpStatsOutOfOrderDataTunnelRecvPackets
                   Counter32,
           usrPptpStatsFlowDiscardedDataTunnelRecvPackets
                   Counter32,
           usrPptpStatsOutOfOrderDiscardedDataTunnelRecvPackets
                   Counter32,
           usrPptpStatsDataTunnelSendPackets
                   Counter32,
           usrPptpStatsDataTunnelWithdataSendPackets
                   Counter32,
           usrPptpStatsDataTunnelWithoutdataSendPackets
                   Counter32,
           usrPptpStatsDataTunnelFlowControlTimeouts
                   Counter32,
           usrPptpStatsLocalDataTunnelFlowControlEnables
                   Counter32,
           usrPptpStatsRemoteDataTunnelFlowControlEnables
                   Counter32,
           usrPptpStatsDataTunnelReassemblyTimeouts
                   Counter32 }
 usrPptpStatsIndex          OBJECT-TYPE
           SYNTAX          Integer32
           MAX-ACCESS      read-only
           STATUS          current
           DESCRIPTION
              " Should be the same value as pptpConfigIndex to
              reference the same logical pptp protocol stack. "
           ::= { usrPptpStatsEntry 1 }
 usrPptpNumActiveTunnels  OBJECT-TYPE
           SYNTAX          Integer32
           MAX-ACCESS      read-only
           STATUS          current
           DESCRIPTION
              "This object returns the number of PPTP tunnels
              that are currently active. "
           ::= { usrPptpStatsEntry 2 }
 usrPptpStatsNumActiveSessions  OBJECT-TYPE
           SYNTAX          Integer32
           MAX-ACCESS      read-only
           STATUS          current
           DESCRIPTION
              "This object returns the number of PPTP sessions
              that are currently active. "
           ::= { usrPptpStatsEntry 3 }
 usrPptpStatsMalformedPackets    OBJECT-TYPE
           SYNTAX          Counter32
           MAX-ACCESS      read-only
           STATUS          current
           DESCRIPTION
              "This object returns a count of the number of malformed
              packets received by this PPTP stack since it was last
              initialized.   "
           ::= { usrPptpStatsEntry 4 }
  usrPptpStatsControlTunnelRecvPackets   OBJECT-TYPE
           SYNTAX          Counter32
           MAX-ACCESS      read-only
           STATUS          current
           DESCRIPTION
              " This object returns a count of the number of control
              packets received by this PPTP stack since it was last
              initialized."
           ::= { usrPptpStatsEntry 5 }
 usrPptpStatsProcessedControlTunnelRecvPackets   OBJECT-TYPE
           SYNTAX          Counter32
           MAX-ACCESS      read-only
           STATUS          current
           DESCRIPTION
              " This object returns a count of the number of received
              control packets that were processed by this PPTP stack
              since it was last initialized."
           ::= { usrPptpStatsEntry 6 }
 usrPptpStatsControlTunnelSendPackets   OBJECT-TYPE
           SYNTAX          Counter32
           MAX-ACCESS      read-only
           STATUS          current
           DESCRIPTION
              " This object returns a count of the number of control
              packets that were transmitted by this PPTP stack since
              it was last initialized. "
           ::= { usrPptpStatsEntry 7 }
  usrPptpStatsDataTunnelRecvPackets     OBJECT-TYPE
           SYNTAX          Counter32
           MAX-ACCESS      read-only
           STATUS          current
           DESCRIPTION
              " This object returns a count of the number of data
              packets that were received by this PPTP stack since
              it was last initialized. "
           ::= { usrPptpStatsEntry 8 }
   usrPptpStatsDataTunnelWithdataRecvPackets     OBJECT-TYPE
           SYNTAX          Counter32
           MAX-ACCESS      read-only
           STATUS          current
           DESCRIPTION
              " This object returns a count of the number of data
              packets that were received with data by this PPTP stack
              since it was last initialized. "
           ::= { usrPptpStatsEntry 9 }
   usrPptpStatsDataTunnelWithoutdataRecvPackets    OBJECT-TYPE
           SYNTAX          Counter32
           MAX-ACCESS      read-only
           STATUS          current
           DESCRIPTION
              " This object returns a count of the number of Zero
              Length data packets that were received by this PPTP
              stack since it was last initialized. "
           ::= { usrPptpStatsEntry 10 }
    usrPptpStatsProcessedDataTunnelRecvPackets  OBJECT-TYPE
           SYNTAX          Counter32
           MAX-ACCESS      read-only
           STATUS          current
           DESCRIPTION
              " This object returns a count of the number of data
              packets that were received and processed by this PPTP
              stack since it was last initialized."
           ::= { usrPptpStatsEntry 11 }
    usrPptpStatsInSequenceDataTunnelRecvPackets    OBJECT-TYPE
           SYNTAX          Counter32
           MAX-ACCESS      read-only
           STATUS          current
           DESCRIPTION
              " This object returns a count of the number of data
              packets that were received in sequence by this PPTP
              stack since it was last initialized. "
           ::= { usrPptpStatsEntry 12 }
     usrPptpStatsOutSequenceDataTunnelRecvPackets    OBJECT-TYPE
           SYNTAX          Counter32
           MAX-ACCESS      read-only
           STATUS          current
           DESCRIPTION
              " This object returns a count of the number of data
              packets that were received out of sequence by this
              PPTP stack since it was last initialized."
           ::= { usrPptpStatsEntry 13 }
     usrPptpStatsInOrderDataTunnelRecvPackets   OBJECT-TYPE
           SYNTAX          Counter32
           MAX-ACCESS      read-only
           STATUS          current
           DESCRIPTION
              " This object returns a count of the number of data
              packets that were received in order by this PPTP
              stack since it was last initialized. "
           ::= { usrPptpStatsEntry 14 }
       usrPptpStatsOutOfOrderDataTunnelRecvPackets     OBJECT-TYPE
           SYNTAX          Counter32
           MAX-ACCESS      read-only
           STATUS          current
           DESCRIPTION
              " This object returns a count of the number of data
              packets that were received out of order by this PPTP
              stack since it was last initialized. "
           ::= { usrPptpStatsEntry 15 }
         usrPptpStatsFlowDiscardedDataTunnelRecvPackets    OBJECT-TYPE
           SYNTAX          Counter32
           MAX-ACCESS      read-only
           STATUS          current
           DESCRIPTION
              " This object returns a count of the number of data
              packets that were received and discarded due to flow
              control by this PPTP stack since it was last initialized."
           ::= { usrPptpStatsEntry 16 }
         usrPptpStatsOutOfOrderDiscardedDataTunnelRecvPackets   OBJECT-TYPE
           SYNTAX          Counter32
           MAX-ACCESS      read-only
           STATUS          current
           DESCRIPTION
              " This object returns a count of the number of data
              packets that were received and discarded due to
              ordering by this PPTP stack since it was last initialized."
           ::= { usrPptpStatsEntry 17 }
        usrPptpStatsDataTunnelSendPackets    OBJECT-TYPE
           SYNTAX          Counter32
           MAX-ACCESS      read-only
           STATUS          current
           DESCRIPTION
              " This object returns a count of the number of data
              packets that were transmitted on the data Tunnel by
              this PPTP stack since it was last initialized."
           ::= { usrPptpStatsEntry 18 }
      usrPptpStatsDataTunnelWithdataSendPackets    OBJECT-TYPE
           SYNTAX          Counter32
           MAX-ACCESS      read-only
           STATUS          current
           DESCRIPTION
              " This object returns a count of the number of data
              packets that were transmitted with data by this PPTP
              stack since it was last initialized. "
           ::= { usrPptpStatsEntry 19 }
       usrPptpStatsDataTunnelWithoutdataSendPackets    OBJECT-TYPE
           SYNTAX          Counter32
           MAX-ACCESS      read-only
           STATUS          current
           DESCRIPTION
              " This object returns a count of the number of Zero
              length data packets that were transmitted by this PPTP
              stack since it was last initialized."
           ::= { usrPptpStatsEntry 20 }
       usrPptpStatsDataTunnelFlowControlTimeouts      OBJECT-TYPE
           SYNTAX          Counter32
           MAX-ACCESS      read-only
           STATUS          current
           DESCRIPTION
              " This object returns a count of the number of data
              Tunnel flow control time-outs seen by this PPTP stack
              since it was last initialized.  "
           ::= { usrPptpStatsEntry 21 }
         usrPptpStatsLocalDataTunnelFlowControlEnables    OBJECT-TYPE
           SYNTAX          Counter32
           MAX-ACCESS      read-only
           STATUS          current
           DESCRIPTION
              " This object returns a count of the number of local
              data Tunnel flow control enables seen by this PPTP
              stack since it was last initialized."
           ::= { usrPptpStatsEntry 22 }
         usrPptpStatsRemoteDataTunnelFlowControlEnables    OBJECT-TYPE
           SYNTAX          Counter32
           MAX-ACCESS      read-only
           STATUS          current
           DESCRIPTION
              " This object returns a count of the number of remote
              data Tunnel flow control enables seen by this PPTP
              stack since it was last initialized. "
           ::= { usrPptpStatsEntry 23 }
         usrPptpStatsDataTunnelReassemblyTimeouts    OBJECT-TYPE
           SYNTAX          Counter32
           MAX-ACCESS      read-only
           STATUS          current
           DESCRIPTION
              " This object returns a count of the number of data
              Tunnel re-assembly time-outs seen by this PPTP stack
              since it was last initialized.  "
           ::= { usrPptpStatsEntry 24 }
usrPptpHostTable OBJECT-TYPE
	SYNTAX SEQUENCE OF UsrPptpHostEntry
	MAX-ACCESS not-accessible
	STATUS current
	DESCRIPTION
		"The table of PPTP Hosts. "
::= { usrPptp 2 }
usrPptpHostEntry OBJECT-TYPE
	SYNTAX UsrPptpHostEntry
	MAX-ACCESS not-accessible
	STATUS current
	DESCRIPTION
		"A (conceptual) entry for one pptp Host."
	INDEX { usrPptpHostIndex }
::= { usrPptpHostTable 1 }
UsrPptpHostEntry ::= SEQUENCE {
	usrPptpHostIndex	Integer32,
	usrPptpHostAddress	IpAddress,
	usrPptpHostStatus      RowStatus
	}
usrPptpHostIndex OBJECT-TYPE
	SYNTAX		Integer32
	MAX-ACCESS	not-accessible
	STATUS		current
	DESCRIPTION
		"The logical identifier of the Host Table. "
::= { usrPptpHostEntry 1 }
usrPptpHostAddress OBJECT-TYPE
	SYNTAX		IpAddress
	MAX-ACCESS	read-write
	STATUS		current
	DESCRIPTION
		"The specified or resolved ip address of the named Host. "
	--CONFIGURABLE
::= { usrPptpHostEntry 2 }
usrPptpHostStatus OBJECT-TYPE
	SYNTAX		RowStatus
	MAX-ACCESS	read-write
	STATUS		current
	DESCRIPTION
		"The status of this row of the Host Table. "
	--CONFIGURABLE
::= { usrPptpHostEntry 3 }
usrPptpTunnel OBJECT IDENTIFIER ::= {usrPptp 3}
   usrPptpTunnelQueryTable OBJECT-TYPE
           SYNTAX          SEQUENCE OF UsrPptpTunnelQueryEntry
           MAX-ACCESS      not-accessible
           STATUS          current
           DESCRIPTION
              "A table containing the READ ONLY propietary extension
                           parameters for PPTP Tunnel MIB."
           ::= { usrPptpTunnel 1 }
  usrPptpTunnelQueryEntry OBJECT-TYPE
           SYNTAX          UsrPptpTunnelQueryEntry
           MAX-ACCESS      not-accessible
           STATUS          current
           DESCRIPTION
              "  "
           INDEX           { usrPptpTunnelLogicalStackIndex,
                             usrPptpTunnelLocalControlTunnelId }
           ::= { usrPptpTunnelQueryTable 1 }
   UsrPptpTunnelQueryEntry ::= SEQUENCE {
           usrPptpTunnelLogicalStackIndex
                   Integer32,
           usrPptpTunnelLocalControlTunnelId
                   Integer32,
           usrPptpTunnelControlTunnelState
                   INTEGER,
           usrPptpTunnelLocalInitConnection
                   TruthValue,
           usrPptpTunnelIpAddress
                   IpAddress,
           usrPptpTunnelControlTunnelRecvPkts
                   Counter32,
           usrPptpTunnelProcessedControlTunnelRecvPkts
                   Counter32,
           usrPptpTunnelCtlTunnelSndPkts
                   Counter32,
           usrPptpTunnelRemoteHostName
                   DisplayString,
           usrPptpTunnelDisconnect
                   Integer32,
                   usrPptpTunnelNumActiveSessions
                   Integer32,
                   usrPptpTunnelStartTime 
                   Integer32,     
           usrPptpTunnelDomainName   
                   OCTET STRING }
   usrPptpTunnelLogicalStackIndex OBJECT-TYPE
           SYNTAX          Integer32
           MAX-ACCESS      read-only
           STATUS          current
           DESCRIPTION
              "This object contains a reference to the logical
              pptp protocol stack and must be the same as the
              usrNppptpConfigIndex."
           ::= { usrPptpTunnelQueryEntry 1 }
   usrPptpTunnelLocalControlTunnelId OBJECT-TYPE
           SYNTAX          Integer32
           MAX-ACCESS      read-only
           STATUS          current
           DESCRIPTION
              "This object contains the local tunnel Identifier."
           ::= { usrPptpTunnelQueryEntry 2 }
   usrPptpTunnelControlTunnelState OBJECT-TYPE
           SYNTAX          INTEGER{
                                    noState(1),
                                    tunnelAllocated(2),
                                    tunnelConnecting(3),
                                    tunnelStartingSession(4),
                                    tunnelEstablished(5),
                                    tunnelStoppingSession(6),
                                    tunnelDisconnecting(7),
                                    tunnelLost(8),
                                    idleTimeOut(9)
                                  }
           MAX-ACCESS      read-only
           STATUS          current
           DESCRIPTION
              "This field contains the current state of
              the control tunnel. "
           ::= { usrPptpTunnelQueryEntry 3 }
   usrPptpTunnelLocalInitConnection OBJECT-TYPE
           SYNTAX          TruthValue
           MAX-ACCESS      read-only
           STATUS          current
           DESCRIPTION
              "This object indicates whether the tunnel was
              generated locally or not.  When this object
              returns a value of true(1) the tunnel was
              locally generated."
           ::= { usrPptpTunnelQueryEntry 4 }
   usrPptpTunnelIpAddress OBJECT-TYPE
            SYNTAX          IpAddress
            MAX-ACCESS      read-only
            STATUS          current
            DESCRIPTION
              "IP address of the remote peer."
            ::= { usrPptpTunnelQueryEntry 5 }
   usrPptpTunnelControlTunnelRecvPkts OBJECT-TYPE
           SYNTAX          Counter32
           MAX-ACCESS      read-only
           STATUS          current
           DESCRIPTION
              "This object contains the number of control packets
              received on the control tunnel."
           ::= { usrPptpTunnelQueryEntry 6 }
    usrPptpTunnelProcessedControlTunnelRecvPkts OBJECT-TYPE
            SYNTAX          Counter32
            MAX-ACCESS      read-only
            STATUS          current
            DESCRIPTION
               "This object contains the number of received packets
               which were processed."
            ::= { usrPptpTunnelQueryEntry 7 }
     usrPptpTunnelCtlTunnelSndPkts OBJECT-TYPE
           SYNTAX          Counter32
           MAX-ACCESS      read-only
           STATUS          current
           DESCRIPTION
              "This object contains the number of packets transmitted."
           ::= { usrPptpTunnelQueryEntry 8 }
    usrPptpTunnelRemoteHostName OBJECT-TYPE
             SYNTAX          DisplayString (SIZE(0..255))
             MAX-ACCESS      read-only
             STATUS          current
             DESCRIPTION
              "This object contains the host name of the PPTP peer."
           ::= { usrPptpTunnelQueryEntry 9 }
    usrPptpTunnelDisconnect OBJECT-TYPE
           SYNTAX          Integer32
           MAX-ACCESS      read-write
           STATUS          current
           DESCRIPTION
              "This object is used to disconnect a specific tunnel.
               Setting this object to any integer value will 
               disconnect the tunnel"
           ::= { usrPptpTunnelQueryEntry 10 }
   usrPptpTunnelNumActiveSessions OBJECT-TYPE
           SYNTAX          Integer32
           MAX-ACCESS      read-only
           STATUS          current
           DESCRIPTION   
              "This object contains the number of sessions beloning to the tunnel."
           ::= { usrPptpTunnelQueryEntry 11 }
   usrPptpTunnelStartTime OBJECT-TYPE
           SYNTAX          Integer32
           MAX-ACCESS      read-only
           STATUS          current  
           DESCRIPTION   
              "This object contains the time elapsed since the tunnel was set up."
           ::= { usrPptpTunnelQueryEntry 12 }
   usrPptpTunnelDomainName OBJECT-TYPE
           SYNTAX          OCTET STRING
           MAX-ACCESS      read-only
           STATUS          current
           DESCRIPTION
              "This object contains the Domain Name of the L2TP peer."
          ::= { usrPptpTunnelQueryEntry 13 }
   usrPptpSession OBJECT-IDENTITY
          STATUS         current 
          DESCRIPTION           
             "The root of PPTP Session Module Object-identifiers."
          ::= { usrPptp 4 }
    usrPptpSessionTable OBJECT-TYPE
           SYNTAX    SEQUENCE OF UsrPptpSessionEntry
           MAX-ACCESS not-accessible
           STATUS current
           DESCRIPTION
              ""
           ::= { usrPptpSession 1 }
     usrPptpSessionEntry OBJECT-TYPE
           SYNTAX          UsrPptpSessionEntry
           MAX-ACCESS      not-accessible
           STATUS          current
           DESCRIPTION
              "."
           INDEX          {usrPptpSessionLogicalStackIndex,
                           usrPptpSessionTunnelID , usrPptpSessionLocalCallID }
           ::= { usrPptpSessionTable 1 }
       UsrPptpSessionEntry ::= SEQUENCE {
          usrPptpSessionLogicalStackIndex
                   Integer32,
          usrPptpSessionTunnelID
                   Integer32,
          usrPptpSessionLocalCallID
                   Integer32,
          usrPptpSessionRemoteCallID
                   Integer32,
	  usrPptpSessionPeerName
                   DisplayString,
          usrPptpSessionDuration
                   MilliSeconds,
          usrPptpSessionLineState
                   INTEGER,
          usrPptpSessionCallDeviceNumber
                   Integer32,
          usrPptpSessionCallSerialNumber
                   DisplayString,
          usrPptpSessionConnectBps
                   Integer32,
          usrPptpSessionCallBearerType
                   INTEGER,
          usrPptpSessionFramingType
                   INTEGER,
          usrPptpSessionLocalRecvPacketWindow
                   Integer32,
          usrPptpSessionRemoteRecvPacketWindow
                   Integer32,
          usrPptpSessionDataTunnelRecvPackets
                   Counter32,
          usrPptpSessionDataTunnelWithDataRecvPackets
                   Counter32,
          usrPptpSessionDataTunnelWithoutDataRecvPackets 
                   Counter32,
          usrPptpSessionProcessedDataTunnelRecvPackets
                   Counter32,
          usrPptpSessionInSequenceDataTunnelRecvPackets
                   Counter32,
          usrPptpSessionOutSequenceDataTunnelRecvPackets
                   Counter32,
          usrPptpSessionInOrderDatTunnelRecvPackets
                   Counter32,
          usrPptpSessionOutOfOrderDataTunnelRecvPackets
                   Counter32,
          usrPptpSessionFlowDiscardedDataTunnelRecvPackets
                   Counter32,
          usrPptpSessionOutOfOrderDiscardedDataTunnelRecvPackets
                   Counter32,
          usrPptpSessionDataTunnelSendPackets
                   Counter32,
          usrPptpSessionDataTunnelWithDataSendPackets
                   Counter32,
          usrPptpSessionDataTunnelWithoutDataSendPackets
                   Counter32,
          usrPptpSessionDataTunnelFlowControlTimeouts
                   Counter32,
          usrPptpSessionLocalDataTunnelFlowControlOn
                   TruthValue,
          usrPptpSessionLocalDataTunnelFlowControlEnables
                   Counter32,
          usrPptpSessionRemoteDataTunnelFlowwControlOn
                   TruthValue,
          usrPptpSessionRemoteDataTunnelFlowControlEnables
                   Counter32,
          usrPptpSessionDataTunnelReassemblyTimeouts
                   Counter32,
          usrPptpSessionDisconnect
                   Integer32,
           usrPptpSessionDomainName   
                   OCTET STRING }
    usrPptpSessionLogicalStackIndex OBJECT-TYPE
           SYNTAX          Integer32
           MAX-ACCESS      read-only
           STATUS          current
           DESCRIPTION
              "This object contains a reference to the logical
              pptp protocol stack and must be the same as the
              pptpConfigIndex and pptpTunelLogicalStackIndex."
           ::= { usrPptpSessionEntry 1 }
    usrPptpSessionTunnelID OBJECT-TYPE
           SYNTAX          Integer32
           MAX-ACCESS      read-only
           STATUS          current
           DESCRIPTION
              "This object contains the control Channel Tunnel
              identifier for this session"
           ::= { usrPptpSessionEntry 2 }
      usrPptpSessionLocalCallID  OBJECT-TYPE
           SYNTAX          Integer32
           MAX-ACCESS      read-only
           STATUS          current
           DESCRIPTION
              "This object contains the local call identifier
              for the session.  "
           ::= { usrPptpSessionEntry 3 }
      usrPptpSessionRemoteCallID OBJECT-TYPE
           SYNTAX          Integer32
           MAX-ACCESS      read-only
           STATUS          current
           DESCRIPTION
              "This object contains the remote call identifier
              for the session.  "
           ::= { usrPptpSessionEntry 4 }
      usrPptpSessionPeerName  OBJECT-TYPE
           SYNTAX          DisplayString
           MAX-ACCESS      read-only
           STATUS          current
           DESCRIPTION
              " identifies the peer session name on this interface.
              This is typically the login name of the remote user "
           ::= { usrPptpSessionEntry 5 }
      usrPptpSessionDuration     OBJECT-TYPE
           SYNTAX          MilliSeconds
           MAX-ACCESS      read-only
           STATUS          current
           DESCRIPTION
           " Number of milliseconds the session has been up on this
           interface "
           ::= { usrPptpSessionEntry 6 }
      usrPptpSessionLineState  OBJECT-TYPE
           SYNTAX          INTEGER {
                                    noState(1),
                                    allocated(2),
                                    waitingControlTunnel(3),
                                    calling(4),
                                    offering(5),
                                    answering(6),
                                    connected(7),
                                    disconnectingLocal(8),
                                    disconnectingRemote(9),
                                    lostControlTunnel(10)
                                   }
           MAX-ACCESS      read-only
           STATUS          current
           DESCRIPTION
              "This object contains the current state of the
              control Tunnel. "
           ::= { usrPptpSessionEntry 7 }
       usrPptpSessionCallDeviceNumber    OBJECT-TYPE
           SYNTAX          Integer32
           MAX-ACCESS      read-only
           STATUS          current
           DESCRIPTION
              "NO DESCRIPTION PROVIDED"
           ::= { usrPptpSessionEntry 8 }
       usrPptpSessionCallSerialNumber    OBJECT-TYPE
           SYNTAX          DisplayString
           MAX-ACCESS      read-only
           STATUS          current
           DESCRIPTION
              "This object contains the serial number that applies
              to the session.  "
           ::= { usrPptpSessionEntry 9 }
       usrPptpSessionConnectBps   OBJECT-TYPE
           SYNTAX          Integer32
           MAX-ACCESS      read-only
           STATUS          current
           DESCRIPTION
              "This object returns the baud rate which this session
              was established at."
           ::= { usrPptpSessionEntry 10 }
        usrPptpSessionCallBearerType    OBJECT-TYPE
            SYNTAX          INTEGER {
                                    digital(2),
                                    analog(1)
                                     }
            MAX-ACCESS      read-only
            STATUS          current
            DESCRIPTION
               "This object returns the bearer type that applies to
                this session."
           ::= { usrPptpSessionEntry 11 }
         usrPptpSessionFramingType  OBJECT-TYPE
           SYNTAX          INTEGER {
                                    asynchronous(1),
                                    synchronous(2)
                                    }
           MAX-ACCESS      read-only
           STATUS          current
           DESCRIPTION
              "This object returns the framing type used for this
              session.  "
           ::= { usrPptpSessionEntry 12 }
   usrPptpSessionLocalRecvPacketWindow    OBJECT-TYPE
           SYNTAX          Integer32
           MAX-ACCESS      read-only
           STATUS          current
           DESCRIPTION
              "This object returns the local send window size for
              this session."
           ::= { usrPptpSessionEntry 13 }
   usrPptpSessionRemoteRecvPacketWindow    OBJECT-TYPE
           SYNTAX          Integer32
           MAX-ACCESS      read-only
           STATUS          current
           DESCRIPTION
              "This object returns the remote send window size for
              this session."
           ::= { usrPptpSessionEntry 14 }
  usrPptpSessionDataTunnelRecvPackets    OBJECT-TYPE
           SYNTAX          Counter32
           MAX-ACCESS      read-only
           STATUS          current
           DESCRIPTION
              "This object returns the total number of packets received
              on the data Tunnel for this session. "
           ::= { usrPptpSessionEntry 15 }
   usrPptpSessionDataTunnelWithDataRecvPackets    OBJECT-TYPE
           SYNTAX          Counter32
           MAX-ACCESS      read-only
           STATUS          current
           DESCRIPTION
              "This object returns the total number of packets received
              on the data Tunnel for this session which contained data. "
           ::= { usrPptpSessionEntry 16 }
   usrPptpSessionDataTunnelWithoutDataRecvPackets    OBJECT-TYPE
           SYNTAX          Counter32
           MAX-ACCESS      read-only
           STATUS          current
           DESCRIPTION
              "This object returns the total number of Zero Length
              packets received on the data Tunnel for this session. "
           ::= { usrPptpSessionEntry 17 }
   usrPptpSessionProcessedDataTunnelRecvPackets    OBJECT-TYPE
           SYNTAX          Counter32
           MAX-ACCESS      read-only
           STATUS          current
           DESCRIPTION
              "This object returns the total number of packets
              received on the data Tunnel for this session which
              were processed. "
           ::= { usrPptpSessionEntry 18 }
    usrPptpSessionInSequenceDataTunnelRecvPackets    OBJECT-TYPE
           SYNTAX          Counter32
           MAX-ACCESS      read-only
           STATUS          current
           DESCRIPTION
              "This object returns the total number of packets
              received on the data Tunnel for this session which
              were received in sequence.  "
           ::= { usrPptpSessionEntry 19 }
    usrPptpSessionOutSequenceDataTunnelRecvPackets    OBJECT-TYPE
           SYNTAX          Counter32
           MAX-ACCESS      read-only
           STATUS          current
           DESCRIPTION
              "This object returns the total number of packets
              received on the data Tunnel for this session which
              were received out of sequence. "
           ::= { usrPptpSessionEntry 20 }
    usrPptpSessionInOrderDatTunnelRecvPackets    OBJECT-TYPE
           SYNTAX          Counter32
           MAX-ACCESS      read-only
           STATUS          current
           DESCRIPTION
              "This object returns the total number of packets
              received on the data Tunnel for this session which
              were received in order. "
           ::= { usrPptpSessionEntry 21 }
   usrPptpSessionOutOfOrderDataTunnelRecvPackets    OBJECT-TYPE
           SYNTAX          Counter32
           MAX-ACCESS      read-only
           STATUS          current
           DESCRIPTION
              "This object returns the total number of packets
              received on the data Tunnel for this session which
              were received out of order. "
           ::= { usrPptpSessionEntry 22 }
    usrPptpSessionFlowDiscardedDataTunnelRecvPackets    OBJECT-TYPE
           SYNTAX          Counter32
           MAX-ACCESS      read-only
           STATUS          current
           DESCRIPTION
              "This object returns the total number of packets
              received on the data Tunnel for this session which
              were discarded due to flow control. "
           ::= { usrPptpSessionEntry 23 }
    usrPptpSessionOutOfOrderDiscardedDataTunnelRecvPackets        OBJECT-TYPE
           SYNTAX          Counter32
           MAX-ACCESS      read-only
           STATUS          current
           DESCRIPTION
              "This object returns the total number of packets
              received on the data Tunnel for this session which
              were discarded due to ordering. "
           ::= { usrPptpSessionEntry 24 }
  usrPptpSessionDataTunnelSendPackets    OBJECT-TYPE
           SYNTAX          Counter32
           MAX-ACCESS      read-only
           STATUS          current
           DESCRIPTION
              "This object returns the total number of packets
              transmitted on the data Tunnel for this session.  "
           ::= { usrPptpSessionEntry 25 }
   usrPptpSessionDataTunnelWithDataSendPackets    OBJECT-TYPE
           SYNTAX          Counter32
           MAX-ACCESS      read-only
           STATUS          current
           DESCRIPTION
              "This object returns the total number of packets
              transmitted on the data Tunnel for this session
              which contained data.  "
           ::= { usrPptpSessionEntry 26 }
     usrPptpSessionDataTunnelWithoutDataSendPackets    OBJECT-TYPE
           SYNTAX          Counter32
           MAX-ACCESS      read-only
           STATUS          current
           DESCRIPTION
              "This object returns the total number of Zero
              Length packets transmitted on the data Tunnel
              for this session.  "
           ::= { usrPptpSessionEntry 27 }
    usrPptpSessionDataTunnelFlowControlTimeouts    OBJECT-TYPE
           SYNTAX          Counter32
           MAX-ACCESS      read-only
           STATUS          current
           DESCRIPTION
              "This object returns the total number of flow
              control time-outs seen on the data Tunnel for
              this session.  "
           ::= { usrPptpSessionEntry 28 }
   usrPptpSessionLocalDataTunnelFlowControlOn    OBJECT-TYPE
           SYNTAX          TruthValue
           MAX-ACCESS      read-only
           STATUS          current
           DESCRIPTION
              "This object returns the current local flow control
              state for the data Tunnel of this session."
           ::= { usrPptpSessionEntry 29 }
   usrPptpSessionLocalDataTunnelFlowControlEnables    OBJECT-TYPE
           SYNTAX          Counter32
           MAX-ACCESS      read-only
           STATUS          current
           DESCRIPTION
              "This object returns the total number of  local flow
              control enables seen on the data Tunnel for this session. "
           ::= { usrPptpSessionEntry 30 }
    usrPptpSessionRemoteDataTunnelFlowwControlOn    OBJECT-TYPE
           SYNTAX          TruthValue
           MAX-ACCESS      read-only
           STATUS          current
           DESCRIPTION
              "This object returns the current remote flow control
              state for the data Tunnel of this session."
           ::= { usrPptpSessionEntry 31 }
    usrPptpSessionRemoteDataTunnelFlowControlEnables    OBJECT-TYPE
           SYNTAX          Counter32
           MAX-ACCESS      read-only
           STATUS          current
           DESCRIPTION
              "This object returns the number of  remote flow control
              enables seen on the data Tunnel for this session."
           ::= { usrPptpSessionEntry 32 }
     usrPptpSessionDataTunnelReassemblyTimeouts    OBJECT-TYPE
           SYNTAX          Counter32
           MAX-ACCESS      read-only
           STATUS          current
           DESCRIPTION
              "This object returns the nubmer of re-assembly time-outs
              seen on the data Tunnel for this session."
           ::= { usrPptpSessionEntry 33 }
      usrPptpSessionDisconnect OBJECT-TYPE
           SYNTAX          Integer32
           MAX-ACCESS      read-write
           STATUS          current
           DESCRIPTION
              "This object is used to disconnect a specific tunnel.
               Setting this object to any integer value will 
               disconnect the session"
           ::= { usrPptpSessionEntry 34 }
   usrPptpSessionDomainName OBJECT-TYPE
           SYNTAX          OCTET STRING
           MAX-ACCESS      read-only
           STATUS          current
           DESCRIPTION
              "This object contains the Domain Name of the L2TP peer."
          ::= { usrPptpSessionEntry 35 }
      usrPPTPConfigFileName OBJECT-TYPE
            SYNTAX      DisplayString
            MAX-ACCESS  read-only
            STATUS      current
            DESCRIPTION
           "The name of a ConfigFile to read/write permanent database records.
            If the value of this object is an empty string, then the
            PPTP process uses the default name `@file://PptpProcess.cfg'. "
            ::= { usrPptp 5 }
 usrPPTPCFMStatusFlag  OBJECT-TYPE
          SYNTAX         UsrConfigStatus
          MAX-ACCESS     read-write
          STATUS         current
          DESCRIPTION
                 "CFM Config Flag"
          ::= { usrPptp 6 }
END         -- End of USR-PPTP-MIB DEFINITIONS
-- ************************************************************************
