ACC-QTP DEFINITIONS ::= BEGIN

    IMPORTS
	 OBJECT-TYPE, IpAddress, TimeTicks, Gauge, Counter FROM RFC1155-SMI
        accTrapLogSeqNum FROM ACC-SYSTEM
accBRG, DisplayString, RowStatus, IfIndex, SmdsAddress
             FROM ACC-MIB;

-- Qtp Group
        accQtp OBJECT IDENTIFIER ::= { accBRG 82 }
 -- QTP Server Group
        accQtpServer OBJECT IDENTIFIER ::= { accQtp 1 }
		accQtpSrvParmsTable	OBJECT-TYPE
	    		SYNTAX	SEQUENCE OF AccQtpSrvParEntry
	    		ACCESS	not-accessible
	    		STATUS	mandatory
	    		DESCRIPTION
	      		"QTP Server parameters table containing parameters
			for all servers installed on this router."
	    		::= { accQtpServer 1 }
	        accQtpSrvParEntry OBJECT-TYPE
	                SYNTAX AccQtpSrvParEntry
	                ACCESS not-accessible
	                STATUS mandatory
	                DESCRIPTION
                        "An entry in the QTP Server parameters table"
	                INDEX  { accQtpSrvAddr }
	                ::= { accQtpSrvParmsTable 1 }
                AccQtpSrvParEntry ::= SEQUENCE {
                        accQtpSrvAddr IpAddress,
                        accQtpSrvEntryStatus INTEGER,
                        accQtpSrvPort INTEGER,
                        accQtpSrvMaxMsg INTEGER,
                        accQtpSrvPkgInterval INTEGER,
                        accQtpSrvStatusDelay TimeTicks,
                        accQtpSrvAckTimer TimeTicks,
                        accQtpSrvMaxCkt INTEGER,
                        accQtpSrvAdStatus INTEGER,
                        accQtpSrvIdleTime TimeTicks,
                        accQtpSrvMsgLvl INTEGER
                        }
                accQtpSrvAddr OBJECT-TYPE
                        SYNTAX	IpAddress
                        ACCESS	read-write
                        STATUS	mandatory
                        DESCRIPTION
                        "QTP server IP address."
                        ::= { accQtpSrvParEntry 1 }
                accQtpSrvEntryStatus OBJECT-TYPE
                        SYNTAX	INTEGER {
                        valid(1),
                        deleted(2)
                        }
                        ACCESS	read-write
                        STATUS	mandatory
                        DESCRIPTION
                        "QTP server entry status, indicating whether it is 
                        valid or deleted."
                        ::= { accQtpSrvParEntry 2 }
                accQtpSrvPort OBJECT-TYPE
                        SYNTAX	INTEGER
                        ACCESS	read-write
                        STATUS	mandatory
                        DESCRIPTION
                        "UDP port number of QTP server."
                        ::= { accQtpSrvParEntry 3 }
                accQtpSrvMaxMsg OBJECT-TYPE
                        SYNTAX	INTEGER (0..100)
                        ACCESS	read-write
                        STATUS	mandatory
                        DESCRIPTION
                        "Max number of QTP messages per datagram."
                        ::= { accQtpSrvParEntry 4 }
                accQtpSrvPkgInterval OBJECT-TYPE
                        SYNTAX	INTEGER (0..5000)
                        ACCESS	read-write
                        STATUS	mandatory
                        DESCRIPTION
                        "Maximum time (in msecs) a packed QTP datagram is
                        held before transmission."
                        ::= { accQtpSrvParEntry 5 }
                accQtpSrvStatusDelay OBJECT-TYPE
                        SYNTAX	TimeTicks
                        ACCESS	read-write
                        STATUS	mandatory
                        DESCRIPTION
                        "Delay (in secs) between QTP link status messages."
                        ::= { accQtpSrvParEntry 6 }
                accQtpSrvAckTimer OBJECT-TYPE
                        SYNTAX	TimeTicks 
                        ACCESS	read-write
                        STATUS	mandatory
                        DESCRIPTION
                        "Maximum time (in secs) QTP waits for an 
                        acknowledgement (call request & call clear)."
                        ::= { accQtpSrvParEntry 7 }
                accQtpSrvMaxCkt OBJECT-TYPE
                        SYNTAX	INTEGER (1..255)
                        ACCESS	read-write
                        STATUS	mandatory
                        DESCRIPTION
                        "Maximum no. of active circuits for this link."
                        ::= { accQtpSrvParEntry 8 }
                accQtpSrvAdStatus OBJECT-TYPE
                        SYNTAX	INTEGER {
                        enabled(1),
                        disabled(2),
                        busyout(3)
                        }
                        ACCESS	read-write
                        STATUS	mandatory
                        DESCRIPTION
                        "Administrative status of the QTP link."
                        ::= { accQtpSrvParEntry 9 }
                accQtpSrvIdleTime OBJECT-TYPE
                        SYNTAX	TimeTicks 
                        ACCESS	read-write
                        STATUS	mandatory
                        DESCRIPTION
                        "Maximum time (in secs) a QTP channel is kept open
                        in absence of data."
                        ::= { accQtpSrvParEntry 10 }
                accQtpSrvMsgLvl OBJECT-TYPE
                        SYNTAX	INTEGER (1..7)
                        ACCESS	read-write
                        STATUS	mandatory
                        DESCRIPTION
                        "Debug message level for this QTP link."
                        ::= { accQtpSrvParEntry 11 }
--
-- QTP server status table
--
		accQtpSrvStatusTable	OBJECT-TYPE
	    		SYNTAX	SEQUENCE OF AccQtpSrvStatusEntry
	    		ACCESS	not-accessible
	    		STATUS	mandatory
	    		DESCRIPTION
	      		"QTP Server status table containing status
			for all servers installed on this router."
	    		::= { accQtpServer 2 }
	        accQtpSrvStatusEntry OBJECT-TYPE
	                SYNTAX AccQtpSrvStatusEntry
	                ACCESS not-accessible
	                STATUS mandatory
	                DESCRIPTION
                        "An entry in the QTP Server status table"
	                INDEX  { accQtpSrvAddr }
	                ::= { accQtpSrvStatusTable 1 }
                AccQtpSrvStatusEntry ::= SEQUENCE {
                        accQtpSrvActiveChnls Gauge,
                        accQtpSrvClrCauseTx INTEGER,
                        accQtpSrvClrTxLcn INTEGER,
                        accQtpSrvClrCauseRx INTEGER,
                        accQtpSrvClrRxLcn INTEGER,
                        accQtpSrvRemFlowCntl INTEGER,
                        accQtpSrvLclFlowCntl INTEGER,
                        accQtpSrvOpStatus INTEGER
                        }
                accQtpSrvActiveChnls OBJECT-TYPE
                        SYNTAX	Gauge
                        ACCESS	read-only
                        STATUS	mandatory
                        DESCRIPTION
                        "Number of active channels."
                        ::= { accQtpSrvStatusEntry 1 }
                accQtpSrvClrCauseTx OBJECT-TYPE
			SYNTAX INTEGER (0..255)
                        ACCESS	read-only
                        STATUS	mandatory
                        DESCRIPTION
                        "Last clear sent cause code."
                        ::= { accQtpSrvStatusEntry 2 }
                accQtpSrvClrTxLcn OBJECT-TYPE
                        SYNTAX	INTEGER
                        ACCESS	read-only
                        STATUS	mandatory
                        DESCRIPTION
                        "LCN on which last clear was sent."
                        ::= { accQtpSrvStatusEntry 3 }
                accQtpSrvClrCauseRx OBJECT-TYPE
			SYNTAX INTEGER (0..255)
                        ACCESS	read-only
                        STATUS	mandatory
                        DESCRIPTION
                        "Cause code of last clear/reject received."
                        ::= { accQtpSrvStatusEntry 4 }
                accQtpSrvClrRxLcn OBJECT-TYPE
                        SYNTAX	INTEGER
                        ACCESS	read-only
                        STATUS	mandatory
                        DESCRIPTION
                        "LCN on which last clear/reject received."
                        ::= { accQtpSrvStatusEntry 5 }
                accQtpSrvRemFlowCntl OBJECT-TYPE
                        SYNTAX	INTEGER {
                        available (1),
                        partially-congested (2),
                        congested (3),
                        shutdown (4)
                        }
                        ACCESS	read-only
                        STATUS	mandatory
                        DESCRIPTION
                        "Remote flow-control state."
                        ::= { accQtpSrvStatusEntry 6 }
                accQtpSrvLclFlowCntl OBJECT-TYPE
                        SYNTAX	INTEGER {
                        available (1),
                        partially-congested (2),
                        congested (3),
                        shutdown (4)
                        }
                        ACCESS	read-only
                        STATUS	mandatory
                        DESCRIPTION
                        "Local flow-control state."
                        ::= { accQtpSrvStatusEntry 7 }
                accQtpSrvOpStatus OBJECT-TYPE
                        SYNTAX	INTEGER {
                        initializing (1),
                        active (2),
                        disabled (3)
                        }
                        ACCESS	read-only
                        STATUS	mandatory
                        DESCRIPTION
                        "Operational state."
                        ::= { accQtpSrvStatusEntry 8 }
--
-- QTP server statistics table
--
		accQtpSrvStatsTable	OBJECT-TYPE
	    		SYNTAX	SEQUENCE OF AccQtpSrvStatsEntry
	    		ACCESS	not-accessible
	    		STATUS	mandatory
	    		DESCRIPTION
	      		"QTP Server statistics table containing statistics
			for all servers installed on this router."
	    		::= { accQtpServer 3 }
	        accQtpSrvStatsEntry OBJECT-TYPE
	                SYNTAX AccQtpSrvStatsEntry
	                ACCESS not-accessible
	                STATUS mandatory
	                DESCRIPTION
                        "An entry in the QTP Server statistics table"
	                INDEX  { accQtpSrvAddr }
	                ::= { accQtpSrvStatsTable 1 }
                AccQtpSrvStatsEntry ::= SEQUENCE {
                        accQtpSrvOKCalls Counter,
                        accQtpSrvFailCalls Counter,
                        accQtpSrvTxDataMsgs Counter,
                        accQtpSrvRxDataMsgs Counter,
                        accQtpSrvAckTimouts Counter,
                        accQtpSrvProtoErrs Counter,
                        accQtpSrvTxStatMsgs Counter,
                        accQtpSrvRxStatMsgs Counter,
                        accQtpSrvTxDgrms Counter,
                        accQtpSrvRxDgrms Counter,
                        accQtpSrvTxOctets Counter,
                        accQtpSrvRxOctets Counter
                        }
                accQtpSrvOKCalls OBJECT-TYPE
                        SYNTAX	Counter
                        ACCESS	read-only
                        STATUS	mandatory
                        DESCRIPTION
                        "Successful QTP call requests."
                        ::= { accQtpSrvStatsEntry 1 }
                accQtpSrvFailCalls OBJECT-TYPE
                        SYNTAX	Counter
                        ACCESS	read-only
                        STATUS	mandatory
                        DESCRIPTION
                        "Unsuccessful QTP call requests."
                        ::= { accQtpSrvStatsEntry 2 }
                accQtpSrvTxDataMsgs OBJECT-TYPE
                        SYNTAX	Counter
                        ACCESS	read-only
                        STATUS	mandatory
                        DESCRIPTION
                        "QTP data messages sent."
                        ::= { accQtpSrvStatsEntry 3 }
                accQtpSrvRxDataMsgs OBJECT-TYPE
                        SYNTAX	Counter
                        ACCESS	read-only
                        STATUS	mandatory
                        DESCRIPTION
                        "QTP data messages received."
                        ::= { accQtpSrvStatsEntry 4 }
                accQtpSrvAckTimouts OBJECT-TYPE
                        SYNTAX	Counter
                        ACCESS	read-only
                        STATUS	mandatory
                        DESCRIPTION
                        "Acknowledgement timeouts."
                        ::= { accQtpSrvStatsEntry 5 }
                accQtpSrvProtoErrs OBJECT-TYPE
                        SYNTAX	Counter
                        ACCESS	read-only
                        STATUS	mandatory
                        DESCRIPTION
                        "Protocol errors."
                        ::= { accQtpSrvStatsEntry 6 }
                accQtpSrvTxStatMsgs OBJECT-TYPE
                        SYNTAX	Counter
                        ACCESS	read-only
                        STATUS	mandatory
                        DESCRIPTION
                        "Status messages sent."
                        ::= { accQtpSrvStatsEntry 7 }
                accQtpSrvRxStatMsgs OBJECT-TYPE
                        SYNTAX	Counter
                        ACCESS	read-only
                        STATUS	mandatory
                        DESCRIPTION
                        "Status messages received."
                        ::= { accQtpSrvStatsEntry 8 }
                accQtpSrvTxDgrms OBJECT-TYPE
                        SYNTAX	Counter
                        ACCESS	read-only
                        STATUS	mandatory
                        DESCRIPTION
                        "UDP datagrams sent."
                        ::= { accQtpSrvStatsEntry 9 }
                accQtpSrvRxDgrms OBJECT-TYPE
                        SYNTAX	Counter
                        ACCESS	read-only
                        STATUS	mandatory
                        DESCRIPTION
                        "UDP datagrams received."
                        ::= { accQtpSrvStatsEntry 10 }
                accQtpSrvTxOctets OBJECT-TYPE
                        SYNTAX	Counter
                        ACCESS	read-only
                        STATUS	mandatory
                        DESCRIPTION
                        "Total of all octets sent to QTP server."
                        ::= { accQtpSrvStatsEntry 11 }
                accQtpSrvRxOctets OBJECT-TYPE
                        SYNTAX	Counter
                        ACCESS	read-only
                        STATUS	mandatory
                        DESCRIPTION
                        "Total of all octets received from QTP server."
                        ::= { accQtpSrvStatsEntry 12 }
-- The following are objects for the QTP Routing MIB:
        accQtpRouting OBJECT IDENTIFIER ::= { accQtp 2 }
                accQtpRtCalls OBJECT-TYPE
                        SYNTAX	Counter
                        ACCESS	read-only
                        STATUS	mandatory
                        DESCRIPTION
                        "Number of successfully routed calls."
                        ::= { accQtpRouting 1 }
                accQtpRtSecCalls OBJECT-TYPE
                        SYNTAX	Counter
                        ACCESS	read-only
                        STATUS	mandatory
                        DESCRIPTION
                        "Number of successfully routed calls on secondary
                        links."
                        ::= { accQtpRouting 2 }
                accQtpRtNotConfigs OBJECT-TYPE
                        SYNTAX	Counter
                        ACCESS	read-only
                        STATUS	mandatory
                        DESCRIPTION
                        "Number of times an incoming call was immediately
                        terminated because no route was configured in the
                        service profile (or the QTP servers in the SP were 
                        not added to the configuration)."
                        ::= { accQtpRouting 3 }
                accQtpRtNoRts OBJECT-TYPE
                        SYNTAX	Counter
                        ACCESS	read-only
                        STATUS	mandatory
                        DESCRIPTION
                        "Number of times a call routing request failed 
                        because all QTP servers were shutdown or disabled."
                        ::= { accQtpRouting 4 }
                accQtpRtToQTPFrms OBJECT-TYPE
                        SYNTAX	Counter
                        ACCESS	read-only
                        STATUS	mandatory
                        DESCRIPTION
                        "Number of frames successfully received from modem
                        and switched to a QTP channel."
                        ::= { accQtpRouting 5 }
                accQtpRtToQTPOcts OBJECT-TYPE
                        SYNTAX	Counter
                        ACCESS	read-only
                        STATUS	mandatory
                        DESCRIPTION
                        "Number of bytes successfully received from modem
                        and switched to a QTP channel."
                        ::= { accQtpRouting 6 }
                accQtpRtToMdmFrms OBJECT-TYPE
                        SYNTAX	Counter
                        ACCESS	read-only
                        STATUS	mandatory
                        DESCRIPTION
                        "Number of frames successfully received from a 
                        QTP channel and switched to the mapped modem port."
                        ::= { accQtpRouting 7 }
                accQtpRtToMdmOcts OBJECT-TYPE
                        SYNTAX	Counter
                        ACCESS	read-only
                        STATUS	mandatory
                        DESCRIPTION
                        "Number of bytes successfully received from a QTP
                        channel and switched to the mapped modem port."
                        ::= { accQtpRouting 8 }
                accQtpRtDropQtpFrms OBJECT-TYPE
                        SYNTAX	Counter
                        ACCESS	read-only
                        STATUS	mandatory
                        DESCRIPTION
                        "Number of frames that were received from QTP and
                        dropped because the connection to the modem port was
                        no longer in the routing table ."
                        ::= { accQtpRouting 9 }
                accQtpRtDropMdmFrms OBJECT-TYPE
                        SYNTAX	Counter
                        ACCESS	read-only
                        STATUS	mandatory
                        DESCRIPTION
                        "Number of frames that were received from modem and
                        dropped because the connection to the modem port was 
                        no longer in the routing table ."
                        ::= { accQtpRouting 10 }
-- The following are the objects for the QTP Server Pool MIB:
        accQtpServerPool OBJECT IDENTIFIER ::= { accQtp 3 }
                accQtpSrvPoolTable OBJECT-TYPE
	                SYNTAX SEQUENCE OF AccQtpSrvPoolEntry
	                ACCESS not-accessible
	                STATUS mandatory
	                DESCRIPTION
	                "The QTP Server Pool Table"
                        ::= { accQtpServerPool 1 }
	        accQtpSrvPoolEntry OBJECT-TYPE
	                SYNTAX AccQtpSrvPoolEntry
	                ACCESS not-accessible
	                STATUS mandatory
	                DESCRIPTION
	                "An entry in the QTP Server Pool Table"
	                INDEX  { accQtpPoolSrvAddr , accQtpPoolSvcProfile }
	                ::= { accQtpSrvPoolTable 1 }
                AccQtpSrvPoolEntry ::= SEQUENCE {
                        accQtpPoolSrvAddr IpAddress,
                        accQtpPoolSvcProfile DisplayString,
                        accQtpPoolEntryStatus INTEGER , 
                        accQtpPoolPriority INTEGER
                        }
                accQtpPoolSrvAddr OBJECT-TYPE
                        SYNTAX	IpAddress
                        ACCESS	read-write
                        STATUS	mandatory
                        DESCRIPTION
                        "IP address of QTP server that this pool entry 
                        refers to."
                        ::= { accQtpSrvPoolEntry 1 }
                accQtpPoolSvcProfile OBJECT-TYPE
                        SYNTAX	DisplayString
                        ACCESS	read-write
                        STATUS	mandatory
                        DESCRIPTION
                        "Name of QTP server that this pool entry refers to."
                        ::= { accQtpSrvPoolEntry 2 }
                accQtpPoolEntryStatus OBJECT-TYPE
                        SYNTAX	INTEGER {
                        valid(1),
                        deleted(2)
                        }
                        ACCESS	read-write
                        STATUS	mandatory
                        DESCRIPTION
                        "Status of the pool entry, valid or deleted."
                        ::= { accQtpSrvPoolEntry 3 }
                accQtpPoolPriority OBJECT-TYPE
                        SYNTAX	INTEGER {
                        primary(1),
                        secondary(2)
                        }
                        ACCESS	read-write
                        STATUS	mandatory
                        DESCRIPTION
                        "Indicates whether the QTP server for this pool entry
                        is used as a primary server or a secondary server
                        when routing a QTP call for the service profile
                        linked to this pool entry."
                        ::= { accQtpSrvPoolEntry 4 }

END
