-- Do not edit this file.
-- It is generated automatically by mib-expand
-- from mgstat.mib.in and *.mibdef.
--
--		Lucent Media Gateway Status & Statistics MIB
--		Supported on TNT and APX platforms starting from TAOS 8.0
--
--			Lucent Technologies, Inc.
--			1701 Harbor Bay Pkwy
--			Alameda, CA 94502
--			+1 510 769 6001
--			info@ascend.com
--
--		Copyright (c) 1999 Lucent Technologies, Inc.
--		All rights reserved.
--
--
-- $Id: mgstat.mib.in,v 29.1.2.1 1999/10/04 17:51:39 iakramov Exp $
-- This file is generated automatically for TAOS version 8.0.5.
--
-- 16 Aug 1999:	iakramov	Initial release.

ASCEND-MGSTAT-MIB DEFINITIONS ::= BEGIN

    IMPORTS
	mgGroup		FROM ASCEND-MIB
	Counter32	FROM SNMPv2-SMI
	IpAddress	FROM RFC1155-SMI
	TimeTicks	FROM RFC1155-SMI
	OBJECT-TYPE	FROM RFC-1212;

	--
	-- Media Gateway Status & Statistics Group
	-- Supported on TNT and APX platforms starting from TAOS 8.0
	--
	-- This group contains monitoring and statistical information
	-- for media gateway control interfaces (ASGCP, IPDC, Q.931+).
	--

    mgNumLinks		OBJECT-TYPE
        SYNTAX		INTEGER
	ACCESS		read-only
	STATUS		mandatory
	DESCRIPTION	"Number of media gateway links (link groups)
			available in this system."
	::= { mgGroup 1 }

    mgTable	OBJECT-TYPE
	SYNTAX		SEQUENCE OF MgTableEntry
	ACCESS		not-accessible
	STATUS		mandatory
	DESCRIPTION	"A list of mgTableEntry objects."
	::= { mgGroup 2 }

    mgTableEntry	OBJECT-TYPE
        SYNTAX		MgTableEntry
	ACCESS		not-accessible
	STATUS		mandatory
	DESCRIPTION	"Entry holding information about a group of
			Media Gateway Controllers sharing the same
			signaling link."
	INDEX		{ mgLinkName }
	::= { mgTable 1 }

    MgTableEntry    ::=
        SEQUENCE {
	    mgLinkName				OCTET STRING,
	    mgProtocol				INTEGER,
	    mgAdminStatus			INTEGER,
	    mgOperStatus			INTEGER,
	    mgLastStatusChange			TimeTicks,
	    mgNumInMessages			Counter32,
	    mgNumInOctets			Counter32,
	    mgNumOutMessages			Counter32,
	    mgNumOutOctets			Counter32,
	    mgNumErrors				Counter32,
	    mgNumTimerRecovery			Counter32,
	    mgTransportNumLosses		Counter32,
	    mgTransportNumSwitchover		Counter32,
	    mgTransportTotalNumAlarms		Counter32,
	    mgTransportLastEvent		INTEGER,
	    mgTransportLastEventTime		TimeTicks,
	    mgResetStatistics			INTEGER,
	    mgLastStatisticsReset		TimeTicks
	}

--  Objects in mgTableEntry:

    mgLinkName		OBJECT-TYPE
        SYNTAX		OCTET STRING
	ACCESS		read-only
	STATUS		mandatory
	DESCRIPTION	"Name of this media gateway control group."
	::= { mgTableEntry 1 }

    mgProtocol		OBJECT-TYPE
	SYNTAX		INTEGER	{
                            notApplicable(1), -- MG control is not enabled by hash code, etc.
                            other(2), -- Other (none from the list below)
                            asgcp(3), -- ASGCP (Ascend Signaling Gateway Control Protocol)
                            ipdc(4) -- IPDC (Internet Protocol Device Control)
                        }
	ACCESS		read-only
	STATUS		mandatory
	DESCRIPTION	"Type of the control protocol in use."
	::= { mgTableEntry 2 }

    mgAdminStatus	OBJECT-TYPE
	SYNTAX		INTEGER	{
                            up(1),
                            down(2)
                        }
	ACCESS		read-write
	STATUS		mandatory
	DESCRIPTION	"Administrative status for this media gateway
			control group."
	::= { mgTableEntry 3 }

    mgOperStatus	OBJECT-TYPE
	SYNTAX		INTEGER	{
                            up(1),
                            down(2),
                            unknown(3)
                        }
	ACCESS		read-only
	STATUS		mandatory
	DESCRIPTION	"Current operational status of the signaling link."
	::= { mgTableEntry 4 }

    mgLastStatusChange OBJECT-TYPE
        SYNTAX		TimeTicks
	ACCESS		read-only
	STATUS		mandatory
	DESCRIPTION	"The value of sysUpTime at the time the associated
			link entered its current operational status. If
			the current status was entered prior to the last
			re-initialization of the local network management
			subsystem, then this object contains a zero value."
	::= { mgTableEntry 5 }

    mgNumInMessages	OBJECT-TYPE
	SYNTAX		Counter32
	ACCESS		read-only
	STATUS		mandatory
	DESCRIPTION	"Total number of messages received on the link."
	::= { mgTableEntry 6 }

    mgNumInOctets	OBJECT-TYPE
	SYNTAX		Counter32
	ACCESS		read-only
	STATUS		mandatory
	DESCRIPTION	"Total number of octets received on the link."
	::= { mgTableEntry 7 }

    mgNumOutMessages	OBJECT-TYPE
	SYNTAX		Counter32
	ACCESS		read-only
	STATUS		mandatory
	DESCRIPTION	"Total number of messages sent on the link."
	::= { mgTableEntry 8 }

    mgNumOutOctets	OBJECT-TYPE
	SYNTAX		Counter32
	ACCESS		read-only
	STATUS		mandatory
	DESCRIPTION	"Total number of octets sent on the link."
	::= { mgTableEntry 9 }

    mgNumErrors		OBJECT-TYPE
	SYNTAX		Counter32
	ACCESS		read-only
	STATUS		mandatory
	DESCRIPTION	"Total number of signaling-level errors
			encountered. Includes, but is not limited to,
			number of bad messages received, number of
			failures to sent a message and number of other
			errors."
	::= { mgTableEntry 10 }

    mgNumTimerRecovery	OBJECT-TYPE
	SYNTAX		Counter32
	ACCESS		read-only
	STATUS		mandatory
	DESCRIPTION	"Number of timer recovery events since the
			statistics was last reset.  This reflects
			all timers."
	::= { mgTableEntry 11 }

    mgTransportNumLosses	 OBJECT-TYPE
        SYNTAX		Counter32
	ACCESS		read-only
	STATUS		mandatory
	DESCRIPTION	"Number of times a transport link was lost (excluding
			switch-over cases)."
	::= { mgTableEntry 12 }

    mgTransportNumSwitchover OBJECT-TYPE
        SYNTAX		Counter32
	ACCESS		read-only
	STATUS		mandatory
	DESCRIPTION	"Number of times when the signaling was switched
			over to an alternative link."
	::= { mgTableEntry 13 }

    mgTransportTotalNumAlarms OBJECT-TYPE
        SYNTAX		Counter32
	ACCESS		read-only
	STATUS		mandatory
	DESCRIPTION	"Total number of all alarms issued for
			the transport layer."
	::= { mgTableEntry 14 }

    mgTransportLastEvent	 OBJECT-TYPE
        SYNTAX		INTEGER	{
                            notApplicable(1), -- Invalid/unknown.
                            other(2), -- None from the list below.
                            linkUp(3), -- Transport link is up.
                            linkLoss(4), -- Transport link loss.
                            persistentError(5), -- No link - persistent error.
                            linkShutdown(6), -- Link is shut down.
                            switchOver(7) -- Fail-over.
			}
	ACCESS		read-only
	STATUS		mandatory
	DESCRIPTION	"Last event reported by the transport layer."
	::= { mgTableEntry 15 }

    mgTransportLastEventTime OBJECT-TYPE
        SYNTAX		TimeTicks
	ACCESS		read-only
	STATUS		mandatory
	DESCRIPTION	"The value of sysUpTime at the time when the event
			specified by mgTransportLastEvent occured.
			If the last event occured prior to the last
			re-initialization of the local network management
			subsystem, then this object contains a zero value."
	::= { mgTableEntry 16 }

    mgResetStatistics	OBJECT-TYPE
        SYNTAX		INTEGER	{
                            notApplicable(1), -- Invalid/unknown.
                            other(2), -- None from the list below.
                            reset(3) -- Reset all statistics now.
			}
	ACCESS		read-write
	STATUS		mandatory
	DESCRIPTION	"This object can be used to reset all statistics
			collected for this media gateway link so far.
			Statistics will be reset when the object is SET
			to 'reset'. GET from this object always returns
			'notApplicable'."
	::= { mgTableEntry 17 }

    mgLastStatisticsReset OBJECT-TYPE
        SYNTAX		TimeTicks
	ACCESS		read-only
	STATUS		mandatory
	DESCRIPTION	"The value of sysUpTime at the time when the 
			statistics was reset. If the reset occured
			prior to the last re-initialization of the local
			network management subsystem, this object contains
			a zero value."
	::= { mgTableEntry 18 }

--  End of mgTableEntry.

    mgControllerTable	OBJECT-TYPE
	SYNTAX		SEQUENCE OF MgControllerEntry
	ACCESS		not-accessible
	STATUS		mandatory
	DESCRIPTION	"Addresses of Media Gateway Controllers."
	::= { mgGroup 3 }

    mgControllerEntry	OBJECT-TYPE
	SYNTAX		MgControllerEntry
	ACCESS		not-accessible
	STATUS		mandatory
	DESCRIPTION	"Entry holding information about an individual
			Media Gateway Controller."
	INDEX		{ mgControllerLinkName, mgControllerIndex }
	::= { mgControllerTable 1 }

    MgControllerEntry ::=
	SEQUENCE {
		mgControllerLinkName	OCTET STRING,
		mgControllerIndex	INTEGER,
		mgControllerIPAddress	IpAddress,
	        mgControllerPort	INTEGER,
		mgControllerOperStatus	INTEGER
        }

--  Objects in mgControllerEntry:

    mgControllerLinkName OBJECT-TYPE
        SYNTAX		OCTET STRING
	ACCESS		read-only
	STATUS		mandatory
	DESCRIPTION	"The same as mgLinkName."
	::= { mgControllerEntry 1 }

    mgControllerIndex	OBJECT-TYPE
	SYNTAX		INTEGER
	ACCESS		read-only
	STATUS		mandatory
	DESCRIPTION	"The index number for this Media Gateway Controller
			entry. Its value ranges from 1 to the maximum
			number of controllers per group and identifies
			which controller the entry is associated with."
	::= { mgControllerEntry 2 }

    mgControllerIPAddress OBJECT-TYPE
	SYNTAX		IpAddress
	ACCESS		read-only
	STATUS		mandatory
	DESCRIPTION	"The IP address of the Media Gateway Controller. The 
			value 0.0.0.0 is returned if the entry is invalid."
	::= { mgControllerEntry 3 }

    mgControllerPort	OBJECT-TYPE
	SYNTAX		INTEGER ( 0..'FFFF'h )
        ACCESS		read-only
        STATUS		mandatory
        DESCRIPTION	"TCP port of the Media Gateway Controller. The value
			0 is returned if the entry is invalid."
         ::= { mgControllerEntry 4 }

    mgControllerOperStatus	     OBJECT-TYPE
	SYNTAX		INTEGER {
                            up(1), -- Up/active.
                            down(2), -- Down.
                            standby(3) -- Standby mode.
			}
	ACCESS		read-only
	STATUS		mandatory
	DESCRIPTION	"Status of the transport link to this particular
			Media Gateway Controller."
	::= { mgControllerEntry 5 }

--  End of mgControllerEntry.

END
