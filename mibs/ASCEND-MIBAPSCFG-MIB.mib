--			Ascend mibapscfg MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBAPSCFG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibapsConfig  OBJECT IDENTIFIER ::= { configuration 148}

	-- The mibapsConfig table
	--
	-- This table contains parameters for the mibapsConfig profile
	--

    mibapsConfigTable	OBJECT-TYPE
	SYNTAX		SEQUENCE OF MibapsConfigEntry
	ACCESS		not-accessible
	STATUS		mandatory
	DESCRIPTION	"A list of mibapsConfig profile entries."
	::= { mibapsConfig 1 }

    mibapsConfigEntry	OBJECT-TYPE
	SYNTAX		MibapsConfigEntry
	ACCESS		not-accessible
	STATUS		mandatory
	DESCRIPTION	"A mibapsConfig entry containing objects that
			 maps to the parameters of mibapsConfig profile."
	INDEX		{ apsConfig-Name }
	::= { mibapsConfigTable 1 }

    MibapsConfigEntry ::=
	SEQUENCE {
	    apsConfig-Name
		DisplayString,
	    apsConfig-Active
		INTEGER,
	    apsConfig-LinearProtectionChannel-Shelf
		INTEGER,
	    apsConfig-LinearProtectionChannel-Slot
		INTEGER,
	    apsConfig-LinearProtectionChannel-ItemNumber
		INTEGER,
	    apsConfig-ProtectionMode
		INTEGER,
	    apsConfig-DirectionMode
		INTEGER,
	    apsConfig-RevertiveMode
		INTEGER,
	    apsConfig-WtrTimerDuration
		INTEGER,
	    apsConfig-PsbfFailureTimerDuration
		INTEGER,
	    apsConfig-PsbfClearTimerDuration
		INTEGER,
	    apsConfig-ModeMismatchFailureTimerDuration
		INTEGER,
	    apsConfig-ModeMismatchClearTimerDuration
		INTEGER,
	    apsConfig-ChannelMismatchFailureTimerDuration
		INTEGER,
	    apsConfig-ChannelMismatchClearTimerDuration
		INTEGER,
	    apsConfig-FeplMismatchFailureTimerDuration
		INTEGER,
	    apsConfig-FeplMismatchClearTimerDuration
		INTEGER,
	    apsConfig-ProtectionChannelSignalDegradeExponent
		INTEGER,
	    apsConfig-ProtectionChannelSignalFailureExponent
		INTEGER,
	    apsConfig-WorkingChannelSignalDegradeExponent
		INTEGER,
	    apsConfig-WorkingChannelSignalFailureExponent
		INTEGER,
	    apsConfig-Action-o
		INTEGER
	}

    apsConfig-Name	OBJECT-TYPE
	SYNTAX	DisplayString
	ACCESS	read-only
	STATUS	mandatory
	DESCRIPTION	"Name of APS Config profile."
	::= { mibapsConfigEntry 1 }

    apsConfig-Active	OBJECT-TYPE
	SYNTAX	INTEGER {
		    no (1),
		    yes (2)
		}
	ACCESS	read-write
	STATUS	mandatory
	DESCRIPTION	"TRUE if the working line is to join a protection group, FALSE otherwise."
	::= { mibapsConfigEntry 2 }

    apsConfig-LinearProtectionChannel-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibapsConfigEntry 3 }

    apsConfig-LinearProtectionChannel-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibapsConfigEntry 4 }

    apsConfig-LinearProtectionChannel-ItemNumber	OBJECT-TYPE
	SYNTAX	INTEGER
	ACCESS	read-write
	STATUS	mandatory
	DESCRIPTION	"A number that specifies an addressable entity within the context of shelf and slot."
	::= { mibapsConfigEntry 5 }

    apsConfig-ProtectionMode	OBJECT-TYPE
	SYNTAX	INTEGER {
		    n-1-plus-1 (1),
		    n-1-divide-n (2)
		}
	ACCESS	read-write
	STATUS	mandatory
	DESCRIPTION	"The linear APS protection mode (1+1, 1:n)."
	::= { mibapsConfigEntry 6 }

    apsConfig-DirectionMode	OBJECT-TYPE
	SYNTAX	INTEGER {
		    unidirectional (1),
		    bidirectional (2)
		}
	ACCESS	read-write
	STATUS	mandatory
	DESCRIPTION	"specifies the protection group direction mode"
	::= { mibapsConfigEntry 7 }

    apsConfig-RevertiveMode	OBJECT-TYPE
	SYNTAX	INTEGER {
		    nonRevertive (2),
		    revertive (1)
		}
	ACCESS	read-write
	STATUS	mandatory
	DESCRIPTION	"specifies the protection group revertive mode"
	::= { mibapsConfigEntry 8 }

    apsConfig-WtrTimerDuration	OBJECT-TYPE
	SYNTAX	INTEGER
	ACCESS	read-write
	STATUS	mandatory
	DESCRIPTION	"specifies the protection group's waiting time to revert timer duration (in tens of milliseconds)"
	::= { mibapsConfigEntry 9 }

    apsConfig-PsbfFailureTimerDuration	OBJECT-TYPE
	SYNTAX	INTEGER
	ACCESS	read-write
	STATUS	mandatory
	DESCRIPTION	"specifies the PSBF failure timer duration (in tens of milliseconds)"
	::= { mibapsConfigEntry 10 }

    apsConfig-PsbfClearTimerDuration	OBJECT-TYPE
	SYNTAX	INTEGER
	ACCESS	read-write
	STATUS	mandatory
	DESCRIPTION	"specifies the PSBF clear timer duration (in tens of milliseconds)"
	::= { mibapsConfigEntry 11 }

    apsConfig-ModeMismatchFailureTimerDuration	OBJECT-TYPE
	SYNTAX	INTEGER
	ACCESS	read-write
	STATUS	mandatory
	DESCRIPTION	"Specifies the Mode Mismatch failure timer duration (in tens of milliseconds)"
	::= { mibapsConfigEntry 12 }

    apsConfig-ModeMismatchClearTimerDuration	OBJECT-TYPE
	SYNTAX	INTEGER
	ACCESS	read-write
	STATUS	mandatory
	DESCRIPTION	"Specifies the Mode Mismatch clear timer duration (in tens of milliseconds)"
	::= { mibapsConfigEntry 13 }

    apsConfig-ChannelMismatchFailureTimerDuration	OBJECT-TYPE
	SYNTAX	INTEGER
	ACCESS	read-write
	STATUS	mandatory
	DESCRIPTION	"Specifies the Channel Mismatch Failure Timer duration (in tens of milliseconds)"
	::= { mibapsConfigEntry 14 }

    apsConfig-ChannelMismatchClearTimerDuration	OBJECT-TYPE
	SYNTAX	INTEGER
	ACCESS	read-write
	STATUS	mandatory
	DESCRIPTION	"Specifies the Channel Mismatch Clear Timer duration (in tens of milliseconds)"
	::= { mibapsConfigEntry 15 }

    apsConfig-FeplMismatchFailureTimerDuration	OBJECT-TYPE
	SYNTAX	INTEGER
	ACCESS	read-write
	STATUS	mandatory
	DESCRIPTION	"Specifies the FEPL Failure Mismatch timer duration (in tens of milliseconds)"
	::= { mibapsConfigEntry 16 }

    apsConfig-FeplMismatchClearTimerDuration	OBJECT-TYPE
	SYNTAX	INTEGER
	ACCESS	read-write
	STATUS	mandatory
	DESCRIPTION	"Specifies the FEPL Clear Mismatch timer duration (in tens of milliseconds)"
	::= { mibapsConfigEntry 17 }

    apsConfig-ProtectionChannelSignalDegradeExponent	OBJECT-TYPE
	SYNTAX	INTEGER
	ACCESS	read-write
	STATUS	mandatory
	DESCRIPTION	"Specifies the signal degrade exponent for the protection channel"
	::= { mibapsConfigEntry 18 }

    apsConfig-ProtectionChannelSignalFailureExponent	OBJECT-TYPE
	SYNTAX	INTEGER
	ACCESS	read-write
	STATUS	mandatory
	DESCRIPTION	"Specifies the signal failure exponent for the protection channel"
	::= { mibapsConfigEntry 19 }

    apsConfig-WorkingChannelSignalDegradeExponent	OBJECT-TYPE
	SYNTAX	INTEGER
	ACCESS	read-write
	STATUS	mandatory
	DESCRIPTION	"Specifies the signal degrade exponent for the working channel"
	::= { mibapsConfigEntry 20 }

    apsConfig-WorkingChannelSignalFailureExponent	OBJECT-TYPE
	SYNTAX	INTEGER
	ACCESS	read-write
	STATUS	mandatory
	DESCRIPTION	"Specifies the signal failure exponent for the working channel"
	::= { mibapsConfigEntry 21 }

    apsConfig-Action-o	OBJECT-TYPE
	SYNTAX	INTEGER {
		    noAction (1),
		    createProfile (2),
		    deleteProfile (3)
		}
	ACCESS	read-write
	STATUS	mandatory
	DESCRIPTION	""
	::= { mibapsConfigEntry 22 }

END
