-- $Id: it-frame-relay-mib.mib,v 1.1 2000/07/25 14:06:05 sse Exp $
        ITOUCH-FRAME-RELAY-MIB DEFINITIONS ::= BEGIN

               IMPORTS
                       OBJECT-TYPE
                               FROM RFC-1212
                       frCircuitIfIndex, frCircuitDlci
                               FROM RFC1315-MIB
                       iTouch
                               FROM ITOUCH-MIB;
       xFrameRelay     OBJECT IDENTIFIER ::= { iTouch 23 }

      
            -- This is a MIB module for all iTouch Communications systems that
            -- implement frame relay.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


       -- the Frame Relay Circuit table

       -- Implementation of this group is mandatory for all iTouch
       -- systems that implement frame relay

       xFrCircuitTable OBJECT-TYPE
           SYNTAX SEQUENCE OF XFrCircuitEntry
           ACCESS not-accessible
           STATUS mandatory
           DESCRIPTION
               "A table containing iTouch extensions to the 
               standard Frame Relay Circuit table."
           ::= { xFrameRelay 1 }

       xFrCircuitEntry OBJECT-TYPE
           SYNTAX XFrCircuitEntry
           ACCESS not-accessible
           STATUS mandatory
           DESCRIPTION
               "Entry parameters."
           INDEX { frCircuitIfIndex, frCircuitDlci }
           ::= { xFrCircuitTable 1 }

       XFrCircuitEntry ::=
           SEQUENCE {
               xFrCircuitIf
                   INTEGER
           }

       xFrCircuitIf OBJECT-TYPE
           SYNTAX INTEGER
           ACCESS read-write
           STATUS mandatory
           DESCRIPTION
               "The ifIndex value of the corresponding ifEntry, 
               that is, the interface to which the DLCI is 
               attached."
           ::= { xFrCircuitEntry 1 }

END
