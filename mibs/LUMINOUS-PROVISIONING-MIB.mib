LUMINOUS-PROVISIONING-MIB DEFINITIONS ::= BEGIN
    IMPORTS
        MODULE-IDENTITY, OBJECT-TYPE, NOTIFICATION-TYPE,
        TimeTicks, IpAddress, ObjectName, Integer32, Counter32, enterprises       
                                    FROM SNMPv2-SMI
			DisplayString FROM RFC1213-MIB

        RowStatus, DateAndTime
                                    FROM SNMPv2-TC

        LumSlotNum, LumPortNum, LumName, LumDescr, LumTdmType
                                    FROM LUMINOUS-TC-MIB;



  -- IANA-registered  Luminous Network Enterprise Number of 4614

    luminous OBJECT IDENTIFIER ::= { enterprises 4614}


  -- leaving tree-space for the future products:

    lumADM   OBJECT IDENTIFIER ::= { luminous 1}

 
    lumProvisioningMIB  MODULE-IDENTITY     
        LAST-UPDATED "0008220000Z"
        ORGANIZATION "Luminous Networks"
        CONTACT-INFO 
                    "Luminous Technical Support

                    Postal: Luminous Networks,
                             14060 Bubb Road,
                             Cupertino, CA 95014

                            Tel: +1 408 342 6400
                            Fax: +1 408 863 1100
                            E-mail: support@luminous.com"
                                         
        DESCRIPTION "The Luminous Provisioning MIB 
                    contains management information
                    required to provision Luminous
                    PacketWave ports. 
                    NOTE: additional settings (like
                    T1 ports setting in DS1 MIB
                    (RFC2495) ) may be required to
                    complement the cross-connect
                    requests in the current MIB." 

        REVISION     "0106130000Z"
        DESCRIPTION "1. Change name of T1CrossConnect to
                        TDM CrossConnect, and use TC's from
                        shelf.my
                    2.  Add TdmConnectType attribute"

        REVISION     "0008220000Z"
        DESCRIPTION "1.PeekBandwidth description fixed.
                    2.NonConformingAction for 
                        rate limitting added.
                    3.ConnectionStatus values
                        createAndWait(5) and
                        notInService(2) allowed and
                        descriptions added.
                    4.Depricated lumADMCrossConnect
                        subtree got actually removed."

        REVISION     "0007110000Z"
        DESCRIPTION "- Description clauses filled in
                        or corrected.
                    - All read-write clauses changed
                        to read-create. An exception is
                        ConnectionStatus that is still
                        read-write to keep row
                        deletion functionality
                    - DEFVAL clause specified where
                        appropriate.
                    - lumTdmConnectionName and 
                        lumDPConnectionName objects
                        sizes limited to 80.
                    - Enumeration value of are 
                        added to lumTdmConfigParam and
                        lumDPProtectionType (defaults
                        to protected(2))objects
                    - SLC96 redefined through
                        lumTdmConfigParam object
                        values, instead of
                        lumTdmLocalPortNumber."

        ::= { lumADM    2}


   
--
-- There two separate tables to instrument provisioning :
--
--        o  TDM CrossConnect Table
--        o  Ether Provisioning Table
--

       
    lumTdmCrossConnect OBJECT IDENTIFIER ::= {lumProvisioningMIB 2}


    lumTdmCrossConnectTable OBJECT-TYPE
        SYNTAX  SEQUENCE OF LumTdmCrossConnectEntry 
        MAX-ACCESS not-accessible
        STATUS  current
        DESCRIPTION
               "The Luminous TDM Cross Connect Table.
               This table is used to provision TDM cross connects,
                including T1, E1, T3 and E3."
        ::= { lumTdmCrossConnect 1  }


    lumTdmCrossConnectEntry OBJECT-TYPE
        SYNTAX      LumTdmCrossConnectEntry 
        MAX-ACCESS  not-accessible
        STATUS      current
        DESCRIPTION "This table can have a variable number of
                    entries(rows), containing cross-connect
                    parameters as seen from this side of the 
                    cross-connect. 

                    When started for the very first time
                    this table is empty (has no rows present).

                    SNMP manager actions are required to
                    create or delete rows in the table.

                    One row typically represents a cross-connect,
                    as seen from this side of cross-connect.

                    Once created, a row is saved in non-volatile
                    memory, and is guarantied to persist after
                    card/shelf reset or a redundant switchover
                    occurs.

                    The lumTdmConnectionStatus object is used
                    to control the process of dynamic row
                    creation and removal as described in RFC2579.
                    Luminous specific adaptation of RFC2579
                    RowStatus convention follows:

                    - To create a new cross-connect an SNMP
                        Manager must in the one SNMP SET request
                        supply not yet existing instances of at
                        least those read-create objects that
                        have no DEFVAL clause specified.
                        The lumTdmConnectionStatus object's
                        instance value MUST be either 
                        createAndGo(4) or createAndWait(5).
                        If the row does not already exist
                        and request is accepted, the SNMP Agent
                        will respond with positive response
                        where it will set the value of
                        lumTdmConnectionStatus instance equal to
                        active(1) or notInService(2) respectfully.

                    - SNMP Manager is allowed to change existing
                        cross-connect from active(1) to 
                        notInService(2) and vice versa.

                    - To remove cross-connect completely an SNMP
                        Manager must in one SNMP SET request
                        supply desired instance of 
                        lumTdmConnectionStatus with the value of
                        destroy(6). "

        INDEX   { lumTdmLocalCardSlotId,
                    lumTdmLocalPortNumber }
        ::= { lumTdmCrossConnectTable 1 }


    LumTdmCrossConnectEntry ::= SEQUENCE {
                lumTdmLocalCardSlotId       LumSlotNum,
                lumTdmLocalPortNumber       LumPortNum,
                lumTdmConnectNodeIP         IpAddress,
                lumTdmConnectCardSlotId     LumSlotNum,
                lumTdmConnectPortNumber     LumPortNum,
                lumTdmConnectNumber         Integer32,
                lumTdmConnectionName        LumDescr,
                lumTdmConnectionStartTime   DateAndTime,
                lumTdmConnectionStopTime    DateAndTime,
                lumTdmConnectConfigParam    INTEGER,
                lumTdmConnectionUpTime      TimeTicks,
                lumTdmConnectionStatus      RowStatus,
                lumTdmConnectType           LumTdmType
                                           }

    lumTdmLocalCardSlotId          OBJECT-TYPE
        SYNTAX  LumSlotNum
        MAX-ACCESS read-create
        STATUS       current
        DESCRIPTION  "The slot number occupied by a card
                    on this node containing the port
                    to be connected. This must be
                    a valid slot number."
        ::= { lumTdmCrossConnectEntry 1 }

    lumTdmLocalPortNumber          OBJECT-TYPE
        SYNTAX  LumPortNum
        MAX-ACCESS read-create
        STATUS       current
        DESCRIPTION  "The local port number to be connected.
                    This must be a valid port number."
        ::= { lumTdmCrossConnectEntry 2 }

    lumTdmConnectNodeIP       OBJECT-TYPE
        SYNTAX  IpAddress
        MAX-ACCESS read-create
        STATUS       current
        DESCRIPTION  "The IP address of the destination node.
                    This is only used when the port is using
                    IP encapsulation."
        DEFVAL { "0.0.0.0" }
        ::= { lumTdmCrossConnectEntry 3 }

    lumTdmConnectCardSlotId     OBJECT-TYPE
        SYNTAX  LumSlotNum
        MAX-ACCESS read-create
        STATUS       current
        DESCRIPTION  "The slot number of the card in 
                    the destination node. "
        ::= { lumTdmCrossConnectEntry 4 }
 
    lumTdmConnectPortNumber     OBJECT-TYPE
        SYNTAX  LumPortNum
        MAX-ACCESS read-create
        STATUS       current
        DESCRIPTION  "The port number on the card in the
                    destination node. "
        ::= { lumTdmCrossConnectEntry 5 }
 
    lumTdmConnectNumber  OBJECT-TYPE
        SYNTAX  Integer32
        MAX-ACCESS read-create
        STATUS       current
        DESCRIPTION  "An arbitrary positive number the user may 
                    specify as a connection identifier."
        DEFVAL { 1 }
        ::= { lumTdmCrossConnectEntry 6 }

    lumTdmConnectionName          OBJECT-TYPE
        SYNTAX  LumDescr
        MAX-ACCESS read-create
        STATUS       current
        DESCRIPTION  "An arbitrary name that the user may 
                    specify as a connection identifier."
        DEFVAL { "" }
        ::= { lumTdmCrossConnectEntry 7 }

    lumTdmConnectionStartTime       OBJECT-TYPE
        SYNTAX  DateAndTime
        MAX-ACCESS read-create
        STATUS       current
        DESCRIPTION  "Currently not used."
        DEFVAL {"00000000000"}
        ::= { lumTdmCrossConnectEntry 8 }

    lumTdmConnectionStopTime     OBJECT-TYPE
        SYNTAX  DateAndTime
        MAX-ACCESS read-create
        STATUS       current
        DESCRIPTION  "Currently not used."
        DEFVAL {"00000000000"}
        ::= { lumTdmCrossConnectEntry 9 }

    lumTdmConnectConfigParam     OBJECT-TYPE
        SYNTAX  INTEGER{
                           pointToPoint(1),
                           slc96(2)             -- deprecated
                           }
        MAX-ACCESS read-create
        STATUS       current
        DESCRIPTION  "pointToPoint(1) - indicates
                        normal TDM cross-connect;
                    slc96(2) - no longer supported."
        DEFVAL { pointToPoint }
        ::= { lumTdmCrossConnectEntry 10 }
                    
    lumTdmConnectionUpTime   OBJECT-TYPE
        SYNTAX  TimeTicks
        MAX-ACCESS read-only
        STATUS       current
        DESCRIPTION  "The actual time passed since
                       the connection has been established.
                       Supplied by the SNMP Agent."
        ::= { lumTdmCrossConnectEntry 11 }


    lumTdmConnectionStatus    OBJECT-TYPE
        SYNTAX  RowStatus
        MAX-ACCESS read-write
        STATUS       current
        DESCRIPTION  "Connection Status. Used to create, 
                    change and remove TDM crossconnect.
                    The format and usage is described in
                    RFC2579. Currently only the following
                    are used :

                        - active(1) - returned after
                          successful createAndGo;
                          also can be set when a change from
                          notInService(2) is desired.
                        - notInService(2) - returned after
                          successful createAndWait(5);
                          also can be set when a change from
                          active(1) (disabling) is desired.
                        - createAndGo(4) for create operation;
                          when successful the resulting state
                          will be transitioned into active(1).
                        - createAndWait(5) - for create only;
                          when successful the resulting state
                          will be transitioned into
                          notInService(2).
                        - destroy(6) for delete operation.

                           This object MUST always be present 
                           in any SNMP Manager TDM cross connect
                           request."
        ::= { lumTdmCrossConnectEntry 12 }

    lumTdmConnectType    OBJECT-TYPE
        SYNTAX  LumTdmType
        MAX-ACCESS read-only
        STATUS       current
        DESCRIPTION  "The type of TDM service being carried."
        ::= { lumTdmCrossConnectEntry 13 }


--   Data Port Provisioning 
--
--   The term Provisioning (Provision) is loosely used in the
--   description below to include wire-model cross-connects
--   as well as  static and dynamic IP prefix provisioning model.
--   
--   
       
    lumDPProvision OBJECT IDENTIFIER ::= {lumProvisioningMIB 3}

    lumDPProvisionTable OBJECT-TYPE
        SYNTAX  SEQUENCE OF LumDPProvisionEntry 
        MAX-ACCESS not-accessible
        STATUS  current
        DESCRIPTION
                "The Luminous Data Provision Table."
        ::= { lumDPProvision 1 }


    lumDPProvisionEntry OBJECT-TYPE
        SYNTAX      LumDPProvisionEntry 
        MAX-ACCESS  not-accessible
        STATUS      current
        DESCRIPTION "This table can have a variable number of
                         entries(rows), containing provisioning
                         parameters as seen from this side of the 
                         cross-connect. 

                         When started for the very first time
                         this table is empty (has no rows present).

                         SNMP manager actions are required to
                         create or delete rows in the table.

                         One row typically represents a provisioning, 
                         as seen from this of the connection.
                        
                         Once created, a row is saved in non-volatile
                         memory, and is guarantied to persist after
                         card/shelf reset or a redundant switchover
                         occurs.

                         The lumDPConnectionStatus object is used
                         to controls the process of dynamic row
                         creation, removal and modification,
                         as described in RFC2579. Luminous specific
                         adaptation of RFC2579 RowStatus convention
                         follows:

                          - To create a new provisioning an SNMP
                            Manager must in one SNMP SET request
                            supply not yet existing instances of at
                            least those read-write and read-create
        DEFVAL clause
                            specified. The lumDPConnectionStatus
                            object's instance value MUST be either
                            createAndGo(4) or createAndWait(5).
                            If the row does not already exist and
                            request is accepted, the SNMP Agent will
                            respond with positive response with the
                            value of lumDPConnectionStatus set to
                            active(1) or notInService(2) respectfully.

                          - SNMP Manager is allowed to change existing
                            provisioning from active(1) to 
                            notInService(2) and vice versa.

                          - To remove provisioning completely an SNMP
                            Manager must in one SNMP SET request
                            supply desired instance of
                            lumDPConnectionStatus object with the
                            value of destroy(6)."

        INDEX   { lumDPLocalCardSlotId,
                lumDPLocalPortNumber,
                lumDPConnectNumber 
              }
        ::= { lumDPProvisionTable 1 }


    LumDPProvisionEntry ::= SEQUENCE {
              lumDPLocalCardSlotId           LumSlotNum,
              lumDPLocalPortNumber           LumPortNum,
              lumDPConnectNumber             Integer32,
              lumDPConnectNodeIP             IpAddress,
              lumDPConnectCardSlotId         LumSlotNum,
              lumDPConnectPortNumber         LumPortNum,
              lumDPConnectionName            LumDescr,
              lumDPConnectionStartTime       DateAndTime,
              lumDPConnectionStopTime        DateAndTime,
              lumDPCategory                  INTEGER,
              lumDPClassOfService            INTEGER,
              lumDPPeakBandwidth             Integer32,
              lumDPSustainedBandwidth        Integer32,
              lumDPMaximumBurstSize          Integer32,
              lumDPNonConformingAction       INTEGER,
              lumDPProtectionType            INTEGER,
              lumDPFacilityProtection        Integer32,
              lumDPIpPrefix1                 IpAddress,
              lumDPIpPrefix2                 IpAddress,
              lumDPIpPrefix3                 IpAddress,
              lumDPConfigFile                DisplayString,
              lumDPVLANId                    Integer32,
              lumDPBufferSize                Integer32,
              lumDPConnectionUpTime          TimeTicks,
              lumDPConnectionStatus          RowStatus
                                       }

    lumDPLocalCardSlotId           OBJECT-TYPE
        SYNTAX  LumSlotNum
        MAX-ACCESS read-create
        STATUS       current
        DESCRIPTION  "The slot number occupied by a card
                    on this node with the port to be
                    provisioned. SNMP Manager must
                    supply a valid positive number
                    for the instance of this object.
                    SNMP Application writer using
                    this  MIB may consider analyzing the
                    value of lumShelfType from
                    LUMINOUS-SHELF-MIB and use internal
                    knowledge of the layout of that shelf
                    type to determine the valid slot
                    values."
        ::= { lumDPProvisionEntry 1 }

    lumDPLocalPortNumber           OBJECT-TYPE
        SYNTAX  LumPortNum
        MAX-ACCESS read-create
        STATUS       current
        DESCRIPTION  "The local port number to be provisioned.
                           SNMP Manager must supply a valid
                           positive value to the instance on this
                           object when establishing provisioning.
                           SNMP Application writer using this MIB 
                           may consider  analyzing the value of
                           lumCardNumbOfPorts from
                           LUMINOUS-SHELF-MIB for the card in this
                           slot to determine a valid range."
        ::= { lumDPProvisionEntry 2 }

    lumDPConnectNumber   OBJECT-TYPE
        SYNTAX  Integer32
        MAX-ACCESS read-create
        STATUS       current
        DESCRIPTION  "An arbitrary, unique positive number
                           to distinguish between multiple
                           provisioning established on the same
                           local port.

                           SNMP Provisioning Application is
                           responsible to supply unique instance
                           value of this object per a given
                           lumDPLocalCardSlotId and 
                           lumDPLocalPortNumber pair when 
                           establishing provisioning."
        ::= { lumDPProvisionEntry 3 }

    lumDPConnectNodeIP        OBJECT-TYPE
        SYNTAX  IpAddress
        MAX-ACCESS read-create
        STATUS       current
        DESCRIPTION  "The IP address of the connecting node.
                           When establishing provisioning SNMP
                           Manager must set the value of the
                           instance of this objects to an
                           existing Luminous node'd IP Addess."
        ::= { lumDPProvisionEntry 4 }

    lumDPConnectCardSlotId      OBJECT-TYPE
        SYNTAX  LumSlotNum
        MAX-ACCESS read-create
        STATUS       current
        DESCRIPTION  "The slot number occupied by the card in 
                           the connecting node.  SNMP Manager must
                           supply a valid positive number
                           for the instance of this object.
                           Internal knowledge of shelf layout
                           is required to determine the valid
                           values. SNMP Application writer using
                           this  MIB may consider analyzing the
                           value of lumShelfType from
                           LUMINOUS-SHELF-MIB and use internal
                           knowledge of that shelf type layout to
                           determine the valid slot values."
        ::= { lumDPProvisionEntry 5 }
 
    lumDPConnectPortNumber      OBJECT-TYPE
        SYNTAX  LumPortNum
        MAX-ACCESS read-create
        STATUS       current
        DESCRIPTION  "The remote port number on the card in
                           the connection node. SNMP Manager must
                           set this field to a valid positive
                           value when establishing provisioning.
                           SNMP Application writer using this MIB 
                           may consider  analyzing the value of
                           lumCardNumbOfPorts from
                           LUMINOUS-SHELF-MIB for the card in the
                           slot to determine the valid port values."
        ::= { lumDPProvisionEntry 6 }
 

    lumDPConnectionName       OBJECT-TYPE
        SYNTAX  LumDescr
        MAX-ACCESS read-create
        STATUS       current
        DESCRIPTION  "An arbitrary name that the user
                           may wish to specify."
        DEFVAL {""}
        ::= { lumDPProvisionEntry 7 }


    lumDPConnectionStartTime        OBJECT-TYPE
        SYNTAX  DateAndTime
        MAX-ACCESS read-create
        STATUS       current
        DESCRIPTION  "Currently not used."
        DEFVAL {"00000000000"}
        ::= { lumDPProvisionEntry 8 }


    lumDPConnectionStopTime  OBJECT-TYPE
        SYNTAX  DateAndTime
        MAX-ACCESS read-create
        STATUS       current
        DESCRIPTION  "Currently not used."
        DEFVAL {"00000000000"}
        ::= { lumDPProvisionEntry 9 }


    lumDPCategory     OBJECT-TYPE
        SYNTAX  INTEGER {
                                   wireModel(1),
                                   staticIP(2),
                                   dynamicIP(3)
                                }
        MAX-ACCESS read-create
        STATUS       current
        DESCRIPTION  "Provisioning Category. Indicates
                           the provisioning model."
        DEFVAL { wireModel }
        ::= { lumDPProvisionEntry 10 }


    lumDPClassOfService     OBJECT-TYPE
        SYNTAX  INTEGER {
                                   bestEffort(1),
                                   expressForwarding(2),
                                   assuredForwarding(3)
                                }
        MAX-ACCESS read-create
        STATUS       current
        DESCRIPTION  "Supported Class of Services."
        DEFVAL { bestEffort }
        ::= { lumDPProvisionEntry 11 }


    lumDPPeakBandwidth      OBJECT-TYPE
        SYNTAX  Integer32
        MAX-ACCESS read-create
        STATUS       current
        DESCRIPTION  "Peak Bandwidth in Bits/Sec;
                           -1 indicates autonegotiation
                           enabled."
        ::= { lumDPProvisionEntry 12 }


    lumDPSustainedBandwidth      OBJECT-TYPE
        SYNTAX  Integer32
        MAX-ACCESS read-create
        STATUS       current
        DESCRIPTION  "Sustained Bandwidth in in Bits/Sec;
                           positive number."
        ::= { lumDPProvisionEntry 13 }


    lumDPMaximumBurstSize        OBJECT-TYPE
        SYNTAX  Integer32
        MAX-ACCESS read-create
        STATUS       current
        DESCRIPTION  "Maximum Burst Size. In bytes.
                           A positive number."
        ::= { lumDPProvisionEntry 14 }

    lumDPNonConformingAction OBJECT-TYPE
        SYNTAX  INTEGER {
                                   off(1),
                                   markDown(2),
                                   drop(3)
                                }
        MAX-ACCESS read-create
        STATUS       current
        DESCRIPTION  "Non-Conforming Action.
                           Indicates rate limiting action."
        DEFVAL { off }
        ::= { lumDPProvisionEntry 15 }
                           

    lumDPProtectionType       OBJECT-TYPE
        SYNTAX   INTEGER {
                                   unprotected(1),
                                   protected(2)
                                 }
        MAX-ACCESS read-create
        STATUS       current
        DESCRIPTION  "Protection type. protected(2)
                           provides protection in the
                           case of ring span failure."
        DEFVAL { protected }
        ::= { lumDPProvisionEntry 16 }



    lumDPFacilityProtection     OBJECT-TYPE
        SYNTAX  Integer32
        MAX-ACCESS read-create
        STATUS       current
        DESCRIPTION  "TBD."
        ::= { lumDPProvisionEntry 17 }



    lumDPIpPrefix1      OBJECT-TYPE
        SYNTAX  IpAddress
        MAX-ACCESS read-create
        STATUS       current
        DESCRIPTION  "The first IP address to augment
                           the IP Prefix Table."
        ::= { lumDPProvisionEntry 18 }



    lumDPIpPrefix2      OBJECT-TYPE
        SYNTAX  IpAddress
        MAX-ACCESS read-create
        STATUS       current
        DESCRIPTION  "The second IP address to augment
                           the IP Prefix Table."
        ::= { lumDPProvisionEntry 19 }


    lumDPIpPrefix3      OBJECT-TYPE
        SYNTAX  IpAddress
        MAX-ACCESS read-create
        STATUS       current
        DESCRIPTION  "The third IP address to augment
                           the IP Prefix Table."
        ::= { lumDPProvisionEntry 20 }


    lumDPConfigFile     OBJECT-TYPE
        SYNTAX  DisplayString
        MAX-ACCESS read-create
        STATUS       current
        DESCRIPTION  "Full qualified path and the
                           file name of the file on 
                           NMS to contain a large amount
                           of provisioning data, as
                           IP Prefixes for Static
                           IP Provisioning."
        ::= { lumDPProvisionEntry 21 }


    lumDPVLANId     OBJECT-TYPE
        SYNTAX  Integer32
        MAX-ACCESS read-create
        STATUS       current
        DESCRIPTION  "VLAN Id. TBD."
        ::= { lumDPProvisionEntry 22 }


    lumDPBufferSize     OBJECT-TYPE
        SYNTAX  Integer32
        MAX-ACCESS read-create
        STATUS       current
        DESCRIPTION  "A positive number.TBD"
        ::= { lumDPProvisionEntry 23 }

    lumDPConnectionUpTime     OBJECT-TYPE
        SYNTAX  TimeTicks
        MAX-ACCESS read-only
        STATUS       current
        DESCRIPTION  "The time past since this
                           provisioning has been
                           established. Supplied by SNMP
                           Agent."
        ::= { lumDPProvisionEntry 24 }


    lumDPConnectionStatus     OBJECT-TYPE
        SYNTAX  RowStatus
        MAX-ACCESS read-write
        STATUS       current
        DESCRIPTION  "Connection Status. Used to create, 
                          change and remove Data Port 
                          provisioning.
                          The format and usage of RowStatus
                          are described in RFC2579.
                          The following values are supported:

                            - active(1) - returned after
                              successful createAndGo;
                              also can be set when a change from
                              notInService(2) is desired.
                            - notInService(2) - returned after
                              successful createAndWait(5);
                              also can be set when a change from
                              active(1) (disabling) is desired.
                            - createAndGo(4) for create operation;
                              when successful the resulting state
                              will be transitioned into active(1).
                            - createAndWait(5) - for create only;
                              when successful the resulting state
                              will be transitioned into
                              notInService(2).
                            - destroy(6) for delete operation.
                              

                          An instance of this object needs
                          always to be present in any SNMP
                          Manager provisioning request."
        ::= { lumDPProvisionEntry 25 }

     END
