NB30MIB DEFINITIONS ::= BEGIN

        --  nb30_mib.txt
        --  Revision: 01.02.01
        --  Part Number: 2170992
        --  Date: April 18, 1997
 
        --  Cabletron Systems, Inc.
        --  35 Industrial Way, P.O. Box 5005
        --  Rochester, NH 03867-0505
        --  (603) 332-9400
        --  support@ctron.com
 
        --  This module provides authoritative definitions for Cabletron's
        --  Management Information Base For the Remote Bridge (NB30)
        --
        --  This module will be extended, as required.
        --
 
        --  Cabletron Systems reserves the right to make changes in
        --  specification and other information contained in this document
        --  without prior notice.  The reader should consult Cabletron Systems
        --  to determine whether any such changes have been made.
        --
        --  In no event shall Cabletron Systems be liable for any incidental,
        --  indirect, special, or consequential damages whatsoever (including
        --  but not limited to lost profits) arising out of or related to this
        --  document or the information contained in it, even if Cabletron
        --  Systems has been advised of, known, or should have known, the
        --  possibility of such damages.
        --
        --  Cabletron grants vendors, end-users, and other interested parties
        --  a non-exclusive license to use this Specification in connection
        --  with the management of Cabletron products.
 
        --  Copyright (c)1996 Cabletron Systems

IMPORTS
                OBJECT-TYPE
                  FROM RFC-1212
                Counter 
                  FROM RFC1155-SMI
	        nb30Rev1
		  FROM IRM-OIDS;

nb30Device      OBJECT IDENTIFIER ::= { nb30Rev1 1 }

nb30Dsx         OBJECT IDENTIFIER ::= { nb30Rev1 2 }

nb30DsxChannel  OBJECT IDENTIFIER ::= { nb30Rev1 3 }

nb30Port        OBJECT IDENTIFIER ::= { nb30Rev1 4 }

nb30RemPort     OBJECT IDENTIFIER ::= { nb30Rev1 5 }

nb30FilterDB    OBJECT IDENTIFIER ::= { nb30Rev1 6 }

nb30AcqDB       OBJECT IDENTIFIER ::= { nb30FilterDB 1 }

nb30PermDB      OBJECT IDENTIFIER ::= { nb30FilterDB 2 }

nb30SpecDB      OBJECT IDENTIFIER ::= { nb30FilterDB 3 }

-- Device Object Definitions
--
--      This section defines the objects under the Device node.
--
-- Instance Identifiers for Device Objects
--
--      There is only one instance of a Device object, thus the Instance
--      Identifier is 0.
--
-- Device Objects


nb30DeviceDisableBdg    OBJECT-TYPE
    --OID       1.3.6.1.4.1.52.1.6.12.1.1
    SYNTAX      INTEGER
                {
                    disableBridge(2),
                    enableBridge(1)
                }
    ACCESS      read-write
    STATUS      mandatory
    DESCRIPTION
                "Indicates if the bridge will be disabled."
::= { nb30Device 1 }

nb30DeviceRestoreSettings   OBJECT-TYPE
    --OID       1.3.6.1.4.1.52.1.6.12.1.2
    SYNTAX      INTEGER
                {
                    restoreSettings(1)
                }
    ACCESS      read-write
    STATUS      mandatory
    DESCRIPTION
                "Restore the following settings to their default values:
                Bridge Name to CABLETRON REMOTE BRIDGE,
                Location to LOCAL,
                Enet Port 1 Name to ETHERNET PORT 1,
                Enet Port 2 Name to ETHERNET PORT 2,
                Remote Port Name to REMOTE PORT,
                Enet Port 1 Network Name to LAN_1,
                Enet Port 2 Network Name to LAN_2,
                Defualt Enet Port to Port 1,
                Enable Redundancy to NO,
                Port 1 and Port 2 Poll Address to 00-00-00-00-00-00,
                Port 1 and Port 2 Poll Interval to 5 Seconds,
                Port 1 and Port 2 Max Retries to 6,
                Remote Port Network Name to REMOTE LINK,
                Ageing Time for Acquired Database to 300 seconds,
                Place seventeen default multicast addresses into
                the permanent and acquired databases,
                Type of Spanning Tree to 802.1,
                Type of Filtering to IEEE 802.1,
                Bridge Max Age to 20 seconds,
                Bridge Forward Delay to 15 seconds,
                Bridge Hello Time to 2 seconds,
                Bridge Priority to 8000,
                Port 1 Priority to 80,
                Port 2 Priority to 80,
                Port 1 Path Cost to 1000,
                Port 2 Path Cost to 1000,
                Number of Restarts to 0."
::= { nb30Device 2 }

nb30DeviceBdgName   OBJECT-TYPE
    --OID       1.3.6.1.4.1.52.1.6.12.1.3
    SYNTAX      OCTET STRING
    ACCESS      read-write
    STATUS      mandatory
    DESCRIPTION
                "The user-defined name (up to 32 characters long) of the
                bridge. The default bridge name is CABLETRON REMOTE BRIDGE."
::= { nb30Device 3 }

nb30DeviceNumPorts      OBJECT-TYPE
    --OID       1.3.6.1.4.1.52.1.6.12.1.4
    SYNTAX      INTEGER
    ACCESS      read-only
    STATUS      mandatory
    DESCRIPTION
                "The number of ports present on the bridge."
::= { nb30Device 4 }

nb30DeviceType      OBJECT-TYPE
    --OID       1.3.6.1.4.1.52.1.6.12.1.5
    SYNTAX      OCTET STRING
    ACCESS      read-only
    STATUS      mandatory
    DESCRIPTION
                "The type of bridge, NB30."
::= { nb30Device 5 }

nb30DeviceVersion       OBJECT-TYPE
    --OID       1.3.6.1.4.1.52.1.6.12.1.6
    SYNTAX      OCTET STRING
    ACCESS      read-only
    STATUS      mandatory
    DESCRIPTION
                "The release version of the firmware installed in the bridge."
::= { nb30Device 6 }

nb30DeviceLocation      OBJECT-TYPE
    --OID       1.3.6.1.4.1.52.1.6.12.1.7
    SYNTAX      OCTET STRING
    ACCESS      read-write
    STATUS      mandatory
    DESCRIPTION
                "The user-defined name (up to 14 characters long) to
                indicate the location of the bridge on the network.
                The default location name is LOCAL."
::= { nb30Device 7 }

nb30DeviceStatus        OBJECT-TYPE
    --OID       1.3.6.1.4.1.52.1.6.12.1.8
    SYNTAX      OCTET STRING
    ACCESS      read-only
    STATUS      mandatory
    DESCRIPTION
                "The status of the bridge, ON-LINE, STAND BY or DISABLED."
::= { nb30Device 8 }

nb30DeviceRestartBdg    OBJECT-TYPE
    --OID       1.3.6.1.4.1.52.1.6.12.1.9
    SYNTAX      INTEGER
                {
                    restartBridge(1)
                }
    ACCESS      read-write
    STATUS      mandatory
    DESCRIPTION
                "Force the bridge to undergo a software reset."
::= { nb30Device 9 }

nb30DeviceFrFwds    OBJECT-TYPE
    --OID       1.3.6.1.4.1.52.1.6.12.1.10
    SYNTAX      Counter
    ACCESS      read-only
    STATUS      mandatory
    DESCRIPTION
                "The number of frames forwarded by the bridge."
::= { nb30Device 10 }

nb30DeviceFrRxs     OBJECT-TYPE
    --OID       1.3.6.1.4.1.52.1.6.12.1.11
    SYNTAX      Counter
    ACCESS      read-only
    STATUS      mandatory
    DESCRIPTION
                "The number of frames received by the bridge."
::= { nb30Device 11 }

nb30DeviceFrFlts    OBJECT-TYPE
    --OID       1.3.6.1.4.1.52.1.6.12.1.12
    SYNTAX      Counter
    ACCESS      read-only
    STATUS      mandatory
    DESCRIPTION
                "The number of frames filtered by the bridge."
::= { nb30Device 12 }

nb30DeviceErrs      OBJECT-TYPE
    --OID       1.3.6.1.4.1.52.1.6.12.1.13
    SYNTAX      Counter
    ACCESS      read-only
    STATUS      mandatory
    DESCRIPTION
                "The total number of network errors that have occurred."
::= { nb30Device 13 }

nb30DeviceNumRestarts   OBJECT-TYPE
    --OID       1.3.6.1.4.1.52.1.6.12.1.14
    SYNTAX      Counter
    ACCESS      read-only
    STATUS      mandatory
    DESCRIPTION
                "The number of times the bridge has been powered up or
                restarted."
::= { nb30Device 14 }

nb30DeviceTypeFiltering OBJECT-TYPE
    --OID       1.3.6.1.4.1.52.1.6.12.1.15
    SYNTAX      INTEGER
                {
                    ieee8021(1),
                    specialDB(2),
                    both(3)
                }
    ACCESS      read-write
    STATUS      mandatory
    DESCRIPTION
                "The type of filtering to be performed by the bridge. The
                default is IEEE 802.1."
::= { nb30Device 15 }

nb30DeviceSTAProtocol   OBJECT-TYPE
    --OID       1.3.6.1.4.1.52.1.6.12.1.16
    SYNTAX      INTEGER
                {
                    ieee8021(1),
                    dec(2),
                    none(3)
                }
    ACCESS      read-write
    STATUS      mandatory
    DESCRIPTION
                "The spanning tree algorithm under which the bridge is
                operating. The selections are as follows:
                - IEEE 802.1 compliant spanning tree algorithm
                  environment (802.1)
                - DEC LAN Bridge 100 environment (DEC)
                - Without the spanning tree algorithm enabled (NONE)
                The default is 802.1."
::= { nb30Device 16 }

nb30DeviceBridgeID      OBJECT-TYPE
    --OID       1.3.6.1.4.1.52.1.6.12.1.17
    SYNTAX      OCTET STRING
    ACCESS      read-only
    STATUS      mandatory
    DESCRIPTION
                "The unique identifier of the bridge. The first two bytes of
                the identifier are the bridge priority and the last six bytes
                are the Ethernet address."
::= { nb30Device 17 }

nb30DeviceTopChgCnts OBJECT-TYPE
    --OID       1.3.6.1.4.1.52.1.6.12.1.18
    SYNTAX      Counter
    ACCESS      read-only
    STATUS      mandatory
    DESCRIPTION
                "The number of times the bridge's Topology Change Flag
                has been changed since the bridge was powered up or
                initialized."
::= { nb30Device 18 }

nb30DeviceTimeTopChg    OBJECT-TYPE
    --OID       1.3.6.1.4.1.52.1.6.12.1.19
    SYNTAX      INTEGER
    ACCESS      read-only
    STATUS      mandatory
    DESCRIPTION
                "The time in seconds that has elapsed since the bridge's
                Topology Change Flag last recorded the value of a
                topology change."
::= { nb30Device 19 }

nb30DeviceTopChg        OBJECT-TYPE
    --OID       1.3.6.1.4.1.52.1.6.12.1.20
    SYNTAX      INTEGER
                {
                    noTopologyChangeInProgress(1),
                    topologyChangeInProgress(2)
                }
    ACCESS      read-only
    STATUS      mandatory
    DESCRIPTION
                "Indicates if a bridge topology change is in progress."
::= { nb30Device 20 }

nb30DeviceRootCost      OBJECT-TYPE
    --OID       1.3.6.1.4.1.52.1.6.12.1.21
    SYNTAX      INTEGER
    ACCESS      read-only
    STATUS      mandatory
    DESCRIPTION
                "The cost of the path to the root from this bridge."
::= { nb30Device 21 }

nb30DeviceRootPort      OBJECT-TYPE
    --OID       1.3.6.1.4.1.52.1.6.12.1.22
    SYNTAX      INTEGER
    ACCESS      read-only
    STATUS      mandatory
    DESCRIPTION
                "The port identifier for the port which offers the lowest cost
                path to the root, i.e. that port for which the sum of the
                values of the designated cost and path cost parameters
                held for the port is lowest."
::= { nb30Device 22 }

nb30DeviceDesigRoot     OBJECT-TYPE
    --OID       1.3.6.1.4.1.52.1.6.12.1.23
    SYNTAX      OCTET STRING
    ACCESS      read-only
    STATUS      mandatory
    DESCRIPTION
                "The unique identifier of the bridge recorded as the root."
::= { nb30Device 23 }

nb30DeviceMaxAge        OBJECT-TYPE
    --OID       1.3.6.1.4.1.52.1.6.12.1.24
    SYNTAX      INTEGER
    ACCESS      read-only
    STATUS      mandatory
    DESCRIPTION
                "The maximum age of received protocol information before
                it is discarded."
::= { nb30Device 24 }

nb30DeviceHoldTime      OBJECT-TYPE
    --OID       1.3.6.1.4.1.52.1.6.12.1.25
    SYNTAX      INTEGER
    ACCESS      read-only
    STATUS      mandatory
    DESCRIPTION
                "The minimum time period elapsing between the transmission
                of configuration BPDU's through a given bridge port."
::= { nb30Device 25 }

nb30DeviceFwdDly        OBJECT-TYPE
    --OID       1.3.6.1.4.1.52.1.6.12.1.26
    SYNTAX      INTEGER
    ACCESS      read-only
    STATUS      mandatory
    DESCRIPTION
                "The time spent in the listening state while moving from the
                blocking state to the learning state, or the time spent in
                the learning state while moving from the listening state to
                the forwarding state."
::= { nb30Device 26 }

nb30DeviceHelloTime     OBJECT-TYPE
    --OID       1.3.6.1.4.1.52.1.6.12.1.27
    SYNTAX      INTEGER
    ACCESS      read-only
    STATUS      mandatory
    DESCRIPTION
                "The time interval between the transmission of Configuration
                BPDU's by a bridge which is attempting to become the root or
                is the root."
::= { nb30Device 27 }

nb30DeviceBdgFwdDly OBJECT-TYPE
    --OID       1.3.6.1.4.1.52.1.6.12.1.28
    SYNTAX      INTEGER
    ACCESS      read-write
    STATUS      mandatory
    DESCRIPTION
                "The value of the forward delay parameter when the bridge
                is the root or is attempting to become the root. A time
                of 4 to 30 seconds is allowed. The default is 15 seconds."
::= { nb30Device 28 }

nb30DeviceBdgMaxAge OBJECT-TYPE
    --OID       1.3.6.1.4.1.52.1.6.12.1.29
    SYNTAX      INTEGER
    ACCESS      read-write
    STATUS      mandatory
    DESCRIPTION
                "The value of the Max Age parameter when the bridge is
                the root or is attempting to become the root. A time of
                6 to 40 seconds is allowed. The default is 20 seconds."
::= { nb30Device 29 }

nb30DeviceBdgHello      OBJECT-TYPE
    --OID       1.3.6.1.4.1.52.1.6.12.1.30
    SYNTAX      INTEGER
    ACCESS      read-write
    STATUS      mandatory
    DESCRIPTION
                "The value of the Hello Time parameter when the bridge is
                the root or is attempting to become the root. A time of 1
                to 10 seconds is allowed. The default is 2 seconds."
::= { nb30Device 30 }

nb30DeviceBdgPriority   OBJECT-TYPE
    --OID       1.3.6.1.4.1.52.1.6.12.1.31
    SYNTAX      INTEGER
    ACCESS      read-write
    STATUS      mandatory
    DESCRIPTION

                "Used in the spanning tree for priority comparisons. Allowed
                range is 0 through FFFF. The default is 8000."
::= { nb30Device 31 }

nb30DeviceResetCounts   OBJECT-TYPE
    --OID       1.3.6.1.4.1.52.1.6.12.1.32
    SYNTAX      INTEGER
                {
                    resetCounts(1)
                }
    ACCESS      read-write
    STATUS      mandatory
    DESCRIPTION
                "Reset all counters to zero."
::= { nb30Device 32 }

nb30DeviceUptime        OBJECT-TYPE
    --OID       1.3.6.1.4.1.52.1.6.12.1.33
    SYNTAX      INTEGER
    ACCESS      read-only
    STATUS      mandatory
    DESCRIPTION
                "The time, in seconds, that has elapsed since the bridge
                was last reset or initialized."
::= { nb30Device 33 }

nb30DeviceRootSwitch OBJECT-TYPE
    --OID       1.3.6.1.4.1.52.1.6.12.1.34
    SYNTAX      INTEGER
                {
                    noRoot(1),
                    root(2)
                }
    ACCESS      read-only
    STATUS      mandatory
    DESCRIPTION
                "The status of the Root switch on the front panel of the
                NB30."
::= { nb30Device 34 }

nb30DeviceFwdBroadcast  OBJECT-TYPE
    --OID       1.3.6.1.4.1.52.1.6.12.1.35
    SYNTAX      INTEGER
                {
                    forwardBroadcast(1),
                    filterBroadcast(2)
                }
    ACCESS      read-only
    STATUS      mandatory
    DESCRIPTION
                "The status of the Forward Broadcast switch on the front
                panel of the NB30."
::= { nb30Device 35 }

nb30DeviceConfigSw1 OBJECT-TYPE
    --OID       1.3.6.1.4.1.52.1.6.12.1.36
    SYNTAX      INTEGER
                {
                    switchOff(1),
                    switchOn(2)
                }
    ACCESS      read-only
    STATUS      mandatory
    DESCRIPTION
                "The status of Config switch 1 on the back panel of the
                NB30."
::= { nb30Device 36 }


nb30DeviceConfigSw2 OBJECT-TYPE
    --OID       1.3.6.1.4.1.52.1.6.12.1.37
    SYNTAX      INTEGER
                {
                    switchOff(1),
                    switchOn(2)
                }
    ACCESS      read-only
    STATUS      mandatory
    DESCRIPTION
                "The status of Config switch 2 on the back panel of the
                NB30."
::= { nb30Device 37 }

nb30DeviceConfigSw3 OBJECT-TYPE
    --OID       1.3.6.1.4.1.52.1.6.12.1.38
    SYNTAX      INTEGER
                {
                    switchOff(1),
                    switchOn(2)
                }
    ACCESS      read-only
    STATUS      mandatory
    DESCRIPTION
                "The status of Config switch 3 on the back panel of the
                NB30."
::= { nb30Device 38 }

nb30DeviceConfigSw4 OBJECT-TYPE
    --OID       1.3.6.1.4.1.52.1.6.12.1.39
    SYNTAX      INTEGER
                {
                    switchOff(1),
                    switchOn(2)
                }
    ACCESS      read-only
    STATUS      mandatory
    DESCRIPTION
                "The status of Config switch 4 on the back panel of the
                NB30."
::= { nb30Device 39 }

nb30DevicePortActive    OBJECT-TYPE
    --OID       1.3.6.1.4.1.52.1.6.12.1.40
    SYNTAX      INTEGER
    ACCESS      read-only
    STATUS      mandatory
    DESCRIPTION
                "The Port number which is acting as the online Ethernet
                Port on the NB30."
::= { nb30Device 40 }

nb30DeviceDefPort       OBJECT-TYPE
    --OID       1.3.6.1.4.1.52.1.6.12.1.41
    SYNTAX      INTEGER
                {
                    ethernetPort1(1),
                    ethernetPort2(2)
                }
    ACCESS      read-write
    STATUS      mandatory
    DESCRIPTION
                "The Port number which is Default Ethernet Port on the
                NB30 at power up."
::= { nb30Device 41 }

nb30DeviceRedEnable OBJECT-TYPE
    --OID       1.3.6.1.4.1.52.1.6.12.1.42
    SYNTAX      INTEGER
                {
                    disableRedundancy(1),
                    enableRedundancy(2)
                }
    ACCESS      read-write
    STATUS      mandatory
    DESCRIPTION
                "The state of the Redundancy Enable Flag."
::= { nb30Device 42 }

-- This section defines the objects specific to the DSX-1 Remote interface.
--
-- DSX-1 Remote Interface Objects

nb30DsxLoopUp       OBJECT-TYPE
    --OID       1.3.6.1.4.1.52.1.6.12.2.1
    SYNTAX      INTEGER
                {
                    loopUp(1)
                }
    ACCESS      read-write
    STATUS      mandatory
    DESCRIPTION
                "The loop up command for the DSX-1 Remote Interface."
::= { nb30Dsx 1 }

nb30DsxLoopDn       OBJECT-TYPE
    --OID       1.3.6.1.4.1.52.1.6.12.2.2
    SYNTAX      INTEGER
                {
                    loopDown(1)
                }
    ACCESS      read-write
    STATUS      mandatory
    DESCRIPTION
                "The loop down command for the DSX-1 Remote Interface."
::= { nb30Dsx 2 }

nb30DsxLoopSt       OBJECT-TYPE
    --OID       1.3.6.1.4.1.52.1.6.12.2.3
    SYNTAX      INTEGER
                {
                    notInLoopback(1),
                    loopbackInProgress(2),
                    networkLoopback(3),
                    loopbackPassed(4),
                    loopbackFailed(5)
                }
    ACCESS      read-only
    STATUS      mandatory
    DESCRIPTION
                "The loop status for the DSX-1 Remote Interface."
::= { nb30Dsx 3 }

nb30DsxLoopPattern      OBJECT-TYPE
    --OID       1.3.6.1.4.1.52.1.6.12.2.4
    SYNTAX      INTEGER
                {
                    alternate1sAnd0s(1),
                    all1s(2),
                    all0s(3),
                    incrementingData(4)
                }
    ACCESS      read-write
    STATUS      mandatory
    DESCRIPTION
                "The loop test pattern for the DSX-1 Remote Interface."
::= { nb30Dsx 4 }

-- DSX-1 Channel Object Definitions
--
-- This section defines the objects under the DSX-1 Channel node.
--
-- Instance Identifiers for DSX-1 Channel Objects
--
--      The Instance Identifier for nb30DsxChannel objects is the number of
--      channels on the DSX-1 interface. Valid instance identifiers for the
--      remote channels are 1 - 24.
--
-- DSX-1 Channel Objects

nb30DsxChannelTable OBJECT-TYPE
    --OID       1.3.6.1.4.1.52.1.6.12.3.1
    SYNTAX      SEQUENCE OF Nb30DsxEntry
    ACCESS      not-accessible
    STATUS      mandatory
    DESCRIPTION
                "NB30 DSX-1 Remote Port Channelization Table"
::= { nb30DsxChannel 1 }

nb30DsxEntry            OBJECT-TYPE
    --OID       1.3.6.1.4.1.52.1.6.12.3.1.1
    SYNTAX      Nb30DsxEntry
    ACCESS      not-accessible
    STATUS      mandatory
    DESCRIPTION
                ""
    INDEX       { nb30DsxChannelId }

::= { nb30DsxChannelTable 1 }

Nb30DsxEntry ::= SEQUENCE
             {
                nb30DsxChannelControl   INTEGER,
		nb30DsxChannelId	INTEGER
             }

nb30DsxChannelControl   OBJECT-TYPE
    --OID       1.3.6.1.4.1.52.1.6.12.3.1.1.1
    SYNTAX      INTEGER
                {
                    disableChannel(1),
                    enableChannel(2)
                }
    ACCESS      read-write
    STATUS      mandatory
    DESCRIPTION
                "Disable the DSX-1 Channel."
::= { nb30DsxEntry 1 }

nb30DsxChannelId	OBJECT-TYPE
    SYNTAX	INTEGER
    ACCESS	read-write
    STATUS	mandatory
    DESCRIPTION
	"The channel number for this entry."
    ::= { nb30DsxEntry 2 }


-- Port Object Definitions
--
-- This section defines the objects under the Port node.
--
-- Instance Identifiers for Port Objects
--
--      The Instance Identifier for nb30Port objects is the number of the
--      port on the bridge. Valid instance identifiers for the ports on
--      the NB30 are 1 and 2.
--
-- Port Objects

nb30PortTable           OBJECT-TYPE
    --OID       1.3.6.1.4.1.52.1.6.12.4.1
    SYNTAX      SEQUENCE OF Nb30PortEntry
    ACCESS      not-accessible
    STATUS      mandatory
    DESCRIPTION
                "Bridge Port information table"
::= { nb30Port 1 }

nb30PortEntry           OBJECT-TYPE
    --OID       1.3.6.1.4.1.52.1.6.12.4.1.1
    SYNTAX      Nb30PortEntry
    ACCESS      not-accessible
    STATUS      mandatory
    DESCRIPTION
                ""
    INDEX       { nb30PortId }

::= { nb30PortTable 1 }

Nb30PortEntry ::=
    SEQUENCE {
                nb30PortAddress         OCTET STRING,
                nb30PortName            OCTET STRING,
                nb30PortType            OCTET STRING,
                nb30PortStatus          OCTET STRING,
                nb30PortNetName         OCTET STRING,
                nb30PortFrRxs           Counter,
                nb30PortDisInbounds     Counter,
                nb30PortFwdOutbs        Counter,
                nb30PortDisLOBs         Counter,
                nb30PortDisTDEs         Counter,
                nb30PortCollisions      Counter,
                nb30PortTxAborts        Counter,
                nb30PortOowCollisions   Counter,
                nb30PortCRCErrs         Counter,
                nb30PortFrAlignErrs     Counter,
                nb30PortPriority        INTEGER,
                nb30PortState           OCTET STRING,
                nb30PortPathCost        INTEGER,
                nb30PortDesigCost       INTEGER,
                nb30PortDesigBrdg       OCTET STRING,
                nb30PortDesigPort       INTEGER,
                nb30PortTopChgAck       INTEGER ,
                nb30PortDesigRoot       OCTET STRING,
                nb30PortOversizePkts    Counter,
                nb30PortFrFiltereds     Counter,
                nb30PortPollAddress     OCTET STRING,
                nb30PortPollInterval    INTEGER,
                nb30PortMaxRetry        INTEGER,
		nb30PortId		INTEGER
             }

nb30PortAddress     OBJECT-TYPE
    --OID       1.3.6.1.4.1.52.1.6.12.4.1.1.1
    SYNTAX      OCTET STRING
    ACCESS      read-only
    STATUS      mandatory
    DESCRIPTION
                "The Ethernet address of the port. Instance of 1 represents
                the local Ethernet address, instance of 2 represents the
                remote Ethernet address."
::= { nb30PortEntry 1 }

nb30PortName        OBJECT-TYPE
    --OID       1.3.6.1.4.1.52.1.6.12.4.1.1.2
    SYNTAX      OCTET STRING
    ACCESS      read-write
    STATUS      mandatory
    DESCRIPTION
                "The user-defined name (up to 32 characters long)
                assigned to the port. The default Enet port 1 name is
                ETHERNET PORT 1 and the default Enet Port 2 name is
                ETHERNET PORT 2."
::= { nb30PortEntry 2 }

nb30PortType            OBJECT-TYPE
    --OID       1.3.6.1.4.1.52.1.6.12.4.1.1.3
    SYNTAX      OCTET STRING
    ACCESS      read-only
    STATUS      mandatory
    DESCRIPTION
                "The IEEE specification the port meets, e.g. 802.3."
::= { nb30PortEntry 3 }

nb30PortStatus      OBJECT-TYPE
     --OID       1.3.6.1.4.1.52.1.6.12.4.1.1.4
    SYNTAX      OCTET STRING
    ACCESS      read-only
    STATUS      mandatory
    DESCRIPTION
                "The status in which the port is operating. The status
                messages for Ports 1 and 2 are:

        OFF - The port is off, due to a failed network interface
        chip associated with that port.

        OK/SQE ON - The port is communicating with the network
        and the transceiver making the connection to the network
        has SQE enabled.

        OK/SQE OFF - The port is communicating with the network
        and the transceiver making the connection to the network
        has SQE disabled.

        CARRIER LOST - Communication with the network has not
        been established or has been lost."
::= { nb30PortEntry 4 }

nb30PortNetName     OBJECT-TYPE
    --OID       1.3.6.1.4.1.52.1.6.12.4.1.1.5
    SYNTAX      OCTET STRING
    ACCESS      read-write
    STATUS      mandatory
    DESCRIPTION
                "The user-defined name (up to 32 characters long)
                assigned to a network segment connected to the port.
                The default network name for Port 1 is LAN_1 and the
                default network name for Port 2 is LAN_2."
::= { nb30PortEntry 5 }

nb30PortFrRxs           OBJECT-TYPE
    --OID       1.3.6.1.4.1.52.1.6.12.4.1.1.6
    SYNTAX      Counter
    ACCESS      read-only
    STATUS      mandatory
    DESCRIPTION
                "The number of frames received at the specified port."
::= { nb30PortEntry 6 }

nb30PortDisInbounds     OBJECT-TYPE
    --OID       1.3.6.1.4.1.52.1.6.12.4.1.1.7
    SYNTAX      Counter
    ACCESS      read-only
    STATUS      mandatory
    DESCRIPTION
                "The total number of valid frames that were received at
                the port but then discarded by the bridge in the
                forwarding process."
::= { nb30PortEntry 7 }

nb30PortFwdOutbs    OBJECT-TYPE
    --OID       1.3.6.1.4.1.52.1.6.12.4.1.1.8
    SYNTAX      Counter
    ACCESS      read-only
    STATUS      mandatory
    DESCRIPTION
                "The number of frames forwarded successfully to the
                appropriate port."
::= { nb30PortEntry 8 }

nb30PortDisLOBs     OBJECT-TYPE
    --OID       1.3.6.1.4.1.52.1.6.12.4.1.1.9
    SYNTAX      Counter
    ACCESS      read-only
    STATUS      mandatory
    DESCRIPTION
                "The number of packets that were discarded by the bridge
                because of a lack of buffer space to maintain the data."
::= { nb30PortEntry 9 }

nb30PortDisTDEs     OBJECT-TYPE
    --OID       1.3.6.1.4.1.52.1.6.12.4.1.1.10
    SYNTAX      Counter
    ACCESS      read-only
    STATUS      mandatory
    DESCRIPTION
                "The number of frames that were intended for forwarding
                but were discarded when the maximum time period set for
                transmission was exceeded before forwarding was possible."
::= { nb30PortEntry 10 }

nb30PortCollisions      OBJECT-TYPE
    --OID       1.3.6.1.4.1.52.1.6.12.4.1.1.11
    SYNTAX      Counter
    ACCESS      read-only
    STATUS      mandatory
    DESCRIPTION
                "The number of collisions that have occurred on the
                network at the specified port."
::= { nb30PortEntry 11 }

nb30PortTxAborts    OBJECT-TYPE
    --OID       1.3.6.1.4.1.52.1.6.12.4.1.1.12
    SYNTAX      Counter
    ACCESS      read-only
    STATUS      mandatory
    DESCRIPTION
                "The number of transmissions that have been aborted due
                to excessive collisions (over 16 attempts to transmit the
                same packet)."
::= { nb30PortEntry 12 }

nb30PortOowCollisions   OBJECT-TYPE
    --OID       1.3.6.1.4.1.52.1.6.12.4.1.1.13
    SYNTAX      Counter
    ACCESS      read-only
    STATUS      mandatory
    DESCRIPTION
                "The number of collisions out of the standard collision
                window (51.2 uS). This indicates a network problem."
::= { nb30PortEntry 13 }

nb30PortCRCErrs      OBJECT-TYPE
    --OID       1.3.6.1.4.1.52.1.6.12.4.1.1.14
    SYNTAX      Counter
    ACCESS      read-only
    STATUS      mandatory
    DESCRIPTION
                "The number of packets detected with Cyclical Redundancy
                Check failures."
::= { nb30PortEntry 14 }

nb30PortFrAlignErrs     OBJECT-TYPE
    --OID       1.3.6.1.4.1.52.1.6.12.4.1.1.15
    SYNTAX      Counter
    ACCESS      read-only
    STATUS      mandatory
    DESCRIPTION
                "The number of errors due to misaligned packets."
::= { nb30PortEntry 15 }

nb30PortPriority        OBJECT-TYPE
    --OID       1.3.6.1.4.1.52.1.6.12.4.1.1.16
    SYNTAX      INTEGER
    ACCESS      read-write
    STATUS      mandatory
    DESCRIPTION
                "The part of the port identifier which is used with the
                spanning tree algorithm when determining which port in a
                LAN segment has priority. The default is 80. Applies to the
                LOCAL and REMOTE Ethernet ports where instance 1 always
                refers to the local ethernet port and instance 2 always
                refers to the remote ethernet port."
::= { nb30PortEntry 16 }

nb30PortState           OBJECT-TYPE
    --OID       1.3.6.1.4.1.52.1.6.12.4.1.1.17
    SYNTAX      OCTET STRING
    ACCESS      read-only
    STATUS      mandatory
    DESCRIPTION
                "The current state of the port, DISABLED, LISTENING,
                LEARNING, FORWARDING or BLOCKING. Applies to the
                LOCAL and REMOTE Ethernet ports where instance 1 always
                refers to the local ethernet port and instance 2 always
                refers to the remote ethernet port."
::= { nb30PortEntry 17 }

nb30PortPathCost        OBJECT-TYPE
    --OID       1.3.6.1.4.1.52.1.6.12.4.1.1.18
    SYNTAX      INTEGER
    ACCESS      read-write
    STATUS      mandatory
    DESCRIPTION
                "The contributory cost of the applicable port to the overall
                cost of the path when the specified port is the root port.
                Allowable range is 1 to 65535. The default is 1000. Applies
                to the LOCAL and REMOTE Ethernet ports where instance 1 always
                refers to the local ethernet port and instance 2 always
                refers to the remote ethernet port."
::= { nb30PortEntry 18 }

nb30PortDesigCost       OBJECT-TYPE
    --OID       1.3.6.1.4.1.52.1.6.12.4.1.1.19
    SYNTAX      INTEGER
    ACCESS      read-only
    STATUS      mandatory
    DESCRIPTION
                "The cost of the path of this port to the root bridge on the
                network. Applies to the LOCAL and REMOTE Ethernet ports where
                instance 1 always refers to the local ethernet port and
                instance 2 always refers to the remote ethernet port."
::= { nb30PortEntry 19 }

nb30PortDesigBrdg       OBJECT-TYPE
    --OID       1.3.6.1.4.1.52.1.6.12.4.1.1.20
    SYNTAX      OCTET STRING
    ACCESS      read-only
    STATUS      mandatory
    DESCRIPTION
                "The network address of the bridge that is assumed to be
                the root bridge on the network. Applies to the LOCAL and
                REMOTE Ethernet ports where instance 1 always refers to
                the local ethernet port and instance 2 always refers to
                the remote ethernet port."
::= { nb30PortEntry 20 }

nb30PortDesigPort       OBJECT-TYPE
    --OID       1.3.6.1.4.1.52.1.6.12.4.1.1.21
    SYNTAX      INTEGER
    ACCESS      read-only
    STATUS      mandatory
    DESCRIPTION
                "The port identifier of the bridge port believed to be the
                designated port for the LAN associated with the port.
                Applies to the LOCAL and REMOTE Ethernet ports where
                instance 1 always refers to the local ethernet port and
                instance 2 always refers to the remote ethernet port."
::= { nb30PortEntry 21 }

nb30PortTopChgAck       OBJECT-TYPE
    --OID       1.3.6.1.4.1.52.1.6.12.4.1.1.22
    SYNTAX      INTEGER
                {
                    noTopologyChangeIsOccurring(1),
                    topologyChangeIsOccurring(2)
                }
    ACCESS      read-only
    STATUS      mandatory
    DESCRIPTION
                "The value of the topology change acknowledgement flag
                in the next configuration BPDU to be transmitted on
                the associated port. Applies to the LOCAL and REMOTE
                Ethernet ports where instance 1 always refers to the
                local ethernet port and instance 2 always refers to
                the remote ethernet port."
::= { nb30PortEntry 22 }

nb30PortDesigRoot       OBJECT-TYPE
    --OID       1.3.6.1.4.1.52.1.6.12.4.1.1.23
    SYNTAX      OCTET STRING
    ACCESS      read-only
    STATUS      mandatory
    DESCRIPTION
                "The unique bridge identifier of the bridge that is assumed
                to be the root bridge on the network. Applies to the
                LOCAL and REMOTE Ethernet ports where instance 1 always
                refers to the local ethernet port and instance 2 always
                refers to the remote ethernet port."
::= { nb30PortEntry 23 }

nb30PortOversizePkts   OBJECT-TYPE
    --OID       1.3.6.1.4.1.52.1.6.12.4.1.1.24
    SYNTAX      Counter
    ACCESS      read-only
    STATUS      mandatory
    DESCRIPTION
                "The number of packets received at the indicated NB30
                Port that were greater than the IEEE 802.3 maximum
                Ethernet frame size of 1518 bytes."
::= { nb30PortEntry 24 }

nb30PortFrFiltereds     OBJECT-TYPE
    --OID       1.3.6.1.4.1.52.1.6.12.4.1.1.25
    SYNTAX      Counter
    ACCESS      read-only
    STATUS      mandatory
    DESCRIPTION
                "The number of frames received at the indicated port that
                were filtered by the bridge."
::= { nb30PortEntry 25 }

nb30PortPollAddress     OBJECT-TYPE
    --OID       1.3.6.1.4.1.52.1.6.12.4.1.1.26
    SYNTAX      OCTET STRING
    ACCESS      read-write
    STATUS      mandatory
    DESCRIPTION
                "The Poll Address that will be used by the Redundant Port
                Algorithm on the NB30."
::= { nb30PortEntry 26 }

nb30PortPollInterval        OBJECT-TYPE
    --OID       1.3.6.1.4.1.52.1.6.12.4.1.1.27
    SYNTAX      INTEGER
    ACCESS      read-write
    STATUS      mandatory
    DESCRIPTION
                "The Poll Interval used by the Redundant Port Algorithm on
                the NB30. Valid range is 1 - 30 seconds."
::= { nb30PortEntry 27 }

nb30PortMaxRetry        OBJECT-TYPE
    --OID       1.3.6.1.4.1.52.1.6.12.4.1.1.28
    SYNTAX      INTEGER
    ACCESS      read-write
    STATUS      mandatory
    DESCRIPTION
                "The Max number of retries for the Redundant Port
                Algorithm on the NB30. Valid range is 2 - 99 retries"
::= { nb30PortEntry 28 }

nb30PortId	OBJECT-TYPE
    SYNTAX	INTEGER
    ACCESS	read-only
    STATUS	mandatory
    DESCRIPTION
	"The port number for this entry."
::= { nb30PortEntry 29 }

-- Remote Port Object Definitions
--
-- This section defines the objects under the Remote Port node.
--
-- Instance Identifiers for Remote Port Objects
--
--      There is only one instance of the remote port on the NB30 bridge
--      thus the Instance Identifier is 0.
--
-- Port Objects

nb30RemPortTable        OBJECT-TYPE
    --OID       1.3.6.1.4.1.52.1.6.12.5.1
    SYNTAX      SEQUENCE OF Nb30RemPortEntry
    ACCESS      not-accessible
    STATUS      mandatory
    DESCRIPTION
                "Bridge Remote Port information table"
::= { nb30RemPort 1 }

nb30RemPortEntry        OBJECT-TYPE
    --OID       1.3.6.1.4.1.52.1.6.12.5.1.1
    SYNTAX      Nb30RemPortEntry
    ACCESS      not-accessible
    STATUS      mandatory
    DESCRIPTION
                ""
    INDEX       { nb30RemPortId }
::= { nb30RemPortTable 1 }

Nb30RemPortEntry ::=
    SEQUENCE {
                nb30RemPortName     OCTET STRING,
                nb30RemPortType     OCTET STRING,
                nb30RemPortStatus   OCTET STRING,
                nb30RemPortNetName  OCTET STRING,
                nb30RemPortFrRxs    Counter,
                nb30RemPortFwdOutbs Counter,
                nb30RemPortDisLOBs  Counter,
                nb30RemPortDisTDEs  Counter,
                nb30RemPortCRCErrs  Counter,
                nb30RemPortFrAlErrs Counter,
		nb30RemPortId	INTEGER
             }

nb30RemPortName     OBJECT-TYPE
    --OID       1.3.6.1.4.1.52.1.6.12.5.1.1.1
    SYNTAX      OCTET STRING
    ACCESS      read-write
    STATUS      mandatory
    DESCRIPTION
                "The user-defined name assigned to the remote port. The
                default Remote port name is REMOTE PORT."
::= { nb30RemPortEntry 1 }

nb30RemPortType     OBJECT-TYPE
    --OID       1.3.6.1.4.1.52.1.6.12.5.1.1.2
    SYNTAX      OCTET STRING
    ACCESS      read-only
    STATUS      mandatory
    DESCRIPTION
                "The Electrical interface specification the port meets, e.g.
                DSX-1, V.35."
::= { nb30RemPortEntry 2 }

nb30RemPortStatus       OBJECT-TYPE
    --OID       1.3.6.1.4.1.52.1.6.12.5.1.1.3
    SYNTAX      OCTET STRING
    ACCESS      read-only
    STATUS      mandatory
    DESCRIPTION
                "The status in which the remote port is operating. The status
                messages for the Remote Port are:

                NO EXT CLOCK
                DCE NOT READY / NO DM
                DCE NOT READY / NO CTS
                LINK OK / DCE READY
                NET LOOP / RED ALARM
                REM LOOP / RED ALARM
                NORMAL / RED ALARM
                NET LOOP / YELLOW ALARM
                REM LOOP / YELLOW ALARM
                NORMAL / YELLOW ALARM
                NET LOOP / LINK OK
                REM LOOP / LINK OK
                NORMAL / LINK OK
                NET LOOP / LINK LOST
                REM LOOP / LINK LOST
                NORMAL / LINK LOST"
::= { nb30RemPortEntry 3 }

nb30RemPortNetName  OBJECT-TYPE
    --OID       1.3.6.1.4.1.52.1.6.12.5.1.1.4
    SYNTAX      OCTET STRING
    ACCESS      read-write
    STATUS      mandatory
    DESCRIPTION
                "The user-defined name assigned to a wide area segment
                connected to the remote port. The default network name
                for Remote Port is REMOTE LINK."
::= { nb30RemPortEntry 4 }

nb30RemPortFrRxs    OBJECT-TYPE
    --OID       1.3.6.1.4.1.52.1.6.12.5.1.1.5
    SYNTAX      Counter
    ACCESS      read-only
    STATUS      mandatory
    DESCRIPTION
                "The number of frames received at the remote port."
::= { nb30RemPortEntry 5}

nb30RemPortFwdOutbs OBJECT-TYPE
    --OID       1.3.6.1.4.1.52.1.6.12.5.1.1.6
    SYNTAX      Counter
    ACCESS      read-only
    STATUS      mandatory
    DESCRIPTION
                "The number of frames forwarded successfully to the
                remote port."
::= { nb30RemPortEntry 6 }

nb30RemPortDisLOBs      OBJECT-TYPE
    --OID       1.3.6.1.4.1.52.1.6.12.5.1.1.7
    SYNTAX      Counter
    ACCESS      read-only
    STATUS      mandatory
    DESCRIPTION
                "The number of packets that were discarded by the bridge
                because of a lack of buffer space to maintain the data."
::= { nb30RemPortEntry 7 }

nb30RemPortDisTDEs      OBJECT-TYPE
    --OID       1.3.6.1.4.1.52.1.6.12.5.1.1.8
    SYNTAX      Counter
    ACCESS      read-only
    STATUS      mandatory
    DESCRIPTION
                "The number of frames that were intended for forwarding
                but were discarded when the maximum time period set for
                transmission was exceeded before forwarding was possible."
::= { nb30RemPortEntry 8 }

nb30RemPortCRCErrs      OBJECT-TYPE
    --OID       1.3.6.1.4.1.52.1.6.12.5.1.1.9
    SYNTAX      Counter
    ACCESS      read-only
    STATUS      mandatory
    DESCRIPTION
                "The number of packets detected with Cyclical Redundancy
                Check failures."
::= { nb30RemPortEntry 9 }

nb30RemPortFrAlErrs     OBJECT-TYPE
    --OID       1.3.6.1.4.1.52.1.6.12.5.1.1.10
    SYNTAX      Counter
    ACCESS      read-only
    STATUS      mandatory
    DESCRIPTION
                "The number of errors due to misaligned packets."
::= { nb30RemPortEntry 10 }

nb30RemPortId	OBJECT-TYPE
    SYNTAX	INTEGER
    ACCESS	read-only
    STATUS	mandatory
    DESCRIPTION
	"The remote port ID, there is only a single port which is
	identified as 0."
::= { nb30RemPortEntry 11 }

-- Acquired Database Statistical Object Definitions
--
-- This section defines the objects under the Acquired Database
-- Statistics node.
--
-- Instance Identifiers for Acquired Database Statistical Objects
--
--      There is only one instance of an Acquired Database Statistical object,
--      thus the Instance Identifier is 0.
--
--  Acquired Database Statistical Objects

nb30AcqTotalEntries     OBJECT-TYPE
    --OID       1.3.6.1.4.1.52.1.6.12.6.1.1
    SYNTAX      INTEGER
    ACCESS      read-only
    STATUS      mandatory
    DESCRIPTION
                "The total number of entries in the acquired database."
::= { nb30AcqDB 1 }

nb30AcqMaxEntries       OBJECT-TYPE
    --OID       1.3.6.1.4.1.52.1.6.12.6.1.2
    SYNTAX      INTEGER
    ACCESS      read-only
    STATUS      mandatory
    DESCRIPTION
                "The maximum number of entries allowed in the acquired
                database 8191 entries."
::= { nb30AcqDB 2 }

nb30AcqStaticEntries        OBJECT-TYPE
    --OID       1.3.6.1.4.1.52.1.6.12.6.1.3
    SYNTAX      INTEGER
    ACCESS      read-only
    STATUS      mandatory
    DESCRIPTION
                "The number of addresses added to the Acquired database
                by the user or network manager."
::= { nb30AcqDB 3 }

nb30AcqDynamicEntries   OBJECT-TYPE
    --OID       1.3.6.1.4.1.52.1.6.12.6.1.4
    SYNTAX      INTEGER
    ACCESS      read-only
    STATUS      mandatory
    DESCRIPTION
                "The number of entries that have been accumulated in
                the Acquired database through the bridge's learning
                process."
::= { nb30AcqDB 4 }

nb30AcqDynAgeTime       OBJECT-TYPE
    --OID       1.3.6.1.4.1.52.1.6.12.6.1.5
    SYNTAX      INTEGER
    ACCESS      read-write
    STATUS      mandatory
    DESCRIPTION
                "The length of time allowed for a dynamic entry in the
                acquired database to be inactive before it is dropped
                from the database. A time from 10 - 1,000,000 seconds is
                allowed. The default is 300 seconds."
::= { nb30AcqDB 5 }

nb30AcqEraseDatabase    OBJECT-TYPE
    --OID       1.3.6.1.4.1.52.1.6.12.6.1.6
    SYNTAX      INTEGER
                {
                    eraseAcquiredDatabase(1)
                }
    ACCESS      read-write
    STATUS      mandatory
    DESCRIPTION
                "Set to one to erase all entries in the acquired database."
::= { nb30AcqDB 6 }

-- Aquired database tables
--

nb30AcqDBTable      OBJECT-TYPE
    --OID       1.3.6.1.4.1.52.1.6.12.6.1.7
    SYNTAX      SEQUENCE OF Nb30AcqDBEntry
    ACCESS      not-accessible
    STATUS      mandatory
    DESCRIPTION
                "Aquired database entrys table"
::= { nb30AcqDB 7 }

nb30AcqDBEntry      OBJECT-TYPE
    --OID       1.3.6.1.4.1.52.1.6.12.6.1.7.1
    SYNTAX      Nb30AcqDBEntry
    ACCESS      not-accessible
    STATUS      mandatory
    DESCRIPTION
                ""
    INDEX       { nb30AcqMacAddress }
::= { nb30AcqDBTable 1 }

Nb30AcqDBEntry ::=
    SEQUENCE {
                nb30AcqCreateFilter     INTEGER,
                nb30AcqCreateForward    INTEGER,
                nb30AcqDeleteFilter     INTEGER,
                nb30AcqFilterType       OCTET STRING,
                nb30AcqFilterAction     INTEGER,
                nb30AcqSourceAddress    OCTET STRING,
		nb30AcqMacAddress	OCTET STRING
             }

-- Acquired Database Option Object Definitions
--
-- This section defines the objects under the Acquired Database
-- Option node.
--
-- Instance Identifiers for Acquired Database Option Objects
--
--      The instance identifier for the acquired database option objects is
--      the 6-byte Ethernet address of the device to be added, deleted or
--      displayed to/from the acquired database.
--
--  Acquired Database Option Objects

nb30AcqCreateFilter     OBJECT-TYPE
    --OID       1.3.6.1.4.1.52.1.6.12.6.1.7.1.1
    SYNTAX      INTEGER
                {
                    createAcquiredFilter(1)
                }
    ACCESS      read-write
    STATUS      mandatory
    DESCRIPTION
                "Add an entry to the acquired database to filter packets
                entering port 1 if those packets are destined for the
                specified address."
::= { nb30AcqDBEntry 1 }

nb30AcqCreateForward    OBJECT-TYPE
    --OID       1.3.6.1.4.1.52.1.6.12.6.1.7.1.2
    SYNTAX      INTEGER
                {
                    createAcquiredForward(1)
                }
    ACCESS      read-write
    STATUS      mandatory
    DESCRIPTION
                "Add an entry to the acquired database to forward
                packets entering port 1 to the remote port  if those
                packets are destined  for the specified address."
::= { nb30AcqDBEntry 2 }

nb30AcqDeleteFilter     OBJECT-TYPE
    --OID       1.3.6.1.4.1.52.1.6.12.6.1.7.1.3
    SYNTAX      INTEGER
                {
                    deleteAcquiredEntry(1)
                }
    ACCESS      read-write
    STATUS      mandatory
    DESCRIPTION
                "Delete an entry from the acquired database."
::= { nb30AcqDBEntry 3 }

nb30AcqFilterType       OBJECT-TYPE
    --OID       1.3.6.1.4.1.52.1.6.12.6.1.7.1.4
    SYNTAX      OCTET STRING
    ACCESS      read-only
    STATUS      mandatory
    DESCRIPTION
                "Display the entry type, STATIC or DYNAMIC."
::= { nb30AcqDBEntry 4 }

nb30AcqFilterAction     OBJECT-TYPE
    --OID       1.3.6.1.4.1.52.1.6.12.6.1.7.1.5
    SYNTAX      INTEGER
                {
                    filter(1),
                    relay(2)
                }
    ACCESS      read-only
    STATUS      mandatory
    DESCRIPTION
                "The action to be taken for packets entering port 1."
::= { nb30AcqDBEntry 5 }

nb30AcqSourceAddress    OBJECT-TYPE
    --OID       1.3.6.1.4.1.52.1.6.12.6.1.7.1.6
    SYNTAX      OCTET STRING
    ACCESS      read-only
    STATUS      mandatory
    DESCRIPTION
                "The source address of this acquired database entry, i.e.
                the instance."
::= { nb30AcqDBEntry 6 }

nb30AcqMacAddress	OBJECT-TYPE
    SYNTAX	OCTET STRING (SIZE (6))
    ACCESS	read-only
    STATUS	mandatory
    DESCRIPTION
	"The MAC address for the specific entry."
::= { nb30AcqDBEntry 7 }


-- Permanent Database Statistical Object Definitions
--
-- This section defines the objects under the Permanent Database
-- Statistics node.
--
-- Instance Identifiers for Permanent Database Statistical Objects
--
--      There is only one instance of an Permanent Database Statistical
--      object, thus the Instance Identifier is 0.
--
--  Permanent Database Statistical Objects

nb30PermMaxEntries      OBJECT-TYPE
    --OID       1.3.6.1.4.1.52.1.6.12.6.2.1
    SYNTAX      INTEGER
    ACCESS      read-only
    STATUS      mandatory
    DESCRIPTION
                "The maximum number of entries allowed in the permanent
                database 2047 entries."
::= { nb30PermDB 1 }

nb30PermCurrentEntries  OBJECT-TYPE
    --OID       1.3.6.1.4.1.52.1.6.12.6.2.2
    SYNTAX      INTEGER
    ACCESS      read-only
    STATUS      mandatory
    DESCRIPTION
                "The number of entries currently recorded in the bridge's
                permanent database."
::= { nb30PermDB 2 }

nb30PermEraseDatabase   OBJECT-TYPE
    --OID       1.3.6.1.4.1.52.1.6.12.6.2.3
    SYNTAX      INTEGER
                {
                    erasePermanentDatabase(1)
                }
    ACCESS      read-write
    STATUS      mandatory
    DESCRIPTION
                "Erase all entries in the permanent database."
::= { nb30PermDB 3 }

-- Permanent Database Option Object Definitions
--
-- This section defines the objects under the Permanent Database
-- Option node.
--
-- Instance Identifiers for Permanent Database Option Objects
--
--      The instance identifier for the permanent database option objects is
--      the 6-byte Ethernet address of the device to be added, deleted or
--      displayed to/from the permanent database.
--
--  Permanent Database Option Objects

nb30PermDBTable     OBJECT-TYPE
    --OID       1.3.6.1.4.1.52.1.6.12.6.2.4
    SYNTAX      SEQUENCE OF Nb30PermDBEntry
    ACCESS      not-accessible
    STATUS      mandatory
    DESCRIPTION
                "Aquired database entrys table"
::= { nb30PermDB 4 }

nb30PermDBEntry     OBJECT-TYPE
    --OID       1.3.6.1.4.1.52.1.6.12.6.2.4.1
    SYNTAX      Nb30PermDBEntry
    ACCESS      not-accessible
    STATUS      mandatory
    DESCRIPTION
                ""
    INDEX       { nb30PermDBMacAddress }
::= { nb30PermDBTable 1 }

Nb30PermDBEntry ::=
    SEQUENCE {
                nb30PermCreateFilter    INTEGER,
                nb30PermCreateForward   INTEGER,
                nb30PermDeleteEntry     INTEGER,
                nb30PermFilterType      OCTET STRING,
                nb30PermFilterAction    INTEGER,
                nb30PermSourceAddress   OCTET STRING,
                nb30PermDBMacAddress    OCTET STRING
             }

nb30PermCreateFilter        OBJECT-TYPE
    --OID       1.3.6.1.4.1.52.1.6.12.6.2.4.1.1
    SYNTAX      INTEGER
                {
                    createPermanentFilter(1)
                }
    ACCESS      read-write
    STATUS      mandatory
    DESCRIPTION
                "Add an entry to the permanent database to filter packets
                entering port 1 if those packets are destined for the
                specified address."
::= { nb30PermDBEntry 1 }

nb30PermCreateForward   OBJECT-TYPE
    --OID       1.3.6.1.4.1.52.1.6.12.6.2.4.1.2
    SYNTAX      INTEGER
                {
                    createPermanentForward(1)
                }
    ACCESS      read-write
    STATUS      mandatory
    DESCRIPTION
                "Add an entry to the permanent database to forward
                packets entering port 1 to the remote port if those
                packets are destined for the specified address."
::= { nb30PermDBEntry 2 }

nb30PermDeleteEntry     OBJECT-TYPE
    --OID       1.3.6.1.4.1.52.1.6.12.6.2.4.1.3
    SYNTAX      INTEGER
                {
                    deletePermanentEntry(1)
                }
    ACCESS      read-write
    STATUS      mandatory
    DESCRIPTION
                "Delete an entry from the permanent database."
::= { nb30PermDBEntry 3 }

nb30PermFilterType      OBJECT-TYPE
    --OID       1.3.6.1.4.1.52.1.6.12.6.2.4.1.4
    SYNTAX      OCTET STRING
    ACCESS      read-only
    STATUS      mandatory
    DESCRIPTION
                "Display the entry type, STATIC ."
::= { nb30PermDBEntry 4 }

nb30PermFilterAction        OBJECT-TYPE
    --OID       1.3.6.1.4.1.52.1.6.12.6.2.4.1.5
    SYNTAX      INTEGER
                {
                    filter(1),
                    relay(2)
                }
    ACCESS      read-only
    STATUS      mandatory
    DESCRIPTION
                "The action taken on packets entering port 1."
::= { nb30PermDBEntry 5 }

nb30PermSourceAddress   OBJECT-TYPE
    --OID       1.3.6.1.4.1.52.1.6.12.6.2.4.1.6
    SYNTAX      OCTET STRING
    ACCESS      read-only
    STATUS      mandatory
    DESCRIPTION
                "The source address in this permanent database entry, i.e.
                the instance."
::= { nb30PermDBEntry 6 }

nb30PermDBMacAddress	OBJECT-TYPE
    SYNTAX	OCTET STRING (SIZE (6))
    ACCESS	read-only
    STATUS	mandatory
    DESCRIPTION
	"The specific MAC address for this entry."
::= { nb30PermDBEntry 7 }


-- Special Database Statistical Object Definitions
--
-- This section defines the objects under the Special Database
-- Statistical node.
--
-- Instance Identifiers for Special Database Statistical Objects
--
--      There is only one instance of a Special Database Statistical object,
--      thus the Instance Identifier is 0.
--
-- Special Database Statistical Objects

nb30SpecNumEntries      OBJECT-TYPE
    --OID       1.3.6.1.4.1.52.1.6.12.6.3.1
    SYNTAX      INTEGER
    ACCESS      read-only
    STATUS      mandatory
    DESCRIPTION
                "The number of filters in the special database."
::= { nb30SpecDB 1 }

nb30SpecMaxEntries      OBJECT-TYPE
    --OID       1.3.6.1.4.1.52.1.6.12.6.3.2
    SYNTAX      INTEGER
    ACCESS      read-only
    STATUS      mandatory
    DESCRIPTION
                "The maximum number of filters the special database can
                contain."
::= { nb30SpecDB 2 }

nb30SpecNextFilterNum   OBJECT-TYPE
    --OID       1.3.6.1.4.1.52.1.6.12.6.3.3
    SYNTAX      INTEGER
    ACCESS      read-only
    STATUS      mandatory
    DESCRIPTION
                "The number of the next available filter that can be added
                to the special database. This OID will return a 255 if the
                database is full"
::= { nb30SpecDB 3 }

-- Special Database Filter Object Definitions
--
-- This section defines the objects under the Special Database
-- Filter node.
--
-- Instance Identifiers for Special Database Filter Objects
--
--      The instance identifier of the special database filter objects
--      is the filter number, values from 1 through 10 are allowed.
--
-- Special Database Filter Objects

nb30SpecDBTable     OBJECT-TYPE
    --OID       1.3.6.1.4.1.52.1.6.12.6.3.4
    SYNTAX      SEQUENCE OF Nb30SpecDBEntry
    ACCESS      not-accessible
    STATUS      mandatory
    DESCRIPTION
                ""
::= { nb30SpecDB 4 }

nb30SpecDBEntry     OBJECT-TYPE
    --OID       1.3.6.1.4.1.52.1.6.12.6.3.4.1
    SYNTAX      Nb30SpecDBEntry
    ACCESS      not-accessible
    STATUS      mandatory
    DESCRIPTION
                ""
    INDEX       { nb30SpecDbFilterNumber }

::= { nb30SpecDBTable 1 }

Nb30SpecDBEntry ::=
    SEQUENCE {
                nb30SpecEnable          INTEGER,
                nb30SpecPort1           INTEGER,
                nb30SpecDestAddress     OCTET STRING,
                nb30SpecSrcAddress      OCTET STRING,
                nb30SpecType            OCTET STRING,
                nb30SpecDataField       OCTET STRING,
                nb30SpecDeleteFilter    INTEGER,
                nb30SpecDbFilterNumber  INTEGER
             }

nb30SpecEnable      OBJECT-TYPE
    --OID       1.3.6.1.4.1.52.1.6.12.6.3.4.1.1
    SYNTAX      INTEGER
                {
                    disableFilter(1),
                    enableFilter(2)
                }
    ACCESS      read-write
    STATUS      mandatory
    DESCRIPTION
                "Enable or disable the filter."
::= { nb30SpecDBEntry 1 }

nb30SpecPort1       OBJECT-TYPE
    --OID       1.3.6.1.4.1.52.1.6.12.6.3.4.1.2
    SYNTAX      INTEGER
                {
                    filter(1),
                    relay(2)
                }
    ACCESS      read-write
    STATUS      mandatory
    DESCRIPTION
                "Set port 1 to filter or forward packets."
::= { nb30SpecDBEntry 2 }

nb30SpecDestAddress OBJECT-TYPE
    --OID       1.3.6.1.4.1.52.1.6.12.6.3.4.1.3
    SYNTAX      OCTET STRING
    ACCESS      read-write
    STATUS      mandatory
    DESCRIPTION
                "Set the special database to filter packets with a specific
                destination address."
::= { nb30SpecDBEntry 3 }

nb30SpecSrcAddress      OBJECT-TYPE
    --OID       1.3.6.1.4.1.52.1.6.12.6.3.4.1.4
    SYNTAX      OCTET STRING
    ACCESS      read-write
    STATUS      mandatory
    DESCRIPTION
                "Set the special database to filter packets with a specific
                source address."
::= { nb30SpecDBEntry 4 }

nb30SpecType        OBJECT-TYPE
    --OID       1.3.6.1.4.1.52.1.6.12.6.3.4.1.5
    SYNTAX      OCTET STRING
    ACCESS      read-write
    STATUS      mandatory
    DESCRIPTION
                "Set the special database to filter packets with a specific
                type field."
::= { nb30SpecDBEntry 5 }

nb30SpecDataField       OBJECT-TYPE
    --OID       1.3.6.1.4.1.52.1.6.12.6.3.4.1.6
    SYNTAX      OCTET STRING
    ACCESS      read-write
    STATUS      mandatory
    DESCRIPTION
                "Set the special database to filter packets based on the
                first sixteen bytes of data in the packet."
::= { nb30SpecDBEntry 6 }

nb30SpecDeleteFilter        OBJECT-TYPE
    --OID       1.3.6.1.4.1.52.1.6.12.6.3.4.1.7
    SYNTAX      INTEGER
                {
                    deleteFilter(1)
                }
    ACCESS      read-write
    STATUS      mandatory
    DESCRIPTION
                "Delete a filter from the special database."
::= { nb30SpecDBEntry 7 }

nb30SpecDbFilterNumber	OBJECT-TYPE
    SYNTAX	INTEGER
    ACCESS	read-only
    STATUS	mandatory
    DESCRIPTION
	"The specific special data base filter number."
::= { nb30SpecDBEntry 8 }

END
