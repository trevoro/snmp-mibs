-- MIB generated by miftomib version 1.0a

ADAPTECSCSI-MIB DEFINITIONS ::= BEGIN

-- DMI support for the Adaptec SCSI interface.  

IMPORTS
    OBJECT-TYPE
    FROM RFC-1212
    Counter, enterprises
    FROM RFC1155-SMI
    DisplayString
    FROM RFC1213-MIB;

DmiCounter          ::= Counter
DmiInteger          ::= INTEGER
DmiDisplaystring    ::= DisplayString
DmiComponentIndex   ::= INTEGER

adaptec                 OBJECT IDENTIFIER ::= {enterprises 795}
products                OBJECT IDENTIFIER ::= {adaptec 2}
scsi                    OBJECT IDENTIFIER ::= {products 6}
dmtfGroups              OBJECT IDENTIFIER ::= {scsi 1}

SComponentid ::= SEQUENCE {
    a1Manufacturer                              DmiDisplaystring,
    a1Product                                   DmiDisplaystring,
    a1Version                                   DmiDisplaystring,
    a1SerialNumber                              DmiDisplaystring,
    a1Installation                              DmiDisplaystring,
    a1Verify                                    DmiInteger
}

tComponentid OBJECT-TYPE
    SYNTAX      SEQUENCE OF SComponentid
    ACCESS      not-accessible
    STATUS      mandatory
    DESCRIPTION "This group defines the attributes common to all components.
 This group is required."
    ::= {dmtfGroups 1}

eComponentid OBJECT-TYPE
    SYNTAX      SComponentid
    ACCESS      not-accessible
    STATUS      mandatory
    DESCRIPTION ""
    INDEX       {DmiComponentIndex}
    ::= {tComponentid 1}

a1Manufacturer OBJECT-TYPE
    SYNTAX      DmiDisplaystring
    ACCESS      read-only
    STATUS      mandatory
    DESCRIPTION "Manufacturer of this system."
    ::= {eComponentid 1}

a1Product OBJECT-TYPE
    SYNTAX      DmiDisplaystring
    ACCESS      read-only
    STATUS      mandatory
    DESCRIPTION "Product name for this system."
    ::= {eComponentid 2}

a1Version OBJECT-TYPE
    SYNTAX      DmiDisplaystring
    ACCESS      read-only
    STATUS      mandatory
    DESCRIPTION "Version number of this system."
    ::= {eComponentid 3}

a1SerialNumber OBJECT-TYPE
    SYNTAX      DmiDisplaystring
    ACCESS      read-only
    STATUS      mandatory
    DESCRIPTION "Serial number for this system."
    ::= {eComponentid 4}

a1Installation OBJECT-TYPE
    SYNTAX      DmiDisplaystring
    ACCESS      read-only
    STATUS      mandatory
    DESCRIPTION "The time and date for the last time this component was installed
"
    ::= {eComponentid 5}

a1Verify OBJECT-TYPE
    SYNTAX      INTEGER {
        vAnErrorOccurredCheckStatusCode             (0),
        vThisComponentDoesNotExist                  (1),
        vTheVerificationIsNotSupported              (2),
        vReserved                                   (3),
        vThisComponentExistsButTheFunctionalityI    (4),
        vThisComponentExistsButTheFunctionality1    (5),
        vThisComponentExistsAndIsNotFunctioningC    (6),
        vThisComponentExistsAndIsFunctioningCorr    (7)
    }
    ACCESS      read-only
    STATUS      mandatory
    DESCRIPTION "A code that provides a level of verification that the component
is still installed and working."
    ::= {eComponentid 6}

SOperationGroup ::= SEQUENCE {
    a2PollDevices                               DmiInteger,
    a2ScanDevices                               DmiInteger,
    a2IndicationControl                         DmiInteger
}

tOperationGroup OBJECT-TYPE
    SYNTAX      SEQUENCE OF SOperationGroup
    ACCESS      not-accessible
    STATUS      mandatory
    DESCRIPTION "The Operation group controls the stystem. "
    ::= {dmtfGroups 2}

eOperationGroup OBJECT-TYPE
    SYNTAX      SOperationGroup
    ACCESS      not-accessible
    STATUS      mandatory
    DESCRIPTION ""
    INDEX       {DmiComponentIndex}
    ::= {tOperationGroup 1}

a2PollDevices OBJECT-TYPE
    SYNTAX      DmiInteger
    ACCESS      read-write
    STATUS      mandatory
    DESCRIPTION "Writing a non-zero value to this variable causes an immediate
one time poll of all currently known devices. This variable will always return
the value zero when it is read."
    ::= {eOperationGroup 1}

a2ScanDevices OBJECT-TYPE
    SYNTAX      DmiInteger
    ACCESS      read-write
    STATUS      mandatory
    DESCRIPTION "Writing a non-zero value to this variable causes an immediate
one time scan of the SCSI busses for all possible devices.  This variable
will always return the value zero when it is read."
    ::= {eOperationGroup 2}

a2IndicationControl OBJECT-TYPE
    SYNTAX      INTEGER {
        vOff                                        (0),
        vOn                                         (1)
    }
    ACCESS      read-write
    STATUS      mandatory
    DESCRIPTION "Controls whether any indications are enabled"
    ::= {eOperationGroup 3}

SHostAdapterGroup ::= SEQUENCE {
    a3HostAdapterIndex                          DmiInteger,
    a3HostAdapterDescription                    DmiDisplaystring,
    a3HostAdapterVersion                        DmiDisplaystring,
    a3ChannelCount                              DmiInteger,
    a3Errorcontrolid                            DmiDisplaystring,
    a3EventStatus                               DmiInteger
}

tHostAdapterGroup OBJECT-TYPE
    SYNTAX      SEQUENCE OF SHostAdapterGroup
    ACCESS      not-accessible
    STATUS      mandatory
    DESCRIPTION "The Host Adapter Description group describes the logical
Host Adapters installed in the system . "
    ::= {dmtfGroups 3}

eHostAdapterGroup OBJECT-TYPE
    SYNTAX      SHostAdapterGroup
    ACCESS      not-accessible
    STATUS      mandatory
    DESCRIPTION ""
    INDEX       {DmiComponentIndex, a3HostAdapterIndex}
    ::= {tHostAdapterGroup 1}

a3HostAdapterIndex OBJECT-TYPE
    SYNTAX      DmiInteger
    ACCESS      read-only
    STATUS      mandatory
    DESCRIPTION "An index into the host adatper table"
    ::= {eHostAdapterGroup 1}

a3HostAdapterDescription OBJECT-TYPE
    SYNTAX      DmiDisplaystring
    ACCESS      read-only
    STATUS      mandatory
    DESCRIPTION "The description string returned from an SCSI Inquiry Command."
    ::= {eHostAdapterGroup 2}

a3HostAdapterVersion OBJECT-TYPE
    SYNTAX      DmiDisplaystring
    ACCESS      read-only
    STATUS      mandatory
    DESCRIPTION "The version string returned from an SCSI Inquiry Command."
    ::= {eHostAdapterGroup 3}

a3ChannelCount OBJECT-TYPE
    SYNTAX      DmiInteger
    ACCESS      read-only
    STATUS      mandatory
    DESCRIPTION "The number of SCSI channels provided by this host adapter."
    ::= {eHostAdapterGroup 4}

a3Errorcontrolid OBJECT-TYPE
    SYNTAX      DmiDisplaystring
    ACCESS      read-only
    STATUS      mandatory
    DESCRIPTION "Identifies the row in the errorControl table providing error
control & status for this group."
    ::= {eHostAdapterGroup 5}

a3EventStatus OBJECT-TYPE
    SYNTAX      INTEGER {
        vDiscovered                                 (0),
        vChanged                                    (1),
        vFailed                                     (2),
        vRecovered                                  (3)
    }
    ACCESS      read-only
    STATUS      mandatory
    DESCRIPTION "Identifies the reason an indication was sent."
    ::= {eHostAdapterGroup 6}

SLogicalUnitGroup ::= SEQUENCE {
    a4HostAdapterIndex                          DmiInteger,
    a4ScsiId                                    DmiInteger,
    a4LogicalUnitId                             DmiInteger,
    a4LogicalUnitType                           DmiInteger,
    a4LogicalUnitDescription                    DmiDisplaystring,
    a4Errorcontrolid                            DmiDisplaystring,
    a4EventStatus                               DmiInteger
}

tLogicalUnitGroup OBJECT-TYPE
    SYNTAX      SEQUENCE OF SLogicalUnitGroup
    ACCESS      not-accessible
    STATUS      mandatory
    DESCRIPTION "The logical units attached to host adapters, "
    ::= {dmtfGroups 4}

eLogicalUnitGroup OBJECT-TYPE
    SYNTAX      SLogicalUnitGroup
    ACCESS      not-accessible
    STATUS      mandatory
    DESCRIPTION ""
    INDEX       {DmiComponentIndex, a4HostAdapterIndex, a4ScsiId, a4LogicalUnitId}
    ::= {tLogicalUnitGroup 1}

a4HostAdapterIndex OBJECT-TYPE
    SYNTAX      DmiInteger
    ACCESS      read-only
    STATUS      mandatory
    DESCRIPTION "The index of the host adapter to which this Logical Unit
is attached."
    ::= {eLogicalUnitGroup 1}

a4ScsiId OBJECT-TYPE
    SYNTAX      DmiInteger
    ACCESS      read-only
    STATUS      mandatory
    DESCRIPTION "The SCSI target ID of the Logical Unit"
    ::= {eLogicalUnitGroup 2}

a4LogicalUnitId OBJECT-TYPE
    SYNTAX      DmiInteger
    ACCESS      read-only
    STATUS      mandatory
    DESCRIPTION "The ID of this Logical Unit."
    ::= {eLogicalUnitGroup 3}

a4LogicalUnitType OBJECT-TYPE
    SYNTAX      INTEGER {
        vDirectaccess                               (1),
        vTape                                       (2),
        vPrinter                                    (3),
        vProcessor                                  (4),
        vWriteonce                                  (5),
        vCdrom                                      (6),
        vScanner                                    (7),
        vOpticalmemory                              (8),
        vJukebox                                    (9),
        vComdevice                                  (10),
        vHostadapter                                (11),
        vOther                                      (12)
    }
    ACCESS      read-only
    STATUS      mandatory
    DESCRIPTION "The type of this Logical Unit."
    ::= {eLogicalUnitGroup 4}

a4LogicalUnitDescription OBJECT-TYPE
    SYNTAX      DmiDisplaystring
    ACCESS      read-only
    STATUS      mandatory
    DESCRIPTION "The description string returned from an SCSI Inquiry Command."
    ::= {eLogicalUnitGroup 5}

a4Errorcontrolid OBJECT-TYPE
    SYNTAX      DmiDisplaystring
    ACCESS      read-only
    STATUS      mandatory
    DESCRIPTION "Identifies the row in the errorControl table providing error
control & status for this group."
    ::= {eLogicalUnitGroup 6}

a4EventStatus OBJECT-TYPE
    SYNTAX      INTEGER {
        vDiscovered                                 (0),
        vChanged                                    (1),
        vFailed                                     (2),
        vRecovered                                  (3)
    }
    ACCESS      read-only
    STATUS      mandatory
    DESCRIPTION "Identifies the reason an indication was sent."
    ::= {eLogicalUnitGroup 7}

SErrorcontrol ::= SEQUENCE {
    a5Selfid                                    DmiInteger,
    a5Fatalcount                                DmiCounter,
    a5Majorcount                                DmiCounter,
    a5Warningcount                              DmiCounter,
    a5Errstatus                                 DmiInteger,
    a5Errstatustype                             DmiInteger,
    a5Indicationcontrol                         DmiInteger
}

tErrorcontrol OBJECT-TYPE
    SYNTAX      SEQUENCE OF SErrorcontrol
    ACCESS      not-accessible
    STATUS      mandatory
    DESCRIPTION "Indication control and status for the parent group"
    ::= {dmtfGroups 5}

eErrorcontrol OBJECT-TYPE
    SYNTAX      SErrorcontrol
    ACCESS      not-accessible
    STATUS      mandatory
    DESCRIPTION ""
    INDEX       {DmiComponentIndex, a5Selfid}
    ::= {tErrorcontrol 1}

a5Selfid OBJECT-TYPE
    SYNTAX      DmiInteger
    ACCESS      read-only
    STATUS      mandatory
    DESCRIPTION "Instance identifer. A unique number that identifies this
row."
    ::= {eErrorcontrol 1}

a5Fatalcount OBJECT-TYPE
    SYNTAX      DmiCounter
    ACCESS      read-only
    STATUS      mandatory
    DESCRIPTION "Count of all fatal errors since system startup."
    ::= {eErrorcontrol 2}

a5Majorcount OBJECT-TYPE
    SYNTAX      DmiCounter
    ACCESS      read-only
    STATUS      mandatory
    DESCRIPTION "Count of all major errors since system startup."
    ::= {eErrorcontrol 3}

a5Warningcount OBJECT-TYPE
    SYNTAX      DmiCounter
    ACCESS      read-only
    STATUS      mandatory
    DESCRIPTION "Count of all warning errors since system startup."
    ::= {eErrorcontrol 4}

a5Errstatus OBJECT-TYPE
    SYNTAX      INTEGER {
        vOk                                         (0),
        vWarning                                    (1),
        vMajor                                      (2),
        vFatal                                      (3)
    }
    ACCESS      read-only
    STATUS      mandatory
    DESCRIPTION "current error status"
    ::= {eErrorcontrol 5}

a5Errstatustype OBJECT-TYPE
    SYNTAX      INTEGER {
        vPost                                       (0),
        vRuntime                                    (1),
        vDiagnosticTest                             (2)
    }
    ACCESS      read-only
    STATUS      mandatory
    DESCRIPTION "Indicates the type of detection that set the current error
status."
    ::= {eErrorcontrol 6}

a5Indicationcontrol OBJECT-TYPE
    SYNTAX      INTEGER {
        vOff                                        (0),
        vOn                                         (1)
    }
    ACCESS      read-write
    STATUS      mandatory
    DESCRIPTION "Enables or disables generation of indications"
    ::= {eErrorcontrol 7}

SMiftomib ::= SEQUENCE {
    a99MibName                                  DmiDisplaystring,
    a99MibOid                                   DmiDisplaystring,
    a99DisableTrap                              DmiInteger
}

tMiftomib OBJECT-TYPE
    SYNTAX      SEQUENCE OF SMiftomib
    ACCESS      not-accessible
    STATUS      mandatory
    DESCRIPTION "This group defines attributes required for DMI to
SNMP translati
n."
    ::= {dmtfGroups 99}

eMiftomib OBJECT-TYPE
    SYNTAX      SMiftomib
    ACCESS      not-accessible
    STATUS      mandatory
    DESCRIPTION ""
    INDEX       {DmiComponentIndex}
    ::= {tMiftomib 1}

a99MibName OBJECT-TYPE
    SYNTAX      DmiDisplaystring
    ACCESS      read-only
    STATUS      mandatory
    DESCRIPTION "The MIB name that defines this MIF"
    ::= {eMiftomib 1}

a99MibOid OBJECT-TYPE
    SYNTAX      DmiDisplaystring
    ACCESS      read-only
    STATUS      mandatory
    DESCRIPTION "The MIB Object Identifier that corresponds to this MIF"
    ::= {eMiftomib 2}

a99DisableTrap OBJECT-TYPE
    SYNTAX      DmiInteger
    ACCESS      read-write
    STATUS      mandatory
    DESCRIPTION "This attribute can be changed to disable sending of traps
from this component"
    ::= {eMiftomib 3}


-- Here is the TRAP definition for the MIB
-- Append this to the MIB produced by MIFTOMIB
-- DO NOT CHANGE ANYTHING in this definition, SNMP-DMI translator only
--         handles this specific format of the TRAP
-- changing this format WILL cause trnaslator to fail

tTrapGroup OBJECT-TYPE
    SYNTAX        SEQUENCE OF STrapGroup
    ACCESS        not-accessible
    STATUS        mandatory
    DESCRIPTION    "This group defines attributes needed for Trap
            definition. This group does not exist in MIF file"
    ::= {dmtfGroups 9999}

STrapGroup ::= SEQUENCE {
    a9999ErrorTime              DisplayString,
    a9999ErrorStatus            DmiInteger,
    a9999ErrorGroupId           DmiInteger,
    a9999ErrorInstanceId        DmiInteger,
    a9999ComponentId            DmiInteger,
    a9999GroupId                DmiInteger,
    a9999InstanceId             DmiInteger,
    a9999VendorCode1            DmiInteger,
    a9999VendorCode2            DmiInteger,
    a9999VendorText             OCTET STRING,
    a9999ParentGroupId          DmiInteger,
    a9999ParentInstanceId       DmiInteger
}

eTrapGroup OBJECT-TYPE
    SYNTAX        STrapGroup
    ACCESS        not-accessible
    STATUS        mandatory
    DESCRIPTION    ""
    INDEX        {DmiComponentIndex}
    ::= {tTrapGroup 1}

a9999ErrorTime OBJECT-TYPE
    SYNTAX        DisplayString
    ACCESS        read-only
    STATUS        mandatory
    DESCRIPTION    "The Date & Time when the error occured"
    ::= {eTrapGroup 1}

a9999ErrorStatus OBJECT-TYPE
    SYNTAX        DmiInteger
    ACCESS        read-only
    STATUS        mandatory
    DESCRIPTION    "Error Status Code"
    ::= {eTrapGroup 2}

a9999ErrorGroupId OBJECT-TYPE
    SYNTAX        DmiInteger
    ACCESS        read-only
    STATUS        mandatory
    DESCRIPTION    "Group ID of the errorControl Group"
    ::= {eTrapGroup 3}

a9999ErrorInstanceId OBJECT-TYPE
    SYNTAX        DmiInteger
    ACCESS        read-only
    STATUS        mandatory
    DESCRIPTION    "Instance ID of the errorControl Group"
    ::= {eTrapGroup 4}

a9999ComponentId OBJECT-TYPE
    SYNTAX        DmiInteger
    ACCESS        read-only
    STATUS        mandatory
    DESCRIPTION    "Component ID of the component that caused this error"
    ::= {eTrapGroup 5}

a9999GroupId OBJECT-TYPE
    SYNTAX        DmiInteger
    ACCESS        read-only
    STATUS        mandatory
    DESCRIPTION    "Group ID of the Group that caused this error"
    ::= {eTrapGroup 6}

a9999InstanceId OBJECT-TYPE
    SYNTAX        DmiInteger
    ACCESS        read-only
    STATUS        mandatory
    DESCRIPTION    "Instance ID of the Group that caused this error"
    ::= {eTrapGroup 7}

a9999VendorCode1 OBJECT-TYPE
    SYNTAX        DmiInteger
    ACCESS        read-only
    STATUS        mandatory
    DESCRIPTION    "Vendor specific code 1"
    ::= {eTrapGroup 8}

a9999VendorCode2 OBJECT-TYPE
    SYNTAX        DmiInteger
    ACCESS        read-only
    STATUS        mandatory
    DESCRIPTION    "Vendor specific code 2"
    ::= {eTrapGroup 9}

a9999VendorText OBJECT-TYPE
    SYNTAX        OCTET STRING
    ACCESS        read-only
    STATUS        mandatory
    DESCRIPTION    "Vendor specific octet string info"
    ::= {eTrapGroup 10}

a9999ParentGroupId OBJECT-TYPE
    SYNTAX        DmiInteger
    ACCESS        read-only
    STATUS        mandatory
    DESCRIPTION    "Group ID of parent of Group that caused this error"
    ::= {eTrapGroup 11}

a9999ParentInstanceId OBJECT-TYPE
    SYNTAX        DmiInteger
    ACCESS        read-only
    STATUS        mandatory
    DESCRIPTION    "Instance ID of parent of Group that caused this error"
    ::= {eTrapGroup 12}

adaptecEventError TRAP-TYPE
    ENTERPRISE eTrapGroup
    VARIABLES  { a9999ErrorTime,
                 a9999ErrorStatus,
                 a9999ErrorGroupId,
                 a9999ErrorInstanceId,
                 a9999ComponentId,
                 a9999GroupId,
                 a9999InstanceId,
                 a9999VendorCode1,
                 a9999VendorCode2,
                 a9999VendorText,
                 a9999ParentGroupId,
                 a9999ParentInstanceId}

    DESCRIPTION "DMI Service Layer generated event for Adaptec Scsi"

    --NMS trap annotation

    --#TYPE       "DMI Adaptec Scsi Error Event"
    --#SUMMARY    "Event Data: (%s,%d,%d,%d) (%d,%d,%d,%d,%d) (%d,%d)"
    --#ARGUMENTS  {0, 1, 2, 3, 4, 5, 6, 7, 8, 10, 11}
    --#SEVERITY   CRITICAL
    --#TIMEINDEX  12
    --#STATE      DEGRADED
    ::= 1
END
