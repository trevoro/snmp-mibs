-- *****************************************************************************
-- Unisphere-Data-ERX-Registry
--
-- Unisphere Networks enterprise SNMP MIB.
-- Registry for the Edge Routing Switch (ERX) product entities.
--
-- Copyright (c) 2001, 2002 Unisphere Networks, Inc.
-- Copyright (c) 2002 Juniper Networks, Inc.
--   All Rights Reserved.
-- *****************************************************************************

Unisphere-Data-ERX-Registry DEFINITIONS ::= BEGIN

IMPORTS
    MODULE-IDENTITY, OBJECT-IDENTITY
        FROM SNMPv2-SMI
    usDataAdmin
        FROM Unisphere-Data-Registry;

usdErxRegistry MODULE-IDENTITY
    LAST-UPDATED "200210101851Z"  -- 10-Oct-02 02:51 PM EDT
    ORGANIZATION "Juniper Networks, Inc."
    CONTACT-INFO
        "       Juniper Networks, Inc.
        Postal: 10 Technology Park Drive
                Westford, MA  01886
                USA
        Tel:    +1 978 589 5800
        Email:  mib@Juniper.net"
    DESCRIPTION
        "Unisphere Edge Routing Switch (ERX) product family system-specific
        object identification values.  This module includes the textual
        convention definition for the ERX module types.  It also defines
        AutonomousType (OID) values for all the physical entity types
        (entPhysicalVendorType).  This module will be updated whenever a new
        type of module or other hardware becomes available in ERX systems."
    -- Revision History
    REVISION    "200210101851Z"  -- 10-Oct-02 02:51 PM EDT  - RX 4.0
    DESCRIPTION
        "Added support for the 12-port E3 IO adapter.
         Added support for the Ut3f12 line card.
         Added SRP module with 40 gbps plus switch fabric.
         Added Vitrual Tunneling Server (VTS) module.
         Added X.21/V.35 Server module and I/O adapter.
         Added OC12 APS I/O adapters.
         Added redundant midplane spare I/O adapters."
    REVISION    "200205081234Z"  -- 08-May-02 08:34 AM EDT  - RX 3.4
    DESCRIPTION
        "Added GE SFP IOA module."
    REVISION    "200205071405Z"  -- 07-May-02 10:05 AM EDT  - RX 3.3
    DESCRIPTION
        "Added SRP modules with 5 gbps and 40 gbps 'plus' switch fabrics."
    REVISION    "200108201608Z"  -- 20-Aug-01 12:08 PM EDT  - RX 3.2
    DESCRIPTION
        "Added 12 port channelized T3 modules."
    REVISION    "200106121827Z"  -- 12-Jun-01 02:27 PM EDT  - RX 3.1
    DESCRIPTION
        "Added High Speed Serial Interface (HSSI) modules."
    REVISION    "200106042011Z"  -- 04-Jun-01 04:11 PM EDT  - RX 3.0
    DESCRIPTION
        "Initial version of this SNMP management information module."
    ::= { usDataAdmin 2 }


-- +++++++++++++++++++++++++++++++++++++++++++++++++++++++++++++++++++++++++++++
--  ERX physical entity identifiers.
--  The OID values under usdErxEntPhysicalType are used by the SNMP agent in the
--  ERX product as the AutonomousType values for the entPhysicalVendorType
--  varbinds for the ERX objects in the entPhysicalTable.
-- +++++++++++++++++++++++++++++++++++++++++++++++++++++++++++++++++++++++++++++

usdErxEntPhysicalType OBJECT IDENTIFIER ::= { usdErxRegistry 1 }

--
-- Chassis class
--
erxChassis  OBJECT-IDENTITY
    STATUS      current
    DESCRIPTION
        "The vendor type ID for a generic Edge Routing Switch (ERX) chassis.
        This identifies an 'overall' physical entity for any ERX system."
    ::= { usdErxEntPhysicalType 1 }

erx700Chassis  OBJECT-IDENTITY
    STATUS      current
    DESCRIPTION
        "The vendor type ID for an Edge Routing Switch 700 (ERX-700) 7-slot
        chassis.  This is the 'overall' physical entity for an ERX-700 system."
    ::= { erxChassis 1 }

erx1400Chassis  OBJECT-IDENTITY
    STATUS      current
    DESCRIPTION
        "The vendor type ID for an Edge Routing Switch 1400 (ERX-1400) 14-slot
        chassis.  This is the 'overall' physical entity for an ERX-1400 system."
    ::= { erxChassis 2 }

--
-- Fan class
--
erxFanAssembly  OBJECT-IDENTITY
    STATUS      current
    DESCRIPTION
        "The vendor type ID for an ERX fan assembly."
    ::= { usdErxEntPhysicalType 2 }

erx700FanAssembly  OBJECT-IDENTITY
    STATUS      current
    DESCRIPTION
        "The vendor type ID for an ERX700 fan assembly with four fans and two
        -12 volt, 15 watt power converters (Product Code: FAN-7)."
    ::= { erxFanAssembly 1 }

erx1400FanAssembly  OBJECT-IDENTITY
    STATUS      current
    DESCRIPTION
        "The vendor type ID for an ERX1400 fan assembly with six fans and two
        -24 volt, 50 watt power converters (Product Code: FAN-14)."
    ::= { erxFanAssembly 2 }

--
-- Power Supply class
--
erxPowerInput  OBJECT-IDENTITY
    STATUS      current
    DESCRIPTION
        "The vendor type ID for an ERX power distribution module (Product Code:
        PDU)."
    ::= { usdErxEntPhysicalType 3 }

--
-- Backplane class
--
erxMidplane  OBJECT-IDENTITY
    STATUS      current
    DESCRIPTION
        "The vendor type ID for an ERX midplane."
    ::= { usdErxEntPhysicalType 4 }

erx700Midplane  OBJECT-IDENTITY
    STATUS      current
    DESCRIPTION
        "The vendor type ID for an ERX700 (7-slot) midplane."
    ::= { erxMidplane 1 }

erx1400Midplane  OBJECT-IDENTITY
    STATUS      current
    DESCRIPTION
        "The vendor type ID for an ERX1400 (14-slot) midplane."
    ::= { erxMidplane 2 }

erx1Plus1RedundantT1E1Midplane  OBJECT-IDENTITY
    STATUS      current
    DESCRIPTION
        "The vendor type ID for an ERX 1 + 1 redundant T1/E1 midplane (Product
        Code: REDMID-T1/E1/1/1)."
    ::= { erxMidplane 3 }

erx2Plus1RedundantT1E1Midplane  OBJECT-IDENTITY
    STATUS      current
    DESCRIPTION
        "The vendor type ID for an ERX 2 + 1 redundant T1/E1 midplane (Product
        Code: REDMID-T1/E1/2/1)."
    ::= { erxMidplane 4 }

erx3Plus1RedundantT1E1Midplane  OBJECT-IDENTITY
    STATUS      current
    DESCRIPTION
        "The vendor type ID for an ERX 3 + 1 redundant T1/E1 midplane (Product
        Code: REDMID-T1/E1/3/1)."
    ::= { erxMidplane 5 }

erx4Plus1RedundantT1E1Midplane  OBJECT-IDENTITY
    STATUS      current
    DESCRIPTION
        "The vendor type ID for an ERX 4 + 1 redundant T1/E1 midplane (Product
        Code: REDMID-T1/E1/4/1)."
    ::= { erxMidplane 6 }

erx5Plus1RedundantT1E1Midplane  OBJECT-IDENTITY
    STATUS      current
    DESCRIPTION
        "The vendor type ID for an ERX 5 + 1 redundant T1/E1 midplane (Product
        Code: REDMID-T1/E1/5/1)."
    ::= { erxMidplane 7 }

erx1Plus1RedundantT3E3Midplane  OBJECT-IDENTITY
    STATUS      current
    DESCRIPTION
        "The vendor type ID for an ERX 1 + 1 redundant CT3/T3/E3 midplane
        (Product Code: REDMID-T3/E3/1/1)."
    ::= { erxMidplane 8 }

erx2Plus1RedundantT3E3Midplane  OBJECT-IDENTITY
    STATUS      current
    DESCRIPTION
        "The vendor type ID for an ERX 2 + 1 redundant CT3/T3/E3 midplane
        (Product Code: REDMID-T3/E3/2/1)."
    ::= { erxMidplane 9 }

erx3Plus1RedundantT3E3Midplane  OBJECT-IDENTITY
    STATUS      current
    DESCRIPTION
        "The vendor type ID for an ERX 3 + 1 redundant CT3/T3/E3 midplane
        (Product Code: REDMID-T3/E3/3/1)."
    ::= { erxMidplane 10 }

erx4Plus1RedundantT3E3Midplane  OBJECT-IDENTITY
    STATUS      current
    DESCRIPTION
        "The vendor type ID for an ERX 4 + 1 redundant CT3/T3/E3 midplane
        (Product Code: REDMID-T3/E3/4/1)."
    ::= { erxMidplane 11 }

erx5Plus1RedundantT3E3Midplane  OBJECT-IDENTITY
    STATUS      current
    DESCRIPTION
        "The vendor type ID for an ERX 5 + 1 redundant CT3/T3/E3 midplane
        (Product Code: REDMID-T3/E3/5/1)."
    ::= { erxMidplane 12 }

erx1Plus1RedundantOcMidplane  OBJECT-IDENTITY
    STATUS      current
    DESCRIPTION
        "The vendor type ID for an ERX 1 + 1 redundant OC3/OC12 midplane
        (Product Code: REDMID-OC/1/1)."
    ::= { erxMidplane 13 }

erx2Plus1RedundantOcMidplane  OBJECT-IDENTITY
    STATUS      current
    DESCRIPTION
        "The vendor type ID for an ERX 2 + 1 redundant OC3/OC12 midplane
        (Product Code: REDMID-OC/2/1)."
    ::= { erxMidplane 14 }

erx3Plus1RedundantOcMidplane  OBJECT-IDENTITY
    STATUS      current
    DESCRIPTION
        "The vendor type ID for an ERX 3 + 1 redundant OC3/OC12 midplane
        (Product Code: REDMID-OC/3/1)."
    ::= { erxMidplane 15 }

erx4Plus1RedundantOcMidplane  OBJECT-IDENTITY
    STATUS      current
    DESCRIPTION
        "The vendor type ID for an ERX 4 + 1 redundant OC3/OC12 midplane
        (Product Code: REDMID-OC/4/1)."
    ::= { erxMidplane 16 }

erx5Plus1RedundantOcMidplane  OBJECT-IDENTITY
    STATUS      current
    DESCRIPTION
        "The vendor type ID for an ERX 5 + 1 redundant OC3/OC12 midplane
        (Product Code: REDMID-OC/5/1)."
    ::= { erxMidplane 17 }

--
-- Module class - SRP
--
erxSrpModule  OBJECT-IDENTITY
    STATUS      current
    DESCRIPTION
        "The vendor type ID for an ERX Switch and Router Processor (SRP)
        module."
    ::= { usdErxEntPhysicalType 5 }

erxSrp5  OBJECT-IDENTITY
    STATUS      current
    DESCRIPTION
        "The vendor type ID for an ERX Switch and Router Processor (SRP) module
        with 5 Gbps switch fabric (Product Code: SRP-5)."
    ::= { erxSrpModule 1 }

erxSrp10  OBJECT-IDENTITY
    STATUS      current
    DESCRIPTION
        "The vendor type ID for an ERX Switch and Router Processor (SRP) module
        with 10 Gbps switch fabric (Product Code: SRP-10)."
    ::= { erxSrpModule 2 }

erxSrp10Ecc  OBJECT-IDENTITY
    STATUS      current
    DESCRIPTION
        "The vendor type ID for an ERX Switch and Router Processor (SRP) module
        with 10 Gbps switch fabric with ECC (Product Code: SRP-10-ECC)."
    ::= { erxSrpModule 3 }

erxSrp40  OBJECT-IDENTITY
    STATUS      current
    DESCRIPTION
        "The vendor type ID for an ERX Switch and Router Processor (SRP) module
        with 40 Gbps switch fabric with ECC (Product Code: SRP-40-ECC)."
    ::= { erxSrpModule 4 }

erxSrp5Plus  OBJECT-IDENTITY
    STATUS      current
    DESCRIPTION
        "The vendor type ID for an ERX Switch and Router Processor (SRP) module
        with 5 Gbps 'plus' switch fabric (Product Code: SRP-5Plus)."
    ::= { erxSrpModule 5 }

erxSrp40Plus  OBJECT-IDENTITY
    STATUS      current
    DESCRIPTION
        "The vendor type ID for an ERX Switch and Router Processor (SRP) module
        with 40 Gbps 'plus' switch fabric (Product Code: ERX-40EC2-SRP)."
    ::= { erxSrpModule 6 }

--
-- Module class - SRP I/O Adapter
--
erxSrpIoAdapter  OBJECT-IDENTITY
    STATUS      current
    DESCRIPTION
        "The vendor type ID for an ERX SRP I/O adapter (Product Code: SRP_I/O)."
    ::= { usdErxEntPhysicalType 6 }

--
-- Module class - Line Card
--
erxLineModule  OBJECT-IDENTITY
    STATUS      current
    DESCRIPTION
        "The vendor type ID for an ERX line module."
    ::= { usdErxEntPhysicalType 7 }

erxCt1  OBJECT-IDENTITY
    STATUS      current
    DESCRIPTION
        "The vendor type ID for an ERX 24 port fully channelized T1 line module
        (Product Code: CT1-FULL)."
    ::= { erxLineModule 1 }

erxCe1  OBJECT-IDENTITY
    STATUS      current
    DESCRIPTION
        "The vendor type ID for an ERX 20 port fully channelized E1 line module
        (Product Code: CE1-FULL)."
    ::= { erxLineModule 2 }

erxCt3  OBJECT-IDENTITY
    STATUS      current
    DESCRIPTION
        "The vendor type ID for an ERX 3 port channelized T3 line module
        (Product Code: CT3-3)."
    ::= { erxLineModule 4 }

erxT3Atm  OBJECT-IDENTITY
    STATUS      current
    DESCRIPTION
        "The vendor type ID for an ERX 3 port unchannelized T3 cell service
        line module (Product Code: T3-3A)."
    ::= { erxLineModule 5 }

erxT3Frame  OBJECT-IDENTITY
    STATUS      current
    DESCRIPTION
        "The vendor type ID for an ERX 3 port unchannelized T3 packet service
        line module (Product Code: T3-3F)."
    ::= { erxLineModule 6 }

erxE3Atm  OBJECT-IDENTITY
    STATUS      current
    DESCRIPTION
        "The vendor type ID for an ERX 3 port unchannelized E3 cell service
        line module (Product Code: E3-3A)."
    ::= { erxLineModule 7 }

erxE3Frame  OBJECT-IDENTITY
    STATUS      current
    DESCRIPTION
        "The vendor type ID for an ERX 3 port unchannelized E3 packet service
        line module (Product Code: E3-3F)."
    ::= { erxLineModule 8 }

erxOc3  OBJECT-IDENTITY
    STATUS      current
    DESCRIPTION
        "The vendor type ID for an ERX dual port Optical Carrier 3 (OC-3/STM-1)
        SONET/SDH line module (Product Code: OC3-2)."
    ::= { erxLineModule 9 }

erxOc3Oc12Atm  OBJECT-IDENTITY
    STATUS      current
    DESCRIPTION
        "The vendor type ID for an ERX OC3/OC12 multi-personality cell service
        line module (Product Code: OC3/OC12-ATM)."
    ::= { erxLineModule 10 }

erxOc3Oc12Pos  OBJECT-IDENTITY
    STATUS      current
    DESCRIPTION
        "The vendor type ID for an ERX OC3/OC12 multi-personality packet service
        line module (Product Code: OC3/OC12-POS)."
    ::= { erxLineModule 11 }

erxCOcx  OBJECT-IDENTITY
    STATUS      current
    DESCRIPTION
        "The vendor type ID for an ERX channelized OC3/STM1 and OC12/STM4 line
        module (Product Code: COCX/STMX-F0)."
    ::= { erxLineModule 12 }

erxFe2  OBJECT-IDENTITY
    STATUS      current
    DESCRIPTION
        "The vendor type ID for an ERX dual port fast (10/100) Ethernet line
        module (Product Code: 10/100_FE-2)."
    ::= { erxLineModule 13 }

erxGeFe  OBJECT-IDENTITY
    STATUS      current
    DESCRIPTION
        "The vendor type ID for an ERX multi-personality gigabit or fast
        (10/100) Ethernet line module (Product Code: GE/FE-8)."
    ::= { erxLineModule 14 }

erxTunnelService  OBJECT-IDENTITY
    STATUS      current
    DESCRIPTION
        "The vendor type ID for an ERX L2TP LNS and GRE Tunnel Service line
        module (Product Code: TUNNEL-SERVICE)."
    ::= { erxLineModule 15 }

erxHssi  OBJECT-IDENTITY
    STATUS      current
    DESCRIPTION
        "The vendor type ID for an ERX 3 port High Speed Serial Interface (HSSI)
        line module (Product Code: HSSI-3F)."
    ::= { erxLineModule 16 }

erxVts  OBJECT-IDENTITY
    STATUS      current
    DESCRIPTION
        "The vendor type ID for an ERX Virtual Tunnelling Server (VTS) line
        module (Product Code: ERX-IPSEC-MOD)."
    ::= { erxLineModule 17 }

erxCt3P12  OBJECT-IDENTITY
    STATUS      current
    DESCRIPTION
        "The vendor type ID for an ERX 12 port channelized T3 line module
        (Product Code: CT3-12-F0)."
    ::= { erxLineModule 18 }

erxV35  OBJECT-IDENTITY
    STATUS      current
    DESCRIPTION
        "The vendor type ID for an ERX X.21/V.35 server line module (Product
        Code: ERX-X21-V35-MOD)."
    ::= { erxLineModule 19 }

erxUt3E3Ocx  OBJECT-IDENTITY
    STATUS      current
    DESCRIPTION
        "The vendor type ID for an ERX OC12, quad OC3 or 12 port T3/E3 server
        line module (Product Code: ERX-UT3E3OCX-MOD)."
    ::= { erxLineModule 20 }

--
-- Module class - Line Card I/O Adapter
--
erxLineIoAdapter  OBJECT-IDENTITY
    STATUS      current
    DESCRIPTION
        "The vendor type ID for an ERX I/O adapter for a line module."
    ::= { usdErxEntPhysicalType 8 }

erxCt1Ioa  OBJECT-IDENTITY
    STATUS      current
    DESCRIPTION
        "The vendor type ID for an ERX 24 port channelized T1/J1 I/O adapter
        (Product Code: CT1-FULL-I/O)."
    ::= { erxLineIoAdapter 1 }

erxCe1Ioa  OBJECT-IDENTITY
    STATUS      current
    DESCRIPTION
        "The vendor type ID for an ERX 20 port channelized E1 I/O adapter
        (Product Code: CE1-FULL-I/O)."
    ::= { erxLineIoAdapter 2 }

erxCe1TIoa  OBJECT-IDENTITY
    STATUS      current
    DESCRIPTION
        "The vendor type ID for an ERX 20 port channelized E1 Telco I/O adapter
        (Product Code: CE1-FULL-I/OT)."
    ::= { erxLineIoAdapter 3 }

erxCt3Ioa  OBJECT-IDENTITY
    STATUS      current
    DESCRIPTION
        "The vendor type ID for an ERX 3 port channelized T3/E3 I/O adapter
        (Product Code: CT3/T3-3_I/O)."
    ::= { erxLineIoAdapter 4 }

erxE3Ioa  OBJECT-IDENTITY
    STATUS      current
    DESCRIPTION
        "The vendor type ID for an ERX 3 port E3 I/O adapter (Product Code:
        E3-3_I/O)."
    ::= { erxLineIoAdapter 5 }

erxOc3Mm2Ioa  OBJECT-IDENTITY
    STATUS      current
    DESCRIPTION
        "The vendor type ID for an ERX dual port OC3/STM1 multi-mode I/O adapter
        (Product Code: OC3-2M_I/O)."
    ::= { erxLineIoAdapter 6 }

erxOc3Sm2Ioa  OBJECT-IDENTITY
    STATUS      current
    DESCRIPTION
        "The vendor type ID for an ERX dual port OC3/STM1 single-mode I/O
        adapter (Product Code: OC3-2S_I/O)."
    ::= { erxLineIoAdapter 7 }

erxOc3Mm4Ioa  OBJECT-IDENTITY
    STATUS      current
    DESCRIPTION
        "The vendor type ID for an ERX 4 port OC3/STM1 multi-mode I/O adapter
        (Product Code: OC3-4MM_I/O)."
    ::= { erxLineIoAdapter 8 }

erxOc3SmIr4Ioa  OBJECT-IDENTITY
    STATUS      current
    DESCRIPTION
        "The vendor type ID for an ERX 4 port OC3/STM single-mode intermediate-
        reach I/O adapter (Product Code: OC3-4SM_I/O)."
    ::= { erxLineIoAdapter 9 }

erxOc3SmLr4Ioa  OBJECT-IDENTITY
    STATUS      current
    DESCRIPTION
        "The vendor type ID for an ERX 4 port OC3/STM1 single-mode long-reach
        I/O adapter (Product Code: OC3-4LH-I/O)."
    ::= { erxLineIoAdapter 10 }

erxCOc3Mm4Ioa  OBJECT-IDENTITY
    STATUS      current
    DESCRIPTION
        "The vendor type ID for an ERX 4 port channelized OC3/STM multi-mode I/O
        adapter (Product Code: COC3F0-MM-I/O)."
    ::= { erxLineIoAdapter 11 }

erxCOc3SmIr4Ioa  OBJECT-IDENTITY
    STATUS      current
    DESCRIPTION
        "The vendor type ID for an ERX 4 port channelized OC3/STM1 single-mode
        intermediate-reach I/O adapter (Product Code: COC3F0-SM-I/O)."
    ::= { erxLineIoAdapter 12 }

erxCOc3SmLr4Ioa  OBJECT-IDENTITY
    STATUS      current
    DESCRIPTION
        "The vendor type ID for an ERX 4 port channelized OC3/STM1 single-mode
        long-reach I/O adapter (Product Code: ERX-COC3-4LH-IOA)."
    ::= { erxLineIoAdapter 13 }

erxOc12Mm1Ioa  OBJECT-IDENTITY
    STATUS      current
    DESCRIPTION
        "The vendor type ID for an ERX single port OC12/STM4 multi-mode I/O
        adapter (Product Code: OC12-MM_I/O)."
    ::= { erxLineIoAdapter 14 }

erxOc12SmIr1Ioa  OBJECT-IDENTITY
    STATUS      current
    DESCRIPTION
        "The vendor type ID for an ERX single port OC12/STM4 single-mode
        intermediate-reach I/O adapter (Product Code: OC12-SM_I/O)."
    ::= { erxLineIoAdapter 15 }

erxOc12SmLr1Ioa OBJECT-IDENTITY
    STATUS      current
    DESCRIPTION
        "The vendor type ID for an ERX single port OC12/STM4 single-mode
        long-reach I/O adapter (Product Code: OC12-LH-I/O)."
    ::= { erxLineIoAdapter 16 }

erxCOc12Mm1Ioa  OBJECT-IDENTITY
    STATUS      current
    DESCRIPTION
        "The vendor type ID for an ERX single port channelized OC12/STM4
        multi-mode I/O adapter (Product Code: COC12F0-MM-I/O)."
    ::= { erxLineIoAdapter 17 }

erxCOc12SmIr1Ioa  OBJECT-IDENTITY
    STATUS      current
    DESCRIPTION
        "The vendor type ID for an ERX single port channelized OC12/STM4
        single-mode intermediate-reach I/O adapter (Product Code:
        COC12F0-SM-I/O)."
    ::= { erxLineIoAdapter 18 }

erxCOc12SmLr1Ioa  OBJECT-IDENTITY
    STATUS      current
    DESCRIPTION
        "The vendor type ID for an ERX single port channelized OC12/STM4
        single-mode long-reach I/O adapter (Product Code: ERX-COC12-LH-IOA)."
    ::= { erxLineIoAdapter 19 }

erxFe2Ioa  OBJECT-IDENTITY
    STATUS      current
    DESCRIPTION
        "The vendor type ID for an ERX dual port 10/100 Fast Ethernet I/O
        adapter (Product Code: 10/100_FE-2_I/O)."
    ::= { erxLineIoAdapter 20 }

erxFe8Ioa  OBJECT-IDENTITY
    STATUS      current
    DESCRIPTION
        "The vendor type ID for an ERX 8 port 10/100 Fast Ethernet I/O
        adapter (Product Code: FE-8_I/O)."
    ::= { erxLineIoAdapter 21 }

erxGeMm1Ioa  OBJECT-IDENTITY
    STATUS      current
    DESCRIPTION
        "The vendor type ID for an ERX single port Gigabit Ethernet multi-mode
        I/O adapter (Product Code: GE_M_I/O)."
    ::= { erxLineIoAdapter 22 }

erxGeSm1Ioa  OBJECT-IDENTITY
    STATUS      current
    DESCRIPTION
        "The vendor type ID for an ERX single port Gigabit Ethernet single-mode
        I/O adapter (Product Code: GE_S_I/O)."
    ::= { erxLineIoAdapter 23 }

erxHssiIoa  OBJECT-IDENTITY
    STATUS      current
    DESCRIPTION
        "The vendor type ID for an ERX 3 port High Speed Serial Interface (HSSI)
        I/O adapter (Product Code: HSSI-3-I/O)."
    ::= { erxLineIoAdapter 24 }

erxCt3P12Ioa  OBJECT-IDENTITY
    STATUS      current
    DESCRIPTION
        "The vendor type ID for an ERX 12 port channelized T3 I/O adapter
        (Product Code: T312-F0-F3-I/O)."
    ::= { erxLineIoAdapter 25 }

erxV35Ioa  OBJECT-IDENTITY
    STATUS      current
    DESCRIPTION
        "The vendor type ID for an ERX X.21/V.35 I/O adapter (Product Code:
        ERX-X21-V35-IOA)."
    ::= { erxLineIoAdapter 26 }

erxGeSfpIoa  OBJECT-IDENTITY
    STATUS      current
    DESCRIPTION
        "The vendor type ID for an ERX single port Gigabit Ethernet SFP I/O
        adapter (Product Code: ERX-GIGESFP-IOA)."
    ::= { erxLineIoAdapter 27 }

erxE3P12Ioa  OBJECT-IDENTITY
    STATUS      current
    DESCRIPTION
        "The vendor type ID for an ERX 12-port E3 I/O adapter (Product Code:
        E3-12-F3-I/O)."
    ::= { erxLineIoAdapter 28 }

erxCOc12Mm2Ioa  OBJECT-IDENTITY
    STATUS      current
    DESCRIPTION
        "The vendor type ID for an ERX dual port OC12/STM4 channelized
        multi-mode I/O adapter (Product Code: ERX-COC12-MA-IOA)."
    ::= { erxLineIoAdapter 30 }

erxCOc12SmIr2Ioa  OBJECT-IDENTITY
    STATUS      current
    DESCRIPTION
        "The vendor type ID for an ERX dual port OC12/STM4 channelized
        single-mode intermediate-reach I/O adapter (Product Code:
        ERX-COC12-SA-IOA)."
    ::= { erxLineIoAdapter 31 }

erxCOc12SmLr2Ioa  OBJECT-IDENTITY
    STATUS      current
    DESCRIPTION
        "The vendor type ID for an ERX dual port OC12/STM4 channelized
        single-mode long-reach I/O adapter (Product Code: ERX-COC12-LA-IOA)."
    ::= { erxLineIoAdapter 32 }

erxOc12Mm2ApsIoa  OBJECT-IDENTITY
    STATUS      current
    DESCRIPTION
        "The vendor type ID for an ERX dual port OC12/STM4 multi-mode with APS
        I/O adapter (Product Code: ERX-OC12MM-A-IOA)."
    ::= { erxLineIoAdapter 33 }

erxOc12SmIr2ApsIoa  OBJECT-IDENTITY
    STATUS      current
    DESCRIPTION
        "The vendor type ID for an ERX dual port OC12/STM4 single-mode
        intermediate-reach with APS I/O adapter (Product Code:
        ERX-OC12SM-A-IOA)."
    ::= { erxLineIoAdapter 34 }

erxOc12SmLr2ApsIoa  OBJECT-IDENTITY
    STATUS      current
    DESCRIPTION
        "The vendor type ID for an ERX dual port OC12/STM4 single-mode
        long-reach with APS I/O adapter (Product Code: ERX-OC12LH-A-IOA)."
    ::= { erxLineIoAdapter 35 }

erxT1E1RMidSpareIoa  OBJECT-IDENTITY
    STATUS      current
    DESCRIPTION
        "The vendor type ID for an ERX T1/E1 redundant midplane spare I/O
        adapter (Product Code: PNL-RDMD-T1/E1)."
    ::= { erxLineIoAdapter 42 }

erxT3E3RMidSpareIoa  OBJECT-IDENTITY
    STATUS      current
    DESCRIPTION
        "The vendor type ID for an ERX T3/E3 redundant midplane spare I/O
        adapter (Product Code: PNL-RDMD-T3/E3)."
    ::= { erxLineIoAdapter 43 }

erxCt3RMidSpareIoa  OBJECT-IDENTITY
    STATUS      current
    DESCRIPTION
        "The vendor type ID for an ERX 12 port channelized T3 redundant midplane
        spare I/O adapter (Product Code: ERX-12PT3E3-PNL)."
    ::= { erxLineIoAdapter 44 }

erxOcxRMidSpareIoa  OBJECT-IDENTITY
    STATUS      current
    DESCRIPTION
        "The vendor type ID for an ERX OC3/OC12 redundant midplane spare I/O
        adapter (Product Code: PNL-RDMD-OCX)."
    ::= { erxLineIoAdapter 45 }

erxCOcxRMidSpareIoa  OBJECT-IDENTITY
    STATUS      current
    DESCRIPTION
        "The vendor type ID for an ERX OC3/OC12 channelized redundant midplane
        spare I/O adapter (Product Code: ERX-COCXPNL-IOA)."
    ::= { erxLineIoAdapter 46 }

END
