-- 
-- Copyright 1999 by Fore Systems, Inc. 
-- Converted to SMIv2 rfc 2578,2579,2580 - STD 58
--

-- This FORE proprietary MIB defines all parameters relevant  to the Frame 
-- Relay/ATM interworking function. It is based on the FRF.8 interworking
-- agreement. 


Fore-frf8-MIB DEFINITIONS ::= BEGIN
 
       IMPORTS
                 Counter32,
		 Integer32,
                 TimeTicks,
		 OBJECT-TYPE,
		 MODULE-IDENTITY,
                 NOTIFICATION-TYPE       FROM SNMPv2-SMI
                 RowStatus               FROM SNMPv2-TC
                 frameInternetworking,
                 atmSwitch,
                 AtmAddress              FROM Fore-Common-MIB
		 InterfaceIndex          FROM IF-MIB;

foreFrf8Module  MODULE-IDENTITY
     LAST-UPDATED    "9705011044-0400"
     ORGANIZATION    "FORE"
     CONTACT-INFO    "
             Postal: FORE Systems Inc.
                     1000 FORE Drive
                     Warrendale, PA 15086-7502
             Tel:    +1 724 742 6900
             Email:  nm_mibs@fore.com
             Web:    http://www.fore.com"
     DESCRIPTION
             "This MIB module defines FR/ATM interworking 
              tables. It gives means to create/remove a FR/ATM 
              interworking connection and provides several 
              statistics at connection level."
       ::= { frameInternetworking 2 }

------------------------------------------------------------------------
 --
 -- this table support the creation of a Frame Relay/ATM interworking
 -- connection.
 -- The frf8ConnTable supports the association of the Frame Relay
 -- connection with the internal ATM fabric connection.
 --
 -- To create a frame relay connection, the manager will request the
 -- agent to create a new row in this table, indexing it by dlci and
 -- serviceId and setting frf8ConnRowStatus to createAndWait.
 
 -- In response to this operation the agent will do the following
 -- (after checking the validity of the ifIndex and dlci values and
 -- making sure that a connection with these parameters does not yet
 -- exist):
 --  o  create a new entry in this table
 --  o  create an entry in frCircuitTable defined  in rfc1315.mib
 --  o  create an entry in frPVCEndptTable defined in rfc1604.mib
 --  o  create an entry in frextCircuitTable of fore-frs.mib
 --  o  define  the appropriate atm service identifier, vpi and vci
 --     for the internal (between the netmod and the switching
 --     fabric) ATM part of the interworked connection, and populate
 --     them in the appropriate objects of this entry.
 --
 -- After the mentioned entries in different tables have been created, the
 -- manager will populate other objects, in proprietary tables which
 -- are applicable to this connection (profile indexes, fabric vpi/vci,
 --  etc.) which will complete the Frame Relay/ATM connection
 -- definition. After that, changing frf8ConnRowStatus to active will
 -- cause the information  to be passed to  the netmod,
 -- so that the connection can be created in the netmod database.
 -- The connection will become operational after the setting of  AdminStatus
 -- to active.
 --

frf8ConnTable       OBJECT-TYPE
  SYNTAX                   SEQUENCE OF Frf8ConnEntry
  MAX-ACCESS                   not-accessible
  STATUS                   current
  DESCRIPTION
    "Table of cross connections between the frame relay and ATM Fabric
     connections"
  ::= { foreFrf8Module 1 }

frf8ConnEntry      OBJECT-TYPE
  SYNTAX                   Frf8ConnEntry
  MAX-ACCESS                   not-accessible
  STATUS                   current
  DESCRIPTION
    "Entry in the frame relay/atm netmod crossconnect table"
  INDEX   { frf8ConnFrServiceIfIndex, frf8ConnDlci }
  ::= { frf8ConnTable 1 }

Frf8ConnEntry ::= SEQUENCE {
                frf8ConnFrServiceIfIndex    
                        InterfaceIndex,
                frf8ConnDlci                
                        Integer32,
                frf8ConnFabServiceIfIndex      
                        InterfaceIndex,
                frf8ConnFabVpi              
                        Integer32,
                frf8ConnFabVci              
                        Integer32,
                frf8ConnRowStatus          
                        RowStatus,
                frf8ConnProfileFrf8Index
                        Integer32,
                frf8ConnProfileEpdPpdIndex
                        Integer32,
                frf8ConnAtmAddrType
                        INTEGER,        
                frf8ConnAtmAddress
                        AtmAddress,
                frf8ConnAtmSubAddrType
                        INTEGER,
                frf8ConnAtmSubAddress
                        AtmAddress,
                frf8ConnFrAddrType
                        INTEGER,               
                frf8ConnFrAddress
                        AtmAddress,
                frf8ConnAdminStatus
                        INTEGER,
                frf8ConnOperStatus
                        INTEGER,
                frf8ConnCreationTime
                        TimeTicks,
                frf8ConnTimeChange
                        TimeTicks,
                frf8ConnPVCAlarmReason
                        INTEGER,
                frf8ConnAtmToFrPDUDiscards  
                        Counter32,
                frf8ConnFrToAtmPDUDiscards    
                        Counter32,
                frf8ConnAtmToFrUnkProts           
                        Counter32,
                frf8ConnFrToAtmUnkProts          
                        Counter32,
                frf8ConnAtmToFrArpNakDiscards    
                        Counter32
                }

  
frf8ConnFrServiceIfIndex    OBJECT-TYPE
               SYNTAX    InterfaceIndex
               MAX-ACCESS    read-only
               STATUS    current
               DESCRIPTION
               "Interface index of the Frame Relay service this 
               connection exists on"
               ::= { frf8ConnEntry 1}

frf8ConnDlci    OBJECT-TYPE
               SYNTAX    Integer32
               MAX-ACCESS    read-only
               STATUS    current
               DESCRIPTION
               "DLCI of this connection on the frame relay service"
               ::= { frf8ConnEntry 2 }

 
frf8ConnFabServiceIfIndex    OBJECT-TYPE
               SYNTAX    InterfaceIndex 
               MAX-ACCESS    read-only
               STATUS    current
               DESCRIPTION
               "This is the IfIndex  associated with the fabric pseudo atm 
               service this connection is mapped to by the agent when this 
               Frame Relay connection is created. This IfIndex  can be converted to
               a BNP notation value through the ifIndexMapTable of the
               fore-switch MIB. That BNP value can be used to establish a
               connection accross the switching fabric by means of the
               FORE-switch MIB"
               ::= { frf8ConnEntry 3 }

frf8ConnFabVpi    OBJECT-TYPE
               SYNTAX    Integer32
               MAX-ACCESS    read-only
               STATUS    current
               DESCRIPTION
               "This is the fabric VPI(equivalent to ivpi) of the ATM 
               connection this frame relay/ATM connection is mapped to by the
               agent when this row is created. This VPI will be used to 
               establish a connection accross the switching fabric by means
               of the FORE-switch MIB"
               ::= { frf8ConnEntry 4 }

frf8ConnFabVci    OBJECT-TYPE
               SYNTAX    Integer32
               MAX-ACCESS    read-only
               STATUS    current
               DESCRIPTION
               "This is the fabric VCI (equivalent to ivci)of the ATM 
               connection this frame relay connection is mapped to by the 
               agent when this row is created. This VCI will be used to 
               establish a connection accross the switching fabric by means
               of the FORE-switch MIB"
               ::= { frf8ConnEntry 5 }


frf8ConnRowStatus    OBJECT-TYPE 
               SYNTAX    RowStatus
               MAX-ACCESS    read-create
               STATUS    current
               DESCRIPTION
               "This object is used for dynamic creation of 
               entries in this table and all frame relay 
               connection level tables. This object is also
               used to delete existing connection rows."
               ::= { frf8ConnEntry 6 }

               
frf8ConnProfileFrf8Index    OBJECT-TYPE
               SYNTAX    Integer32                 
               MAX-ACCESS    read-create
               STATUS    current
               DESCRIPTION
               "the profileFrf8Index, in the fore-profile.mib " 
               ::= { frf8ConnEntry 7 }

frf8ConnProfileEpdPpdIndex    OBJECT-TYPE
               SYNTAX    Integer32                 
               MAX-ACCESS    read-create
               STATUS    current
               DESCRIPTION
               "The index of the EpdPpd Controller profile which contains: 
                1 ) Enable/disable the EPD for CLP=0 cells for a specific 
                connection;
	            2 ) Enable/disable the EPD for CLP=1 cells for a specific 
                connection;
	            3 ) Enable/disable the PPD for CLP=1 cells for a specific
                connection. " 
               ::= { frf8ConnEntry 8 }

frf8ConnAtmAddrType    OBJECT-TYPE
               SYNTAX    INTEGER {
                         null(1),
                         e164(2),
                         nsap(3)
                         }
               MAX-ACCESS    read-create
               STATUS    current
               DESCRIPTION
               "Defines the address format of the ATM 
               Service User end point" 
               ::= { frf8ConnEntry 9 }

frf8ConnAtmAddress    OBJECT-TYPE
               SYNTAX    AtmAddress
               MAX-ACCESS    read-create
               STATUS    current
               DESCRIPTION
               "The destination ATM address to which this Virtual 
               Circuit is connected."
               ::= { frf8ConnEntry 10 }



frf8ConnAtmSubAddrType    OBJECT-TYPE
               SYNTAX     INTEGER{
                          null(1),
                          e164(2),
                          nsap(3)
                          }
               MAX-ACCESS    read-create
               STATUS    current
               DESCRIPTION
               "Defines the sub-address format of the ATM
               Service User end point " 
                ::= { frf8ConnEntry 11 }


frf8ConnAtmSubAddress     OBJECT-TYPE
               SYNTAX  AtmAddress
               MAX-ACCESS  read-create
               STATUS  current
               DESCRIPTION
               "The destination ATM subaddress to which this Virtual
               Circuit is connected."
               ::= { frf8ConnEntry 12 }

                                                                                  
frf8ConnFrAddrType    OBJECT-TYPE
               SYNTAX    INTEGER{
                         null(1),
                         e164(2)
                         }
               MAX-ACCESS    read-create
               STATUS    current
               DESCRIPTION
               "Defines the frame relay address format of the Frame
               Relay Service User end point" 
               ::= { frf8ConnEntry 13}


frf8ConnFrAddress    OBJECT-TYPE
               SYNTAX    AtmAddress
               MAX-ACCESS    read-create
               STATUS    current
               DESCRIPTION
               "The address to which the Frame Relay DLCI is
               connected."
               ::= { frf8ConnEntry 14}


frf8ConnAdminStatus    OBJECT-TYPE
               SYNTAX    INTEGER {
                         up       (1),
                         down     (2),
                         testing  (3)
                         }
               MAX-ACCESS    read-create
               STATUS    current
               DESCRIPTION
               "Indicates whether the particular virtual  circuit 
               is operational. "
               DEFVAL { down }
               ::= {frf8ConnEntry 15 }


frf8ConnOperStatus        OBJECT-TYPE
               SYNTAX    INTEGER {
                         up(1),
                         down(2)
                        }
               MAX-ACCESS    read-only
               STATUS    current
               DESCRIPTION
               " The current operational status of the interworking 
               connection"
               ::= {frf8ConnEntry 16 }

frf8ConnCreationTime    OBJECT-TYPE
               SYNTAX    TimeTicks
               MAX-ACCESS    read-only
               STATUS    current
               DESCRIPTION
               "The value of sysUpTime when the  virtual circuit was created"
               ::= {frf8ConnEntry 17 }


frf8ConnTimeChange  OBJECT-TYPE
               SYNTAX    TimeTicks
               MAX-ACCESS    read-only
               STATUS    current
               DESCRIPTION
               "The value of sysUpTime (MIB II) when last there was a change 
               in the virtual circuit state "
               ::= {frf8ConnEntry 18 }

frf8ConnPVCAlarmReason     OBJECT-TYPE
               SYNTAX    INTEGER{
                         nodefect   (1),
                         frAlarmed  (2),
                         frClear    (3),
                         aisAlarmed (4),
                         aisClear   (5),
                         rdiAlarmed (6),
                         rdiClear   (7)
                        }                      
               MAX-ACCESS    read-only
               STATUS    current
               DESCRIPTION
               "Defines the reason why the PVC entered/exited  the alarmed
               condition.Defines if the SAC (service affect Condition) is 
               caused/cleared by the Frame Relay network(frAlarmed/frClear),
               or by the ATM network (aisAlarmed/aisClear,rdiAlarmed/aisClear).
               The nodefect means no current SAC in either network. This
               object will be part of the frf8PVCAlarmTRAP."                              
               ::={frf8ConnEntry  19 }


frf8ConnAtmToFrPDUDiscards   OBJECT-TYPE
               SYNTAX    Counter32
               MAX-ACCESS    read-only
               STATUS    current
               DESCRIPTION
               "The number of  PDU's coming from the ATM network
               to the FR network that are discarded by the interworking
               function"  
               ::= {frf8ConnEntry  20 }

frf8ConnFrToAtmPDUDiscards    OBJECT-TYPE
               SYNTAX    Counter32
               MAX-ACCESS    read-only
               STATUS    current
               DESCRIPTION
               "The number of  PDU's coming from the FR network to the ATM 
               network that are discarded by the interworking function "
               ::= {frf8ConnEntry  21}

frf8ConnAtmToFrUnkProts    OBJECT-TYPE
               SYNTAX    Counter32
               MAX-ACCESS    read-only
               STATUS    current
               DESCRIPTION
               "The number of PDU's received with an unknown protocol type 
               by the interworking function from the ATM network"
               ::= {frf8ConnEntry  22 }

frf8ConnFrToAtmUnkProts    OBJECT-TYPE
               SYNTAX    Counter32
               MAX-ACCESS    read-only
               STATUS    current
               DESCRIPTION
               "The number of  PDU's received with an unknown protocol type 
               by the interworking function from the Frame Relay network"
               ::= {frf8ConnEntry  23 }

                
frf8ConnAtmToFrArpNakDiscards  OBJECT-TYPE
               SYNTAX    Counter32
               MAX-ACCESS    read-only
               STATUS    current
               DESCRIPTION
               "The number of AAL-5 ARP NAK PDU's that are discarded 
               by the interworking function on this ATM VCC.If the
               iwf, interworking function receives an ATM ARP with 
               opcode 10 (NAK), the ARP packet is discarde, since 
               FR ARP does not support that opcode. "
               ::= {frf8ConnEntry  24 }

                        

---------------------------------------------------------------
--
--      This table provides information on a per-Connection
--      and Protocol Type basis
--      This table includes statistics and state information 
--      regarding the protocols registered on a particular
--      Virtual Circuit. 
--

frf8ProtTable   OBJECT-TYPE
                SYNTAX  SEQUENCE OF Frf8ProtEntry
                MAX-ACCESS  not-accessible
                STATUS  current
                DESCRIPTION
                "The Objects associated with the protocols
                registered on a specific Virtual Circuit."
                REFERENCE   "Frame Relay Forum Implementation Agreement 8."
                ::= { foreFrf8Module  2}

frf8ProtEntry       OBJECT-TYPE
                SYNTAX  Frf8ProtEntry
                MAX-ACCESS  not-accessible
                STATUS  current
                DESCRIPTION
                "The statistics entry for the  Protocol Table."
                INDEX { frf8ProtServiceIfIndex, frf8ProtDlci , frf8ProtProtocol}
                ::= { frf8ProtTable 1 }

Frf8ProtEntry ::= SEQUENCE {
                frf8ProtServiceIfIndex
                         InterfaceIndex,
                frf8ProtDlci
                         Integer32,
                frf8ProtProtocol
                        INTEGER,
                frf8ProtAtmToFrPdus
                        Counter32,
                frf8ProtAtmToFrOctets
                        Counter32,
                frf8ProtFrToAtmPdus
                        Counter32,
                frf8ProtFrToAtmOctets
                        Counter32
                 }

         
frf8ProtServiceIfIndex    OBJECT-TYPE
                SYNTAX      InterfaceIndex
                MAX-ACCESS  read-only
                STATUS      current
                DESCRIPTION
                "Interface index of the Frame Relay service this connection 
                exists on. "
                ::= { frf8ProtEntry 1 }


frf8ProtDlci    OBJECT-TYPE
                SYNTAX    Integer32
                MAX-ACCESS    read-only
                STATUS    current
                DESCRIPTION
                "DLCI of this connection on the frame relay service."
                ::= { frf8ProtEntry 2 }

   
frf8ProtProtocol    OBJECT-TYPE
                SYNTAX   INTEGER {
                         prot8023withfcs(1),
                         prot8023(2),
                         prot8025withfcs(3),
                         prot8025(4),
                         ip(5),
                         arp(6),
                         ipx (7),
                         sna (8),
                         fddi (9),
                         fddiwithfcs (10),
                         x25x75 (11),
                         prot8026 (12),
                         routediso (13)
                         }
                MAX-ACCESS    read-only
                STATUS    current
                DESCRIPTION
                "The protocol(s) registered over this Virtual Circuit."
                ::= { frf8ProtEntry 3 }

frf8ProtAtmToFrPdus    OBJECT-TYPE
                SYNTAX    Counter32
                MAX-ACCESS    read-only
                STATUS    current
                DESCRIPTION
                "The number of AAL-5 PDU's received by FRF.8 of this
                 protocol type from ATM to FR network direction."
                ::= { frf8ProtEntry 4 }

frf8ProtAtmToFrOctets    OBJECT-TYPE
                SYNTAX    Counter32
                MAX-ACCESS    read-only
                STATUS    current
                DESCRIPTION
               "The number of AAL-5 octets received by FRF.8 of this
                protocol type  from ATM to FR network direction."
                ::= { frf8ProtEntry 5 }


frf8ProtFrToAtmPdus    OBJECT-TYPE
                SYNTAX    Counter32
                MAX-ACCESS    read-only
                STATUS    current
                DESCRIPTION
                "The number of AAL-5 PDU's transmitted by FRF.8 of
                 this protocol type from FR to ATM network direction."
                ::= { frf8ProtEntry 6 }


frf8ProtFrToAtmOctets    OBJECT-TYPE
                SYNTAX    Counter32
                MAX-ACCESS    read-only
                STATUS    current
                DESCRIPTION
               "The number of AAL-5 octets transmitted by FRF.8 of
                this protocol type from FR to ATM network direction."
                ::= { frf8ProtEntry 7 }


---------------------------------------------------------------
--
-- OAM F5 for FR/ATM 
--
-- This table provides information on a per VCC basis
-- keeping the statistics of the OAM F5 end-to-end
-- cells

                   
frf8OamF5Table    OBJECT-TYPE
               SYNTAX    SEQUENCE OF Frf8OamF5Entry
               MAX-ACCESS    not-accessible
               STATUS    current
               DESCRIPTION
               "The OAM statistics table on a VCC basis"
               ::= { foreFrf8Module 3 }


frf8OamF5Entry    OBJECT-TYPE
               SYNTAX    Frf8OamF5Entry
               MAX-ACCESS    not-accessible
               STATUS    current
               DESCRIPTION
               "An Entry in the OAM F5 statistics table on a VCC basis"
               INDEX {frf8OamF5ServiceIfIndex , frf8OamF5VcDlci }
               ::={ frf8OamF5Table 1}


Frf8OamF5Entry ::= SEQUENCE {
               frf8OamF5ServiceIfIndex
                    InterfaceIndex,
               frf8OamF5VcDlci
                    Integer32,
               frf8OamF5AISRxCounter 
                    Counter32,
               frf8OamF5AISTxCounter
                    Counter32,
               frf8OamF5RDIRxCounter
                    Counter32,
               frf8OamF5RDITxCounter
                    Counter32
                }


frf8OamF5ServiceIfIndex    OBJECT-TYPE
               SYNTAX        InterfaceIndex
               MAX-ACCESS    read-only
               STATUS        current
               DESCRIPTION
               "Interface index of the Frame Relay service this 
               connection exists on. "
               ::={frf8OamF5Entry 1 }
                                        

frf8OamF5VcDlci    OBJECT-TYPE
               SYNTAX    Integer32
               MAX-ACCESS    read-only
               STATUS    current
               DESCRIPTION
               "DLCI of this connection on the frame relay service."
               ::= { frf8OamF5Entry 2 }



frf8OamF5AISRxCounter    OBJECT-TYPE
               SYNTAX    Counter32
               MAX-ACCESS    read-only
               STATUS    current
               DESCRIPTION
               "Number of VC-AIS cells received since the PVC was
               brought into service."
               ::={frf8OamF5Entry 3}

         
frf8OamF5AISTxCounter    OBJECT-TYPE
               SYNTAX    Counter32
               MAX-ACCESS    read-only
               STATUS    current
               DESCRIPTION
               "Number of VC-AIS cells transmited since the PVC was
               brought into service."
               ::={frf8OamF5Entry 4}

frf8OamF5RDIRxCounter    OBJECT-TYPE
               SYNTAX    Counter32
               MAX-ACCESS    read-only
               STATUS    current
               DESCRIPTION
               "Number of VC-RDI cells received since the PVC was
               brought into service."
               ::={frf8OamF5Entry 5}


frf8OamF5RDITxCounter    OBJECT-TYPE
               SYNTAX    Counter32
               MAX-ACCESS    read-only
               STATUS    current
               DESCRIPTION
               "Number of VC-RDI cells transmited since the PVC was
               brought into service."
               ::={frf8OamF5Entry 6}


 
------------------------------------------------------------------------
-- Note: this TRAP definition is commented due to the restriction that
--       ForeThought TRAPs have to be defined and compiled in the 
--       fore-switch.mib.However this definition  is still kept in this
--       file for being considered pertinent to the FR/ATM interworking 
--       functional information.
------------------------------------------------------------------------

-- Definition of the TRAP generated by the FR/ATM interworking function

-- This TRAP will provide the support to manage defects  that might 
-- occur in either the Frame Relay network or the ATM network,irrespective
-- of the PVC operation status.
--
-- This trap is now obsolete, use the standard trap frDLCIStatusChange 
-- defined in rfc1315.

frf8PVCStatus  NOTIFICATION-TYPE
               OBJECTS  {frf8ConnFrServiceIfIndex,frf8ConnDlci,
                           frf8ConnOperStatus,frf8ConnPVCAlarmReason }
               STATUS      current
               DESCRIPTION
               "This trap indicates when an interworking 
               PVC has experienced an alarmed condition, 
               either on the ATM network side or Frame Relay side.
               Also it is generated when the PVC alarmed
               condition is cleared. It carries the opera
               tional status of the PVC by the frf8ConnOperStatus
               as well as the reason why  exiting,entering or
               changing  the alarmed state frf8ConnPVCAlarmReason.
               If the interworking PVC changes its status by a
               AdminStatus command (active/inactive/testing), 
               causing the frf8ConnOperStatus to change (up/down),
               this trap will be generated with frf8ConnPVCAlarmReason 
               set to 'nodefect'. This TRAP will give the support
               to manage defects  that might occur in either Frame
               Relay network or ATM network, even if the PVC Operational 
               Status is already down."
               ::= { atmSwitch  0 2000 }

END
