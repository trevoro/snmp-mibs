CAJUN-PORT-COPY-EXTENSIONS DEFINITIONS ::= BEGIN

-- Referencing the parent branch.

IMPORTS
            MODULE-IDENTITY, OBJECT-TYPE FROM SNMPv2-SMI
            portCopyEntry FROM SMON-MIB
            lsg FROM AVAYAGEN-MIB;

-- All representations of MAC addresses in this MIB Module
-- use, as a textual convention (i.e. this convention does
-- not affect their encoding), the data type:

   MacAddress ::= OCTET STRING (SIZE (6))

-- a 6 octet address in the "canonical" order
-- defined by IEEE 802.1a, i.e., as if it were transmitted
-- least significant bit first, even though 802.5 (in
-- contrast to other n802.x protocols) requires MAC
-- addresses to be transmitted most significant bit first.
--

cjnPortCopyExtensions MODULE-IDENTITY
        LAST-UPDATED "0105290000Z"
        ORGANIZATION "Avaya's Concord Technology Center (CTC)"
        CONTACT-INFO
                "Julie Flannery -- jflannery@avayactc.com"
        DESCRIPTION
                "Cajun Private Port Copy Extensions MIB.  
                 Extension to RFC2613 Port Copy definitions."
        ::= { lsg 5 }

cjnPortCopyTable  OBJECT-TYPE
    SYNTAX      SEQUENCE OF CjnPortCopyEntry
    MAX-ACCESS  not-accessible
    STATUS      current
    DESCRIPTION
        " The Cajun Port Copy Table provides and extension to the 
         portCopyTable defined in RFC2613 to allow the user to configure
         additional port copy parameters. The cjnPortCopyTable is
         always the same size as the portCopyTable. Rows are created
         with default values in this table when rows are created in 
         the port copy table.  Conversely rows are deleted when the 
         row is removed from the portCopyTable."
   ::= { cjnPortCopyExtensions 1 }

   cjnPortCopyEntry  OBJECT-TYPE
    SYNTAX      CjnPortCopyEntry
    MAX-ACCESS  not-accessible
    STATUS      current
    DESCRIPTION
        "Describes a particular port copy entry. Corresponds to the entry in the portCopyTable."
   AUGMENTS { portCopyEntry }
   ::= { cjnPortCopyTable 1 }

   CjnPortCopyEntry ::= SEQUENCE {
        cjnPortCopyChannel
                INTEGER,
        cjnPortCopySamplingMode
                INTEGER,
        cjnPortCopyMaxPacketsPerSecond
                INTEGER,
        cjnPortCopySAFilter
                MacAddress,
        cjnPortCopyDAFilter
                MacAddress,
        cjnPortCopyFilter 
                INTEGER
        }

   cjnPortCopyChannel OBJECT-TYPE
    SYNTAX       INTEGER
    MAX-ACCESS   read-only
    STATUS       current
    DESCRIPTION
        "The monitor channel that is being used to monitor the traffic. There are 
        maximum of four channels available to monitor the traffic."
    ::= { cjnPortCopyEntry 1 }

   cjnPortCopySamplingMode OBJECT-TYPE
    SYNTAX       INTEGER {
        disabled(0),
        always(1),
        periodic(2)
    }
    MAX-ACCESS   read-write
    STATUS       current
    DESCRIPTION
        "This object selects how often the copy port will receive traffic samples.  
         
         If this object has the value 'disabled(0)', then traffic samples to the mirror port
         are shut off.
         If this object has the value 'always(1)', then all samples are sent.
         If this object has the value 'periodic(2)', then samples are sent at intervals."
   DEFVAL { always }
   ::= { cjnPortCopyEntry 2 }

   cjnPortCopyMaxPacketsPerSecond OBJECT-TYPE
    SYNTAX       INTEGER
    MAX-ACCESS   read-write
    STATUS       current
    DESCRIPTION
        "Sets the maximum number of packets per second that are served by the mirror port."
    ::= { cjnPortCopyEntry 3 }

   cjnPortCopySAFilter OBJECT-TYPE
    SYNTAX       MacAddress
    MAX-ACCESS   read-write
    STATUS       current
    DESCRIPTION
        "Traffic on the source port with this source MAC address will 
		  be monitored if SA filtering is configured.  All other traffic will
		  not be monitored."
    ::= { cjnPortCopyEntry 4 }

   cjnPortCopyDAFilter OBJECT-TYPE
    SYNTAX       MacAddress
    MAX-ACCESS   read-write
    STATUS       current
    DESCRIPTION
        "Traffic on the source port with this destination MAC address 
		  will be monitored if DA filtering is configured. All other traffic will
		  not be monitored."
    ::= { cjnPortCopyEntry 5 }

   cjnPortCopyFilter OBJECT-TYPE
    SYNTAX       INTEGER {
        disabled(0),
        sa(1),
        da(2)
    }
    MAX-ACCESS   read-write
    STATUS       current
    DESCRIPTION
        "Specifies that a traffic filter is to be used.
         If this object has the value 'disabled(0)', then no filter will be used.
         If this object has the value 'sa(1)', then the SA specified in cjnPortCopySAFilter
         will be monitored in both directions.
         If this object has the value 'da(2)', then the DA specified in cjnPortCopyDAFilter
         will be monitored in both directions. "

    ::= { cjnPortCopyEntry 6 }
 
  
END
