-- Do not edit this file.
-- It is generated automatically by mib-expand
-- from ascend.mib.in and *.mibdef.
--			Ascend Enterprise MIB
--
--			Ascend Communications, Inc
--			1275 Harbor Bay Pkwy
--			Alameda, CA 94502
--			+1 510 769 6001
--			info@ascend.com
--
--		Copyright (c) 1999 Lucent Technologies, Inc.
--		All rights reserved.
--
-- CVS ID:      $Id: ascend.mib.in,v 29.1.2.21 2000/02/10 03:13:25 asarma Exp $
--
-- 01 Dec 93:	Initial release
-- 18 Aug 94:	Added status and console groups
-- 22 Mar 95:	Added systemStatus, event, callStatus, and sessionStatus groups
-- 13 Apr 95:	Shortened some object names to under 32 chars.
-- 15 Aug 95:	rc  Added eventDisconnectReason, eventConnectProgress, and
--		    baudRateChanged(6).
-- 28 Aug 95:	rc  Added serviceModem(37) to hostStatusDataSvc.
-- 07 Sep 95:	rc  Added sysMibVersionNum, sysMibMinorRevNum, and radiusGroup.
-- 07 Nov 95:	rc  Added pppCloseNoNcpsOpened(47), pppCloseUnknownMpBundle(48),
--		    pppCloseMpAddChanFail(49).
-- 16 Nov 95:	rc  Added prIPXNCPOpened(80).
-- 18 Dec 95:	rc  Added virtualConnect(16), prModemOutdialCallUp(50),
--		    tsClosedVirtualConnect(29), tsVirtualConnectDestroyed(30).
-- 29 Jan 95:	Added additional enums to eventDisconnectReason
-- 12 Jan 96:   les Added eventCallCharge.
-- 18 Jan 96:   les Added eventCalledPartyID, eventCallingPartyID,
--		    eventInOctets, eventOutOctets.
-- 14 Feb 96:   rc  Added requestByRadiusClient(150).
-- 20 Apr 96:   kh  Added radAuthHostIPAddress, radAuthCurrentServerFlag,
--		    radAcctHostIPAddress and radAcctCurrentServerFlag.
-- 23 Apr 96:   kh  changed radius CurrentServerFlag's to read-write in
--                  order to allow user to select current server.
-- 13 Jun 96:   cag Added sysConfigTftpCmd options 3, 4 & 5.
-- 14 Jun 96:   cag Added product subcategory information to define MAX/PIPE
--                  models returned by sysObjectID.
-- 18 Sep 96:   pj  Added mCastGroup
-- 27 Sep 96:	cag Added sysConfigTftpCmd option 6: load code.
-- 15 Oct 96:   kh  Added prBACPOpening and prBACPOpened
-- 17 Oct 96:   rm  Added callStatusType in the callStatusTable
-- 17 Oct 96:   rm  Added the lanModemGroup
-- 25 Oct 96:   rm  Added eventCurrentActiveCalls, ....
-- 29 Oct 96:   rm  Added eventMultiLinkID
-- 06 Nov 96:   rm  Added busyLanModem, busyLanModemTable sub-group, suspectTrapState
-- 05 Dec 96:   rm  Added call[Current|Total][Analog|Digital|FrameRelay][Outgoing|Incoming]
-- 26 Dec 96:   rm  Added sysAbsoluteCurrentTime read-write variable
-- 07 Jan 97:   rm  Added slotMdmItemStatus and slotMdmItemStatusChar
-- 15 Jan 97:   rm  Added sessionActiveTable
-- 16 Jan 97:   rm  Defined new slotType values for TNT
-- 22 Jan 97:   rm  Added sysReset
-- 28 Jan 97:   rm  Added callActiveTable
-- 07 Feb 97:   rm  Added sysLoadName
-- 22 Mar 97:   jh  Added sysAuthPreference
-- 19 Feb 97:   dl  Added mppActiveStatsTable
-- 20 Feb 97:   rm  Added mechanism to kill sessions
-- 21 Feb 97:   rm  Commented ranges as SunNet Manager does not like it!
-- 11 Mar 97:   rm  separated the eventGroup, callStatusGroup, sessionStatusGroup,
--                  lanModemGroup, radiusGroup, mCastGroup, slotMdmTable
--                  Refer to event.mib, call.mib, session.mib lmodem.mib,
--                           radius.mib mcast.mib
-- 02 Apr 97:   lcs Refer to firewall.mib,
--			     add firewallGroup ::= { ascend 16 }
-- 16 Apr 97:	dba Added additional enums to eventDisconnectReason
-- 23 Apr 97:   rm  Added sysProm subgroup
-- 07 Jul 97:   rm  Added wanDialoutPkt subgroup
-- 01 Aug 97:   rm  Added powerSupply subgroup
-- 04 Aug 97:   rm  Added multiShelf subgroup
-- 28 Aug 97:   rm  Created advancedAgent
-- 02 Oct 97:   kn  EOI-12553: Back out the changes made on 8/28/97 and
--                  rename wanInfo to adavancedAgent 
-- 21 Jan 98:   rm  Added sysLastRestartReason
-- 02 Feb 98:   kn  Added sysOID for DSLPipe products
-- 09 Feb 98:   kn  Added sysOID for dslTnt and Pipeline85
-- 11 Feb 98:   kn  Added sysOID for Pipeline50LS56
-- 07 Apr 98:   kc  Added additional enums to eventDisconnectReason
-- 21 Apr 98:   hcl Added 2 enums to sysConfigTftpCmd and created
--                  sysConfigTftpParameter
-- 26 May 98    aq  Added flashGroup
-- 28 May 98    aq  Added asgGroup per kn request.
-- 12 Jun 98    aq  Added configuration per kn request.
-- 16 Jun 98    mb  Added Call Logging Group 
-- 18 Jun 98    kn  Added atmpGroup
-- 19 Jun 98    mb  Added new sysOID for pipe130 series.
-- 19 Jun 98    aq  Added srvcMgmt group for dnis management.
-- 04 Sep 98    djl Added sysConfigChange.
-- 04 Nov 98    se  Added sysOID for DMT pipes
-- 06 Nov 98    mk  Transfer slot, item and slotIf MIBs to chassis.mib
-- 20 Nov 98    kn  Added resourceGroup.
-- 20 Jan 98	kv  Added sysConfigFlash
-- 11 Mar 99	ane Added sysOID for AQ products and AQ300
-- 12 Mar 99	mk  Corrected spell err in the sysConfigRadiusCmd.
-- 18 Mar 99	rvg Added sysOID for spipe155 and spipe95.
-- 26 Mar 99	ryu Added sysOID for ST100 platform: dslmax20 and terminator.
-- 10 Jun 99    aks Added fatalLogTable.
-- 25 Jul 99	ama Changed sysAbsoluteStartupTime, sysAbsoluteCurrentTime,
--                  sysSecsSinceStartup SYNTAX to TimeTicks
-- 11 Aug 99    mk  Added voipGrp
-- 01 Sep 99    sb  Changed sysAbsoluteStartupTime, sysAbsoluteCurrentTime,
--                  sysSecsSinceStartup SYNTAX from Timeticks back to INTEGER.
--                  Reference: EOI 39513.
-- 15 Sep 99   ilya Added mgGroup
-- 25 Oct 99    mk  Added a Note to the consoleSerurity DESCRIPTION field.
-- 04 Nov 99     of Added LIM sparing configuration MIB
-- 04 Nov 99     of Added sparing ( LIM and TM ) status MIB
-- 05 Nov 99	 kn Added three new bits (18-20) to sysSPROMOptions2.  Those
--		    new network management features are available in TAOS
--		    Release 8.0 or later.
-- 26 Jan 00     vl Added sysOID for the cvMax 100.


ASCEND-MIB DEFINITIONS ::= BEGIN

    IMPORTS
	enterprises,
	TimeTicks
	    FROM RFC1155-SMI
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING
				
	--
	-- The Ascend Communications enterprise OID.
	--

    ascend		OBJECT IDENTIFIER ::= {	 enterprises 529 }


	--
	-- Groups in the Ascend Enterprise mib
	--

    products		OBJECT IDENTIFIER ::= { ascend 1 }

    slots		OBJECT IDENTIFIER ::= { ascend 2 }

    hostTypes		OBJECT IDENTIFIER ::= { ascend 3 }

    advancedAgent 	OBJECT IDENTIFIER ::= { ascend 4 }

    lanTypes		OBJECT IDENTIFIER ::= { ascend 5 }

    doGroup		OBJECT IDENTIFIER ::= { ascend 6 }

    hostStatus		OBJECT IDENTIFIER ::= { ascend 7 }

    console		OBJECT IDENTIFIER ::= { ascend 8 }

    systemStatusGroup	OBJECT IDENTIFIER ::= { ascend 9 }

    eventGroup		OBJECT IDENTIFIER ::= { ascend 10 }

    callStatusGroup	OBJECT IDENTIFIER ::= { ascend 11 }

    sessionStatusGroup	OBJECT IDENTIFIER ::= { ascend 12 }

    radiusGroup		OBJECT IDENTIFIER ::= { ascend 13 }

    mCastGroup          OBJECT IDENTIFIER ::= { ascend 14 }

    lanModemGroup       OBJECT IDENTIFIER ::= { ascend 15 }

    firewallGroup	OBJECT IDENTIFIER ::= { ascend 16 }

    wanDialoutPkt	OBJECT IDENTIFIER ::= { ascend 17 }

    powerSupply		OBJECT IDENTIFIER ::= { ascend 18 }

    multiShelf		OBJECT IDENTIFIER ::= { ascend 19 }

    miscGroup		OBJECT IDENTIFIER ::= { ascend 20 }

    asgGroup            OBJECT IDENTIFIER ::= { ascend 21 }

    flashGroup          OBJECT IDENTIFIER ::= { ascend 22 }

    configuration       OBJECT IDENTIFIER ::= { ascend 23 }

    atmpGroup		OBJECT IDENTIFIER ::= { ascend 24 }

    callLoggingGroup    OBJECT IDENTIFIER ::= { ascend 25 }

    srvcMgmtGroup       OBJECT IDENTIFIER ::= { ascend 26 }

    resourcesGroup	OBJECT IDENTIFIER ::= { ascend 27 }

    voipGroup		OBJECT IDENTIFIER ::= { ascend 28 }

    mgGroup		OBJECT IDENTIFIER ::= { ascend 29 }

    sparingGroup        OBJECT IDENTIFIER ::= { ascend 30 }

    cltmGroup		OBJECT IDENTIFIER ::= { ascend 31 }

	-- Ascend products.
	--
	-- Each Ascend product family is Assigned an Object Identifier.
	-- This is the identifier stored in the MIB-II system group
	-- item sysObjectID to identify the product to a network manager.
	-- If product family specific items need to be defined they should
	-- be defined in the appropriate product family subtree

    multiband		OBJECT IDENTIFIER ::= { products 1 }

    max			OBJECT IDENTIFIER ::= { products 2 }

    pipeline		OBJECT IDENTIFIER ::= { products 3 }

    max-tnt		OBJECT IDENTIFIER ::= { products 4 }

    dslTnt		OBJECT IDENTIFIER ::= { products 5 }

    aqueduct		OBJECT IDENTIFIER ::= { products 6 }

    stinger-10		OBJECT IDENTIFIER ::= { products 7 }

    apx-8000		OBJECT IDENTIFIER ::= { products 8 }


	-- Ascend max product family.
	--
	-- There are several products in the MAX family.  This is the
	-- identifier that enumerates the individual products.

    max200		OBJECT IDENTIFIER ::= { max 1 }

    max1800		OBJECT IDENTIFIER ::= { max 2 }

    max2000		OBJECT IDENTIFIER ::= { max 3 }

    max4000		OBJECT IDENTIFIER ::= { max 4 }

    max4002		OBJECT IDENTIFIER ::= { max 5 }

    max4004		OBJECT IDENTIFIER ::= { max 6 }

    max6000		OBJECT IDENTIFIER ::= { max 7 }

    max800		OBJECT IDENTIFIER ::= { max 8 }

    max3000		OBJECT IDENTIFIER ::= { max 9 }

    dslmax20		OBJECT IDENTIFIER ::= { max 10 }

    terminator		OBJECT IDENTIFIER ::= { max 11 }

    cvmax100		OBJECT IDENTIFIER ::= { max 12 }

	-- Ascend pipeline product family.
	--
	-- There are several products in the PIPELINE family.  This is
	-- the identifier that enumerates the individual products.

    pipe15		OBJECT IDENTIFIER ::= { pipeline 1 }

    pipe25		OBJECT IDENTIFIER ::= { pipeline 2 }

    pipe25Px            OBJECT IDENTIFIER ::= { pipeline 3 }

    pipe25Fx            OBJECT IDENTIFIER ::= { pipeline 4 }

    pipe50		OBJECT IDENTIFIER ::= { pipeline 5 }

    pipe75		OBJECT IDENTIFIER ::= { pipeline 6 }

    pipe130T1           OBJECT IDENTIFIER ::= { pipeline 7 }

    pipe400		OBJECT IDENTIFIER ::= { pipeline 8 }

    pipe220		OBJECT IDENTIFIER ::= { pipeline 9 }

	-- sysOID for DSLPipe CPE products in the PIPELINE family
    
    dslPipeAcap  	OBJECT IDENTIFIER ::= { pipeline 10 }

    dslPipeS		OBJECT IDENTIFIER ::= { pipeline 11 }

    dslPipe2S		OBJECT IDENTIFIER ::= { pipeline 12 }

    dslPipeAdmt         OBJECT IDENTIFIER ::= { pipeline 21 }

    dslPipeAlctlDmt     OBJECT IDENTIFIER ::= { pipeline 22 }

	-- sysOID for DSLPipe COE products in the PIPELINE family
    
    dslPipeAdslCoeC	OBJECT IDENTIFIER ::= { pipeline 13 }

    dslPipeSdslCoe	OBJECT IDENTIFIER ::= { pipeline 14 }

    dslPipeSdslCoe2S	OBJECT IDENTIFIER ::= { pipeline 15 }

    dslPipeAdslCoeD     OBJECT IDENTIFIER ::= { pipeline 20 }

	-- sysOID for more Pipeline Products 
    
    pipe85		OBJECT IDENTIFIER ::= { pipeline 16 }

    pipe50LS56		OBJECT IDENTIFIER ::= { pipeline 17 }

        -- sysOID for more Pipeline Products
        -- Pipeline 130 with V35 interface
    pipe130V35          OBJECT IDENTIFIER ::= { pipeline 18 }
        -- Pipeline 130 with Switched 56 interface
    pipe130N56          OBJECT IDENTIFIER ::= { pipeline 19 }


        -- Super Pipeline 95 
    spipe95		OBJECT IDENTIFIER ::= { pipeline 23 }

        -- Super Pipeline 155 with T1 interface
    spipe155T1		OBJECT IDENTIFIER ::= { pipeline 24 }

        -- SDSL Cell Pipeline 
    dslPipe50SdslCell   OBJECT IDENTIFIER ::= { pipeline 25 }

        -- SDSL High Speed Pipeline
    dslPipeSdslHs       OBJECT IDENTIFIER ::= { pipeline 26 }

	-- Ascend max-tnt product family.
	--
	-- There is only a single product in the MAX-TNT family.
        -- As more products are added future qualification will
        -- be performed.

	-- Ascend aqueduct product family.
	--
	-- There is currently only one product in the AQUEDUCT family.
	-- This is the identifier that enumerates the individual products.

    aq300		OBJECT IDENTIFIER ::= { aqueduct 1 }

	-- Ascend stinger-10 product family.
	--
	-- There is only a single product in the stinger-10 family.
        -- As more products are added future qualification will
        -- be performed.

	-- Ascend Host types
	--
	-- Each Ascend host type is assigned an object ID.  These ids are
	-- the root of MIB subtrees containing host specific information.
	-- These subtrees, when required, are described in separate files.

    hostTypeAny		OBJECT IDENTIFIER ::= { hostTypes 1 }
    hostTypeDual	OBJECT IDENTIFIER ::= { hostTypes 2 }
    hostTypeQuad	OBJECT IDENTIFIER ::= { hostTypes 3 }
    hostTypeAim2	OBJECT IDENTIFIER ::= { hostTypes 4 }
    hostTypeAim6	OBJECT IDENTIFIER ::= { hostTypes 5 }


	-- Ascend LAN types
	--
	-- Each Ascend LAN type is assigned an object ID.  These ids are
	-- the root of MIB subtrees containing LAN specific information.
	-- These subtrees, when required, are described in separate files.

    lanTypeAny		OBJECT IDENTIFIER ::= { lanTypes 1 }
    lanTypeEthernet	OBJECT IDENTIFIER ::= { lanTypes 2 }
    lanTypeEtherData	OBJECT IDENTIFIER ::= { lanTypes 3 }

	-- Ascend Do Group
	--
	-- This group implements the Ascend action commands.  The action
	-- is performed on the indicated slot/item.  To implement this
	-- the do commands are treated as a table indexed by slot and item.

    doTable		OBJECT-TYPE
	SYNTAX		SEQUENCE OF DoEntry
	ACCESS		not-accessible
	STATUS		mandatory
	DESCRIPTION	"A list of do entries."
	::= { doGroup 1 }

    doEntry		OBJECT-TYPE
	SYNTAX		DoEntry
	ACCESS		not-accessible
	STATUS		mandatory
	DESCRIPTION	"An entry containing all of the action (do) commands
			and the slot and item index."
	INDEX		{ doSlotIndex, doItemIndex }
	::= { doTable 1 }

    DoEntry ::=
	SEQUENCE {
	    doSlotIndex
		INTEGER,
	    doItemIndex
		INTEGER,
	    doDial
		INTEGER,
	    doHangUp
		INTEGER,
	    doAnswer
		INTEGER,
	    doExtendBW
		INTEGER,
	    doContractBW
		INTEGER,
	    doBegEndRemoteLB
		INTEGER,
	    doBegEndBERT
		INTEGER,
	    doResynchronize
		INTEGER
	}

    doSlotIndex		OBJECT-TYPE
	SYNTAX		INTEGER
	ACCESS		read-only
	STATUS		mandatory
	DESCRIPTION	"The index of the slot containing the item for which
			an action is desired.  The valid range is 1 through
			the value slotNumber."
	::= { doEntry 1 }

    doItemIndex		OBJECT-TYPE
	SYNTAX		INTEGER
	ACCESS		read-only
	STATUS		mandatory
	DESCRIPTION	"The item number on the indexed slot for which an
			action is desired.  The valid range is 1 through
			the value slotItems in the slotTable when indexed by
			a value equal to doSlotIndex."
	::= { doEntry 2 }

    doDial		OBJECT-TYPE
	SYNTAX		INTEGER {
			    valid( 1 ),
			    notValid( 2 )
			}
	ACCESS		read-write
	STATUS		mandatory
	DESCRIPTION	"When read returns valid if the indexed slot/item
			can dial a call.  Writing any value will cause
			a call to be placed when valid, otherwise the write
			is ignored."
	::= { doEntry 3 }

    doHangUp		OBJECT-TYPE
	SYNTAX		INTEGER {
			    valid( 1 ),
			    notValid( 2 )
			}
	ACCESS		read-write
	STATUS		mandatory
	DESCRIPTION	"When read returns valid if the indexed slot/item
			can terminate a call.  Writing any value will cause
			the call to be terminated when valid, otherwise the
			write is ignored."
	::= { doEntry 4 }

    doAnswer		OBJECT-TYPE
	SYNTAX		INTEGER {
			    valid( 1 ),
			    notValid( 2 )
			}
	ACCESS		read-write
	STATUS		mandatory
	DESCRIPTION	"When read returns valid if the indexed slot/item
			can answer a call.  Writing any value will cause
			the call to be answered when valid, otherwise the
			write is ignored."
	::= { doEntry 5 }

    doExtendBW	OBJECT-TYPE
	SYNTAX		INTEGER {
			    valid( 1 ),
			    notValid( 2 )
			}
	ACCESS		read-write
	STATUS		mandatory
	DESCRIPTION	"When read returns valid if the indexed slot/item
			can extend bandwidth.  Writing any value will cause
			bandwidth to be extended when valid, otherwise the
			write is ignored."
	::= { doEntry 6 }

    doContractBW	OBJECT-TYPE
	SYNTAX		INTEGER {
			    valid( 1 ),
			    notValid( 2 )
			}
	ACCESS		read-write
	STATUS		mandatory
	DESCRIPTION	"When read returns valid if the indexed slot/item
			can contract bandwidth.	 Writing any value will cause
			bandwidth to be contracted when valid, otherwise the
			write is ignored."
	::= { doEntry 7 }

    doBegEndRemoteLB	OBJECT-TYPE
	SYNTAX		INTEGER {
			    valid( 1 ),
			    notValid( 2 )
			}
	ACCESS		read-write
	STATUS		mandatory
	DESCRIPTION	"When read returns valid if the indexed slot/item
			can enter or exit remote loopback.  Writing any
			value will cause the current remote loopback state
			to be toggled when valid, otherwise the write is
			ignored."
	::= { doEntry 8 }

    doBegEndBERT	OBJECT-TYPE
	SYNTAX		INTEGER {
			    valid( 1 ),
			    notValid( 2 )
			}
	ACCESS		read-write
	STATUS		mandatory
	DESCRIPTION	"When read returns valid if the indexed slot/item
			can enter or exit BERT test mode.  Writing any
			value will cause the current BERT test state
			to be toggled when valid, otherwise the write is
			ignored."
	::= { doEntry 9 }

    doResynchronize	OBJECT-TYPE
	SYNTAX		INTEGER {
			    valid( 1 ),
			    notValid( 2 )
			}
	ACCESS		read-write
	STATUS		mandatory
	DESCRIPTION	"When read returns valid if the indexed slot/item
			can issue a resynchronize command.  Writing any
			value will cause a resynchronize command to be
			issued when valid, otherwise the write is
			ignored."
	::= { doEntry 10 }


	-- Ascend Status Group
	--
	-- This group displays the status of a session when indexed by
	-- slot and item.  No such item is returned if the slot/item
	-- does not reference something that identifies a session.

    hostStatusTable	OBJECT-TYPE
	SYNTAX		SEQUENCE OF HostStatusEntry
	ACCESS		not-accessible
	STATUS		mandatory
	DESCRIPTION	"A table of host port status entries.  A host port
			status entry potentialy exists for every slot/item.
			Host port status entries are only meaningful for
			slot/items that reference a host port.	When indexed
			by other slot/items NO SUCH NAME will be returned."
	::= { hostStatus 1 }

    hostStatusEntry	OBJECT-TYPE
	SYNTAX		HostStatusEntry
	ACCESS		not-accessible
	STATUS		mandatory
	DESCRIPTION	"An entry containing the host port status of the
			indexed slot/item."
	INDEX		{ hostStatusSlotIndex, hostStatusItemIndex }
	::= { hostStatusTable 1 }

    HostStatusEntry ::=
	SEQUENCE {
	    hostStatusSlotIndex
		INTEGER,
	    hostStatusItemIndex
		INTEGER,
	    hostStatusLocalName
		OCTET STRING,
	    hostStatusDialNum
		OCTET STRING,
	    hostStatusCallType
		INTEGER,
	    hostStatusCallMgm
		INTEGER,
	    hostStatusDataSvc
		INTEGER,
	    hostStatusCallState
		INTEGER,
	    hostStatusRemName
		OCTET STRING,
	    hostStatusChannels
		INTEGER,
	    hostStatusDuration
		INTEGER
	}

    hostStatusSlotIndex	OBJECT-TYPE
	SYNTAX		INTEGER
	ACCESS		read-only
	STATUS		mandatory
	DESCRIPTION	"A unique value for each slot. The slot identified
			by a particular value of this index is the same slot
			as identified by the same value of slotIndex."
	::= { hostStatusEntry 1 }


    hostStatusItemIndex	OBJECT-TYPE
	SYNTAX		INTEGER
	ACCESS		read-only
	STATUS		mandatory
	DESCRIPTION	"Index to each item defined for each slot. Since
			entries in this table are only valid for host ports
			an item number is a port number within the indexed
			slot."
	::= { hostStatusEntry 2 }

    hostStatusLocalName	OBJECT-TYPE
	SYNTAX		OCTET STRING
	ACCESS		read-only
	STATUS		mandatory
	DESCRIPTION	"The name from the current call profile of the indexed
			host slot and port."
	::= { hostStatusEntry 3 }

    hostStatusDialNum	OBJECT-TYPE
	SYNTAX		OCTET STRING
	ACCESS		read-only
	STATUS		mandatory
	DESCRIPTION	"The phone number from the current call profile of the
			indexed host slot and port."
	::= { hostStatusEntry 4 }

    hostStatusCallType	OBJECT-TYPE
	SYNTAX		INTEGER {
			    aim( 1 ),
			    bonding( 2 ),
			    one-channel( 3 ),
			    two-channel( 4 ),
			    ft1( 5 ),
			    ft1Aim( 6 ),
			    ft1BandO( 7 )
			}
	ACCESS		read-only
	STATUS		mandatory
	DESCRIPTION	"The type of call from the current call profile of the
			indexed host slot and port."
	::= { hostStatusEntry 5 }

    hostStatusCallMgm	OBJECT-TYPE
	SYNTAX		INTEGER {
			    none( 1 ),
			    manual( 2 ),
			    static( 3 ),
			    dynamic( 4 ),
			    delta( 5 ),
			    one-of-8( 6 ),
			    one-of-40( 7 ),
			    mode1( 8 ),
			    mode2( 9 ),
			    mode3( 10 ),
			    mode0( 11 )
			}
	ACCESS		read-only
	STATUS		mandatory
	DESCRIPTION	"The call management protocol from the current
			call profile for the indexed host slot and port.
			Call management is only meaningful for calls using
			an inverse multiplexing protocol."
	::= { hostStatusEntry 6 }

    hostStatusDataSvc	OBJECT-TYPE
	SYNTAX		INTEGER {
			    serviceVoice( 1 ),
			    service56KR( 2 ),
			    service56K( 3 ),
			    service64K( 4 ),
			    service384KR( 5 ),
			    service384K-H0( 6 ),
			    service1536K( 7 ),
			    service1536KR( 8 ),
			    service128K( 9 ),
			    service192K( 10 ),
			    service256K( 11 ),
			    service320K( 12 ),
			    service384K( 13 ),
			    service448K( 14 ),
			    service512K( 15 ),
			    service576K( 16 ),
			    service640K( 17 ),
			    service704K( 18 ),
			    service768K( 19 ),
			    service832K( 20 ),
			    service896K( 21 ),
			    service960K( 22 ),
			    service1024K( 23 ),
			    service1088K( 24 ),
			    service1152K( 25 ),
			    service1216K( 26 ),
			    service1280K( 27 ),
			    service1344K( 28 ),
			    service1408K( 29 ),
			    service1472K( 30 ),
			    service1600K( 31 ),
			    service1664K( 32 ),
			    service1728K( 33 ),
			    service1792K( 34 ),
			    service1856K( 35 ),
			    service1920K( 36 ),
			    serviceModem( 37 ),
			    serviceV110-24-56K( 38 ),
			    serviceV110-48-56K( 39 ),
			    serviceV110-96-56K( 40 ),
			    serviceV110-192-56K( 41 ),
			    serviceV110-384-56K( 42 ),
			    serviceV110-24-56KR( 43 ),
			    serviceV110-48-56KR( 44 ),
			    serviceV110-96-56KR( 45 ),
			    serviceV110-192-56KR( 46 ),
			    serviceV110-384-56KR( 47 ),
			    serviceV110-24-64K( 48 ),
			    serviceV110-48-64K( 49 ),
			    serviceV110-96-64K( 50 ),
			    serviceV110-192-64K( 51 ),
			    serviceV110-384-64K( 52 ),
			    serviceV110-24-64KR( 53 ),
			    serviceV110-48-64KR( 54 ),
			    serviceV110-96-64KR( 55 ),
			    serviceV110-192-64KR( 56 ),
			    serviceV110-384-64KR( 57 )
			}
	ACCESS		read-only
	STATUS		mandatory
	DESCRIPTION	"The type of service from the current call profile
			for the indexed host slot and port."
	::= { hostStatusEntry 7 }

    hostStatusCallState	OBJECT-TYPE
	SYNTAX		INTEGER {
			    other( 1 ),
			    answering( 2 ),
			    calling( 3 ),
			    clearing( 4 ),
			    localLoop( 5 ),
			    handshake( 6 ),
			    idle( 7 ),
			    online( 8 ),
			    loopMast( 9 ),
			    loopSlav( 10 ),
			    bertMast( 11 ),
			    bertSlav( 12 ),
			    remoteMg( 13 ),
			    ringing ( 14 ), 
			    setupAdd( 15 ), 
			    setupHnd( 16 ), 
			    setupRem( 17 )
			}
	ACCESS		read-only
	STATUS		mandatory
	DESCRIPTION	"Shows the current state of the current call for the 
			indexed host slot and port.  The returned value will
			indicates the same state displayed in a call status
			window for the port."
	::= { hostStatusEntry 8 }

    hostStatusRemName	OBJECT-TYPE
	SYNTAX		OCTET STRING
	ACCESS		read-only
	STATUS		mandatory
	DESCRIPTION	"The value displayed on the 4th line of the call
			status menu.  When the hostStatusCallType is aim( 1 ) 
			this value is the name of the host port on the far
			end of a connection, or the far-end system name if
			the host port has not been named.  An empty string
			is returned when there is no call active or when
			aim( 1 ) is not being used."
	::= { hostStatusEntry 9 }

    hostStatusChannels	OBJECT-TYPE
	SYNTAX		INTEGER
	ACCESS		read-only
	STATUS		mandatory
	DESCRIPTION	"The number of channels in use by the call as
			displayed on the third line of the call status
			menu for the indexed slot and port."
	::= { hostStatusEntry 10 }

    hostStatusDuration	OBJECT-TYPE
	SYNTAX		INTEGER
	ACCESS		read-only
	STATUS		mandatory
	DESCRIPTION	"The duration of the call associated with the
			indexed host slot and port, measured in seconds."
	::= { hostStatusEntry 11 }


	-- Ascend Console Group
	--
	-- This group maps the console interfaces to their SNMP interface
	-- number and points to the appropriate management MIB object
	-- for the console type.  Multiple consoles may exist, e.g
	-- a palmtop port is a console port.

    consoleNumber	OBJECT-TYPE
	SYNTAX		INTEGER
	ACCESS		read-only
	STATUS		mandatory
	DESCRIPTION	"The number of consoles supported by this device."
	::= { console 1 }

	-- The console table
	--
	-- This table contains consoleNumber entries describing each
	-- console port.

    consoleTable	OBJECT-TYPE
	SYNTAX		SEQUENCE OF ConsoleEntry
	ACCESS		not-accessible
	STATUS		mandatory
	DESCRIPTION	"A list of console entries."
	::= { console 2 }

    consoleEntry	OBJECT-TYPE
	SYNTAX		ConsoleEntry
	ACCESS		not-accessible
	STATUS		mandatory
	DESCRIPTION	"An entry containing objects that describe the
			indexed console port."
	INDEX		{ consoleIndex }
	::= { consoleTable 1 }

    ConsoleEntry ::=
	SEQUENCE {
	    consoleIndex
		INTEGER,
	    consoleIf
		INTEGER,
	    consoleType
		INTEGER,
	    consoleSecurity
		INTEGER,
	    consoleSpecific
		OBJECT IDENTIFIER
	}

    consoleIndex	OBJECT-TYPE
	SYNTAX		INTEGER
	ACCESS		read-only
	STATUS		mandatory
	DESCRIPTION	"A unique value for each console.  It's value ranges
			between 1 and the value consoleNumber.	This is the
			index into the console table to identify a
			particular console."
	::= { consoleEntry 1 }

    consoleIf		OBJECT-TYPE
	SYNTAX		INTEGER
	ACCESS		read-only
	STATUS		mandatory
	DESCRIPTION	"The interface number associated with the indexed
			console.  This number can be used to index into
			the interface (and other) tables to obtain detailed
			console status."
	::= { consoleEntry 2 }

    consoleType		OBJECT-TYPE
	SYNTAX		INTEGER {
			    other( 1 ),		-- none of the following
			    primary( 2 ),	-- Primary VT100 console
			    secondary( 3 ),	-- VT100 console in palmtop port
			    palmtop( 4 ),	-- palmtop console
			    inactive( 5 ),	-- inactive/unused session
			    remote( 6 )		-- active remote session
			}
	ACCESS		read-only
	STATUS		mandatory
	DESCRIPTION	"The type of console in the indexed entry.  When
			no console is plugged into a console port the
			value inactive(5) is returned.	The value remote(6)
			indicates a console initiated via remote management
			or TELNET session."
	::= { consoleEntry 3 }

    consoleSecurity	OBJECT-TYPE
	SYNTAX		INTEGER
	ACCESS		read-only
	STATUS		mandatory
	DESCRIPTION	"The security profile, in the range of 1 through
			the number of profiles supported by the unit, of
			the indexed console.  The default security profile
			is profile number 1.
			Note: This attribute is supported on non-TNT 
			      platforms only."
	::= { consoleEntry 4 }

    consoleSpecific	OBJECT-TYPE
	SYNTAX		OBJECT IDENTIFIER
	ACCESS		read-only
	STATUS		mandatory
	DESCRIPTION	"A reference to MIB definitions specific to the
			console port. Contains the object identifier { 0 0 }
			if there is no console specific information for the
			indexed console."
	::= { consoleEntry 5 }


	--
	-- Ascend System Status group
	--
	-- This group contains general information regarding the system
	-- as a whole.	This information provided by this group can be
	-- viewed as an extension of the system group under MIB-II.
	--

    sysAbsoluteStartupTime  OBJECT-TYPE
	SYNTAX		INTEGER
	ACCESS		read-only
	STATUS		mandatory
	DESCRIPTION	"The time system startup up in seconds since
			 January 1, 1990.  This value in concert with
			 'sysSecsSinceStartup' below can be used to
			 compute the current time in seconds since 1/1/90."
	::= { systemStatusGroup 1 }

    sysSecsSinceStartup OBJECT-TYPE
	SYNTAX		INTEGER
	ACCESS		read-only
	STATUS		mandatory
	DESCRIPTION	"The number of seconds since system startup."
	::= { systemStatusGroup 2 }

    sysMibVersionNum   OBJECT-TYPE
--	SYNTAX		INTEGER (1..'7fffffff'h)
	SYNTAX		INTEGER
	ACCESS		read-only
	STATUS		mandatory
	DESCRIPTION	"Version number of this private MIB. Versions
			 numbers start at 1 and increment by 1 for
			 every major revision.  Major revisions are
			 additions/deletions to this MIB."
	::= { systemStatusGroup 3 }

    sysMibMinorRevNum  OBJECT-TYPE
--	SYNTAX		INTEGER (1..'7fffffff'h)
	SYNTAX		INTEGER
	ACCESS		read-only
	STATUS		mandatory
	DESCRIPTION	"Value represents the minor revision number
			 of this MIB.  Minor revision numbers start
			 at 0 and increment by 1 for each revision.
			 Minor revisions are textual or comment changes."
	::= { systemStatusGroup 4 }


    sysConfigTftp OBJECT IDENTIFIER ::= { systemStatusGroup 5 }

    sysConfigTftpCmd OBJECT-TYPE
	SYNTAX	INTEGER {
		    save( 1 ),		-- save configuration
		    restore( 2 ),	-- restore configuration
		    saveAll( 3 ),	-- save ALL config options
		    saveMib( 4 ),	-- save config w/MIB numbers
		    saveAllMib( 5 ),	-- save ALL config w/MIB numbers
		    loadCode( 6 ),	-- load a code image
		    saveIncProf( 7 ),	-- save specified config
		    saveExcProf( 8 )	-- save All except specified config
		}
	ACCESS	read-write
	STATUS	mandatory
	DESCRIPTION
	   "This variable instructs the system to perform the specified
	    tftp operation.
	    Note: loadCode( 6 ) is not supported on TNT platform."
	::= { sysConfigTftp 1 }

    sysConfigTftpStatus OBJECT-TYPE
	SYNTAX	INTEGER {
		    ok( 1 ),			-- tftp operation succeeded
		    notFound( 2 ),		-- file not found
		    access( 3 ),		-- access violation
		    noSpace( 4 ),		-- no disk space to write file
		    badOp( 5 ),			-- bad tftp operation 
		    badTid( 6 ),		-- unknown transfer ID
		    exists( 7 ),		-- file already exists
		    noSuchUser( 8 ),		-- no such user
		    parameter( 9 ),		-- parameter error
		    busy( 10 ),			-- tftp server cannot handle request
		    noResources( 11 ),		-- no memory for request
		    timeout( 12 ),		-- timed out
		    unrecoverable( 13 ),	-- unrecoverable error
		    tooManyRetries( 14 ),	-- too many retries
		    createFile( 15 ),		-- create file
		    openFile( 16 ),		-- open file
		    inProgress( 17 )		-- get/put request in progress
		}
	ACCESS	read-only
	STATUS	mandatory
	DESCRIPTION
	   "This variable indicates the status of a save or restore operation
	    through tftp."
	::= { sysConfigTftp 2 }

    sysConfigTftpHostAddr OBJECT-TYPE
	SYNTAX	IpAddress
	ACCESS	read-write
	STATUS	mandatory
	DESCRIPTION
	   "This variable indicates the host address where the configuration 
	    file is saved to or restored from through tftp."
	::= { sysConfigTftp 3 }

    sysConfigTftpFilename OBJECT-TYPE
	SYNTAX	DisplayString
	ACCESS	read-write
	STATUS	mandatory
	DESCRIPTION
	   "This variable indicates the file name of the configuration file to 
	    save to or restore from a SNMP host through tftp."
	::= { sysConfigTftp 4 }

    sysConfigTftpPort OBJECT-TYPE
	SYNTAX	INTEGER
	ACCESS	read-write
	STATUS	mandatory
	DESCRIPTION
	   "This variable indicates the port # to use when starting a TSAVE
	    TRESTORE command.  Normally this would be port 69, but we need
	    to allow the Java Console to override this in case the Console
	    workstation has a TFTP server already running."
	::= { sysConfigTftp 5 }

    sysConfigTftpParameter OBJECT-TYPE
        SYNTAX  DisplayString
        ACCESS  read-write
        STATUS  mandatory
        DESCRIPTION
           "This variable indicates the list of profiles to be included or
            excluded during the save operation through tftp. The snmp agent
	    will modify the set string to an uppercase space-separated
	    new string and return the changed value.  This is to clarify
	    the case insensitive profile naming."
        ::= { sysConfigTftp 6 }

    sysConfigRadius OBJECT IDENTIFIER ::= { systemStatusGroup 6 }

    sysConfigRadiusCmd OBJECT-TYPE
	SYNTAX	INTEGER {
		    all( 1 ),		-- all configuration
		    routes( 2 ),	-- bridge/ip/ipx routes configuration
		    pools( 3 ),		-- ip address pool configuration
		    nailed( 4 ),	-- permanent and nailed configuration
		    termsrv( 5 ),	-- term server banners
                    source( 6 )         -- source auth configuration
		}
	ACCESS	read-write
	STATUS	mandatory
	DESCRIPTION
	   "This variable instructs the system to re-read its RADIUS 
	    configuration. This variable will return a general error if
	    RADIUS is not configured or if sysConfigRadiusStatus has a
	    value of processing(2)."
	::= { sysConfigRadius 1 }

    sysConfigRadiusStatus OBJECT-TYPE
	SYNTAX	INTEGER {
		    init( 1 ),		-- configuration has not started
		    processing( 2 ),	-- configuration is in progress
		    timeout( 3 ),	-- configuration request timed-out
		    error( 4 ),		-- configuration received other error
		    complete( 5 )	-- configuration complete sucessfully
		}
	ACCESS	read-only
	STATUS	mandatory
	DESCRIPTION
	   "This variable indicates the status of the last RADIUS configuration
	    retrieval. This includes the boot time retrieval."
	::= { sysConfigRadius 2 }

    sysAbsoluteCurrentTime  OBJECT-TYPE
	SYNTAX		INTEGER
	ACCESS		read-write
	STATUS		mandatory
	DESCRIPTION	"The current system time in seconds since
			 January 1, 1990. Changing this value may 
                         result in a change of sysAbsoluteStartupTime
                         and not of sysSecsSinceStartup. The following
                         relationship holds:
                         sysAbsoluteCurrentTime - sysAbsoluteStartupTime = sysSecsSinceStartup."
	::= { systemStatusGroup 7 }

    sysReset            OBJECT-TYPE
	SYNTAX		INTEGER {
                        no-op( 1 ),
                        reset( 2 ) 
                        }
	ACCESS		read-write
	STATUS		mandatory
	DESCRIPTION	"The reset takes effect after 1 minute."
	::= { systemStatusGroup 8 }

    sysLoadName         OBJECT-TYPE
	SYNTAX		DisplayString
	ACCESS		read-only
	STATUS		mandatory
	DESCRIPTION	"The name of the load which is currently running."
	::= { systemStatusGroup 9 }

    sysAuthPreference   OBJECT-TYPE
	SYNTAX		INTEGER {
                        no-op(1),
                        local-first(2),
                        remote-first(3),
                        remote-no(4)
                        }
	ACCESS		read-write
	STATUS		mandatory
	DESCRIPTION	
           "An incoming call can be authenticated using a local profile
	    or one from an authentication server such as RADIUS or TACACS.
	    local-first means authenticate from a local profile first,
	    and if that fails, try the authentication server.
	    remote-first means get a profile from the authentication
	    server and authenticate from that and if that fails,
	    try to authenticate from a local profile.
	    remote-no is the same as remote-first except if the external
	    authentication server NACKs the request, then the connection
	    will be denied, i.e. no search of the local profiles will be
	    made."
	::= { systemStatusGroup 10 }

--
--  system security PROM subgroup of systemStatusGroup
--
    sysSPROM	OBJECT IDENTIFIER ::= { systemStatusGroup 11 }

    sysSPROMSerialNumber   OBJECT-TYPE
	SYNTAX   	   INTEGER
	ACCESS		   read-only
	STATUS		   mandatory
	DESCRIPTION	
           "The serial number as stored in the security PROM.
            The same value is also returned as part of sysName."
	::= { sysSPROM 1 }

    sysSPROMOptions1       OBJECT-TYPE
	SYNTAX   	   INTEGER
	ACCESS		   read-only
	STATUS		   mandatory
	DESCRIPTION	
           "The various bit positions are:
           (2 ** 0)  - rs366Enabled
           (2 ** 1)  - dChannelEnabled
           (2 ** 2)  - autoDBAEnabled
           (2 ** 3)  - bondingEnabled
           (2 ** 4)  - aimEnabled
           (2 ** 5)  - v25bisEnabled
           (2 ** 6)  - x21Enabled
           (2 ** 7)  - switchedEnabled
           (2 ** 8)  - mrateEnabled
           (2 ** 9)  - pbxEnabled
           (2 ** 10) - pcbusEnabled
           (2 ** 11) - bridgingEnabled
           (2 ** 12) - pipeHxEnabled
           (2 ** 13) - frameRelayEnabled
           (2 ** 14) - maxLinkClientEnabled
           (2 ** 15) - dataCallEnabled
           (2 ** 16) - dualSlotT1Enabled
           (2 ** 17) - r2SignalingEnabled
           (2 ** 18) - domesticEnabled
           (2 ** 19) - modemTSDialoutEnabled
           (2 ** 20) - pipePxEnabled
           (2 ** 21) - firewallsEnabled
           (2 ** 22) - serialPortT1_CSU_Enabled
           (2 ** 23) - pipePotsEnabled
           (2 ** 24) - forceMultibandPlatformSimulationEnabled
           (2 ** 25) - k56SlotCardOnlyEnabled
           (2 ** 26) - networkManagementEnabled
           (2 ** 27) - advancedAgentEnabled (DEPRECATED)
           (2 ** 28) - phsSupportEnabled
           (2 ** 29) - selectoolsEnabled
           (2 ** 30) - routingProtocolsDisabled
           (2 ** 31) - tunnelProtocolsDisabled (DEPRECATED)."
	::= { sysSPROM 2 }

    sysSPROMOptions2       OBJECT-TYPE
	SYNTAX   	   INTEGER
	ACCESS		   read-only
	STATUS		   mandatory
	DESCRIPTION	
           "The various bit positions are:
           (2 ** 0)  - atmpEnabled
           (2 ** 1)  - l2tpEnabled
           (2 ** 2)  - pptpEnabled
           (2 ** 3)  - l2fEnabled
           (2 ** 4)  - ipinipEnabled
           (2 ** 5)  - vRouterEnabled
           (2 ** 6)  - aodiEnabled
           (2 ** 7)  - maddModemEnabled
           (2 ** 8)  - madd96DevicesEnabled
           (2 ** 9)  - maddHdlcEnabled
           (2 ** 10) - v110Enabled
           (2 ** 11) - sdtnEnabled
           (2 ** 12) - restrictDSLTermEnabled
           (2 ** 13) - megamaxEnabled
           (2 ** 14) - maxtapEnabled
           (2 ** 15) - phs21Enabled
           (2 ** 16) - atmSvcEnabled
           (2 ** 17) - frVcEnabled
	   (2 ** 18) - networkManagementVoipEnabled
	   (2 ** 19) - networkManagementPlusEnabled
	   (2 ** 20) - networkManagementPlusVoipEnabled"
	::= { sysSPROM 3 }

    sysSPROMCountries1     OBJECT-TYPE
	SYNTAX   	   INTEGER
	ACCESS		   read-only
	STATUS		   mandatory
	DESCRIPTION	
           "The various bit positions are:
           (2 ** 0)  -    FranceIsdn
           (2 ** 1)  -    UKIsdn
           (2 ** 2)  -    BelgiumIsdn
           (2 ** 3)  -    JapanIsdn
           (2 ** 4)  -    AustraliaIsdn
           (2 ** 5)  -    GermanIsdn
           (2 ** 6)  -    UKDpnss
           (2 ** 7)  -    SwissIsdn
           (2 ** 8)  -    GloBandIsdn
           "
	::= { sysSPROM 4 }

    resetStat	OBJECT IDENTIFIER ::= { systemStatusGroup 12 }

    resetStatEther	   OBJECT-TYPE
	SYNTAX   	   INTEGER
	ACCESS		   read-write
	STATUS		   mandatory
	DESCRIPTION	   "Clear Ethernet statistics."
	::= { resetStat 1 }

    resetStatWAN	   OBJECT-TYPE
	SYNTAX		   INTEGER
	ACCESS		   read-write
	STATUS		   mandatory
	DESCRIPTION	   "Clear specified interface's WAN statistics."
	::= { resetStat 2 }

    resetStatAll	   OBJECT-TYPE
	SYNTAX		   INTEGER
	ACCESS		   read-write
	STATUS		   mandatory
	DESCRIPTION	   "Clear all WAN statistics."
	::= { resetStat 3 }

    sysLastRestartReason OBJECT-TYPE
	SYNTAX		INTEGER {
			    fatalAssert(1),
			    fatalPoolsNoBuffer(2),
			    fatalProfileBad(3),
			    fatalSwitchTypeBad(4),
			    fatalLif(5),
			    fatalLcdError(6),
			    fatalIsacTimeout(7),
			    fatalSCCSpuriousInterrupt(8), -- 8 is a.k.a. PROCESSOR EXCEPTION!!
			    fatalExecInvalidSwitch(9),
			    fatalExecNoMailDesc(10),
			    fatalExecNoMailPoll(11),
			    fatalExecNoTask(12),
			    fatalExecNoTimer(13),
			    fataExecNoTimerPool(14),
			    fatalExecWaitInCtricalSection(15),
			    fatalDspDead(16),
			    fatalDspProtocolError(17),
			    fatalDspInternalError(18),
			    fatalDspLossOfSync(19),
			    fatalDspUnUsed(20),
			    fatalDDDDead(21),
			    fatalDDDProtocolError(22),
			    fatalX25Buffers(23),
			    fatalX25Init(24),
			    fatalX25Stack(25),
			    fatalZeroMemoryAlloc(27),
			    fatalNegativeMemoryAllocate(28),
			    fatalTaskLoop(29),
			    fatalMemcpyTooLarge(30),
			    fatalMemcpyNoMagic(31),
			    fatalMemcpyWrongMagic(32),
			    fatalMemcoyBadStart(33),
			    fatalIDECTimeout(34),
			    fatalExecRestricted(35),
			    fatalStackOverflow(36),
			    fatalDRAMCard(37),
			    fatalMbufPanic(38),
			    fatalNoPriority2Task(39),
			    fatalProtectionFault(40),
			    fatalClipping(41), -- clipping (may indicate memory leak)
			    fatalReadyHangFault(42),
			    fatalExcessPostCompl(43),
			    fatalWriteProtect(44),
			    fatalPureVirtual(45), -- C++ pure virtual call attempted
			    fatalATMSVC(46),
			    fatalFRSVC(47),
			    fatalInterruptCode(48),
			    fatalLinkedListCorruption(55),
			    fatalBadPower(60), -- NMI related fatal logs
			    fatalWatchdogTimeout(61), -- NMI related fatal logs
			    fatalUnexplainedNMI(62), -- NMI related fatal logs
			    fatalPrimarySelected(98),
			    fatalOperatorReset(99),
			    fatalSystemUp(100),
			    warningBufferInUse(101),
			    warningBufferWrongPool(102),
			    warningBufferWrongHeap(103),
			    warningBufferNotMemAlloc(104),
			    warningBufferBadMemAlloc(105),
			    warningBufferBogusPool(106),
			    warningBufferBogusHeap(107),
			    warningBufferNegativeMemalloc(108),
			    warningBufferZeroMemalloc(109),
			    warningBufferBoundary(110),
			    warningBufferTooBig(111),
			    warningBufferNull(112),
			    warningBufferSegmentCountZero(113),
			    warningBufferTrailerMagic(114),
			    warningBufferTrailerBuffer(115),
			    warningBufferTrailerLength(116),
			    warningBufferTrailerUserMagic(117),
			    warningBufferWriteAfterFree(118),
			    warningBufferNotInUse(119),
			    warningBufferMemcpyMagic(120),
			    warningBufferMemcpyMagicNext(121),
			    warningBufferNoExtraDRAM(129), -- V2P75 only: no xtra DRAM detected, or memtest on xtra DRAM  failed
			    errprPPPAsuncBufferInUse(130), -- PPP errors
			    warningIpcpIpLookup(131), -- PPP errors
			    warningBadChunk(135), -- wandata (& wansess) errors
			    warningUnexpectedIF(136), -- wandata (& wansess) errors
			    warningNoTimers(140), -- timer errors
			    warningLCDAllocFailure(145), -- getBuff failure in lcd
			    warningLCDNonSense(146), -- From lcdlogin.c; which should not be in this state
			    warningMemcpyTooLarge(150), -- memcpy was called with too large a length
			    warningMemcpyNoMagic(151), -- memcpy was called with too large a length
			    warningMemcpyWrongMagic(152), -- memcpy was called with too large a length
			    warningMemcpyBadStart(153), -- memcpy was called with too large a length
			    warningWANBufferLeak(154), -- wandrv errors
			    warningTermSrvState(160), -- termsrv debugging
			    warningTermSrvSemaphore(161), -- termsrv debugging
			    warningTelnetFreeDrv(165), -- telnet debugging
			    warningSTACTimeout(170), -- stacdrv/compress debugging
			    warningSTACDataNotOwned(171), -- stacdrv/compress debugging
			    warningExecFailure(175), -- misc debugging
			    warningExecNoMailbox(177), -- misc debugging sendMsg called w/NULL mbox
			    warningExecNoResources(178), -- misc debugging sendMsg called w/NULL mbox
			    warningUnexpected(179), -- an unexpected error
			    warningChannelMapStuck(180), -- t1 missing channel debugging
			    warningChannelDisplayStuck(181), -- t1 missing channel debugging
			    warningNewCallNoDiscRequest(182), -- t1 missing channel debugging
			    warningNewCallNoDiscResp(183), -- t1 missing channel debugging
			    warningDisconnectRequestDropped(184), -- t1 missing channel debugging
			    warningSpyderBuffer(185), -- spyder debugging
			    warningSpyderDesc(186), -- spyder debugging
			    warningSpyderLoseChannel(187), -- spyder debugging
			    warningHscxSlowRelay(188), -- HSCX post problem on the 6000
			    warningTcpSbcontTooBig(190), -- TCP Error conditions
			    warningTcpSequenceGap(191), -- TCP Error conditions
			    warningTcpTooMuchData(192), -- TCP Error conditions
			    warningTcpTooMuchWrite(193), -- TCP Error conditions
			    warningTcpBadOptions(194), -- TCP Error conditions
			    warningLmodSlotDown(195),
			    warningLmodDspDown(196),
			    warningLmodDspmodemDown(197),
			    warningTcpXmitLooping(198),
			    warningOspfFatal(200), -- OSPF's error messages.
			    warningOspfWarn(201), -- OSPF's error messages.
			    warningBriJumperNotPresent(210), -- On Max3000 BRI, jumpers must be all S/T or all U, a mixture is not allowed.
			    warningBriJumperConfiguration(211), -- On Max3000 BRI, jumpers must be all S/T or all U, a mixture is not allowed.
			    infoCardBounced(220), -- Slot card bounced or down. Note: was initially 96 and 97.
			    infoCardDown(221), -- Slot card bounced or down. Note: was initially 96 and 97.
			    warningTacacsplusBase(300), -- TACACS+ error messages.
			    warningTacacsplusPointerInconsistency(301), -- TACACS+ error messages.
			    warningTacacsplusIndexInconsistency(302), -- TACACS+ error messages.
			    warningTacacsplusTcpInconsistency(303), -- TACACS+ error messages.
			    warningTacacsplusTcpOutofrangesocket(304), -- TACACS+ error messages.
			    warningTacacsplusSocketMismatch(305), -- TACACS+ error messages.
			    warningTacacsplusUnexpectedAuthState(306), -- TACACS+ error messages.
			    warningTacacsplusMax(309), -- TACACS+ error messages.
			    warningCidrWrongTree(310), -- CIDR Routing table warning messages.
			    warningCidrNoMem(311), -- CIDR Routing table warning messages.
			    warningCidrBusy(312), -- CIDR Routing table warning messages.
			    warningCidrNonempty(313), -- CIDR Routing table warning messages.
			    warningCidrDupDelete(314), -- CIDR Routing table warning messages.
			    warningSauthWrongInfo(320), -- Source Auth (source-based CIDR) warning messages.
			    warningSauthBadAddr(321), -- Source Auth (source-based CIDR) warning messages.
			    warningGdbProtectionFault(330), -- GDB Errors
			    warningInFilterList(381), -- Misc Errors
			    warningNoCountInFilterList(382), -- Misc Errors
			    warningMismatchCountFilterList(383), -- Misc Errors
			    warningCdtUnprotectedAccess(384), -- Misc Errors See EOI 42160 for explanation of warning 384 and how to resolve it.
			    infoSystemResetOccurred(385), -- To report a system reset that is not caused by an OperatorReset or by a fatal error
			    warningBadPowerSupply(400), -- Power supply failure in MAX 6000 redundant units
			    warningEthernetNoTxBuf(550), -- Warning ran out of ethernet TX bufs
			    warningDspCrashMin(512), -- Errors accompanied by a crash code in the lower 0xFF.
			    warningDspCrashMax(767), -- (512 + 255)
			    warningDspWrongSlot(768),
			    warningUnalignedAccess(800), -- This is a MIPS only error currently
			    warningH323NoResources(801), -- H.323 warnings
			    warningExecRestricted(999), -- unexpected blocking call
			    warningEthernetCuBusy(1001), -- i82596/i82507 ethernet warnings
			    warningEthernetAckFailure(1002), -- i82596/i82507 ethernet warnings
			    warningEthernetReset(1003), -- i82596/i82507 ethernet warnings
			    warningEthernetCuActive(1005), -- i82596/i82507 ethernet warnings
			    warningEthernetWaitScb(1006), -- i82596/i82507 ethernet warnings
			    warningEthernetNoMACAddress(1007), -- ethernet MAC address warning
			    warningBaeepromChange(2001), -- EEPROM driver warnings
			    warningBaeepromImageMismatch(2002), -- EEPROM driver warnings
			    warningFlashTypeBad(2010), -- Flash used for SecPROM is the wrong type
			    warningMaxiopLoadFailure(2022), -- MAX IOP failed to load
			    warningPrimaryHWsetupFailed(2100), -- Redundancy bus aquisition warning
			    warningSecondaryHWsetupFailed(2101), -- Redundancy bus aquisition warning
			    warningIpxsapFilterMagic(3001), -- IPX SAP filter warnings
			    warningIpxsapFilterCountZero(3002), -- IPX SAP filter warnings
			    warningIpxsapFilterCountMismatch(3003), -- IPX SAP filter warnings
			    warningModemTxChannelStuck(4000), -- stuck csmx transmit modem queue problem
			    warningModemTxChannelRecovered(4100), -- stuck csmx transmit modem queue problem
			    notApplicable(9998),
			    unknown(9999)
                        }	
	ACCESS		read-only
	STATUS		mandatory
	DESCRIPTION	
           "The error code for the previous box restart. The error codes
            are identical to ones obtained via fatal-history from the
            debug monitor screen."
	::= { systemStatusGroup 13 }

    sysConfigChange	OBJECT-TYPE
	SYNTAX		DisplayString
	ACCESS		read-only
	STATUS		mandatory
	DESCRIPTION	"The name and security index (if available)
                        of the user who changed the configuration."
	::= { systemStatusGroup 14 }

    sysConfigFlash OBJECT IDENTIFIER ::= { systemStatusGroup 15 }

    fatalLogTable OBJECT-TYPE
         SYNTAX  SEQUENCE OF FatalLogTableEntry
         ACCESS  not-accessible
         STATUS  mandatory
         DESCRIPTION "A list of the most recent Fatal Log entries of the
                      system as well as the included slot cards"
         ::= { systemStatusGroup 16 }

-- Table Definations
     fatalLogTableEntry   OBJECT-TYPE
        SYNTAX  FatalLogTableEntry
        ACCESS  not-accessible
        STATUS  mandatory
        DESCRIPTION "Definition of the row entries in the Fatal Log Table"
        INDEX  { fatalLogIndex }
        ::= { fatalLogTable 1 }

      FatalLogTableEntry   ::=
        SEQUENCE {
           fatalLogIndex
                         INTEGER,
           fatalLogSlotIndex
                         INTEGER,
           fatalLogSoftwareVerion
                         DisplayString,
           fatalLogUserprofile
                         DisplayString,
           fatalLogLoadName
                         DisplayString,
           fatalLogLocation
                         DisplayString,
           fatalLogReason
                         INTEGER,
	   fatalLogAbsoluteTime
                         INTEGER
           }

       fatalLogIndex OBJECT-TYPE
          SYNTAX  INTEGER
          ACCESS  read-only
          STATUS  mandatory
          DESCRIPTION     "Dynamic index that reflects the index used in the 
                           Fatal LOG table, starting with the most oldest event."
          ::= { fatalLogTableEntry 1 }

       fatalLogSlotIndex  OBJECT-TYPE
          SYNTAX  INTEGER
          ACCESS  read-only
          STATUS  mandatory
          DESCRIPTION     "An index into the slotTable This has the same 
                           value as slotIndex, it is set to 0 for systems 
                           with one logical slot card."
          ::= { fatalLogTableEntry 2 }

       fatalLogSoftwareVerion OBJECT-TYPE
           SYNTAX  DisplayString
           ACCESS  read-only
           STATUS  mandatory
           DESCRIPTION     "The version of the software running, when this
                            entry was created by the system."
           ::= { fatalLogTableEntry 3 }

       fatalLogUserprofile OBJECT-TYPE
            SYNTAX  DisplayString
            ACCESS  read-only
            STATUS  mandatory
            DESCRIPTION     "The user responsible for reseting the card. This
                             will be set to the empty string if unknown."
            ::= { fatalLogTableEntry 4 }
 
       fatalLogLoadName OBJECT-TYPE
            SYNTAX  DisplayString
            ACCESS  read-only
            STATUS  mandatory
            DESCRIPTION     "The name of the Load executing on the card, it gives
                             a textual description of the software code that was
                             running on the system when the entry was created."
            ::= { fatalLogTableEntry 5 }

        fatalLogLocation OBJECT-TYPE
            SYNTAX  DisplayString
            ACCESS  read-only
            STATUS  mandatory
            DESCRIPTION     "The IP address from which a manual system reset was triggered."
            ::= { fatalLogTableEntry 6 }

       fatalLogReason	OBJECT-TYPE
	    SYNTAX		INTEGER {
			    fatalAssert(1),
			    fatalPoolsNoBuffer(2),
			    fatalProfileBad(3),
			    fatalSwitchTypeBad(4),
			    fatalLif(5),
			    fatalLcdError(6),
			    fatalIsacTimeout(7),
			    fatalSCCSpuriousInterrupt(8), -- 8 is a.k.a. PROCESSOR EXCEPTION!!
			    fatalExecInvalidSwitch(9),
			    fatalExecNoMailDesc(10),
			    fatalExecNoMailPoll(11),
			    fatalExecNoTask(12),
			    fatalExecNoTimer(13),
			    fataExecNoTimerPool(14),
			    fatalExecWaitInCtricalSection(15),
			    fatalDspDead(16),
			    fatalDspProtocolError(17),
			    fatalDspInternalError(18),
			    fatalDspLossOfSync(19),
			    fatalDspUnUsed(20),
			    fatalDDDDead(21),
			    fatalDDDProtocolError(22),
			    fatalX25Buffers(23),
			    fatalX25Init(24),
			    fatalX25Stack(25),
			    fatalZeroMemoryAlloc(27),
			    fatalNegativeMemoryAllocate(28),
			    fatalTaskLoop(29),
			    fatalMemcpyTooLarge(30),
			    fatalMemcpyNoMagic(31),
			    fatalMemcpyWrongMagic(32),
			    fatalMemcoyBadStart(33),
			    fatalIDECTimeout(34),
			    fatalExecRestricted(35),
			    fatalStackOverflow(36),
			    fatalDRAMCard(37),
			    fatalMbufPanic(38),
			    fatalNoPriority2Task(39),
			    fatalProtectionFault(40),
			    fatalClipping(41), -- clipping (may indicate memory leak)
			    fatalReadyHangFault(42),
			    fatalExcessPostCompl(43),
			    fatalWriteProtect(44),
			    fatalPureVirtual(45), -- C++ pure virtual call attempted
			    fatalATMSVC(46),
			    fatalFRSVC(47),
			    fatalInterruptCode(48),
			    fatalLinkedListCorruption(55),
			    fatalBadPower(60), -- NMI related fatal logs
			    fatalWatchdogTimeout(61), -- NMI related fatal logs
			    fatalUnexplainedNMI(62), -- NMI related fatal logs
			    fatalPrimarySelected(98),
			    fatalOperatorReset(99),
			    fatalSystemUp(100),
			    warningBufferInUse(101),
			    warningBufferWrongPool(102),
			    warningBufferWrongHeap(103),
			    warningBufferNotMemAlloc(104),
			    warningBufferBadMemAlloc(105),
			    warningBufferBogusPool(106),
			    warningBufferBogusHeap(107),
			    warningBufferNegativeMemalloc(108),
			    warningBufferZeroMemalloc(109),
			    warningBufferBoundary(110),
			    warningBufferTooBig(111),
			    warningBufferNull(112),
			    warningBufferSegmentCountZero(113),
			    warningBufferTrailerMagic(114),
			    warningBufferTrailerBuffer(115),
			    warningBufferTrailerLength(116),
			    warningBufferTrailerUserMagic(117),
			    warningBufferWriteAfterFree(118),
			    warningBufferNotInUse(119),
			    warningBufferMemcpyMagic(120),
			    warningBufferMemcpyMagicNext(121),
			    warningBufferNoExtraDRAM(129), -- V2P75 only: no xtra DRAM detected, or memtest on xtra DRAM  failed
			    errprPPPAsuncBufferInUse(130), -- PPP errors
			    warningIpcpIpLookup(131), -- PPP errors
			    warningBadChunk(135), -- wandata (& wansess) errors
			    warningUnexpectedIF(136), -- wandata (& wansess) errors
			    warningNoTimers(140), -- timer errors
			    warningLCDAllocFailure(145), -- getBuff failure in lcd
			    warningLCDNonSense(146), -- From lcdlogin.c; which should not be in this state
			    warningMemcpyTooLarge(150), -- memcpy was called with too large a length
			    warningMemcpyNoMagic(151), -- memcpy was called with too large a length
			    warningMemcpyWrongMagic(152), -- memcpy was called with too large a length
			    warningMemcpyBadStart(153), -- memcpy was called with too large a length
			    warningWANBufferLeak(154), -- wandrv errors
			    warningTermSrvState(160), -- termsrv debugging
			    warningTermSrvSemaphore(161), -- termsrv debugging
			    warningTelnetFreeDrv(165), -- telnet debugging
			    warningSTACTimeout(170), -- stacdrv/compress debugging
			    warningSTACDataNotOwned(171), -- stacdrv/compress debugging
			    warningExecFailure(175), -- misc debugging
			    warningExecNoMailbox(177), -- misc debugging sendMsg called w/NULL mbox
			    warningExecNoResources(178), -- misc debugging sendMsg called w/NULL mbox
			    warningUnexpected(179), -- an unexpected error
			    warningChannelMapStuck(180), -- t1 missing channel debugging
			    warningChannelDisplayStuck(181), -- t1 missing channel debugging
			    warningNewCallNoDiscRequest(182), -- t1 missing channel debugging
			    warningNewCallNoDiscResp(183), -- t1 missing channel debugging
			    warningDisconnectRequestDropped(184), -- t1 missing channel debugging
			    warningSpyderBuffer(185), -- spyder debugging
			    warningSpyderDesc(186), -- spyder debugging
			    warningSpyderLoseChannel(187), -- spyder debugging
			    warningHscxSlowRelay(188), -- HSCX post problem on the 6000
			    warningTcpSbcontTooBig(190), -- TCP Error conditions
			    warningTcpSequenceGap(191), -- TCP Error conditions
			    warningTcpTooMuchData(192), -- TCP Error conditions
			    warningTcpTooMuchWrite(193), -- TCP Error conditions
			    warningTcpBadOptions(194), -- TCP Error conditions
			    warningLmodSlotDown(195),
			    warningLmodDspDown(196),
			    warningLmodDspmodemDown(197),
			    warningTcpXmitLooping(198),
			    warningOspfFatal(200), -- OSPF's error messages.
			    warningOspfWarn(201), -- OSPF's error messages.
			    warningBriJumperNotPresent(210), -- On Max3000 BRI, jumpers must be all S/T or all U, a mixture is not allowed.
			    warningBriJumperConfiguration(211), -- On Max3000 BRI, jumpers must be all S/T or all U, a mixture is not allowed.
			    infoCardBounced(220), -- Slot card bounced or down. Note: was initially 96 and 97.
			    infoCardDown(221), -- Slot card bounced or down. Note: was initially 96 and 97.
			    warningTacacsplusBase(300), -- TACACS+ error messages.
			    warningTacacsplusPointerInconsistency(301), -- TACACS+ error messages.
			    warningTacacsplusIndexInconsistency(302), -- TACACS+ error messages.
			    warningTacacsplusTcpInconsistency(303), -- TACACS+ error messages.
			    warningTacacsplusTcpOutofrangesocket(304), -- TACACS+ error messages.
			    warningTacacsplusSocketMismatch(305), -- TACACS+ error messages.
			    warningTacacsplusUnexpectedAuthState(306), -- TACACS+ error messages.
			    warningTacacsplusMax(309), -- TACACS+ error messages.
			    warningCidrWrongTree(310), -- CIDR Routing table warning messages.
			    warningCidrNoMem(311), -- CIDR Routing table warning messages.
			    warningCidrBusy(312), -- CIDR Routing table warning messages.
			    warningCidrNonempty(313), -- CIDR Routing table warning messages.
			    warningCidrDupDelete(314), -- CIDR Routing table warning messages.
			    warningSauthWrongInfo(320), -- Source Auth (source-based CIDR) warning messages.
			    warningSauthBadAddr(321), -- Source Auth (source-based CIDR) warning messages.
			    warningGdbProtectionFault(330), -- GDB Errors
			    warningInFilterList(381), -- Misc Errors
			    warningNoCountInFilterList(382), -- Misc Errors
			    warningMismatchCountFilterList(383), -- Misc Errors
			    warningCdtUnprotectedAccess(384), -- Misc Errors See EOI 42160 for explanation of warning 384 and how to resolve it.
			    infoSystemResetOccurred(385), -- To report a system reset that is not caused by an OperatorReset or by a fatal error
			    warningBadPowerSupply(400), -- Power supply failure in MAX 6000 redundant units
			    warningEthernetNoTxBuf(550), -- Warning ran out of ethernet TX bufs
			    warningDspCrashMin(512), -- Errors accompanied by a crash code in the lower 0xFF.
			    warningDspCrashMax(767), -- (512 + 255)
			    warningDspWrongSlot(768),
			    warningUnalignedAccess(800), -- This is a MIPS only error currently
			    warningH323NoResources(801), -- H.323 warnings
			    warningExecRestricted(999), -- unexpected blocking call
			    warningEthernetCuBusy(1001), -- i82596/i82507 ethernet warnings
			    warningEthernetAckFailure(1002), -- i82596/i82507 ethernet warnings
			    warningEthernetReset(1003), -- i82596/i82507 ethernet warnings
			    warningEthernetCuActive(1005), -- i82596/i82507 ethernet warnings
			    warningEthernetWaitScb(1006), -- i82596/i82507 ethernet warnings
			    warningEthernetNoMACAddress(1007), -- ethernet MAC address warning
			    warningBaeepromChange(2001), -- EEPROM driver warnings
			    warningBaeepromImageMismatch(2002), -- EEPROM driver warnings
			    warningFlashTypeBad(2010), -- Flash used for SecPROM is the wrong type
			    warningMaxiopLoadFailure(2022), -- MAX IOP failed to load
			    warningPrimaryHWsetupFailed(2100), -- Redundancy bus aquisition warning
			    warningSecondaryHWsetupFailed(2101), -- Redundancy bus aquisition warning
			    warningIpxsapFilterMagic(3001), -- IPX SAP filter warnings
			    warningIpxsapFilterCountZero(3002), -- IPX SAP filter warnings
			    warningIpxsapFilterCountMismatch(3003), -- IPX SAP filter warnings
			    warningModemTxChannelStuck(4000), -- stuck csmx transmit modem queue problem
			    warningModemTxChannelRecovered(4100), -- stuck csmx transmit modem queue problem
			    notApplicable(9998),
			    unknown(9999)
	                }
       	    ACCESS		read-only
	    STATUS		mandatory	
	    DESCRIPTION      "The reason for reset as reported by the system. For a more
                              detailed description consult the user manual."
	    ::= { fatalLogTableEntry 7 } 

    fatalLogAbsoluteTime  OBJECT-TYPE
            SYNTAX	   INTEGER (1..'7fffffff'h)
            ACCESS	   read-only
	    STATUS	   mandatory
	    DESCRIPTION	   "The time at which the system was reset."
            ::= {  fatalLogTableEntry 8 } 

    sysConfigFlashCmd OBJECT-TYPE
	SYNTAX	INTEGER {
		    copyPCMCIAtoInternal( 1 ),	-- copy image from PCMCIA
		    copyInternalToPCMCIA( 2 )   -- copy image from internal
		}
	ACCESS	read-write
	STATUS	mandatory
	DESCRIPTION
	   "This variable instructs the system to copy the stored code
	    image from PCMCIA flash to internal flash or vice versa."
	::= { sysConfigFlash 1 }

    sysConfigFlashCopyStatus OBJECT-TYPE
	SYNTAX	INTEGER {
		    ok( 1 ),			-- flash copy succeeded
	            inProgress( 2 ),		-- flash copy in progress
		    failed( 3 )			-- flash copy failed			
		}
	ACCESS	read-only
	STATUS	mandatory
	DESCRIPTION
	   "This variable indicates the status of a flash image copy."
	::= { sysConfigFlash 2 }

     sysConfigInternalFlashImageVersion		OBJECT-TYPE
	SYNTAX		DisplayString
	ACCESS		read-only
	STATUS		mandatory
	DESCRIPTION	"The code version stored on the internal flash." 
	::= { sysConfigFlash 3 }

     sysConfigPCMCIAFlashImageVersion		OBJECT-TYPE
	SYNTAX		DisplayString
	ACCESS		read-only
	STATUS		mandatory
	DESCRIPTION	"The code version stored on the PCMCIA flash." 
	::= { sysConfigFlash 4 }

	-- Ascend configuration group
	--
	-- Each profile is assigned an object ID.  These ids are
	-- the root of MIB subtrees containing profile specific information.
	-- These subtrees, when required, are described in separate files.

    mibinternetProfile		OBJECT IDENTIFIER ::= { configuration 1 }
    mibframeRelayProfile	OBJECT IDENTIFIER ::= { configuration 2 }
    mibanswerProfile		OBJECT IDENTIFIER ::= { configuration 3 }
    mibdS3NetworkProfile	OBJECT IDENTIFIER ::= { configuration 4 }
    mibuds3NetworkProfile	OBJECT IDENTIFIER ::= { configuration 5 }
    mibcadslNetworkProfile	OBJECT IDENTIFIER ::= { configuration 6 }
    mibdadslNetworkProfile	OBJECT IDENTIFIER ::= { configuration 7 }
    mibsdslNetworkProfile	OBJECT IDENTIFIER ::= { configuration 8 }
    mibvdslNetworkProfile	OBJECT IDENTIFIER ::= { configuration 9 }
    mibdmtAlDslNetworkProfile   OBJECT IDENTIFIER ::= { configuration 10 }
    miboc3AtmNetworkProfile     OBJECT IDENTIFIER ::= { configuration 11 }
    miblimSparingConfigProfile  OBJECT IDENTIFIER ::= { configuration 12 }
    mibds3AtmNetworkProfile     OBJECT IDENTIFIER ::= { configuration 13 }
    mibhdsl2NetworkProfile      OBJECT IDENTIFIER ::= { configuration 14 }
    mibe3AtmNetworkProfile      OBJECT IDENTIFIER ::= { configuration 15 }  
    mibredundancyProfile        OBJECT IDENTIFIER ::= { configuration 16 }
    mibredundancyStatsProfile   OBJECT IDENTIFIER ::= { configuration 17 }
END
