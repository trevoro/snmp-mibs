-- TyLink Enterprise MIB for 1250                             =
--                                                            =
-- SCCS info: @(#)ty1250i.mib	5.10  Last delta-ed on: 11/13/95
--                                                            =
-- This file contains MIB Definitions for extended management =
-- of TyLink 1250 Product (DDS product with integral agent).  =
--                                                            =
-- This MIB is copyrighted by TyLink Corporation (1995).      =
-- Permission is granted to the general public to use this    =
-- file for management of TyLink Products.                    =
--                                                            =
-- Updates to this Enterprise MIB may be obtained from        =
-- TyLink Customer Service 1-800-828-2780.                    =
--                                                            =

TY1250I-MIB DEFINITIONS ::= BEGIN

   IMPORTS

      DisplayString
         FROM SNMPv2-TC
      Counter, TimeTicks, enterprises, IpAddress
         FROM RFC1155-SMI
      TRAP-TYPE
         FROM RFC-1215
      OBJECT-TYPE
         FROM RFC-1212;

   --  This MIB module uses the extended OBJECT-TYPE macro.

   tylink  OBJECT IDENTIFIER ::= { enterprises 466 }
   dsucsu  OBJECT IDENTIFIER ::= { tylink 1 }
   tyview  OBJECT IDENTIFIER ::= { tylink 2 }
   ty1250  OBJECT IDENTIFIER ::= { tylink 3 }


   -- textual conventions

       --DisplayString ::=
       --    OCTET STRING
       -- This data type is used to model textual information taken
       -- from the NVT ASCII character set.  By convention, objects
       -- with this syntax are declared as having
       --
       --      SIZE (0..255)


-- *********************************************************************
--                     TY1250I ENTERPRISE SPECIFIC MIB
-- *********************************************************************


-- ======================================================================
--
--  The 1250 MIB Tree
--      This MIB covers the TyLink 1250, a DDS CSU for dedicated
--      or switched (SW56) applications.  This product is managed 
--      via an integral agent.
--
--  The 1250 MIB Consists of three groups (plus Traps):
--      The SYSTEM group
--      The CONFIGURATION group
--      The CONTROL group
--
--
--      The SYSTEM group
--          This group provides system level attributes of the node.
--
--          The group consists of the following tables:
--              ty1250SysTable       - System level attributes
--
--      The CONFIGURATION group
--          This group provides for configuration of the node.
--
--          The group consists of the following tables:
--              ty1250CfgAppTable    - Application level configuration
--              ty1250CfgNetTable    - Network port configuration
--              ty1250CfgDteTable    - DTE port configuration
--              ty1250CfgDialTable   - Dial configuration
--              ty1250CfgMaintTable  - Maintenance port configuration
--              ty1250CfgSlipTable   - Configuration of SLIP maintenance port
--              ty1250CfgSnmpTable   - SNMP configuration
--              
--      The CONTROL group
--          This group provides for run-time control of the node.
--
--          The group consists of the following tables:
--              ty1250CallTable      - Call status/commands
--              ty1250DiagUnitTable  - Unit level Diagnostics
--              ty1250DiagNetTable   - Network Port Diagnostics
--              ty1250DiagDteTable   - DTE port diagnostics
--              ty1250StatsDteTable  - DTE port statistics
--              ty1250StatsNetTable  - Network port statistics
--
--      The MIB also contains enterprise trap information:
--              ty1250Trap
--
-- =======================================================================



-- ========================
-- ==   SYSTEM group     ==
-- ========================
--
--       The ty1250SysTable
--              This table contains the system attributes of the 1250 CSU.
      
ty1250SysTable      OBJECT IDENTIFIER ::= { ty1250 1 }

ty1250SysType       OBJECT-TYPE
          SYNTAX      DisplayString (SIZE (0..10))
          ACCESS      read-only
          STATUS      mandatory
          DESCRIPTION
             "A textual description of the system model identifier.
              for example: TYLINK1250"
          ::= { ty1250SysTable 1 }

ty1250SysSoftRev    OBJECT-TYPE
          SYNTAX      DisplayString (SIZE (0..10))
          ACCESS      read-only
          STATUS      mandatory
          DESCRIPTION
             "Displays the Software Revision installed in this node."
          ::= { ty1250SysTable 2 }

ty1250SysHardRev    OBJECT-TYPE
          SYNTAX      DisplayString (SIZE (0..10))
          ACCESS      read-only
          STATUS      mandatory
          DESCRIPTION
             "Displays the Hardware Revision of the node."
          ::= { ty1250SysTable 3 }

ty1250SysNumNetInstalled    OBJECT-TYPE
          SYNTAX      INTEGER (0..1)
          ACCESS      read-only
          STATUS      mandatory
          DESCRIPTION
             "The number of Network (DDS) ports that are
              installed.  There is 1 on the 1250."
          ::= { ty1250SysTable 4 }

ty1250SysNumDteInstalled    OBJECT-TYPE
          SYNTAX      INTEGER (0..1)
          ACCESS      read-only
          STATUS      mandatory
          DESCRIPTION
             "The number of channels (DTE) that are
              installed.  There is 1 on the 1250."
          ::= { ty1250SysTable 5 }

ty1250SysNumMaintInstalled    OBJECT-TYPE
          SYNTAX      INTEGER (0..2)
          ACCESS      read-only
          STATUS      mandatory
          DESCRIPTION
             "The number of Maintenance ports that are 
              installed.  There are 2 on the 1250."
          ::= { ty1250SysTable 6 }

ty1250SysName       OBJECT-TYPE
          SYNTAX      DisplayString (SIZE (0..16))
          ACCESS      read-write
          STATUS      mandatory
          DESCRIPTION
             "The user supplied name of the node.  This object
              does not affect operation, but may be useful
              for network management."
          ::= { ty1250SysTable 7 }



-- =========================
-- == CONFIGURATION group ==
-- =========================
--
--       The Application Configuration Table
--              This table contains the Application (system) Configuration
--              information for the 1250 DDS DSU.

ty1250CfgAppTable   OBJECT IDENTIFIER ::= { ty1250 2 }

ty1250CfgAppClockSource OBJECT-TYPE
          SYNTAX      INTEGER
          {
               internal (1),
               network  (2)
          }
          ACCESS      read-write
          STATUS      mandatory
          DESCRIPTION
             "Default timing, or clock, source.  There must be only one
              source on a DDS line.  Node should always be network (2) 
              timed on a point-to-network application. Line
              Driver applications need one node as internal (1),
              one as network (2)."  
          ::= { ty1250CfgAppTable 2 }

ty1250CfgAppCircuitId    OBJECT-TYPE
          SYNTAX      DisplayString (SIZE (0..30))
          ACCESS      read-write
          STATUS      mandatory
          DESCRIPTION
             "Circuit identifier provided by the service provider."
          ::= { ty1250CfgAppTable 3 }


--
--       The Network Configuration Table
--              This table contains the Network port Configuration
--              information for the 1250 DDS DSU.

ty1250CfgNetTable   OBJECT IDENTIFIER ::= { ty1250 3 }

ty1250CfgNetType    OBJECT-TYPE
          SYNTAX      INTEGER
          {
               dedicated   (1),
               switch56  (2)
          } 
          ACCESS      read-write
          STATUS      mandatory
          DESCRIPTION
             "Indicates type of service purchased on the attached
              network line (DDS or SW56).  Valid selections are
              dedicated (1) and switch56 (2)."
          ::= { ty1250CfgNetTable 11 }

ty1250CfgNetGlareType OBJECT-TYPE
          SYNTAX      INTEGER
          {
               external-glare (1),
               internal-glare (2)
          }
          ACCESS      read-write
          STATUS      mandatory
          DESCRIPTION
             "In switched applications, defines who wins when
              there are simultanious incomming and outgoing 
              calls.  If in doubt, select external-glare (2)."
          ::= { ty1250CfgNetTable 4 }
 
ty1250CfgNetEchoCan OBJECT-TYPE
          SYNTAX      INTEGER
          {
               ignore-echo-cancellers (1),
               disable-echo-cancellers (2)
          }
          ACCESS      read-write
          STATUS      mandatory
          DESCRIPTION
             "In switched applications, some carriers, such
              as Sprint, require you to disable-echo-cancellors (2)
              for data apps on most lines.  Calls take longer 
              to come up when disabling is done; use 
              ignore-echo-cancellers (1) on clear channel lines."
          ::= { ty1250CfgNetTable 5 }
 
ty1250CfgNetAnsMode OBJECT-TYPE
          SYNTAX      INTEGER
          {
               manual-answer (1),
               automatic-answer (2)
          }
          ACCESS      read-write
          STATUS      mandatory
          DESCRIPTION
             "In switched applications, allows for manual-answer (1)
              or automatic-answer (2) of inbound calls.  Calls
              may be answered in manual mode via vt100, DTR, or the
              front panel button if so configured."
          ::= { ty1250CfgNetTable 6 }
 
ty1250CfgNetDialTimeout OBJECT-TYPE
          SYNTAX      INTEGER (1..255)
          ACCESS      read-write
          STATUS      mandatory
          DESCRIPTION
             "In switched applications, time in seconds to wait
              for far end to answer before giving up, and possibly
              redialing."
          ::= { ty1250CfgNetTable 7 }
 
ty1250CfgNetNumRedial OBJECT-TYPE
          SYNTAX      INTEGER (1..255)
          ACCESS      read-write
          STATUS      mandatory
          DESCRIPTION
             "In switched applications, number of times to
              redial if the call fails."
          ::= { ty1250CfgNetTable 8 }
 
ty1250CfgNetRedialDelay OBJECT-TYPE
          SYNTAX      INTEGER (1..255)
          ACCESS      read-write
          STATUS      mandatory
          DESCRIPTION
             "In switched applications, delay in seconds
              between redial attempts."
          ::= { ty1250CfgNetTable 9 }
 
ty1250CfgNetDefNum2Dial OBJECT-TYPE
          SYNTAX      DisplayString (SIZE (0..20))
          ACCESS      read-write
          STATUS      mandatory
          DESCRIPTION
             "In switched applications, default phone number
              to dial.  Numbers and dashes are allowed."
          ::= { ty1250CfgNetTable 10 }

ty1250CfgNetBPVThresholding OBJECT-TYPE
          SYNTAX      INTEGER 
          {
               thresholding-at-10E-4 (1),
               disable-thresholding (2)
          }
          ACCESS      read-write
          STATUS      mandatory
          DESCRIPTION
             "Allows the user to turn on and off the BPV thresholding
              function.  Valid values are thresholding_at_10E-4 (1) and
              disable-thresholding (2)."
          ::= { ty1250CfgNetTable 12 }


--
--       The DTE (Channel) Configuration Table
--              This table contains the DTE (Channel) Configuration
--              information for the 1250 DDS DSU.

ty1250CfgDteTable   OBJECT IDENTIFIER ::= { ty1250 4 }

ty1250CfgDteType    OBJECT-TYPE
          SYNTAX      INTEGER
          {
               v35 (2),
               rs449 (3)
          }
          ACCESS      read-only
          STATUS      mandatory
          DESCRIPTION
             "The Dte channel type identifies the electrical
              specification of the interface.  Read-only." 
          ::= { ty1250CfgDteTable 1 }
 
ty1250CfgDteClockInvert OBJECT-TYPE
          SYNTAX      INTEGER
          {
               normal-dte-clock (1),
               invert-dte-clock (2)
          }
          ACCESS      read-write
          STATUS      mandatory
          DESCRIPTION
             "Clock Inversion, invert-dte-clock (2), can be 
              used to solve out of phase timing problems on 
              DTE link.  normal-dte-clock (1) can be used in
              most cases."
          ::= { ty1250CfgDteTable 5 }
 
ty1250CfgDteTiming OBJECT-TYPE
          SYNTAX      INTEGER
          {
               loop1-timing (1),
               loop2-timing (2)
          }
          ACCESS      read-write
          STATUS      mandatory
          DESCRIPTION
             "The DTE channel Timing mode.  Use loop2-timing (2)
              when in doubt."
          ::= { ty1250CfgDteTable 6 }


--
--       The Dial Configuration Table
--              This table contains the Dial Configuration
--              information for the 1250 DDS DSU, for use in switched
--              applications.

ty1250CfgDialTable  OBJECT IDENTIFIER ::= { ty1250 5 }

ty1250CfgDialButton OBJECT-TYPE
          SYNTAX      INTEGER 
          {
               enable-button  (1),
               disable-button (2)
          }
          ACCESS      read-write
          STATUS      mandatory
          DESCRIPTION
             "In switched applications, Enables/Disables 
              the button on front of unit.  This button can
              used to manual answer an incomming call, or
              dial out the default number.  The valid values
              are enable-button (1) and disable-button (2)."
          ::= { ty1250CfgDialTable 1 }

ty1250CfgDialDtr  OBJECT-TYPE
          SYNTAX      INTEGER 
          {
               enable-dtr  (1),
               disable-dtr (2)
          }
          ACCESS      read-write
          STATUS      mandatory
          DESCRIPTION
             "In switched applications, Enables/Disables
              dialing on DTR signal transition.  Valid values
              enable-dtr (1) and disable-dtr (2)."
          ::= { ty1250CfgDialTable 2 }

ty1250CfgDialRtsDisc OBJECT-TYPE
          SYNTAX      INTEGER
          {
               enable-rts  (1),
               disable-rts (2)
          }
          ACCESS      read-write
          STATUS      mandatory
          DESCRIPTION
             "In switched applications, Enables/Disables
              disconnecting on RTS signal transition.  Valid 
              values are enable-rts (1) and disable-rts (2)."
          ::= { ty1250CfgDialTable 3 }

ty1250CfgDialRi OBJECT-TYPE
          SYNTAX      INTEGER
          {
               enable-ri  (1),
               disable-ri (2)
          }
          ACCESS      read-write
          STATUS      mandatory
          DESCRIPTION
             "In switched applications, Enables/Disables
              incoming call notification to DTE via RI
              signal.   Valid values are enable-ri (1)
              and disable-ri (2)."
          ::= { ty1250CfgDialTable 4 }


--
--       The Maintenance Port Configuration Table
--              This table contains the Configuration for Maintenance Ports
--              on the 1250 DDS DSU.

ty1250CfgMaintTable OBJECT-TYPE
          SYNTAX      SEQUENCE OF Ty1250CfgMaintEntry
          ACCESS      not-accessible
          STATUS      mandatory
          DESCRIPTION
             "The Maintenance Port Configuration table contains
              parameters for the Maintenance ports on the
              1250.  The Terminal Port is Index=1; SLIP port is 2"
          ::= { ty1250 6 }

ty1250CfgMaintEntry OBJECT-TYPE
          SYNTAX      Ty1250CfgMaintEntry
          ACCESS      not-accessible
          STATUS      mandatory
          DESCRIPTION
             "Maintenance Port Configuration Object"
          INDEX { ty1250CfgMaintIndex }
          ::= { ty1250CfgMaintTable 1 }

Ty1250CfgMaintEntry ::=
          SEQUENCE
          {
               ty1250CfgMaintIndex    INTEGER (1..2),
               ty1250CfgMaintMode     INTEGER,
               ty1250CfgMaintBaud     INTEGER,
               ty1250CfgMaintDataBits INTEGER,
               ty1250CfgMaintStopBits INTEGER,
               ty1250CfgMaintParity   INTEGER,
               ty1250CfgMaintFlowCtrl INTEGER
          } 

ty1250CfgMaintIndex  OBJECT-TYPE
          SYNTAX      INTEGER (1..2)
          ACCESS      read-only
          STATUS      mandatory
          DESCRIPTION
             "The Maintenance port under consideration.  On the
              1250, the Terminal Port is Index=1; SLIP port is 2."
          ::= { ty1250CfgMaintEntry 1 }

ty1250CfgMaintMode OBJECT-TYPE
          SYNTAX      INTEGER
          {
               ascii-vt100 (4),
               slip (7),
               cslip (8)
          }
          ACCESS      read-write
          STATUS      mandatory
          DESCRIPTION
             "The Mode for this Maintenance Port.  Values include
              ascii-vt100 (4), slip (7), and cslip (8)."
          ::= { ty1250CfgMaintEntry 2 }

ty1250CfgMaintBaud OBJECT-TYPE
          SYNTAX      INTEGER
          {
              baud-2400 (2),
              baud-9600 (4),
              baud-19200 (5)
          }
          ACCESS      read-write
          STATUS      mandatory
          DESCRIPTION
             "Baud rate for this Maintenance port.  Values are
              baud-2400 (2), baud-9600 (4), baud-19200 (5)."
          ::= { ty1250CfgMaintEntry 3 }

ty1250CfgMaintDataBits OBJECT-TYPE
          SYNTAX      INTEGER
          {
              databits-7 (1),
              databits-8 (2)
          }
          ACCESS      read-write
          STATUS      mandatory
          DESCRIPTION
             "Databits for this Maintenance port.  Values
              are databits-7 (1) and databits-8 (2)."
          ::= { ty1250CfgMaintEntry 4 }

ty1250CfgMaintStopBits OBJECT-TYPE
          SYNTAX      INTEGER
          {
              stopbits-1 (1),
              stopbits-1-5 (2),
              stopbits-2 (3)
          }
          ACCESS      read-write
          STATUS      mandatory
          DESCRIPTION
             "Number of Stopbits for this Maintenance port.
              Values are stopbits-1 (1), stopbits-1-5 (2),
              and stopbits-2 (3)."
          ::= { ty1250CfgMaintEntry 5 }

ty1250CfgMaintParity OBJECT-TYPE
          SYNTAX      INTEGER
          {
              no-parity   (1),
              odd-parity  (2),
              even-parity (3)
          }
          ACCESS      read-write
          STATUS      mandatory
          DESCRIPTION
             "Parity for this Maintenance port.  Values are
              no-parity (1), odd-parity (2), even-parity (3)."
          ::= { ty1250CfgMaintEntry 6 }

ty1250CfgMaintFlowCtrl OBJECT-TYPE
          SYNTAX      INTEGER
          {
              no-flow-control (1),
              software-flow-control  (2),
              hardware-flow-control  (3)
          }
          ACCESS      read-write
          STATUS      mandatory
          DESCRIPTION
             "Flow Control for this Maintenance port.  Values
              are no-flow-control (1), software-flow-control (2),
              and hardware-flow-control (3)."
          ::= { ty1250CfgMaintEntry 7 }


--
--       The SLIP Configuration Table
--              This table contains the Configuration for Maintenance Port
--              when in SLIP mode on the 1250 DDS DSU.

ty1250CfgSlipTable OBJECT IDENTIFIER ::= { ty1250 8 }
 
ty1250CfgSlipMyIP   OBJECT-TYPE
          SYNTAX      IpAddress
          ACCESS      read-write
          STATUS      mandatory
          DESCRIPTION
             "The IP address for this node."
          ::= { ty1250CfgSlipTable 1 }
 
ty1250CfgSlipPeerIP   OBJECT-TYPE
          SYNTAX      IpAddress
          ACCESS      read-write
          STATUS      mandatory
          DESCRIPTION
             "The IP address for other end of slip connection."
          ::= { ty1250CfgSlipTable 2 }
 
ty1250CfgSlipMask   OBJECT-TYPE
          SYNTAX      IpAddress
          ACCESS      read-write
          STATUS      mandatory
          DESCRIPTION
             "The IP Network Mask (eg 255.255.255.0) for the
              SLIP link."
          ::= { ty1250CfgSlipTable 3 }
 
ty1250CfgSlipMaxMTU OBJECT-TYPE
          SYNTAX      INTEGER  (1..1024)
          ACCESS      read-write
          STATUS      mandatory
          DESCRIPTION
             "The Maximum Transmission Unit is the size of the
              largest IP packet supported.  This value should
              be set to the lowest value supported by any
              equipment in the transmission path.  A size of
              1006 (including header) is suggested."
          ::= { ty1250CfgSlipTable 4 }


--
--       The SNMP Configuration Table
--              This table contains the Configuration for the SNMP
--              support on the 1250 DDS DSU.

ty1250CfgSnmpTable OBJECT IDENTIFIER ::= { ty1250 14 }
 
ty1250CfgSnmpManagerIP   OBJECT-TYPE
          SYNTAX      IpAddress
          ACCESS      read-write
          STATUS      mandatory
          DESCRIPTION
             "The IP address for the SNMP manager to receive
              this node's TRAPs."
          ::= { ty1250CfgSnmpTable 1 }

ty1250CfgTelnetTable OBJECT IDENTIFIER ::= { ty1250 17 }

ty1250CfgTelnetEnable   OBJECT-TYPE
          SYNTAX      INTEGER
          {
              enable-telnet  (1),
              disable-telnet (2)
          }
          ACCESS      read-write
          STATUS      mandatory
          DESCRIPTION
             "Enables/Disables the telnet feature.
              Valid values are enable-telnet (1)
              and disable-telnet (2)."
          ::= { ty1250CfgTelnetTable 1 }

ty1250CfgTelnetAutoLogOut   OBJECT-TYPE
          SYNTAX      INTEGER
          {
              autologout-at-15-minutes (1),
              disable-autologout (2)
          }
          ACCESS      read-write
          STATUS      mandatory
          DESCRIPTION
             "Enables/Disables the telnet auto-logout, logging out
              the user after a certain length of idle time.
              Valid values are autologout-at-15-minutes (1)
              and disable-autologout (2)."
          ::= { ty1250CfgTelnetTable 2 }

 
-- =========================
-- ==    CONTROL group    ==
-- =========================
--
--       The Call Table
--              This table contains the Call information for switched
--              application mode on the 1250 DDS DSU.

ty1250CallTable OBJECT IDENTIFIER ::= { ty1250 9 }

ty1250CallState     OBJECT-TYPE
          SYNTAX      INTEGER 
          {
               connect (1),
               disconnect (2),
               answer (3)
          }
          ACCESS      write-only
          STATUS      mandatory
          DESCRIPTION
             "Call-related actions:
             a: Connect (initiate a call),
             b: Disconnect (terminate a call)
             c: Answer (answer an incoming call)."
          ::= { ty1250CallTable 4 }

ty1250CallStatus    OBJECT-TYPE
          SYNTAX      INTEGER 
          {
               none (1),
               idle (2),
               dialing (3),
               busy (4),
               waiting-for-redial (5),
               redialing (6),
               active (7),
               incoming-call (8),
               line-in-maintenance (253),
               line-down (254)
          }
          ACCESS      read-only
          STATUS      mandatory
          DESCRIPTION
             "The call status is shown here."
          ::= { ty1250CallTable 1 }
 
ty1250CallNumber    OBJECT-TYPE
          SYNTAX      DisplayString (SIZE(0..20))
          ACCESS      read-write
          STATUS      mandatory
          DESCRIPTION
             "The last phone number dialed out."
          ::= { ty1250CallTable 2 }
 
ty1250CallUpTime    OBJECT-TYPE
          SYNTAX      TimeTicks
          ACCESS      read-only
          STATUS      mandatory
          DESCRIPTION
             "Number of seconds the call has been up."
          ::= { ty1250CallTable 3 }


--
--       The Diagnostics/Unit Table
--              This table contains the objects for unit level diagnostics
--              on the 1250 DDS DSU.

ty1250DiagUnitTable OBJECT IDENTIFIER ::= { ty1250 10 }

ty1250DiagUnitLocLoop OBJECT-TYPE
          SYNTAX      INTEGER 
          {
               enable-loopback-mode  (1),
               disable-loopback-mode (2)
          }
          ACCESS      read-write
          STATUS      mandatory
          DESCRIPTION
             "Enables the operator to control and examine the 
             UNIT local loopback.  This loopback occurs on
             all network ports transmit and receive logic.
             The unit will transmit DTE data out to the network
             as normal, and will also loop DTE data back to
             the DTE."
          ::= { ty1250DiagUnitTable 1 }

ty1250DiagUnitReset OBJECT-TYPE
          SYNTAX      INTEGER 
          {
               reset-unit (1)
          }
          ACCESS      write-only
          STATUS      mandatory
          DESCRIPTION
             "Enables the operator to remotely reset the unit.
              Using this command will cause the unit to terminate
              all its connections and drop data."
          ::= { ty1250DiagUnitTable 2 }


--
--       The Diagnostics/Net Table
--              This table contains the objects for Network port diagnostics
--              on the 1250 DDS DSU.

ty1250DiagNetTable  OBJECT IDENTIFIER ::= { ty1250 11 }

ty1250DiagNetLineStatus   OBJECT-TYPE
          SYNTAX      INTEGER 
          {
               in-sync (1),
               out-of-service (2),
               out-of-frame (3),
               bpv-threshold-failure (4),
               loss-of-signal (5),
               simplex-current-loopback (6)
          }
          ACCESS      read-only
          STATUS      mandatory
          DESCRIPTION
             "The Current status of the physical interface.
              Your network carrier can send Out-of-Service 
              or Maintenance Mode codes."
          ::= { ty1250DiagNetTable 1 }

ty1250DiagNetLclLpbk  OBJECT-TYPE
          SYNTAX      INTEGER
          {
               enable-loopback-mode  (1),
               disable-loopback-mode (2)
          }
          ACCESS      read-write
          STATUS      mandatory
          DESCRIPTION
             "Enables the operator to control and examine the 
             network local loopback.  This loopback occurs on
             the net side of the local transmit and receive 
             logic.  The unit continues to receive data from
             the network and also loops received data back to
             the network."
          ::= { ty1250DiagNetTable 2 }

ty1250DiagNetRmtLpbk  OBJECT-TYPE
          SYNTAX      INTEGER
          {
               no-loop-from-remote  (1),
               simplex-current-loop (2),
               non-latching-loop    (3)
          }
          ACCESS      read-only
          STATUS      mandatory
          DESCRIPTION
             "Enables the operator to examine (ONLY) the 
             status of network loopbacks placed by external
             equipment, such as your local CO.  These loopbacks
             will loop received network data back out the 
             network, disconnecting the DTE completely."
          ::= { ty1250DiagNetTable 3 }


--
--       The Diagnostics/Dte Table
--              This table contains the objects for DTE port diagnostics
--              on the 1250 DDS DSU.

ty1250DiagDteTable     OBJECT IDENTIFIER ::= { ty1250 12 }

ty1250DiagDteSigRTS OBJECT-TYPE
          SYNTAX      INTEGER 
          {
               rts-signal-on  (1),
               rts-signal-off (2)
          }
          ACCESS      read-only
          STATUS      mandatory
          DESCRIPTION
             "The Dte Channel RTS signal.  Values are
              rts-signal-on (1) and rts-signal-off (2)."
          ::= { ty1250DiagDteTable 1 }

ty1250DiagDteSigDTR OBJECT-TYPE
          SYNTAX      INTEGER 
          {
               dtr-signal-on  (1),
               dtr-signal-off (2)
          }
          ACCESS      read-only
          STATUS      mandatory
          DESCRIPTION
             "The Dte Channel DTR signal.
              Values are dtr-signal-on (1) and dtr-signal-off (2)."
          ::= { ty1250DiagDteTable 2 }

ty1250DiagDteLclLpbk OBJECT-TYPE
          SYNTAX      INTEGER
          {
               enable-loopback-mode (1),
               disable-loopback-mode (2)
          }
          ACCESS      read-write
          STATUS      mandatory
          DESCRIPTION
             "This selection displays the status or controls the
             Local DTE Channel Loopback for the selected channel. 
             This is will loop DTE data back towards the DTE interface
             in addition to passing it on to the network."
          ::= { ty1250DiagDteTable 5 }

ty1250DiagDteV54Lpbk   OBJECT-TYPE
          SYNTAX      INTEGER
          {
               loopback-enable (1),
               loopback-disable (2)
          }
          ACCESS      read-only
          STATUS      mandatory
          DESCRIPTION
             "This selection displays the status of the DTE Channel
             V.54 Loopback for the channel.  This loopback is
             initiated by the remote node, causing this node to loop
             data back to the remote node." 
          ::= { ty1250DiagDteTable 6 }

ty1250DiagDteRmtV54Lpbk   OBJECT-TYPE
          SYNTAX      INTEGER
          {
               transmit-code-enable  (3),
               transmit-code-disable (4)
          }
          ACCESS      write-only
          STATUS      mandatory
          DESCRIPTION
             "This selection controls the DTE Channel V.54 Remote Loopback.
             Transmit-code-enable (3) will cause the node to transmit 
             a V.54 code to the remote node which will then loop
             received data back to this node.  transmit-code-disable (4)
             will transmit the disable code." 
          ::= { ty1250DiagDteTable 13 }

ty1250DiagDteBerState   OBJECT-TYPE
          SYNTAX      INTEGER
          {
               start-bert-test (1),
               stop-bert-test (2),
               inject-error-bert-test (3),
               clear-error-bert-test (4)
          }
          ACCESS      write-only
          STATUS      mandatory
          DESCRIPTION
             "BERT test related actions:
             a: Starts a BERT test on a channel,
             b: Stops a BERT test on a channel,
             c: Inject Errors while the BERT test is running,
             d: Clears BERT test errors."
          ::= { ty1250DiagDteTable 7 }

ty1250DiagDteBerStatus  OBJECT-TYPE
          SYNTAX      INTEGER 
          {
               bert-off         (1),
               bert-out-of-sync (2),
               bert-in-sync     (3)
          }
          ACCESS      read-only
          STATUS      mandatory
          DESCRIPTION
             "Displays the current BERT test sync status."
          ::= { ty1250DiagDteTable 8 }

ty1250DiagDteBerErrors   OBJECT-TYPE
          SYNTAX      Counter
          ACCESS      read-only
          STATUS      mandatory
          DESCRIPTION
             "Displays the number of errors detected in Bert Test."
          ::= { ty1250DiagDteTable 9 }

ty1250DiagDteBerErrSec OBJECT-TYPE
          SYNTAX      Counter
          ACCESS      read-only
          STATUS      mandatory
          DESCRIPTION
             "Displays the number of seconds containing errors
              in BERT Test."
          ::= { ty1250DiagDteTable 10 }

ty1250DiagDteBerTimeElaps OBJECT-TYPE
          SYNTAX      TimeTicks
          ACCESS      read-only
          STATUS      mandatory
          DESCRIPTION
             "Elapsed time since BERT test was started or cleared."
          ::= { ty1250DiagDteTable 11 }

ty1250DiagDteBerResyncs OBJECT-TYPE
          SYNTAX      Counter
          ACCESS      read-only
          STATUS      mandatory
          DESCRIPTION
             "Displays the number of times BERT test has synched up
              on the pattern."
          ::= { ty1250DiagDteTable 12 }


--
--       The DTE Statistics Table
--              This table contains the Statistics for the DTE.

ty1250StatsDteTable   OBJECT IDENTIFIER ::= { ty1250 15 }

ty1250StatsDteTxByteCount    OBJECT-TYPE
          SYNTAX      INTEGER
          ACCESS      read-only
          STATUS      mandatory
          DESCRIPTION
             "The statistic counting the number of bytes transmitted
              on the DTE channel." 
          ::= { ty1250StatsDteTable 1 }

ty1250StatsDteRxByteCount    OBJECT-TYPE
          SYNTAX      INTEGER
          ACCESS      read-only
          STATUS      mandatory
          DESCRIPTION
             "The statistic counting the number of bytes received
              on the DTE channel." 
          ::= { ty1250StatsDteTable 2 }

ty1250StatsDteClearStats    OBJECT-TYPE
          SYNTAX      INTEGER
          {
              clear-statistics (1)
          }
          ACCESS      write-only
          STATUS      mandatory
          DESCRIPTION
             "Allows the user to zero out all the statistics in
              the DTE statistics table."
          ::= { ty1250StatsDteTable 3 }


--
--       The NET Statistics Table
--              This table contains the Statistics for the network port.

ty1250StatsNetTable   OBJECT IDENTIFIER ::= { ty1250 16 }

ty1250StatsNetLoopLength    OBJECT-TYPE
          SYNTAX      INTEGER
          ACCESS      read-only
          STATUS      mandatory
          DESCRIPTION
             "The statistic that estimates line attentuation
              on the network channel." 
          ::= { ty1250StatsNetTable 1 }

ty1250StatsNetBpvCount    OBJECT-TYPE
          SYNTAX      INTEGER
          ACCESS      read-only
          STATUS      mandatory
          DESCRIPTION
             "The statistic counting the number of BPV errors
              on the network channel." 
          ::= { ty1250StatsNetTable 2 }

ty1250StatsNetTxByteCount    OBJECT-TYPE
          SYNTAX      INTEGER
          ACCESS      read-only
          STATUS      mandatory
          DESCRIPTION
             "The statistic counting the number of bytes transmitted
              on the network channel." 
          ::= { ty1250StatsNetTable 3 }

ty1250StatsNetRxByteCount    OBJECT-TYPE
          SYNTAX      INTEGER
          ACCESS      read-only
          STATUS      mandatory
          DESCRIPTION
             "The statistic counting the number of bytes received
              on the network channel." 
          ::= { ty1250StatsNetTable 4 }

ty1250StatsNetClearStats    OBJECT-TYPE
          SYNTAX      INTEGER
          {
              clear-statistics (1)
          }
          ACCESS      write-only
          STATUS      mandatory
          DESCRIPTION
             "Allows the user to zero out all the statistics in
              the network statistics table."
          ::= { ty1250StatsNetTable 5 }



-- =========================
-- ==        TRAPS        ==
-- =========================
--
--       The Alarm (Trap) table for the 1250.
--              This table contains definitions for enterprise specific traps
--              associated with the 1250 DDS DSU.
ty1250AlarmType     OBJECT-TYPE
          SYNTAX      INTEGER
          {
               line-failure (1),
               line-in-service (2),
               connected (3),
               connect-failure (4),
               incoming-call (5),
               disconnected (6),
               bad-config-in-set (7),
               config-local-update (8),
               bpv-threshold-exceeded (9),
               bpv-threshold-acceptable (10),
               local-unit-loopback-enabled (11),
               local-unit-loopback-disabled (12),
               local-network-loopback-enabled (13),
               local-network-loopback-disabled (14),
               remote-network-simplex-loopback-enabled (15),
               remote-network-simplex-loopback-disabled (16),
               remote-network-non-latching-loopback-enabled (17),
               remote-network-non-latching-loopback-disabled (18),
               v54-loop-up-initiated (19),
               v54-loop-down-completed (20),
               v54-loopback-enabled-by-remote (21),
               v54-loopback-disabled-by-remote (22),
               bert-test-pattern-initiated (23),
               bert-test-pattern-completed (24),
               local-dte-loopback-enabled (25),
               local-dte-loopback-disabled (26),
               local-unit-loopback-failure (27),
               local-network-loopback-failure (28),
               bert-test-pattern-failure (29),
               local-dte-loopback-failure (30),
               v54-loopback-failure (31)
          }
          ACCESS      read-only
          STATUS      mandatory
          DESCRIPTION
             "The type of alarms that are generated on the node"
          ::= { ty1250 13 }

ty1250Trap          TRAP-TYPE
          ENTERPRISE  ty1250
          VARIABLES   
          { 
               ty1250AlarmType
          }
          DESCRIPTION
             "A ty1250Trap trap signifies that the
             sending node had its `ty1250AlarmType`
             variable modified."
          ::= 0

ty1250LineFailureTrap          TRAP-TYPE
          ENTERPRISE  ty1250
          VARIABLES   
          { 
               ty1250AlarmType
          }
          DESCRIPTION
             "The line has failed."
          ::= 1

ty1250LineInServiceTrap          TRAP-TYPE
          ENTERPRISE  ty1250
          VARIABLES   
          { 
               ty1250AlarmType
          }
          DESCRIPTION
             "The line is back in service."
          ::= 2

ty1250ConnectedTrap          TRAP-TYPE
          ENTERPRISE  ty1250
          VARIABLES   
          { 
               ty1250AlarmType
          }
          DESCRIPTION
             "The 1250 unit is connected."
          ::= 3

ty1250ConnectFailureTrap          TRAP-TYPE
          ENTERPRISE  ty1250
          VARIABLES   
          { 
               ty1250AlarmType
          }
          DESCRIPTION
             "The attempted connection failed."
          ::= 4

ty1250IncomingCallTrap          TRAP-TYPE
          ENTERPRISE  ty1250
          VARIABLES   
          { 
               ty1250AlarmType
          }
          DESCRIPTION
             "Incoming call."
          ::= 5

ty1250DisconnectedTrap          TRAP-TYPE
          ENTERPRISE  ty1250
          VARIABLES   
          { 
               ty1250AlarmType
          }
          DESCRIPTION
             "Disconnected."
          ::= 6

ty1250BadConfigTrap          TRAP-TYPE
          ENTERPRISE  ty1250
          VARIABLES   
          { 
               ty1250AlarmType
          }
          DESCRIPTION
             "The configuration specified in the
              SET command was bad.  SET failed."
          ::= 7

ty1250LocalConfigTrap          TRAP-TYPE
          ENTERPRISE  ty1250
          VARIABLES   
          { 
               ty1250AlarmType
          }
          DESCRIPTION
             "The configuration has been changed
              by a means other than SNMP."
          ::= 8

ty1250BPVThresholdExceededTrap          TRAP-TYPE
          ENTERPRISE  ty1250
          VARIABLES   
          { 
               ty1250AlarmType
          }
          DESCRIPTION
             "BPV threshold exceeded."
          ::= 9

ty1250BPVThresholdAcceptableTrap          TRAP-TYPE
          ENTERPRISE  ty1250
          VARIABLES   
          { 
               ty1250AlarmType
          }
          DESCRIPTION
             "BPV threshold acceptable."
          ::= 10

ty1250LocalUnitLoopbackEnabledTrap          TRAP-TYPE
          ENTERPRISE  ty1250
          VARIABLES   
          { 
               ty1250AlarmType
          }
          DESCRIPTION
             "Local unit loopback enabled."
          ::= 11

ty1250LocalUnitLoopbackDisabledTrap          TRAP-TYPE
          ENTERPRISE  ty1250
          VARIABLES   
          { 
               ty1250AlarmType
          }
          DESCRIPTION
             "Local unit loopback disabled."
          ::= 12

ty1250LocalNetLoopbackEnabledTrap          TRAP-TYPE
          ENTERPRISE  ty1250
          VARIABLES   
          { 
               ty1250AlarmType
          }
          DESCRIPTION
             "Local network loopback enabled."
          ::= 13

ty1250LocalNetLoopbackDisabledTrap          TRAP-TYPE
          ENTERPRISE  ty1250
          VARIABLES   
          { 
               ty1250AlarmType
          }
          DESCRIPTION
             "Local network loopback disabled."
          ::= 14

ty1250SimplexCurrentLoopbackEnabledTrap          TRAP-TYPE
          ENTERPRISE  ty1250
          VARIABLES   
          { 
               ty1250AlarmType
          }
          DESCRIPTION
             "Simplex current loopback enabled."
          ::= 15

ty1250SimplexCurrentLoopbackDisabledTrap          TRAP-TYPE
          ENTERPRISE  ty1250
          VARIABLES   
          { 
               ty1250AlarmType
          }
          DESCRIPTION
             "Simplex current loopback disabled."
          ::= 16

ty1250NonLatchingLoopbackEnabledTrap          TRAP-TYPE
          ENTERPRISE  ty1250
          VARIABLES   
          { 
               ty1250AlarmType
          }
          DESCRIPTION
             "Nonlatching loopback enabled."
          ::= 17

ty1250NonLatchingLoopbackDisabledTrap          TRAP-TYPE
          ENTERPRISE  ty1250
          VARIABLES   
          { 
               ty1250AlarmType
          }
          DESCRIPTION
             "Nonlatching loopback disabled."
          ::= 18

ty1250V54LoopUpInitiatedTrap          TRAP-TYPE
          ENTERPRISE  ty1250
          VARIABLES   
          { 
               ty1250AlarmType
          }
          DESCRIPTION
             "Starting to loop up a V54 loopback on the remote unit."
          ::= 19

ty1250V54LoopDownCompletedTrap          TRAP-TYPE
          ENTERPRISE  ty1250
          VARIABLES   
          { 
               ty1250AlarmType
          }
          DESCRIPTION
             "Completed the loop down of a V54 loopback on the remote unit."
          ::= 20

ty1250V54LoopbackEnabledTrap          TRAP-TYPE
          ENTERPRISE  ty1250
          VARIABLES   
          { 
               ty1250AlarmType
          }
          DESCRIPTION
             "V54 loopback enabled by remote unit."
          ::= 21

ty1250V54LoopbackDisabledTrap          TRAP-TYPE
          ENTERPRISE  ty1250
          VARIABLES   
          { 
               ty1250AlarmType
          }
          DESCRIPTION
             "V54 loopback disabled by remote unit."
          ::= 22

ty1250BertInitiatedTrap          TRAP-TYPE
          ENTERPRISE  ty1250
          VARIABLES   
          { 
               ty1250AlarmType
          }
          DESCRIPTION
             "BERT test pattern initiated."
          ::= 23

ty1250BertCompletedTrap          TRAP-TYPE
          ENTERPRISE  ty1250
          VARIABLES   
          { 
               ty1250AlarmType
          }
          DESCRIPTION
             "BERT test pattern completed."
          ::= 24

ty1250LocalDteLoopbackEnabledTrap          TRAP-TYPE
          ENTERPRISE  ty1250
          VARIABLES   
          { 
               ty1250AlarmType
          }
          DESCRIPTION
             "Local DTE loopback enabled."
          ::= 25

ty1250LocalDteLoopbackDisabledTrap          TRAP-TYPE
          ENTERPRISE  ty1250
          VARIABLES   
          { 
               ty1250AlarmType
          }
          DESCRIPTION
             "Local DTE loopback disabled."
          ::= 26

ty1250LocalUnitLoopbackFailedTrap          TRAP-TYPE
          ENTERPRISE  ty1250
          VARIABLES   
          { 
               ty1250AlarmType
          }
          DESCRIPTION
             "Unable to do a local unit loopback."
          ::= 27

ty1250LocalNetLoopbackFailedTrap          TRAP-TYPE
          ENTERPRISE  ty1250
          VARIABLES   
          { 
               ty1250AlarmType
          }
          DESCRIPTION
             "Unable to do a local network loopback."
          ::= 28

ty1250BertFailedTrap          TRAP-TYPE
          ENTERPRISE  ty1250
          VARIABLES   
          { 
               ty1250AlarmType
          }
          DESCRIPTION
             "Unable to do a BERT."
          ::= 29

ty1250LocalDteLoopbackFailedTrap          TRAP-TYPE
          ENTERPRISE  ty1250
          VARIABLES   
          { 
               ty1250AlarmType
          }
          DESCRIPTION
             "Unable to do a local DTE loopback."
          ::= 30

ty1250V54LoopbackFailedTrap          TRAP-TYPE
          ENTERPRISE  ty1250
          VARIABLES   
          { 
               ty1250AlarmType
          }
          DESCRIPTION
             "Unable to do a V54 loopback."
          ::= 31

END
