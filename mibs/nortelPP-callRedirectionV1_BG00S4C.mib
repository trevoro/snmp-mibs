Nortel-Magellan-Passport-CallRedirectionMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      Integer32,
      Unsigned32
   FROM Nortel-Magellan-Passport-StandardTextualConventionsMIB

      AsciiString,
      NonReplicated,
      Link,
      AsciiStringIndex
   FROM Nortel-Magellan-Passport-TextualConventionsMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     CallRedirection Enterprise MIB."

callRedirectionMIB OBJECT IDENTIFIER ::= { passportMIBs 132 }










-- CallRedirectionServer
-- The CallRedirectionServer component provides a set of alternate 
-- destinations for an original address. The alternate destination could 
-- be DPRS routing information (that is, RID/MID) or up to seven 
-- addresses.

crs OBJECT IDENTIFIER ::= { components 132 }



crsRowStatusTable OBJECT-TYPE
   SYNTAX     SEQUENCE OF CrsRowStatusEntry
   ACCESS     not-accessible
   STATUS     mandatory
   DESCRIPTION
     "This entry controls the addition and deletion of 
      crs components."
::= { crs 1 }

crsRowStatusEntry OBJECT-TYPE
   SYNTAX     CrsRowStatusEntry
   ACCESS     not-accessible
   STATUS     mandatory
   DESCRIPTION
     "A single entry in the table represents a single 
      crs component."
   INDEX {
      crsIndex }
::= { crsRowStatusTable 1 }

CrsRowStatusEntry ::= SEQUENCE {
   crsRowStatus
      RowStatus,
   crsComponentName
      DisplayString,
   crsStorageType
      StorageType,
   crsIndex
      NonReplicated }

crsRowStatus OBJECT-TYPE
   SYNTAX     RowStatus 
   ACCESS     read-write
   STATUS     mandatory
   DESCRIPTION
     "This variable is used as the basis for SNMP naming of
      crs components.
      These components can be added and deleted."
::= { crsRowStatusEntry 1 }

crsComponentName OBJECT-TYPE
   SYNTAX     DisplayString 
   ACCESS     read-only
   STATUS     mandatory
   DESCRIPTION
     "This variable provides the component's string name for
      use with the ASCII Console Interface"
::= { crsRowStatusEntry 2 }

crsStorageType OBJECT-TYPE
   SYNTAX     StorageType 
   ACCESS     read-only
   STATUS     mandatory
   DESCRIPTION
     "This variable represents the storage type value for the
      crs tables."
::= { crsRowStatusEntry 4 }

crsIndex OBJECT-TYPE
   SYNTAX     NonReplicated 
   ACCESS     not-accessible
   STATUS     mandatory
   DESCRIPTION
     "This variable represents the index for the crs tables."
::= { crsRowStatusEntry 10 }

crsProvTable OBJECT-TYPE
   SYNTAX     SEQUENCE OF CrsProvEntry
   ACCESS     not-accessible
   STATUS     mandatory
   DESCRIPTION
     "The Provisioned group contains provisionable attributes of the 
      CallRedirectionServer component."
::= { crs 10 }

crsProvEntry OBJECT-TYPE
   SYNTAX     CrsProvEntry
   ACCESS     not-accessible
   STATUS     mandatory
   DESCRIPTION
     "An entry in the crsProvTable."
   INDEX {
      crsIndex }
::= { crsProvTable 1 }

CrsProvEntry ::= SEQUENCE {
   crsLogicalProcessor
      Link }

crsLogicalProcessor OBJECT-TYPE
   SYNTAX     Link 
   ACCESS     read-write
   STATUS     mandatory
   DESCRIPTION
     "This attribute specifies the logical processor on which the call 
      redirection server process is to run."
::= { crsProvEntry 2 }

crsStateTable OBJECT-TYPE
   SYNTAX     SEQUENCE OF CrsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { crs 11 }

crsStateEntry OBJECT-TYPE
   SYNTAX     CrsStateEntry
   ACCESS     not-accessible
   STATUS     mandatory
   DESCRIPTION
     "An entry in the crsStateTable."
   INDEX {
      crsIndex }
::= { crsStateTable 1 }

CrsStateEntry ::= SEQUENCE {
   crsAdminState
      INTEGER,
   crsOperationalState
      INTEGER,
   crsUsageState
      INTEGER }

crsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { crsStateEntry 1 }

crsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { crsStateEntry 2 }

crsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { crsStateEntry 3 }

crsStatTable OBJECT-TYPE
   SYNTAX     SEQUENCE OF CrsStatEntry
   ACCESS     not-accessible
   STATUS     mandatory
   DESCRIPTION
     "The Statistics operational group defines the statistics associated 
      with the CallRedirectionServer component."
::= { crs 12 }

crsStatEntry OBJECT-TYPE
   SYNTAX     CrsStatEntry
   ACCESS     not-accessible
   STATUS     mandatory
   DESCRIPTION
     "An entry in the crsStatTable."
   INDEX {
      crsIndex }
::= { crsStatTable 1 }

CrsStatEntry ::= SEQUENCE {
   crsTotalAddresses
      Unsigned32,
   crsRequestsReceived
      Counter32,
   crsPrimaryMatches
      Counter32,
   crsSecAddressListExhausted
      Counter32,
   crsMaxAddrLenExceeded
      Counter32,
   crsSecRidMidUnsuccessful
      Counter32,
   crsSecAddrUnsuccessful
      Counter32,
   crsRidRedirected
      Counter32,
   crsRidMidRedirected
      Counter32,
   crsAddressRedirected
      Counter32,
   crsAltRidUnsuccessful
      Counter32 }

crsTotalAddresses OBJECT-TYPE
   SYNTAX     Unsigned32 (0..4294967295)
   ACCESS     read-only
   STATUS     mandatory
   DESCRIPTION
     "The totalAddresses attribute indicates the number of 
      PrimaryAddress components associated with the 
      CallRedirectionServer component."
   DEFVAL     { 0 }
::= { crsStatEntry 2 }

crsRequestsReceived OBJECT-TYPE
   SYNTAX     Counter32 
   ACCESS     read-only
   STATUS     mandatory
   DESCRIPTION
     "The requestsReceived attribute counts the number of redirection 
      requests received by the CallRedirectionServer component. This 
      counter wraps to 0 when it exceeds its maximum value."
::= { crsStatEntry 3 }

crsPrimaryMatches OBJECT-TYPE
   SYNTAX     Counter32 
   ACCESS     read-only
   STATUS     mandatory
   DESCRIPTION
     "The primaryMatches attribute counts the Call Redirection Server 
      attempts to find a matching PrimaryAddress where the lookup 
      attempt was successful. This counter wraps to 0 when it exceeds its 
      maximum value."
::= { crsStatEntry 4 }

crsSecAddressListExhausted OBJECT-TYPE
   SYNTAX     Counter32 
   ACCESS     read-only
   STATUS     mandatory
   DESCRIPTION
     "The secAddressListExhausted attribute counts the Call Redirection 
      Server attempts to find a SecondaryAddress component given a 
      PrimaryAddress component where the lookup attempt resulted in 
      the exhaustion of the secondary redirection list. This counter wraps 
      to 0 when it exceeds its maximum value."
::= { crsStatEntry 5 }

crsMaxAddrLenExceeded OBJECT-TYPE
   SYNTAX     Counter32 
   ACCESS     read-only
   STATUS     mandatory
   DESCRIPTION
     "The maxAddrLenExceeded attribute counts how often the 
      concatenation of the secondary address and the suffix digits from 
      the original called address have exceeded the maximum of 15 
      digits.
      The suffix digits can be determined by removing the primary 
      address digits from the front of the original called address.
      If appending the suffix digits to a secondary address causes the 
      resulting address to exceed 15 digits, this secondary member is 
      skipped and the next secondary member is tried."
::= { crsStatEntry 6 }

crsSecRidMidUnsuccessful OBJECT-TYPE
   SYNTAX     Counter32 
   ACCESS     read-only
   STATUS     mandatory
   DESCRIPTION
     "The secRidMidUnsuccessful attribute counts the number of RID/
      MID redirections resulting in the destination address not being 
      reached. This situation could occur when the destination address 
      does not exist on the specified module or the specified module could 
      not be reached."
::= { crsStatEntry 7 }

crsSecAddrUnsuccessful OBJECT-TYPE
   SYNTAX     Counter32 
   ACCESS     read-only
   STATUS     mandatory
   DESCRIPTION
     "The secAddrUnsuccessful attribute counts the number of Address 
      redirections resulting in the destination user not being reached. This 
      situation could occur when the destination user line is disabled, the 
      destination address does not exist on the specified module, or the 
      specified module could not be reached."
::= { crsStatEntry 8 }

crsRidRedirected OBJECT-TYPE
   SYNTAX     Counter32 
   ACCESS     read-only
   STATUS     mandatory
   DESCRIPTION
     "The ridRedirected attribute counts requests received by the Call 
      Redirection Server resulting in the request being redirected to 
      another RID specified by the AlternateRid component. This counter 
      wraps to 0 when it exceeds its maximum value."
::= { crsStatEntry 9 }

crsRidMidRedirected OBJECT-TYPE
   SYNTAX     Counter32 
   ACCESS     read-only
   STATUS     mandatory
   DESCRIPTION
     "The ridMidRedirected attribute counts requests received by the Call 
      Redirection Server resulting in the request being redirected to 
      another RID/MID specified by the SecondaryRidMid component. 
      This counter wraps to 0 when it exceeds its maximum value."
::= { crsStatEntry 10 }

crsAddressRedirected OBJECT-TYPE
   SYNTAX     Counter32 
   ACCESS     read-only
   STATUS     mandatory
   DESCRIPTION
     "The addressRedirected attribute counts requests received by the 
      Call Redirection Server resulting in the request being redirected to 
      another Address specified by the SecondaryAddress component. 
      This counter wraps to 0 when it exceeds its maximum value."
::= { crsStatEntry 11 }

crsAltRidUnsuccessful OBJECT-TYPE
   SYNTAX     Counter32 
   ACCESS     read-only
   STATUS     mandatory
   DESCRIPTION
     "The altRidUnsuccessful attribute counts the number of RID 
      redirections resulting in the destination address not being reached. 
      This situation could occur when the alternate RID cannot be 
      reached, the module hosting the destination address is isolated, or 
      the port associated with the secondary address is unavailable at the 
      alternate RID."
::= { crsStatEntry 12 }


-- Crs PrimaryAddress/<address>
-- The PrimaryAddress component defines a primary address for 
-- which a list of alternate destinations are specified. This primary 
-- address has either a secondary RID/MID destination or up to seven 
-- secondary addresses associated with it.
-- A primary address matches the original destination address if, 
-- beginning with the most significant digit, all digits are identical and 
-- the primary address is less than or equal to the original destination 
-- address in length. The "best match" is the longest such primary 
-- address.
-- The PrimaryAddress component instance value takes the form:
-- x.<X.121 address> or e.<E.164 address>

crsPAddr OBJECT IDENTIFIER ::= { crs 2 }



crsPAddrRowStatusTable OBJECT-TYPE
   SYNTAX     SEQUENCE OF CrsPAddrRowStatusEntry
   ACCESS     not-accessible
   STATUS     mandatory
   DESCRIPTION
     "This entry controls the addition and deletion of 
      crsPAddr components."
::= { crsPAddr 1 }

crsPAddrRowStatusEntry OBJECT-TYPE
   SYNTAX     CrsPAddrRowStatusEntry
   ACCESS     not-accessible
   STATUS     mandatory
   DESCRIPTION
     "A single entry in the table represents a single 
      crsPAddr component."
   INDEX {
      crsIndex,
      crsPAddrIndex }
::= { crsPAddrRowStatusTable 1 }

CrsPAddrRowStatusEntry ::= SEQUENCE {
   crsPAddrRowStatus
      RowStatus,
   crsPAddrComponentName
      DisplayString,
   crsPAddrStorageType
      StorageType,
   crsPAddrIndex
      AsciiStringIndex }

crsPAddrRowStatus OBJECT-TYPE
   SYNTAX     RowStatus 
   ACCESS     read-write
   STATUS     mandatory
   DESCRIPTION
     "This variable is used as the basis for SNMP naming of
      crsPAddr components.
      These components can be added and deleted."
::= { crsPAddrRowStatusEntry 1 }

crsPAddrComponentName OBJECT-TYPE
   SYNTAX     DisplayString 
   ACCESS     read-only
   STATUS     mandatory
   DESCRIPTION
     "This variable provides the component's string name for
      use with the ASCII Console Interface"
::= { crsPAddrRowStatusEntry 2 }

crsPAddrStorageType OBJECT-TYPE
   SYNTAX     StorageType 
   ACCESS     read-only
   STATUS     mandatory
   DESCRIPTION
     "This variable represents the storage type value for the
      crsPAddr tables."
::= { crsPAddrRowStatusEntry 4 }

crsPAddrIndex OBJECT-TYPE
   SYNTAX     AsciiStringIndex (SIZE (1..17))
   ACCESS     not-accessible
   STATUS     mandatory
   DESCRIPTION
     "This variable represents the index for the crsPAddr tables."
::= { crsPAddrRowStatusEntry 10 }


-- Crs Paddr/<address> SecondaryRidMid
-- The SecondaryRidMid component identifies an alternate destination 
-- module on which the primary address is also supported. RID/MID 
-- redirection allows the call redirection server to effectively override 
-- the original destination identified by the call routing system and 
-- forward the call to a different module.

crsPAddrSRidMid OBJECT IDENTIFIER ::= { crsPAddr 2 }



crsPAddrSRidMidRowStatusTable OBJECT-TYPE
   SYNTAX     SEQUENCE OF CrsPAddrSRidMidRowStatusEntry
   ACCESS     not-accessible
   STATUS     mandatory
   DESCRIPTION
     "This entry controls the addition and deletion of 
      crsPAddrSRidMid components."
::= { crsPAddrSRidMid 1 }

crsPAddrSRidMidRowStatusEntry OBJECT-TYPE
   SYNTAX     CrsPAddrSRidMidRowStatusEntry
   ACCESS     not-accessible
   STATUS     mandatory
   DESCRIPTION
     "A single entry in the table represents a single 
      crsPAddrSRidMid component."
   INDEX {
      crsIndex,
      crsPAddrIndex,
      crsPAddrSRidMidIndex }
::= { crsPAddrSRidMidRowStatusTable 1 }

CrsPAddrSRidMidRowStatusEntry ::= SEQUENCE {
   crsPAddrSRidMidRowStatus
      RowStatus,
   crsPAddrSRidMidComponentName
      DisplayString,
   crsPAddrSRidMidStorageType
      StorageType,
   crsPAddrSRidMidIndex
      NonReplicated }

crsPAddrSRidMidRowStatus OBJECT-TYPE
   SYNTAX     RowStatus 
   ACCESS     read-write
   STATUS     mandatory
   DESCRIPTION
     "This variable is used as the basis for SNMP naming of
      crsPAddrSRidMid components.
      These components can be added and deleted."
::= { crsPAddrSRidMidRowStatusEntry 1 }

crsPAddrSRidMidComponentName OBJECT-TYPE
   SYNTAX     DisplayString 
   ACCESS     read-only
   STATUS     mandatory
   DESCRIPTION
     "This variable provides the component's string name for
      use with the ASCII Console Interface"
::= { crsPAddrSRidMidRowStatusEntry 2 }

crsPAddrSRidMidStorageType OBJECT-TYPE
   SYNTAX     StorageType 
   ACCESS     read-only
   STATUS     mandatory
   DESCRIPTION
     "This variable represents the storage type value for the
      crsPAddrSRidMid tables."
::= { crsPAddrSRidMidRowStatusEntry 4 }

crsPAddrSRidMidIndex OBJECT-TYPE
   SYNTAX     NonReplicated 
   ACCESS     not-accessible
   STATUS     mandatory
   DESCRIPTION
     "This variable represents the index for the crsPAddrSRidMid tables."
::= { crsPAddrSRidMidRowStatusEntry 10 }

crsPAddrSRidMidRidMidProvTable OBJECT-TYPE
   SYNTAX     SEQUENCE OF CrsPAddrSRidMidRidMidProvEntry
   ACCESS     not-accessible
   STATUS     mandatory
   DESCRIPTION
     "The SecRidMidProv group defines the secondary RID/MID pair 
      associated with a specific primary address."
::= { crsPAddrSRidMid 10 }

crsPAddrSRidMidRidMidProvEntry OBJECT-TYPE
   SYNTAX     CrsPAddrSRidMidRidMidProvEntry
   ACCESS     not-accessible
   STATUS     mandatory
   DESCRIPTION
     "An entry in the crsPAddrSRidMidRidMidProvTable."
   INDEX {
      crsIndex,
      crsPAddrIndex,
      crsPAddrSRidMidIndex }
::= { crsPAddrSRidMidRidMidProvTable 1 }

CrsPAddrSRidMidRidMidProvEntry ::= SEQUENCE {
   crsPAddrSRidMidRoutingId
      Unsigned32,
   crsPAddrSRidMidModuleId
      Unsigned32 }

crsPAddrSRidMidRoutingId OBJECT-TYPE
   SYNTAX     Unsigned32 (1..126)
   ACCESS     read-write
   STATUS     mandatory
   DESCRIPTION
     "This attribute specifies a group of one or more interconnected nodes 
      (called a subnet) to which the primary address is redirected."
::= { crsPAddrSRidMidRidMidProvEntry 2 }

crsPAddrSRidMidModuleId OBJECT-TYPE
   SYNTAX     Unsigned32 (1..1909)
   ACCESS     read-write
   STATUS     mandatory
   DESCRIPTION
     "This attribute specifies a Passport node to which the primary 
      address is redirected."
::= { crsPAddrSRidMidRidMidProvEntry 3 }


-- Crs Paddr/<address> SecondaryAddress/n
-- The SecondaryAddress component identifies an alternate destination 
-- address. Address redirection allows the call redirection server to 
-- effectively override the original destination address and forward the 
-- call to a different destination within the Passport network. 

crsPAddrSAddr OBJECT IDENTIFIER ::= { crsPAddr 3 }



crsPAddrSAddrRowStatusTable OBJECT-TYPE
   SYNTAX     SEQUENCE OF CrsPAddrSAddrRowStatusEntry
   ACCESS     not-accessible
   STATUS     mandatory
   DESCRIPTION
     "This entry controls the addition and deletion of 
      crsPAddrSAddr components."
::= { crsPAddrSAddr 1 }

crsPAddrSAddrRowStatusEntry OBJECT-TYPE
   SYNTAX     CrsPAddrSAddrRowStatusEntry
   ACCESS     not-accessible
   STATUS     mandatory
   DESCRIPTION
     "A single entry in the table represents a single 
      crsPAddrSAddr component."
   INDEX {
      crsIndex,
      crsPAddrIndex,
      crsPAddrSAddrIndex }
::= { crsPAddrSAddrRowStatusTable 1 }

CrsPAddrSAddrRowStatusEntry ::= SEQUENCE {
   crsPAddrSAddrRowStatus
      RowStatus,
   crsPAddrSAddrComponentName
      DisplayString,
   crsPAddrSAddrStorageType
      StorageType,
   crsPAddrSAddrIndex
      Integer32 }

crsPAddrSAddrRowStatus OBJECT-TYPE
   SYNTAX     RowStatus 
   ACCESS     read-write
   STATUS     mandatory
   DESCRIPTION
     "This variable is used as the basis for SNMP naming of
      crsPAddrSAddr components.
      These components can be added and deleted."
::= { crsPAddrSAddrRowStatusEntry 1 }

crsPAddrSAddrComponentName OBJECT-TYPE
   SYNTAX     DisplayString 
   ACCESS     read-only
   STATUS     mandatory
   DESCRIPTION
     "This variable provides the component's string name for
      use with the ASCII Console Interface"
::= { crsPAddrSAddrRowStatusEntry 2 }

crsPAddrSAddrStorageType OBJECT-TYPE
   SYNTAX     StorageType 
   ACCESS     read-only
   STATUS     mandatory
   DESCRIPTION
     "This variable represents the storage type value for the
      crsPAddrSAddr tables."
::= { crsPAddrSAddrRowStatusEntry 4 }

crsPAddrSAddrIndex OBJECT-TYPE
   SYNTAX     Integer32 (1..7)
   ACCESS     not-accessible
   STATUS     mandatory
   DESCRIPTION
     "This variable represents the index for the crsPAddrSAddr tables."
::= { crsPAddrSAddrRowStatusEntry 10 }

crsPAddrSAddrSecAddrProvTable OBJECT-TYPE
   SYNTAX     SEQUENCE OF CrsPAddrSAddrSecAddrProvEntry
   ACCESS     not-accessible
   STATUS     mandatory
   DESCRIPTION
     "The SecAddrProv group defines one of the secondary addresses 
      associated with a specific primary address."
::= { crsPAddrSAddr 10 }

crsPAddrSAddrSecAddrProvEntry OBJECT-TYPE
   SYNTAX     CrsPAddrSAddrSecAddrProvEntry
   ACCESS     not-accessible
   STATUS     mandatory
   DESCRIPTION
     "An entry in the crsPAddrSAddrSecAddrProvTable."
   INDEX {
      crsIndex,
      crsPAddrIndex,
      crsPAddrSAddrIndex }
::= { crsPAddrSAddrSecAddrProvTable 1 }

CrsPAddrSAddrSecAddrProvEntry ::= SEQUENCE {
   crsPAddrSAddrAddress
      AsciiString }

crsPAddrSAddrAddress OBJECT-TYPE
   SYNTAX     AsciiString (SIZE (1..17))
   ACCESS     read-write
   STATUS     mandatory
   DESCRIPTION
     "This attribute specifies a secondary address to which the primary 
      address is redirected. 
      The address attribute includes the Numbering Plan Indicator (NPI) 
      and the digits which form a unique identifier of the customer 
      interface. The address may belong to the X.121 or E.164 addressing 
      plan. Address digits are selected and assigned by network operators. 
      The address attribute takes the form:
      x.<X.121 address> or e.<E.164 address>"
::= { crsPAddrSAddrSecAddrProvEntry 3 }


-- Crs AlternateRid
-- The AlternateRid component defines the routing identifier value that 
-- is used as the alternate DPRS routing information when routing to 
-- the RID specified by the Call Router (CR) is unsuccessful. This 
-- component should only be provisioned as a temporary 
-- measure.When activated the RID redirection feature as significant 
-- impact on the normal redirection operation, since RID redirection is 
-- always attempted first.
-- One of the possible application of this feature being RID splitting, 
-- the AlternateRid component should be deleted as soon as all module 
-- have been migrated from their original RID and the Call Router 
-- (CR) throughout the network have been updated with the new RID 
-- information. 

crsAltRid OBJECT IDENTIFIER ::= { crs 3 }



crsAltRidRowStatusTable OBJECT-TYPE
   SYNTAX     SEQUENCE OF CrsAltRidRowStatusEntry
   ACCESS     not-accessible
   STATUS     mandatory
   DESCRIPTION
     "This entry controls the addition and deletion of 
      crsAltRid components."
::= { crsAltRid 1 }

crsAltRidRowStatusEntry OBJECT-TYPE
   SYNTAX     CrsAltRidRowStatusEntry
   ACCESS     not-accessible
   STATUS     mandatory
   DESCRIPTION
     "A single entry in the table represents a single 
      crsAltRid component."
   INDEX {
      crsIndex,
      crsAltRidIndex }
::= { crsAltRidRowStatusTable 1 }

CrsAltRidRowStatusEntry ::= SEQUENCE {
   crsAltRidRowStatus
      RowStatus,
   crsAltRidComponentName
      DisplayString,
   crsAltRidStorageType
      StorageType,
   crsAltRidIndex
      NonReplicated }

crsAltRidRowStatus OBJECT-TYPE
   SYNTAX     RowStatus 
   ACCESS     read-write
   STATUS     mandatory
   DESCRIPTION
     "This variable is used as the basis for SNMP naming of
      crsAltRid components.
      These components can be added and deleted."
::= { crsAltRidRowStatusEntry 1 }

crsAltRidComponentName OBJECT-TYPE
   SYNTAX     DisplayString 
   ACCESS     read-only
   STATUS     mandatory
   DESCRIPTION
     "This variable provides the component's string name for
      use with the ASCII Console Interface"
::= { crsAltRidRowStatusEntry 2 }

crsAltRidStorageType OBJECT-TYPE
   SYNTAX     StorageType 
   ACCESS     read-only
   STATUS     mandatory
   DESCRIPTION
     "This variable represents the storage type value for the
      crsAltRid tables."
::= { crsAltRidRowStatusEntry 4 }

crsAltRidIndex OBJECT-TYPE
   SYNTAX     NonReplicated 
   ACCESS     not-accessible
   STATUS     mandatory
   DESCRIPTION
     "This variable represents the index for the crsAltRid tables."
::= { crsAltRidRowStatusEntry 10 }

crsAltRidAltRidProvTable OBJECT-TYPE
   SYNTAX     SEQUENCE OF CrsAltRidAltRidProvEntry
   ACCESS     not-accessible
   STATUS     mandatory
   DESCRIPTION
     "The AltRidProv group defines the alternate RID associated with the 
      Crs component."
::= { crsAltRid 10 }

crsAltRidAltRidProvEntry OBJECT-TYPE
   SYNTAX     CrsAltRidAltRidProvEntry
   ACCESS     not-accessible
   STATUS     mandatory
   DESCRIPTION
     "An entry in the crsAltRidAltRidProvTable."
   INDEX {
      crsIndex,
      crsAltRidIndex }
::= { crsAltRidAltRidProvTable 1 }

CrsAltRidAltRidProvEntry ::= SEQUENCE {
   crsAltRidRoutingId
      Unsigned32 }

crsAltRidRoutingId OBJECT-TYPE
   SYNTAX     Unsigned32 (1..126)
   ACCESS     read-write
   STATUS     mandatory
   DESCRIPTION
     "This attribute specifies a group of one or more interconnected nodes 
      (called a subnet) to which the request is redirected."
::= { crsAltRidAltRidProvEntry 2 }




-- 
-- Version and Compliance statements
-- 



-- Object-Group Statement:
-- A list of all current accessible leaf objects.

-- OBJECTS { crsTotalAddresses,
--           crsPAddrRowStatus,
--           crsPAddrSRidMidRoutingId,
--           crsUsageState,
--           crsAltRidRoutingId,
--           crsOperationalState,
--           crsPAddrSRidMidModuleId,
--           crsComponentName,
--           crsRidMidRedirected,
--           crsRequestsReceived,
--           crsMaxAddrLenExceeded,
--           crsAddressRedirected,
--           crsStorageType,
--           crsAltRidRowStatus,
--           crsPAddrSAddrRowStatus,
--           crsAltRidStorageType,
--           crsPAddrComponentName,
--           crsPAddrSRidMidRowStatus,
--           crsPAddrStorageType,
--           crsLogicalProcessor,
--           crsAdminState,
--           crsSecAddrUnsuccessful,
--           crsAltRidUnsuccessful,
--           crsSecAddressListExhausted,
--           crsPAddrSAddrComponentName,
--           crsSecRidMidUnsuccessful,
--           crsRowStatus,
--           crsPAddrSRidMidComponentName,
--           crsPAddrSAddrStorageType,
--           crsAltRidComponentName,
--           crsRidRedirected,
--           crsPAddrSAddrAddress,
--           crsPrimaryMatches,
--           crsPAddrSRidMidStorageType }
-- STATUS  mandatory
-- DESCRIPTION
--   "A list of all current accessible leaf objects."

callRedirectionGroup OBJECT IDENTIFIER ::= { callRedirectionMIB 1 }
callRedirectionGroupBE OBJECT IDENTIFIER ::= { callRedirectionGroup 5 }
callRedirectionGroupBE01 OBJECT IDENTIFIER ::= { callRedirectionGroupBE 2 }
callRedirectionGroupBE01A OBJECT IDENTIFIER ::= { callRedirectionGroupBE01 2 }



-- Agent-Capabilities Statement:

-- PRODUCT-RELEASE "Passport Release 7.0 CallRedirection."
-- STATUS          mandatory
-- DESCRIPTION     "CallRedirection MIB: MIB Version BE01A,
--                  Software Version BG00S4C."
-- SUPPORTS        Nortel-Magellan-Passport-CallRedirectionMIB
--    INCLUDES     { callRedirectionGroupBE01A }

callRedirectionCapabilities OBJECT IDENTIFIER ::= { callRedirectionMIB 3 }
callRedirectionCapabilitiesBE OBJECT IDENTIFIER ::= { callRedirectionCapabilities 5 }
callRedirectionCapabilitiesBE01 OBJECT IDENTIFIER ::= { callRedirectionCapabilitiesBE 2 }
callRedirectionCapabilitiesBE01A OBJECT IDENTIFIER ::= { callRedirectionCapabilitiesBE01 2 }





END
