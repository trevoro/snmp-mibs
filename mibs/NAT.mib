-- size : 51k
-- Network Application Technology
--	Version 2.01  12-5-91
-- This file has complete NAT private mib's definitions in ASN.1 format

   NAT DEFINITIONS ::= BEGIN
	
IMPORTS
	Counter
		FROM RFC1155-SMI
	OBJECT-TYPE, enterprises, IpAddress, TimeTicks
		FROM SNMPv2-SMI
;

           -- common configuration for all NAT devices

		  nat 		OBJECT IDENTIFIER ::= { enterprises 86 }
		  products 	OBJECT IDENTIFIER ::= { nat 1 }
		  natmib	OBJECT IDENTIFIER ::= { nat 2 }
		  trapinfo	OBJECT IDENTIFIER ::= { nat 8 }

		  -- natBridge     OBJECT IDENTIFIER ::= { products 1 }
		  -- natEtherMeter OBJECT IDENTIFIER ::= { products 2 }
		  -- natRemBridge  OBJECT IDENTIFIER ::= { products 3 }
		  -- natIPRouter   OBJECT IDENTIFIER ::= { products 4 }

		  configuration	OBJECT IDENTIFIER ::= { natmib 1 }
		  natinf	OBJECT IDENTIFIER ::= { natmib 2 }
		  natopr	OBJECT IDENTIFIER ::= { natmib 3 }
		  natbrg	OBJECT IDENTIFIER ::= { natmib 4 }
		  natmtr	OBJECT IDENTIFIER ::= { natmib 5 }
		  natalert	OBJECT IDENTIFIER ::= { natmib 6 }
		  rmeter	OBJECT IDENTIFIER ::= { natmib 7 }
		  natrtr	OBJECT IDENTIFIER ::= { natmib 8 }
		  dialup	OBJECT IDENTIFIER ::= { natmib 9 }
		
		  -- object types

		  -- the configuration group, supported by all NAT devices

                  cfFirmware OBJECT-TYPE
                          SYNTAX  OCTET STRING
                          ACCESS  read-only
                          STATUS  mandatory
                          ::= { configuration 1 }

                  -- the community string table

                  cfCmstrTable OBJECT-TYPE
                          SYNTAX  SEQUENCE OF CfCmstrEntry
                          ACCESS  read-only
                          STATUS  mandatory
                          ::= { configuration 2 }

                  cfCmstrEntry OBJECT-TYPE
                          SYNTAX  CfCmstrEntry
                          ACCESS  read-only
                          STATUS  mandatory
			  INDEX	  { INTEGER }
                          ::= { cfCmstrTable 1 }

                  CfCmstrEntry ::= SEQUENCE {
                      cfCmstrReadPublic
                          OCTET STRING,
                      cfCmstrReadEnterprise
                          OCTET STRING,
                      cfCmstrReadTrap
                          OCTET STRING,
                      cfCmstrReadWrite
                          OCTET STRING
                  }

                  cfCmstrReadPublic OBJECT-TYPE
                          SYNTAX  OCTET STRING
                          ACCESS  read-only
                          STATUS  mandatory
                          ::= { cfCmstrEntry 1 }

                  cfCmstrReadEnterprise OBJECT-TYPE
                          SYNTAX  OCTET STRING
                          ACCESS  read-only
                          STATUS  mandatory
                          ::= { cfCmstrEntry 2 }

                  cfCmstrReadTrap OBJECT-TYPE
                          SYNTAX  OCTET STRING
                          ACCESS  read-only
                          STATUS  mandatory
                          ::= { cfCmstrEntry 3 }

                  cfCmstrReadWrite OBJECT-TYPE
                          SYNTAX  OCTET STRING
                          ACCESS  read-only
                          STATUS  mandatory
                          ::= { cfCmstrEntry 4 }

                  -- the community string alias table

                  cfCmstrAliasTable OBJECT-TYPE
                          SYNTAX  SEQUENCE OF CfCmstrAliasEntry
                          ACCESS  read-write
                          STATUS  mandatory
                          ::= { configuration 3 }

                  cfCmstrAliasEntry OBJECT-TYPE
                          SYNTAX  CfCmstrAliasEntry
                          ACCESS  read-write
                          STATUS  mandatory
			  INDEX	  { INTEGER }
                          ::= { cfCmstrAliasTable 1 }

                  CfCmstrAliasEntry ::= SEQUENCE {
                      cfCmstrAliasReadPublic
                          OCTET STRING,
                      cfCmstrAliasReadEnterprise
                          OCTET STRING,
                      cfCmstrAliasReadTrap
                          OCTET STRING,
                      cfCmstrAliasReadWrite
                          OCTET STRING
                  }

                  cfCmstrAliasReadPublic OBJECT-TYPE
                          SYNTAX  OCTET STRING
                          ACCESS  read-write
                          STATUS  mandatory
                          ::= { cfCmstrAliasEntry 1 }

                  cfCmstrAliasReadEnterprise OBJECT-TYPE
                          SYNTAX  OCTET STRING
                          ACCESS  read-write
                          STATUS  mandatory
                          ::= { cfCmstrAliasEntry 2 }

                  cfCmstrAliasReadTrap OBJECT-TYPE
                          SYNTAX  OCTET STRING
                          ACCESS  read-write
                          STATUS  mandatory
                          ::= { cfCmstrAliasEntry 3 }

                  cfCmstrAliasReadWrite OBJECT-TYPE
                          SYNTAX  OCTET STRING
                          ACCESS  read-write
                          STATUS  mandatory
                          ::= { cfCmstrAliasEntry 4 }


                  -- the access host table

                  cfAcchostTable OBJECT-TYPE
                          SYNTAX  SEQUENCE OF CfAccHostEntry
                          ACCESS  read-only
                          STATUS  mandatory
                          ::= { configuration 4 }

                  cfAcchostEntry OBJECT-TYPE
                          SYNTAX  CfAccHostEntry
                          ACCESS  read-only
                          STATUS  mandatory
			  INDEX	  { INTEGER }
                          ::= { cfAcchostTable 1 }

                  CfAccHostEntry ::= SEQUENCE {
                      cfAcchostHostIP
                          IpAddress,
                      cfAcchostLevel
                          INTEGER
                  }

                  cfAcchostHostIP OBJECT-TYPE
                          SYNTAX  IpAddress
                          ACCESS  read-only
                          STATUS  mandatory
                          ::= { cfAcchostEntry 1 }

                  cfAcchostLevel OBJECT-TYPE
                          SYNTAX  INTEGER {
			  	readstandard(1),
			  	readenterprise(2),
			  	trap(3),
			  	readwrite(4),
			  	readwriteenterprise(5)
			  }	
                          ACCESS  read-only
                          STATUS  mandatory
                          ::= { cfAcchostEntry 2 }

                  cfDenyReadPublic OBJECT-TYPE
                          SYNTAX  INTEGER {
			  	off(0),
				on(1)		-- deny standard read
			  }	
                          ACCESS  read-write
                          STATUS  mandatory
                          ::= { configuration 5 }

                  cfDevIPAddr OBJECT-TYPE
                          SYNTAX IpAddress 
                          ACCESS  read-write
                          STATUS  mandatory
                          ::= { configuration 6 }

                  cfSubnetMask OBJECT-TYPE
                          SYNTAX IpAddress 
                          ACCESS  read-write
                          STATUS  mandatory
                          ::= { configuration 7 }

                  -- the configurable access host table

                  cfAcchostCfgTable OBJECT-TYPE
                          SYNTAX  SEQUENCE OF CfAccHostCfgEntry
                          ACCESS  read-write
                          STATUS  mandatory
                          ::= { configuration 8 }

                  cfAcchostCfgEntry OBJECT-TYPE
                          SYNTAX  CfAccHostCfgEntry
                          ACCESS  read-write
                          STATUS  mandatory
			  INDEX	  { IpAddress }
                          ::= { cfAcchostCfgTable 1 }

                  CfAccHostCfgEntry ::= SEQUENCE {
                      cfAcchostcfgAcclvl
                         INTEGER 
                  }

                  cfAcchostCfgAcclvl OBJECT-TYPE
                          SYNTAX  INTEGER {
				cfDelet(0),
			  	cfAddReadStd(1),
			  	cfAddReadEnterprise(2),
			  	cfAddTrap(3),
			  	cfAddReadwrite(4)
			  }	
                          ACCESS  read-write
                          STATUS  mandatory
                          ::= { cfAcchostCfgEntry 1 }

                  cfParmsSave OBJECT-TYPE
                          SYNTAX  INTEGER {
				cfClear(0),
				cfStore(1)
			  }
                          ACCESS  read-write
                          STATUS  mandatory
                          ::= { configuration 9 }

                  cfPassword OBJECT-TYPE
                          SYNTAX  OCTET STRING
                          ACCESS  write-only
                          STATUS  mandatory
                          ::= { configuration 10 }

                  cfIPAddr2 OBJECT-TYPE
                          SYNTAX IpAddress 
                          ACCESS  read-write
                          STATUS  mandatory
                          ::= { configuration 11 }

                  cfSubnetMask2 OBJECT-TYPE
                          SYNTAX IpAddress 
                          ACCESS  read-write
                          STATUS  mandatory
                          ::= { configuration 12 }

		  -- the interfaces group, supported by all NAT devices
		  -- the statistics table
		  
                  statsTable OBJECT-TYPE
                          SYNTAX  SEQUENCE OF StatsEntry
                          ACCESS  read-write
                          STATUS  mandatory
                          ::= { natinf 1 }

                  statsEntry OBJECT-TYPE
                          SYNTAX  StatsEntry
                          ACCESS  read-write
                          STATUS  mandatory
			  INDEX	  { INTEGER }
                          ::= { statsTable 1 }

		  StatsEntry ::= SEQUENCE {
		  	statsReset
				INTEGER,
			statsResetTime
				TimeTicks,
			statsRcvpkts
				Counter,
			statsFwdpkts
				Counter,
			statsBufOvflows
				Counter,
			statsCrcs
				Counter,
			statsAlgns
				Counter,
			statsCntlOvflows
				Counter,
			statsXmtColls
				Counter,
			statsBlkDiscards
				Counter,
			statsPassDIscards
				Counter,
			statsFwdMultiPkts
				Counter,
			statsKbytes
                          	Counter,
			statsBcastPkts
                          	Counter,
			statsMcastPkts
                          	Counter,
			statsSize64-127Pkts
                          	Counter,
			statsSize128-255Pkts
                          	Counter,
			statsSize256-511Pkts
                          	Counter,
			statsSize512-1023Pkts
                          	Counter,
			statsSize1024-1518Pkts
                          	Counter,
			statsShortPkts
                          	Counter,
			statsOvsizePkts
                          	Counter
		  }		

                  statsReset OBJECT-TYPE
                          SYNTAX  INTEGER
                          ACCESS  read-write
                          STATUS  mandatory
                          ::= { statsEntry 1 }

		  statsResetTime OBJECT-TYPE
			  SYNTAX TimeTicks
			  ACCESS read-only
			  STATUS mandatory
			  ::= { statsEntry 2 }

                  statsRcvpkts OBJECT-TYPE
                          SYNTAX  Counter
                          ACCESS  read-only
                          STATUS  mandatory
                          ::= { statsEntry 3 }

                  statsFwdpkts OBJECT-TYPE
                          SYNTAX  Counter
                          ACCESS  read-only
                          STATUS  mandatory
                          ::= { statsEntry 4 }

                  statsBufOvflows OBJECT-TYPE
                          SYNTAX  Counter
                          ACCESS  read-only
                          STATUS  mandatory
                          ::= { statsEntry 5 }

                  statsCrcs OBJECT-TYPE
                          SYNTAX  Counter
                          ACCESS  read-only
                          STATUS  mandatory
                          ::= { statsEntry 6 }

                  statsAlgns OBJECT-TYPE
                          SYNTAX  Counter
                          ACCESS  read-only
                          STATUS  mandatory
                          ::= { statsEntry 7 }

                  statsCntlOvflows OBJECT-TYPE
                          SYNTAX  Counter
                          ACCESS  read-only
                          STATUS  mandatory
                          ::= { statsEntry 8 }

                  statsXmtColls OBJECT-TYPE
                          SYNTAX  Counter
                          ACCESS  read-only
                          STATUS  mandatory
                          ::= { statsEntry 9 }

                  statsBlkDiscards OBJECT-TYPE
                          SYNTAX  Counter
                          ACCESS  read-only
                          STATUS  mandatory
                          ::= { statsEntry 10 }

                  statsPassDiscards OBJECT-TYPE
                          SYNTAX  Counter
                          ACCESS  read-only
                          STATUS  mandatory
                          ::= { statsEntry 11 }

		  statsFwdMultiPkts OBJECT-TYPE
			  SYNTAX  Counter
			  ACCESS  read-only
			  STATUS  mandatory
			  ::= { statsEntry 12 }

		  -- Meter specific mibs

                  statsKbytes OBJECT-TYPE
                          SYNTAX  Counter
                          ACCESS  read-only
                          STATUS  mandatory
                          ::= { statsEntry 13 }

                  statsBcastPkts OBJECT-TYPE
                          SYNTAX  Counter
                          ACCESS  read-only
                          STATUS  mandatory
                          ::= { statsEntry 14 }

                  statsMcastPkts OBJECT-TYPE
                          SYNTAX  Counter
                          ACCESS  read-only
                          STATUS  mandatory
                          ::= { statsEntry 15 }

                  statsSize64-127Pkts OBJECT-TYPE
                          SYNTAX  Counter
                          ACCESS  read-only
                          STATUS  mandatory
                          ::= { statsEntry 16 }

                  statsSize128-255Pkts OBJECT-TYPE
                          SYNTAX  Counter
                          ACCESS  read-only
                          STATUS  mandatory
                          ::= { statsEntry 17 }

                  statsSize256-511Pkts OBJECT-TYPE
                          SYNTAX  Counter
                          ACCESS  read-only
                          STATUS  mandatory
                          ::= { statsEntry 18 }

                  statsSize512-1023Pkts OBJECT-TYPE
                          SYNTAX  Counter
                          ACCESS  read-only
                          STATUS  mandatory
                          ::= { statsEntry 19 }

                  statsSize1024-1518Pkts OBJECT-TYPE
                          SYNTAX  Counter
                          ACCESS  read-only
                          STATUS  mandatory
                          ::= { statsEntry 20 }

                  statsShortPkts OBJECT-TYPE
                          SYNTAX  Counter
                          ACCESS  read-only
                          STATUS  mandatory
                          ::= { statsEntry 21 }

                  statsOvsizePkts OBJECT-TYPE
                          SYNTAX  Counter
                          ACCESS  read-only
                          STATUS  mandatory
                          ::= { statsEntry 22 }


		  -- the operation group, supported by all NAT devices

                  opSysReset OBJECT-TYPE
                          SYNTAX  INTEGER
                          ACCESS  read-write
                          STATUS  mandatory
                          ::= { natopr 1 }

                  opNoStatColl OBJECT-TYPE
                          SYNTAX  INTEGER {
			  	off(0),
				on(1)
			  }
                          ACCESS  read-write
                          STATUS  mandatory
                          ::= { natopr 2 }

                  opTrapInact OBJECT-TYPE
                          SYNTAX  INTEGER {
			  	off(0),
				on(1)
			  }
                          ACCESS  read-write
                          STATUS  mandatory
                          ::= { natopr 3 }


	        -- the trap Info


		 trapSrcAddr OBJECT-TYPE
		  	  SYNTAX IpAddress
			  ACCESS read-only
			  STATUS mandatory
			  ::= { trapinfo 1 }

		 trapErrMsg OBJECT-TYPE
		  	  SYNTAX OCTET STRING
			  ACCESS read-only
			  STATUS mandatory
			  ::= { trapinfo 2 }


         -- NAT bridge group, supported by NAT bridge product family

		--  the local learned table

                  lanTable OBJECT-TYPE
                          SYNTAX  SEQUENCE OF LanEntry
                          ACCESS  read-only
                          STATUS  mandatory
                          ::= { natbrg 1 }

                  lanEntry OBJECT-TYPE
                          SYNTAX  LanEntry
                          ACCESS  read-only
                          STATUS  mandatory
			  INDEX   { lanPhyAddr }
                          ::= { lanTable 1 }

		  LanEntry ::= SEQUENCE {
		  	lanIfIndex
				INTEGER,
			lanPhyAddr
				OCTET STRING
		  }		


                  lanIfIndex OBJECT-TYPE
                          SYNTAX  INTEGER
                          ACCESS  read-only
                          STATUS  mandatory
                          ::= { lanEntry 1 }

                  lanPhyAddr OBJECT-TYPE
                          SYNTAX  OCTET STRING
                          ACCESS  read-only
                          STATUS  mandatory
                          ::= { lanEntry 2 }

		--  the block table

                  blanTable OBJECT-TYPE
		  	  SYNTAX  SEQUENCE OF BlanEntry
                          ACCESS  read-write
                          STATUS  mandatory
                          ::= { natbrg 2 }

                  blanEntry OBJECT-TYPE
                          SYNTAX  BlanEntry
                          ACCESS  read-write
                          STATUS  mandatory
			  INDEX   { blanIfIndex, blanOffset, blanPtrn }
                          ::= { blanTable 1 }

		  BlanEntry ::= SEQUENCE {
		  	blanIfIndex
				INTEGER,
			blanOffset
				INTEGER,
			blanLength
				INTEGER,
			blanPtrn
				OCTET STRING
		  }		


                  blanIfIndex OBJECT-TYPE
                          SYNTAX  INTEGER
                          ACCESS  read-only
                          STATUS  mandatory
                          ::= { blanEntry 1 }

                  blanOffset OBJECT-TYPE
                          SYNTAX  INTEGER
                          ACCESS  read-only
                          STATUS  mandatory
                          ::= { blanEntry 2 }

                  blanLength OBJECT-TYPE
                          SYNTAX  INTEGER
                          ACCESS  read-write
                          STATUS  mandatory
                          ::= { blanEntry 3 }

                  blanPtrn OBJECT-TYPE
                          SYNTAX  OCTET STRING
                          ACCESS  read-only
                          STATUS  mandatory
                          ::= { blanEntry 4 }


		--  the pass table

                  planTable OBJECT-TYPE
                          SYNTAX  SEQUENCE OF PlanEntry
                          ACCESS  read-write
                          STATUS  mandatory
                          ::= { natbrg 3 }

                  planEntry OBJECT-TYPE
                          SYNTAX  PlanEntry
                          ACCESS  read-write
                          STATUS  mandatory
			  INDEX   { planIfIndex, planOffset, planPtrn }
                          ::= { planTable 1 }

		  PlanEntry ::= SEQUENCE {
		  	planIfIndex
				INTEGER,
			planOffset
				INTEGER,
			planLength
				INTEGER,
			planPtrn
				OCTET STRING
		  }		


                  planIfIndex OBJECT-TYPE
                          SYNTAX  INTEGER
                          ACCESS  read-only
                          STATUS  mandatory
                          ::= { planEntry 1 }

                  planOffset OBJECT-TYPE
                          SYNTAX  INTEGER
                          ACCESS  read-only
                          STATUS  mandatory
                          ::= { planEntry 2 }

                  planLength OBJECT-TYPE
                          SYNTAX  INTEGER
                          ACCESS  read-write
                          STATUS  mandatory
                          ::= { planEntry 3 }

                  planPtrn OBJECT-TYPE
                          SYNTAX  OCTET STRING
                          ACCESS  read-only
                          STATUS  mandatory
                          ::= { planEntry 4 }

		  lanTblFlush OBJECT-TYPE
			  SYNTAX  INTEGER
			  ACCESS  read-write
			  STATUS  mandatory
			  ::= { natbrg 4 }

                  brgState OBJECT-TYPE
                          SYNTAX  INTEGER {
			  	init(0),
				backup(1),
				forwarding(2),
				idle(3),
				serial-handshake(4)
			  }
                          ACCESS  read-only
                          STATUS  mandatory
                          ::= { natbrg 5 }


         -- NAT EtherMeter group, supported by NAT EtherMeter product family

		-- the E-type data

                  etypeInfo OBJECT IDENTIFIER ::= { natmtr 1 }

                  etypeTypes OBJECT-TYPE
                          SYNTAX  Counter
                          ACCESS  read-only
                          STATUS  mandatory
                          ::= { etypeInfo 1 }

                  etypeTable OBJECT-TYPE
                          SYNTAX  SEQUENCE OF EtypeTblEntry
                          ACCESS  read-only
                          STATUS  mandatory
                          ::= { etypeInfo 2 }

                  etypeTblEntry OBJECT-TYPE
                          SYNTAX  EtypeTblEntry
                          ACCESS  read-only
                          STATUS  mandatory
			  INDEX   { INTEGER }
                          ::= { etypeTable 1 }

		  EtypeTblEntry ::= SEQUENCE {
		  	etypeEtype
				INTEGER,
			etypePkts
				Counter
		  }		

                  etypeEtype OBJECT-TYPE
                          SYNTAX  INTEGER {
			  	veeco(32871),
				gd(32872),
				xrx-PUP(512),      
				atandt(32873),         
				xrx-PUPUT(513),
				autophon(32874),
				comdesign(32876),    
				xns-IDP(1536),
				compuGraphic(32877),
				lg(32878),           
				lg-1(32879),           
				dod-TCPIP(2048),    
				xdot75-IP(2049),
				ung-DB(2304),       
				lg-2(32880),           
				xrx-PUP2(2560),     
				nbs-IP(2050),       
				lg-3(32881),           
				xrx-PUPAT2(2561),
				lg-4(32882),           
				ecma-IP(2051),      
				lg-5(32883),           
				chaosnet(2052),     
				xdot25-LEV3(2053),    
				lg-6(32884),           
				tcpip-ARP(2054),    
				lg-7(32885),           
				xrx-XNS(2055),      
				lg-8(32886),           
				lg-9(32887),           
				berk-IP-0(4096),    
				berk-IP-1(4097),    
				berk-IP-2(4098),    
				matra(32890),        
				berk-IP-3(4099),    
				vit-B-MAN(32896),    
				dansk(32891),        
				berk-IP-4(4100),    
				mrt-I-NODAL(32892),  
				cc(32897),           
				berk-IP-5(4101),    
				vitalink(32893),     
				valid-MH(5632),     
				cc-1(32898),           
				berk-IP-6(4102),    
				vitalink-1(32894),     
				cc-2(32899),           
				berk-IP-7(4103),    
				vitalink-2(32895),     
				berk-IP-8(4104),    
				bbn-VITA(65280),     
				berk-IP-9(4105),    
				berk-IP-10(4106),    
				berk-IP-11(4107),    
				berk-IP-12(4108),    
				berk-IP-13(4109),    
				berk-IP-14(4110),    
				berk-IP-15(4111),    
				symbolics(2076),    
				appletlk(32923),     
				datability(32924),   
				datability-1(32925),   
				datability-2(32926),   
				spider(32927),       
				nixdorf(32931),      
				siemens(32932),      
				siemens-1(32933),      
				siemens-2(32934),      
				siemens-3(32935),      
				siemens-4(32936),      
				siemens-5(32937),      
				siemens-6(32938),      
				siemens-7(32939),      
				siemens-8(32940),      
				siemens-9(32941),      
				siemens-10(32942),      
				siemens-11(32943),      
				nbp(15367),          
				siemens-12(32944),      
				siemens-13(32945),      
				siemens-14(32946),      
				dca-MULTI(4660),    
				siemens-15(32947),      
				dca-HELLO(32960),    
				dca-TALK1(32961),    
				dca-TALK2(32962),    
				dca(32963),          
				pacer(32966),        
				bbn-SIMNET(21000),   
				applitek(32967),     
				integraph(32968),    
				integraph-1(32969),    
				integraph-2(32970),    
				integraph-3(32971),    
				integraph-4(32972),    
				dec-C-UA1(24576),    
				harris(32973),       
				dec-C-MOPDL(24577),  
				harris-1(32974),       
				dec-C-MOPRC(24578),  
				taylor(32975),       
				taylor-1(32976),       
				dec-C-NET(24579),    
				thd-DIDDLE(17185),   
				dec-C-LAT(24580),    
				taylor-2(32977),       
				dec-C-DIAG(24581),   
				taylor-3(32978),       
				dec-C-USE(24582),    
				rosemount(32979),    
				dec-C-LAVC(24583),   
				rosemount-1(32980),    
				dec-C-UA2(24584),    
				dec-C-UA3(24585),    
				ung-BASSO(28672),    
				three-COM(24592),        
				varian(32989),       
				ung-BASS1(28673),    
				three-COM-1(24593),        
				ung-BASS2(28674),    
				is-TRFS(32990),      
				three-COM-2(24594),        
				is(32991),           
				three-COM-3(24595),        
				ab(32992),           
				three-COM-4(24596),        
				ung-BASS5(28677),    
				ab-1(32993),           
				ab-2(32994),           
				os9net-1(28679),     
				ab-3(32995),           
				datability-3(32996),   
				os9net-2(28681),     
				datability-4(32997),   
				datability-5(32998),   
				datability-6(32999),   
				datability-7(33000),   
				datability-8(33001),   
				datability-9(33002),   
				datability-10(33003),   
				datability-11(33004),   
				datability-12(33005),   
				datability-13(33006),   
				datability-14(33007),   
				datability-15(33008),   
				retix(33010),        
				apple-TSS(33011),    
				kinetics(33012),     
				kinetics-1(33013),     
				apollo(33015),       
				lrt(28704),          
				lrt-1(28705),          
				lrt-2(28706),          
				wellfleet(33023),    
				lrt-3(28707),          
				lrt-4(28708),          
				wellfleet-1(33024),    
				lrt-5(28709),          
				wellfleet-2(33025),    
				lrt-6(28710),          
				wellfleet-3(33026),    
				lrt-7(28711),          
				cron-VLN(32771),     
				wellfleet-4(33027),    
				lrt-8(28712),          
				cron-DIR(32772),     
				lrt-9(28713),          
				hp-PROBE(32773),     
				nestar(32774),       
				symbolics-1(33031),    
				atandt-1(32776),         
				symbolics-2(33032),    
				symbolics-3(33033),    
				proteon(28720),      
				xyplex(2184),       
				loopback(36864),     
				excelan(32784),      
				xyplex-1(2185),       
				brg-BRG1(36865),     
				xyplex-2(2186),       
				brg-BRG2(36866),     
				sg-DIAG(32787),      
				brg-BRG3(36867),     
				sg(32788),           
				sg-UA(32789),        
				sg-XNS(32790),       
				ap-DOMAIN(32793),    
				talaris(33067),      
				tymshare(32814),     
				tigan(32815),        
				waterloo(33072),     
				vg(33073),           
				rev-ARP(32821),      
				aeonic(32822),       
				novell(33079),       
				dec-BRIDGE(32824),   
				banyan(2989),       
				novell-1(33080),       
				dec-C-UA4(32825),    
				kti(33081),          
				dec-C-UA5(32826),    
				kti-1(33082),          
				dec-C-UA6(32827),    
				kti-2(33083),          
				dec-DNS(32828),      
				kti-3(33084),          
				dec-ENCRYP(32829),   
				kti-4(33085),          
				dec-C-UA9(32830),    
				dec-LTM(32831),      
				dec-PC-ENim(32832),  
				dec-MS-DOS(32833),   
				dec-C-UA13(32834),   
				prc(32836),          
				atandt-2(32838),         
				atandt-3(32839),         
				expertdata(32841),   
				stan-ESP(32859),     	
				stan-PRO(32860),     
				eands(32861),          
				lm(32864),           
				cc-3(32866),           
				um-AMH(32869),       
				um-AMH-1(32870),       
				mytype(39321)
                              }
                          ACCESS  read-only
                          STATUS  mandatory
                          ::= { etypeTblEntry 1 }

                  etypePkts OBJECT-TYPE
                          SYNTAX  Counter
                          ACCESS  read-only
                          STATUS  mandatory
                          ::= { etypeTblEntry 2 }

                  etypeOtherTypes OBJECT-TYPE
                          SYNTAX  Counter
                          ACCESS  read-only
                          STATUS  mandatory
                          ::= { etypeInfo 3 }

		-- the peak value data


                  peakInfo OBJECT IDENTIFIER ::= { natmtr 2 }


                  peakReset OBJECT-TYPE
                          SYNTAX  INTEGER
                          ACCESS  read-write
                          STATUS  mandatory
                          ::= { peakInfo 1 }
  

                  peakResetTime OBJECT-TYPE
                          SYNTAX  TimeTicks
                          ACCESS  read-only
                          STATUS  mandatory
                          ::= { peakInfo 2 }
  

                  peakSmplIntv OBJECT-TYPE
                          SYNTAX  INTEGER
                          ACCESS  read-write
                          STATUS  mandatory
                          ::= { peakInfo 3 }
  

                  peakData OBJECT IDENTIFIER ::= { peakInfo 4 }
  
		  peakFrameInfo OBJECT IDENTIFIER ::= { peakData 1 }
			  
		  peakFramePkts OBJECT-TYPE
			  SYNTAX Counter
			  ACCESS read-only
			  STATUS mandatory
			  ::= { peakFrameInfo 1 }

		  peakFrameTime OBJECT-TYPE
			  SYNTAX TimeTicks	
			  ACCESS read-only
			  STATUS mandatory
			  ::= { peakFrameInfo 2 }

  
		  peakFrameErrors OBJECT-TYPE
			  SYNTAX Counter
			  ACCESS read-only
			  STATUS mandatory
			  ::= { peakFrameInfo 3 }

  
                  peakKbyteInfo OBJECT IDENTIFIER ::= { peakData 2 }


		  peakKbytes OBJECT-TYPE
			  SYNTAX Counter
			  ACCESS read-only
			  STATUS mandatory
			  ::= { peakKbyteInfo 1 }

		  peakKbyteTime OBJECT-TYPE
			  SYNTAX TimeTicks	
			  ACCESS read-only
			  STATUS mandatory
			  ::= { peakKbyteInfo 2 }
  
		  peakKbyteTotalPkts OBJECT-TYPE
			  SYNTAX Counter
			  ACCESS read-only
			  STATUS mandatory
			  ::= { peakKbyteInfo 3 }

		  peakKbyteErrors OBJECT-TYPE
			  SYNTAX Counter
			  ACCESS read-only
			  STATUS mandatory
			  ::= { peakKbyteInfo 4 }

                  peakBcastInfo OBJECT IDENTIFIER ::= { peakData 3 }

  
		  peakBcastPkts OBJECT-TYPE
			  SYNTAX Counter
			  ACCESS read-only
			  STATUS mandatory
			  ::= { peakBcastInfo 1 }

		  peakBcastTime OBJECT-TYPE
			  SYNTAX TimeTicks	
			  ACCESS read-only
			  STATUS mandatory
			  ::= { peakBcastInfo 2 }

		  peakBcastTotalPkts OBJECT-TYPE
			  SYNTAX Counter
			  ACCESS read-only
			  STATUS mandatory
			  ::= { peakBcastInfo 3 }

		  peakBcastErrors OBJECT-TYPE
			  SYNTAX Counter
			  ACCESS read-only
			  STATUS mandatory
			  ::= { peakBcastInfo 4 }

                  peakMcastInfo OBJECT IDENTIFIER ::= { peakData 4 }

  
		  peakMcastPkts OBJECT-TYPE
			  SYNTAX Counter
			  ACCESS read-only
			  STATUS mandatory
			  ::= { peakMcastInfo 1 }

		  peakMcastTime OBJECT-TYPE
			  SYNTAX TimeTicks	
			  ACCESS read-only
			  STATUS mandatory
			  ::= { peakMcastInfo 2 }

		  peakMcastTotalPkts OBJECT-TYPE
			  SYNTAX Counter
			  ACCESS read-only
			  STATUS mandatory
			  ::= { peakMcastInfo 3 }

		  peakMcastErrors OBJECT-TYPE
			  SYNTAX Counter
			  ACCESS read-only
			  STATUS mandatory
			  ::= { peakMcastInfo 4 }

                  peakErrInfo OBJECT IDENTIFIER ::= { peakData 5 }

  
		  peakErrErrors OBJECT-TYPE
			  SYNTAX Counter
			  ACCESS read-only
			  STATUS mandatory
			  ::= { peakErrInfo 1 }

		  peakErrTime OBJECT-TYPE
			  SYNTAX TimeTicks	
			  ACCESS read-only
			  STATUS mandatory
			  ::= { peakErrInfo 2 }

		  peakErrTotalPkts OBJECT-TYPE
			  SYNTAX Counter
			  ACCESS read-only
			  STATUS mandatory
			  ::= { peakErrInfo 3 }

		  peakErrCrcs OBJECT-TYPE
			  SYNTAX Counter
			  ACCESS read-only
			  STATUS mandatory
			  ::= { peakErrInfo 4 }

		  peakErrAlgns OBJECT-TYPE
			  SYNTAX Counter
			  ACCESS read-only
			  STATUS mandatory
			  ::= { peakErrInfo 5 }

		  peakErrXmtColls OBJECT-TYPE
			  SYNTAX Counter
			  ACCESS read-only
			  STATUS mandatory
			  ::= { peakErrInfo 6 }

		  peakErrShorts OBJECT-TYPE
			  SYNTAX Counter
			  ACCESS read-only
			  STATUS mandatory
			  ::= { peakErrInfo 7 }

		  peakErrOvsizes OBJECT-TYPE
			  SYNTAX Counter
			  ACCESS read-only
			  STATUS mandatory
			  ::= { peakErrInfo 8 }

                  peakUtilInfo OBJECT IDENTIFIER ::= { peakData 6 }
	  

		  peakUtilVal OBJECT-TYPE
			  SYNTAX INTEGER	
			  ACCESS read-only
			  STATUS mandatory
			  ::= { peakUtilInfo 1 }

		  peakUtilTime OBJECT-TYPE
			  SYNTAX TimeTicks	
			  ACCESS read-only
			  STATUS mandatory
			  ::= { peakUtilInfo 2 }

		  peakUtilTotalPkts OBJECT-TYPE
			  SYNTAX Counter
			  ACCESS read-only
			  STATUS mandatory
			  ::= { peakUtilInfo 3 }

		  peakUtilErrors OBJECT-TYPE
			  SYNTAX Counter
			  ACCESS read-only
			  STATUS mandatory
			  ::= { peakUtilInfo 4 }

                  top10Info OBJECT IDENTIFIER ::= { natmtr 3 }

                  top10Enable OBJECT-TYPE
                          SYNTAX  INTEGER {
				off(0),
				ethernettalkerON(1),
				iptalkerON(2),
				ethernetlistenerON(3),
				iplistenerON(4),
				ethernetpairON(5),
				ippairON(6),
				ethernetbroadcasterON(7)
			  }
                          ACCESS  read-write
                          STATUS  mandatory
                          ::= { top10Info 1 }


                  top10ThresholdVal OBJECT-TYPE
                          SYNTAX  INTEGER
                          ACCESS  read-write
                          STATUS  mandatory
                          ::= { top10Info 2 }

                  top10SmplIntv OBJECT-TYPE
                          SYNTAX  INTEGER
                          ACCESS  read-write
                          STATUS  mandatory
                          ::= { top10Info 3 }

                  top10SeqNum OBJECT-TYPE
                          SYNTAX  INTEGER
                          ACCESS  read-only
                          STATUS  mandatory
                          ::= { top10Info 4 }

                  top10SmplTime OBJECT-TYPE
                          SYNTAX  TimeTicks
                          ACCESS  read-only
                          STATUS  mandatory
                          ::= { top10Info 5 }

                  top10TotalEntries OBJECT-TYPE
                          SYNTAX  Counter
                          ACCESS  read-only
                          STATUS  mandatory
                          ::= { top10Info 6 }

                  top10Ovflow OBJECT-TYPE
                          SYNTAX  INTEGER
                          ACCESS  read-only
                          STATUS  mandatory
                          ::= { top10Info 7 }

                  top10TotalPkts OBJECT-TYPE
                          SYNTAX  Counter
                          ACCESS  read-only
                          STATUS  mandatory
                          ::= { top10Info 8 }

                  top10MatchedPkts OBJECT-TYPE
                          SYNTAX  Counter
                          ACCESS  read-only
                          STATUS  mandatory
                          ::= { top10Info 9 }

                  top10ValidEntries OBJECT-TYPE
                          SYNTAX  Counter
                          ACCESS  read-only
                          STATUS  mandatory
                          ::= { top10Info 10 }

                  top10Data OBJECT IDENTIFIER ::= { top10Info 11 }


                  top10StrID OBJECT-TYPE
                          SYNTAX  OCTET STRING
                          ACCESS  read-only
                          STATUS  mandatory
                          ::= { top10Data 1 }

                  top10Pkts OBJECT-TYPE
                          SYNTAX  Counter 
                          ACCESS  read-only
                          STATUS  mandatory
                          ::= { top10Data 2 }


	        -- the alert group


                  alertParms OBJECT IDENTIFIER ::= { natalert 1 }

		  alertTypes OBJECT-TYPE
		  	  SYNTAX Counter
			  ACCESS read-only
			  STATUS mandatory
			  ::= { alertParms 1 }

		  alertSmplIntv OBJECT-TYPE
		  	  SYNTAX INTEGER
			  ACCESS read-write
			  STATUS mandatory
			  ::= { alertParms 2 }

		  alertReset OBJECT-TYPE
		  	  SYNTAX INTEGER 
			  ACCESS read-write
			  STATUS mandatory
			  ::= { alertParms 3 }

		  alertResetTime OBJECT-TYPE
		  	  SYNTAX TimeTicks
			  ACCESS read-only
			  STATUS mandatory
			  ::= { alertParms 4 }

                  alerts OBJECT IDENTIFIER ::= { natalert 2 }

                  alertFrameInfo OBJECT IDENTIFIER ::= { alerts 1 }

                  alertFrameEnable OBJECT-TYPE
                          SYNTAX  INTEGER {
			  	off(0),
				on(1)
			  }
                          ACCESS  read-write
                          STATUS  mandatory
                          ::= { alertFrameInfo 1 }

		  alertFrameThreshold OBJECT-TYPE
			  SYNTAX INTEGER
			  ACCESS read-write
			  STATUS mandatory
			  ::= { alertFrameInfo 2 }

		  alertFramePkts OBJECT-TYPE
			  SYNTAX Counter
			  ACCESS read-only
			  STATUS mandatory
			  ::= { alertFrameInfo 3 }

		  alertFrameTime OBJECT-TYPE
			  SYNTAX TimeTicks
			  ACCESS read-only
			  STATUS mandatory
			  ::= { alertFrameInfo 4 }

		  alertFrameTotalPkts OBJECT-TYPE
			  SYNTAX Counter
			  ACCESS read-only
			  STATUS mandatory
			  ::= { alertFrameInfo 5 }

		  alertFrameErrors OBJECT-TYPE
			  SYNTAX Counter
			  ACCESS read-only
			  STATUS mandatory
			  ::= { alertFrameInfo 6 }

                  alertBcastInfo OBJECT IDENTIFIER ::= { alerts 2 }

                  alertBcastEnable OBJECT-TYPE
                          SYNTAX  INTEGER {
			  	off(0),
				on(1)
			  }
                          ACCESS  read-write
                          STATUS  mandatory
                          ::= { alertBcastInfo 1 }

		  alertBcastThreshold OBJECT-TYPE
			  SYNTAX INTEGER
			  ACCESS read-write
			  STATUS mandatory
			  ::= { alertBcastInfo 2 }

		  alertBcastPkts OBJECT-TYPE
			  SYNTAX Counter
			  ACCESS read-only
			  STATUS mandatory
			  ::= { alertBcastInfo 3 }

		  alertBcastTime OBJECT-TYPE
			  SYNTAX TimeTicks
			  ACCESS read-only
			  STATUS mandatory
			  ::= { alertBcastInfo 4 }

		  alertBcastTotalPkts OBJECT-TYPE
			  SYNTAX Counter
			  ACCESS read-only
			  STATUS mandatory
			  ::= { alertBcastInfo 5 }

		  alertBcastErrors OBJECT-TYPE
			  SYNTAX Counter
			  ACCESS read-only
			  STATUS mandatory
			  ::= { alertBcastInfo 6 }

                  alertMcastInfo OBJECT IDENTIFIER ::= { alerts 3 }

                  alertMcastEnable OBJECT-TYPE
                          SYNTAX  INTEGER {
			  	off(0),
				on(1)
			  }
                          ACCESS  read-write
                          STATUS  mandatory
                          ::= { alertMcastInfo 1 }

		  alertMcastThreshold OBJECT-TYPE
			  SYNTAX INTEGER
			  ACCESS read-write
			  STATUS mandatory
			  ::= { alertMcastInfo 2 }

		  alertMcastPkts OBJECT-TYPE
			  SYNTAX Counter
			  ACCESS read-only
			  STATUS mandatory
			  ::= { alertMcastInfo 3 }

		  alertMcastTime OBJECT-TYPE
			  SYNTAX TimeTicks
			  ACCESS read-only
			  STATUS mandatory
			  ::= { alertMcastInfo 4 }

		  alertMcastTotalPkts OBJECT-TYPE
			  SYNTAX Counter
			  ACCESS read-only
			  STATUS mandatory
			  ::= { alertMcastInfo 5 }

		  alertMcastErrors OBJECT-TYPE
			  SYNTAX Counter
			  ACCESS read-only
			  STATUS mandatory
			  ::= { alertMcastInfo 6 }

                  alertErrInfo OBJECT IDENTIFIER ::= { alerts 4 }

                  alertErrEnable OBJECT-TYPE
                          SYNTAX  INTEGER {
			  	off(0),
				on(1)
			  }
                          ACCESS  read-write
                          STATUS  mandatory
                          ::= { alertErrInfo 1 }

		  alertErrThreshold OBJECT-TYPE
			  SYNTAX INTEGER
			  ACCESS read-write
			  STATUS mandatory
			  ::= { alertErrInfo 2 }

		  alertErrErrors OBJECT-TYPE
			  SYNTAX Counter
			  ACCESS read-only
			  STATUS mandatory
			  ::= { alertErrInfo 3 }

		  alertErrTime OBJECT-TYPE
			  SYNTAX TimeTicks
			  ACCESS read-only
			  STATUS mandatory
			  ::= { alertErrInfo 4 }

		  alertErrTotalPkts OBJECT-TYPE
			  SYNTAX Counter
			  ACCESS read-only
			  STATUS mandatory
			  ::= { alertErrInfo 5 }

		  alertErrTotalErrors OBJECT-TYPE
			  SYNTAX Counter
			  ACCESS read-only
			  STATUS mandatory
			  ::= { alertErrInfo 6 }

		  alertErrCrcs OBJECT-TYPE
			  SYNTAX Counter
			  ACCESS read-only
			  STATUS mandatory
			  ::= { alertErrInfo 7 }

		  alertErrAlgns OBJECT-TYPE
			  SYNTAX Counter
			  ACCESS read-only
			  STATUS mandatory
			  ::= { alertErrInfo 8 }

		  alertErrXmtColls OBJECT-TYPE
			  SYNTAX Counter
			  ACCESS read-only
			  STATUS mandatory
			  ::= { alertErrInfo 9 }

		  alertErrShorts OBJECT-TYPE
			  SYNTAX Counter
			  ACCESS read-only
			  STATUS mandatory
			  ::= { alertErrInfo 10 }

		  alertErrOvsizes OBJECT-TYPE
			  SYNTAX Counter
			  ACCESS read-only
			  STATUS mandatory
			  ::= { alertErrInfo 11 }

                  alertUtilInfo OBJECT IDENTIFIER ::= { alerts 5 }

                  alertUtilEnable OBJECT-TYPE
                          SYNTAX  INTEGER {
			  	off(0),
				on(1)
			  }
                          ACCESS  read-write
                          STATUS  mandatory
                          ::= { alertUtilInfo 1 }

		  alertUtilThreshold OBJECT-TYPE
			  SYNTAX INTEGER
			  ACCESS read-write
			  STATUS mandatory
			  ::= { alertUtilInfo 2 }

		  alertUtilValue OBJECT-TYPE
			  SYNTAX INTEGER
			  ACCESS read-only
			  STATUS mandatory
			  ::= { alertUtilInfo 3 }

		  alertUtilTime OBJECT-TYPE
			  SYNTAX TimeTicks
			  ACCESS read-only
			  STATUS mandatory
			  ::= { alertUtilInfo 4 }

		  alertUtilTotalPkts OBJECT-TYPE
			  SYNTAX Counter
			  ACCESS read-only
			  STATUS mandatory
			  ::= { alertUtilInfo 5 }

		  alertUtilErrors OBJECT-TYPE
			  SYNTAX Counter
			  ACCESS read-only
			  STATUS mandatory
			  ::= { alertUtilInfo 6 }



           -- NAT remote ethermeter group, supported by NAT Remote EtherMeter

                  rconfiguration OBJECT IDENTIFIER ::= { rmeter 1 }
		
                  prTrapchannel OBJECT-TYPE
                          SYNTAX  INTEGER
                          ACCESS  read-write
                          STATUS  mandatory
                          ::= { rconfiguration 1 }

                  auxTrapchannel OBJECT-TYPE
                          SYNTAX  INTEGER
                          ACCESS  read-write
                          STATUS  mandatory
                          ::= { rconfiguration 2 }


 	   -- NAT dialup group, supported by NAT Remote EtherMeter product

                  phonenum OBJECT-TYPE
                          SYNTAX  OCTET STRING
                          ACCESS  read-write
                          STATUS  mandatory
                          ::= { dialup 1 }

                  modemInitstr OBJECT-TYPE
                          SYNTAX  OCTET STRING
                          ACCESS  read-write
                          STATUS  mandatory
                          ::= { dialup 2 }

                  modemDialprefix OBJECT-TYPE
                          SYNTAX  OCTET STRING
                          ACCESS  read-write
                          STATUS  mandatory
                          ::= { dialup 3 }

                  modemDialsuffix OBJECT-TYPE
                          SYNTAX  OCTET STRING
                          ACCESS  read-write
                          STATUS  mandatory
                          ::= { dialup 4 }

                  modemHangupprefix OBJECT-TYPE
                          SYNTAX  OCTET STRING
                          ACCESS  read-write
                          STATUS  mandatory
                          ::= { dialup 5 }

                  modemHangupsuffix OBJECT-TYPE
                          SYNTAX  OCTET STRING
                          ACCESS  read-write
                          STATUS  mandatory
                          ::= { dialup 6 }


           -- NAT router group, supported by NAT Remote IP Router product family

		--  the configuration group

                  rtrcfg OBJECT IDENTIFIER ::= { natrtr 1 }


                  rtrcfRtupdintv OBJECT-TYPE
                          SYNTAX  INTEGER
                          ACCESS  read-write
                          STATUS  mandatory
                          ::= { rtrcfg 1 }

                  rtrcfRtdownintv OBJECT-TYPE
                          SYNTAX  INTEGER
                          ACCESS  read-write
                          STATUS  mandatory
                          ::= { rtrcfg 2 }

                  rtrcfRtholdintv OBJECT-TYPE
                          SYNTAX  INTEGER
                          ACCESS  read-write
                          STATUS  mandatory
                          ::= { rtrcfg 3 }

                  rtrcfRtdropintv OBJECT-TYPE
                          SYNTAX  INTEGER
                          ACCESS  read-write
                          STATUS  mandatory
                          ::= { rtrcfg 4 }

                  rtrcfIfTable OBJECT-TYPE
                          SYNTAX  SEQUENCE OF RtrcfIfEntry
                          ACCESS  read-only
                          STATUS  mandatory
                          ::= { rtrcfg 5 }

                  rtrcfIfEntry OBJECT-TYPE
                          SYNTAX  RtrcfIfEntry
                          ACCESS  read-only
                          STATUS  mandatory
			  INDEX   { INTEGER }
                          ::= { rtrcfIfTable 1 }

		  RtrcfIfEntry ::= SEQUENCE {
		  	rtrcfProxyarp
				INTEGER,
		  	rtrcfIcmp
				INTEGER,
		  	rtrcfHelperAddr
				IpAddress,
		  	rtrcfBcastAddr
				IpAddress
		  }		


                 rtrcfProxyarp OBJECT-TYPE
                          SYNTAX  INTEGER {
                            enabled(1),      -- proxy ARP enabled
                            disabled(2)      -- proxy ARP disabled

                              }
                          ACCESS  read-write
                          STATUS  mandatory
                          ::= { rtrcfIfEntry 1 }

                 rtrcfIcmp OBJECT-TYPE
                          SYNTAX  INTEGER {
                            enabled(1),      -- ICMP services enabled
                            disabled(2)      -- ICMP services disabled

                              }
                          ACCESS  read-write
                          STATUS  mandatory
                          ::= { rtrcfIfEntry 2 }

                 rtrcfHelperAddr OBJECT-TYPE
                          SYNTAX IpAddress 
                          ACCESS  read-write
                          STATUS  mandatory
                          ::= { rtrcfIfEntry 3 }

                 rtrcfBcastAddr OBJECT-TYPE
                          SYNTAX IpAddress 
                          ACCESS  read-write
                          STATUS  mandatory
                          ::= { rtrcfIfEntry 4 }

                 rtrcfStatRtTbl OBJECT-TYPE
                          SYNTAX  SEQUENCE OF RtrcfStatRtEntry
                          ACCESS  read-only
                          STATUS  mandatory
                          ::= { rtrcfg 6 }

                  rtrcfStatRtEntry OBJECT-TYPE
                          SYNTAX  RtrcfStatRtEntry
                          ACCESS  read-only
                          STATUS  mandatory
			  INDEX   { rtrcfStatRtRoute }
                          ::= { rtrcfStatRtTbl 1 }

		  RtrcfStatRtEntry ::= SEQUENCE {
		  	rtrcfStatRtRoute
				IpAddress,
		  	rtrcfStatRtRouter
				IpAddress,
		  	rtrcfStatRtMetric
				INTEGER
		  }		


                 rtrcfStatRtRoute OBJECT-TYPE
                          SYNTAX IpAddress 
                          ACCESS  read-only
                          STATUS  mandatory
                          ::= { rtrcfStatRtEntry 1 }

                 rtrcfStatRtRouter OBJECT-TYPE
                          SYNTAX IpAddress 
                          ACCESS  read-only
                          STATUS  mandatory
                          ::= { rtrcfStatRtEntry 2 }

                 rtrcfStatRtMetric OBJECT-TYPE
                          SYNTAX INTEGER 
                          ACCESS  read-write
                          STATUS  mandatory
                          ::= { rtrcfStatRtEntry 3 }

		 rtrrtInFltrTbl OBJECT-TYPE
                          SYNTAX SEQUENCE OF RtrrtInFltrEntry
                          ACCESS  read-only
                          STATUS  mandatory
                          ::= { natrtr 3 }

		 rtrrtInFltrEntry OBJECT-TYPE
                          SYNTAX  RtrrtInFltrEntry
                          ACCESS  read-only
                          STATUS  mandatory
			  INDEX   { rtrrtInFltrInf, rtrrtInFltrAddr,
			  	    rtrrtInFltrMask }
                          ::= { rtrrtInFltrTbl 1 }

                  RtrrtInFltrEntry ::= SEQUENCE {
		  	rtrrtInFltrInf
				INTEGER,
		  	rtrrtInFltrAddr
				IpAddress,
		  	rtrrtInFltrMask
				IpAddress,
		  	rtrrtInFltrFlag
				INTEGER
		  }		


		rtrrtInFltrInf OBJECT-TYPE
                          SYNTAX INTEGER 
                          ACCESS  read-only
                          STATUS  mandatory
                          ::= { rtrrtInFltrEntry 1 }

		rtrrtInFltrAddr OBJECT-TYPE
                          SYNTAX IpAddress 
                          ACCESS  read-only
                          STATUS  mandatory
                          ::= { rtrrtInFltrEntry 2 }

		rtrrtInFltrMask OBJECT-TYPE
                          SYNTAX IpAddress
                          ACCESS  read-only
                          STATUS  mandatory
                          ::= { rtrrtInFltrEntry 3 }

		rtrrtInFltrFlag OBJECT-TYPE
                          SYNTAX INTEGER 
                          ACCESS  read-write
                          STATUS  mandatory
                          ::= { rtrrtInFltrEntry 4 }


		 rtrrtOutFltrTbl OBJECT-TYPE
                          SYNTAX SEQUENCE OF RtrrtOutFltrEntry
                          ACCESS  read-only
                          STATUS  mandatory
                          ::= { natrtr 4 }

		 rtrrtOutFltrEntry OBJECT-TYPE
                          SYNTAX  RtrrtOutFltrEntry
                          ACCESS  read-only
                          STATUS  mandatory
			  INDEX   { rtrrtOutFltrInf, rtrrtOutFltrAddr,
			  	    rtrrtOutFltrMask }
                          ::= { rtrrtOutFltrTbl 1 }

                  RtrrtOutFltrEntry ::= SEQUENCE {
		  	rtrrtOutFltrInf
				INTEGER,
		  	rtrrtOutFltrAddr
				IpAddress,
		  	rtrrtOutFltrMask
				IpAddress,
		  	rtrrtOutFltrFlag
				INTEGER
		  }		


		rtrrtOutFltrInf OBJECT-TYPE
                          SYNTAX INTEGER 
                          ACCESS  read-only
                          STATUS  mandatory
                          ::= { rtrrtOutFltrEntry 1 }

		rtrrtOutFltrAddr OBJECT-TYPE
                          SYNTAX IpAddress 
                          ACCESS  read-only
                          STATUS  mandatory
                          ::= { rtrrtOutFltrEntry 2 }

		rtrrtOutFltrMask OBJECT-TYPE
                          SYNTAX IpAddress
                          ACCESS  read-only
                          STATUS  mandatory
                          ::= { rtrrtOutFltrEntry 3 }

		rtrrtOutFltrFlag OBJECT-TYPE
                          SYNTAX INTEGER 
                          ACCESS  read-write
                          STATUS  mandatory
                          ::= { rtrrtOutFltrEntry 4 }

		END
