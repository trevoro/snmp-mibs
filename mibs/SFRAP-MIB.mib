-- Sync Research enterprise MIB for SFRAP                        =
--                                                               =
--                                                               =
--                      MIB VERSION 4.00                         =
--                                                               =
--                                                               =
-- internal version 4.00.16                                      =
--                                                               =
--                                                               =
-- This file contains MIB Definitions for extended management    =
-- of Sync Research SFRAP Product (Serial Frame Relay Access     =
-- product with integral agent).                                 =
--                                                               =
-- This MIB is copyrighted by Sync Research (1997, 1998, 1999).  =
-- Permission is granted to the general public to use this       =
-- file for management of TyLink Products.                       =
--                                                               =
-- Updates to this Enterprise MIB may be obtained from           =
-- Sync Research Customer Service 1-800-828-2780.                =
--                                                               =

SFRAP-MIB DEFINITIONS ::= BEGIN

   IMPORTS

      DisplayString
         FROM SNMPv2-TC
      Counter, TimeTicks, IpAddress, internet, Gauge
         FROM RFC1155-SMI
      TRAP-TYPE
         FROM RFC-1215
      OBJECT-TYPE
         FROM RFC-1212;

   --   This MIB module uses the extended OBJECT-TYPE macro.

   private     OBJECT IDENTIFIER ::= { internet 4 }
   enterprises OBJECT IDENTIFIER ::= { private 1 }
   sync        OBJECT IDENTIFIER ::= { enterprises 485 }
   sfrap       OBJECT IDENTIFIER ::= { sync 7 }

   -- textual conventions

       --DisplayString ::=
       --    OCTET STRING
       -- This data type is used to model textual information taken
       -- from the NVT ASCII character set.  By convention, objects
       -- with this syntax are declared as having
       --
       --      SIZE (0..255)


-- *********************************************************************
--                     SFRAP ENTERPRISE SPECIFIC MIB
-- *********************************************************************


-- ======================================================================
--
--  The SFRAP MIB Tree
--      This MIB covers common aspects of the Sync Research sfrap family
--      of products.
--
--  The SFRAP MIB Consists of five groups (plus Traps):
--      The SYSTEM group
--      The CONFIGURATION group
--      The DIAGNOSTICS group    (not common)
--      The STATUS group
--      The PERFORMANCE group
--
--  The SYSTEM group
--      This group provides system level attributes of the node.
--
--      The group consists of the following tables:
--          sfrapSysTable           - System level attributes
--          sfrapSysFeatureTable    - System level features
--
--  The CONFIGURATION group
--      This group provides for configuration of the node.
--
--      The group consists of the following tables:
--          sfrapCfgMgmtTable       - Configuration of management features
--          sfrapCfgIpTable         - IP configuration
--          sfrapCfgTftpTable       - TFTP configuration
--          sfrapCfgSnmpTable       - SNMP configuration
--          sfrapCfgSnmpMgrTable    - SNMP managers (TRAP destinations)
--          sfrapCfgFrDLCITable     - DLCI configuration
--          sfrapCfgAppTable        - Application level configuration
--          sfrapCfgFrTable         - Frame Relay configuration
--          sfrapCfgVnipTable       - VNIP configuration
--          sfrapCfgFrPerfTable     - Frame Relay performance configuration
--          sfrapCfgFrPerfDlciNamesTable        - Table of DLCI names
--          sfrapCfgFrPerfUserProtocolsTable    - User-specified protocols
--          sfrapCfgFrPerfLTDlciFilterTable     - LT stats: DLCI filter
--          sfrapCfgFrPerfLTProtocolFilterTable - LT stats: protocol filter
--          sfrapCfgSecurityTable   - Security configuration
--          
--  The STATUS group
--      This group provides status information.
--
--      The group consists of the following tables:
--          sfrapVnipTopologyTable  - VNIP topology
--          
--  The PERFORMANCE group
--      This group provides statistical information.
--
--      The group consists of the following tables:
--          sfrapPerfMgmtIp            - IP protocol stack statistics
--          sfrapPerfMgmtIpIFStatsTable      - Interface statistics
--          sfrapPerfMgmtIpIPStatsTable      - IP statistics
--          sfrapPerfMgmtIpICMPStatsTable    - ICMP statistics
--          sfrapPerfMgmtIpUDPStatsTable     - UDP statistics
--          sfrapPerfMgmtIpTCPStatsTable     - TCP statistics
--          sfrapPerfThruput           - Thruput statistics
--          sfrapPerfThruputPerDlciTable     - Thruput per DLCI
--          sfrapPerfThruputPerIntfTable     - Thruput per Interface
--          sfrapPerfNetworkShortTerm  - Short term DLCI statistics
--          sfrapPerfNetwProtoPerDlciTable   - Network protocol stats per DLCI
--          sfrapPerfNetwProtoTotalTable     - Total network protocol stats
--          sfrapPerfIpPerDlciTable          - IP stats per DLCI
--          sfrapPerfIpTotalTable            - Total IP stats
--          sfrapPerfIcmpPerDlciTable        - ICMP stats per DLCI
--          sfrapPerfIcmpTotalTable          - Total ICMP stats
--          sfrapPerfApplicationPerDlciTable - Application stats per DLCI
--          sfrapPerfApplicationTotalTable   - Total application stats
--          sfrapPerfRoutingPerDlciTable     - Routing stats per DLCI
--          sfrapPerfRoutingTotalTable       - Total Routing stats
--          sfrapPerfIpxPerDlciTable         - IPX stats per DLCI
--          sfrapPerfIpxTotalTable           - Total IPX stats
--          sfrapPerfSnaPerDlciTable         - SNA stats per DLCI
--          sfrapPerfSnaTotalTable           - Total SNA stats
--          sfrapPerfArpPerDlciTable         - ARP stats per DLCI
--          sfrapPerfArpTotalTable           - Total ARP stats
--          sfrapPerfNetworkLongTerm   - Long term DLCI statistics
--          sfrapPerfNetwLongTermTable       - Long term stats
--          sfrapPerfNetwLongTermAltTable    - Alternate format LTS
--
--  The MIB also contains enterprise trap information:
--          sfrapTrap
--
-- =======================================================================



-- ========================
-- ==   SYSTEM group     ==
-- ========================

sfrapSystem      OBJECT IDENTIFIER ::= { sfrap 1 }
--
--       The sfrapSysTable
--              This table contains the system attributes of the SFRAP.
--
     
sfrapSysTable      OBJECT IDENTIFIER ::= { sfrapSystem 1 }

sfrapSysType       OBJECT-TYPE
          SYNTAX      DisplayString (SIZE (0..255))
          ACCESS      read-only
          STATUS      mandatory
          DESCRIPTION
             "A textual description of the system model identifier.
              for example: SYNC-sfrap"
          ::= { sfrapSysTable 1 }

sfrapSysSoftRev    OBJECT-TYPE
          SYNTAX      DisplayString (SIZE (0..10))
          ACCESS      read-only
          STATUS      mandatory
          DESCRIPTION
             "Displays the Software Revision of the application code 
              installed in this node."
          ::= { sfrapSysTable 2 }

sfrapSysHardRev    OBJECT-TYPE
          SYNTAX      DisplayString (SIZE (0..10))
          ACCESS      read-only
          STATUS      mandatory
          DESCRIPTION
             "Displays the Hardware Revision of the node."
          ::= { sfrapSysTable 3 }

sfrapSysNumToDteInstalled    OBJECT-TYPE
          SYNTAX      INTEGER (0..1)
          ACCESS      read-only
          STATUS      mandatory
          DESCRIPTION
             "The number of channels (TO-DTE) that are
              installed."
          ::= { sfrapSysTable 5 }

sfrapSysNumToDceInstalled    OBJECT-TYPE
          SYNTAX      INTEGER (0..1)
          ACCESS      read-only
          STATUS      mandatory
          DESCRIPTION
             "The number of channels (TO-DCE) that are
              installed."
          ::= { sfrapSysTable 14 }

sfrapSysNumMaintInstalled    OBJECT-TYPE
          SYNTAX      INTEGER (0..2)
          ACCESS      read-only
          STATUS      mandatory
          DESCRIPTION
             "The number of Maintenance ports that are 
              installed."
          ::= { sfrapSysTable 6 }

sfrapSysName       OBJECT-TYPE
          SYNTAX      DisplayString (SIZE (0..16))
          ACCESS      read-write
          STATUS      mandatory
          DESCRIPTION
             "The user supplied name of the node.  This object
              does not affect operation, but may be useful
              for network management."
          ::= { sfrapSysTable 7 }

sfrapSysSerialNo      OBJECT-TYPE
          SYNTAX      DisplayString (SIZE (0..10))
          ACCESS      read-only
          STATUS      mandatory
          DESCRIPTION
             "The serial number of the board."
          ::= { sfrapSysTable 8 }

sfrapSysResetNode    OBJECT-TYPE
          SYNTAX      INTEGER
          {
               reset-node (321)
          }
          ACCESS      write-only
          STATUS      mandatory
          DESCRIPTION
           "Command to reset the node. NODE WILL BE OFF-LINE AND 
           USER DATA WILL BE INTERRUPTED FOR APPROXIMATELY 15 
           SECONDS. "
          ::= { sfrapSysTable 9 }

sfrapSysAmtMemoryInstalled    OBJECT-TYPE
          SYNTAX      INTEGER
          ACCESS      read-only
          STATUS      mandatory
          DESCRIPTION
             "The amount of memory (RAM) installed (in megabytes)."
          ::= { sfrapSysTable 10 }

sfrapSysLocation       OBJECT-TYPE
          SYNTAX  DisplayString (SIZE (0..16))
          ACCESS  read-write
          STATUS  mandatory
          DESCRIPTION
             "The user supplied location of the node.  This
              object does not affect operation, but may be
              useful for network management."
          ::= { sfrapSysTable 12 }

sfrapSysContact        OBJECT-TYPE
          SYNTAX      DisplayString (SIZE (0..16))
          ACCESS      read-write
          STATUS      mandatory
          DESCRIPTION
             "The user supplied contact information for the
              node.  This object does not affect operation,
              but may be useful for network management."
          ::= { sfrapSysTable 13 }                                

sfrapSysPrompt        OBJECT-TYPE
     SYNTAX      DisplayString (SIZE (0..8))
     ACCESS      read-write
     STATUS      mandatory
     DESCRIPTION
        "Configurable Command Line Interface (CLI) prompt. CLI
         is the User Interface protocol used for directly 
         attached VT100 terminal access as well as Remote
         access via Telnet."
     ::= { sfrapSysTable 15 }                                

sfrapSysBootRev    OBJECT-TYPE
          SYNTAX      DisplayString (SIZE (0..10))
          ACCESS      read-only
          STATUS      mandatory
          DESCRIPTION
             "Displays the Software Revision of the Bootstrapping
         code installed in this node."
          ::= { sfrapSysTable 16 }

--       The sfrapSysFeatureTable
--              This table contains the system features of the sfrap CSU.
--
sfrapSysFeatureTable      OBJECT IDENTIFIER ::= { sfrapSystem 2 }

sfrapSysSLIPSupported     OBJECT-TYPE
     SYNTAX      DisplayString (SIZE (0..10))
     ACCESS      read-only
     STATUS      mandatory
     DESCRIPTION
        "Shows whether the unit has SLIP (Serial Line IP) capability.
         SLIP is a method for out-of-band management that connects
         through the asynchronous terminal port."
     ::= { sfrapSysFeatureTable 1 }

sfrapSysPPPSupported     OBJECT-TYPE
     SYNTAX      DisplayString (SIZE (0..10))
     ACCESS      read-only
     STATUS      mandatory
     DESCRIPTION
        "Shows whether the unit has PPP (Point to Point protocol)
         capability. PPP is a method for out-of-band management 
         that connects through the asynchronous terminal port."
     ::= { sfrapSysFeatureTable 2 }

sfrapSysRDOSupported     OBJECT-TYPE
     SYNTAX      DisplayString (SIZE (0..10))
     ACCESS      read-only
     STATUS      mandatory
     DESCRIPTION
        "Shows whether the unit has Remote Dial Out capability."
     ::= { sfrapSysFeatureTable 3 }

sfrapSysETHSupported     OBJECT-TYPE
     SYNTAX      DisplayString (SIZE (0..10))
     ACCESS      read-only
     STATUS      mandatory
     DESCRIPTION
        "Shows whether the unit has Ethernet capability."
     ::= { sfrapSysFeatureTable 4 }

sfrapSysTKRSupported     OBJECT-TYPE
     SYNTAX      DisplayString (SIZE (0..10))
     ACCESS      read-only
     STATUS      mandatory
     DESCRIPTION
        "Shows whether the unit has Token Ring capability."
     ::= { sfrapSysFeatureTable 5 }

sfrapSysExtTimSupported     OBJECT-TYPE
     SYNTAX      DisplayString (SIZE (0..10))
     ACCESS      read-only
     STATUS      mandatory
     DESCRIPTION
        "Shows whether the unit has External Timing capability.
         This is the ability to derive WAN timing from the DTE port."
     ::= { sfrapSysFeatureTable 6 }

sfrapSysBRISupported     OBJECT-TYPE
     SYNTAX      DisplayString (SIZE (0..10))
     ACCESS      read-only
     STATUS      mandatory
     DESCRIPTION
        "Shows whether the unit has BRI (ISDN Basic Rate) capability."
     ::= { sfrapSysFeatureTable 7 }

sfrapSysSelDTESupported     OBJECT-TYPE
     SYNTAX      DisplayString (SIZE (0..10))
     ACCESS      read-only
     STATUS      mandatory
     DESCRIPTION
        "Shows whether the unit has a Selectable DTE interface.
         This being the ability to select amongst various electrical 
         interface formats (V.35, RS449, RS232, etc.) via software."
     ::= { sfrapSysFeatureTable 8 }

sfrapSysMLSupported     OBJECT-TYPE
     SYNTAX      DisplayString (SIZE (0..10))
     ACCESS      read-only
     STATUS      mandatory
     DESCRIPTION
        "Shows whether the unit supports MLs
         (out-of-band management links)."
     ::= { sfrapSysFeatureTable 9 }

sfrapSysNumDlcisSupported     OBJECT-TYPE
     SYNTAX      INTEGER
     ACCESS      read-only
     STATUS      mandatory
     DESCRIPTION
        "Shows how many DLCIs can be monitored for frame-based 
         statistics. The unit will pass an unlimited number of 
         DLCIs but will only collect statistics on this number 
         (first come first served)."
     ::= { sfrapSysFeatureTable 10 }

sfrapSysLTFNumDlcis     OBJECT-TYPE
     SYNTAX      INTEGER
     ACCESS      read-only
     STATUS      mandatory
     DESCRIPTION
        "Shows how many DLCIs can be specified
         in the Long Term Statistics Filter."
     ::= { sfrapSysFeatureTable 11 }

sfrapSysLTFNumProtocols     OBJECT-TYPE
     SYNTAX      INTEGER
     ACCESS      read-only
     STATUS      mandatory
     DESCRIPTION
        "Shows how many protocols can be specified
         in the Long Term Statistics Filter."
     ::= { sfrapSysFeatureTable 12 }

sfrapSysNumUserProtocols     OBJECT-TYPE
     SYNTAX      INTEGER
     ACCESS      read-only
     STATUS      mandatory
     DESCRIPTION
        "Shows how many protocols can be defined by the user.
         The user configures TCP/UDP ports which can be monitored
         as protocols.  They are available for short term or
         long term statistics monitoring."
     ::= { sfrapSysFeatureTable 13 }

sfrapSysNumSnmpMgrs     OBJECT-TYPE
     SYNTAX      INTEGER
     ACCESS      read-only
     STATUS      mandatory
     DESCRIPTION
        "Shows how many SNMP managers can be programmed in the
         table sfrapCfgSnmpMngrTable. These managers are sent 
         TRAPs if configured to do so."
     ::= { sfrapSysFeatureTable 14 }

sfrapSysNumDlciNames     OBJECT-TYPE
     SYNTAX      INTEGER
     ACCESS      read-only
     STATUS      mandatory
     DESCRIPTION
        "Shows how many DLCI names can be defined by the user
         in the table sfrapCfgFrPerfDlciNamesTable."
     ::= { sfrapSysFeatureTable 15 }

sfrapSysHighSpeedSupported     OBJECT-TYPE
     SYNTAX      DisplayString (SIZE (0..10))
     ACCESS      read-only
     STATUS      mandatory
     DESCRIPTION
        "Shows whether the unit is in high speed mode."
     ::= { sfrapSysFeatureTable 16 }



-- =========================
-- == CONFIGURATION group ==
-- =========================

sfrapConfiguration   OBJECT IDENTIFIER ::= { sfrap 2 }


--
--       The Management Configuration Table
--              This table contains the management-related
---             Configuration information for the sfrap DSU.

sfrapCfgMgmtTable   OBJECT IDENTIFIER ::= { sfrapConfiguration 1 }

--
--       The IP Configuration Table
--              This table contains the Configuration for Maintenance Port
--              when in IP mode on the sfrap DSU.

sfrapCfgIpTable OBJECT IDENTIFIER ::= { sfrapCfgMgmtTable 1 }
 
sfrapCfgIpMyIP   OBJECT-TYPE
          SYNTAX      IpAddress
          ACCESS      read-write
          STATUS      mandatory
          DESCRIPTION
             "The IP address for this node. This address will be unique to
              the IP network and is required for in-band or out-of-band
              ip and SNMP management."
          ::= { sfrapCfgIpTable 1 }
 
sfrapCfgIpPeerIP   OBJECT-TYPE
          SYNTAX      IpAddress
          ACCESS      read-write
          STATUS      mandatory
          DESCRIPTION
             "This parameter is not used internally by
              the unit. It is intended to identify either
              the device directly connected to the SLIP
              port or, in Frame Relay applications, the
              address of the primary network management 
              station. This should always be non-zero."
          ::= {sfrapCfgIpTable 2 }
 
sfrapCfgIpMask   OBJECT-TYPE
          SYNTAX      IpAddress
          ACCESS      read-write
          STATUS      mandatory
          DESCRIPTION
             "The IP Subnet Mask (eg 255.255.255.0). This
              parameter should be consisent with the IP
              subnet address setting of the external
              internetworking equipment (router/frad)."
          ::= { sfrapCfgIpTable 3 }
 
sfrapCfgIpMaxMTU OBJECT-TYPE
          SYNTAX      INTEGER  (1..1024)
          ACCESS      read-write
          STATUS      mandatory
          DESCRIPTION
             "The Maximum Transmission Unit is the size of the
              largest IP packet supported (including header).
              This value should be set to the lowest value supported 
              by any equipment in the transmission path.
              For Frame Relay management the typical value is 1500. 
              For SLIP management the typical value is 1006."
          ::= { sfrapCfgIpTable 4 }

sfrapCfgIpChannel   OBJECT-TYPE
          SYNTAX      INTEGER
          {
              none           (1),
              slip-port      (2),
              in-band-dlci   (3)
          }
          ACCESS      read-only
          STATUS      mandatory
          DESCRIPTION
               "This is the method by which IP traffic is being carried.
                Either via the SLIP port or a DLCI.  This is how
                your InBand Managenent scheme is set up."
          ::= { sfrapCfgIpTable 5 }

sfrapCfgIpTelnetEnable   OBJECT-TYPE
          SYNTAX      INTEGER
          {
              enable-telnet  (1),
              disable-telnet (2)
          }
          ACCESS      read-write
          STATUS      mandatory
          DESCRIPTION
             "Enables/Disables the telnet feature.
              Valid values are enable-telnet (1)
              and disable-telnet (2)."
          ::= { sfrapCfgIpTable 6 }

sfrapCfgIpTelnetAutoLogOut   OBJECT-TYPE
          SYNTAX      INTEGER
          {
              autologout-at-15-minutes (1),
              disable-autologout       (2),
              autologout-at-3-minutes  (3),
              autologout-at-5-minutes  (5),
              autologout-at-10-minutes (10),
              autologout-at-30-minutes (30),
              autologout-at-60-minutes (60)
          }
          ACCESS      read-write
          STATUS      mandatory
          DESCRIPTION
             "If Telnet Auto logout is enabled the unit
              will automatically disconnect from a Telnet
              session after a period of inactivity (absence 
              of key strokes from remote terminal). 
              (2)  disables this feature
              (1)  auto logout after 15 minutes inactivity
              (3)  auto logout after 3 minutes inactivity
              (5)  auto logout after 5 minutes inactivity
              (10) auto logout after 10 minutes inactivity
              (30) auto logout after 30 minutes inactivity
              (60) auto logout after 60 minutes inactivity"
          ::= { sfrapCfgIpTable 7 }


--
--       The TFTP Configuration Table
--              This table contains the Configuration for the TFTP
--              support on the sfrap DSU.

sfrapCfgTftpTable OBJECT IDENTIFIER ::= { sfrapCfgMgmtTable 2 }

sfrapCfgTftpInitiate OBJECT-TYPE
          SYNTAX DisplayString (SIZE (0..8))
          ACCESS write-only
          STATUS mandatory
          DESCRIPTION
             "Setting this object to a value that matches
              the TFTP Password will command the unit to
              attempt a TFTP file transfer. A TFTP profile
              including host ip address, dlci value, interface, 
              and file name must first be configured."
          ::= {sfrapCfgTftpTable 1}

sfrapCfgTftpIpAddress   OBJECT-TYPE
          SYNTAX     IpAddress
          ACCESS     read-write
          STATUS     mandatory
          DESCRIPTION
             "The IP address of the TFTP host with which
              the unit will attempt to establish a TFTP
              session when initiated."
          ::= {sfrapCfgTftpTable 2}
   
sfrapCfgTftpFilename OBJECT-TYPE
          SYNTAX DisplayString (SIZE (0..80))
          ACCESS read-write
          STATUS mandatory
          DESCRIPTION
             "The name of the file located on the TFTP host
              that will be transferred to the unit. Typically 
              this is a product-specific software image that
              will be programmed into unit FLASH. The unit 
              provides several levels of checking to verify 
              the validity and integrity of this file. 
              Note - depending upon the host, this file name 
              may be case sensitive."
          ::= {sfrapCfgTftpTable 3}

sfrapCfgTftpInterface OBJECT-TYPE
          SYNTAX      INTEGER
          {
              to-dte-interface  (1),
              to-dce-interface  (2),
              slip-interface    (3)
          }
          ACCESS read-write
          STATUS mandatory
          DESCRIPTION
             "The physical interface out which the TFTP host
              is located. This parameter is only required for
              Piggyback and Bi-directional in-band frame relay
              managed applications. With Local and Remote in-band 
              and SLIP-based applications the interface is known
              and Sets to this will be ignored."
          ::= {sfrapCfgTftpTable 4}

sfrapCfgTftpDlci OBJECT-TYPE
          SYNTAX INTEGER (-1..63487)
          ACCESS read-write
          STATUS mandatory
          DESCRIPTION
            "The local DLCI value on which the TFTP host can be 
             reached. This DLCI should be active prior to 
             initiating the TFTP session. This parameter is only 
             required for Piggyback in-band frame relay managed 
             applications. With Private management (Local, Remote 
             or Bi-directional in-band applications) the DLCI is
             known and will be reported here (Sets will be ignored). 
             In SLIP-based applications the DLCI value is not 
             applicable and a value of -1 is reported (Sets will 
             be ignored)."
          ::= {sfrapCfgTftpTable 5}

sfrapCfgTftpStatus OBJECT-TYPE
          SYNTAX INTEGER
          {
              inactive          (1),
              requested         (2),
              transferring      (3),
              programming       (4),
              transfer-aborted  (5),
              host-no-reply     (6),
              file-not-found    (7),
              invalid-file      (8),
              corrupt-file      (9),
              successful        (10)
          }
          ACCESS read-write
          STATUS mandatory
          DESCRIPTION
             "The status of current or most recent TFTP operation.
              (1) TFTP inactive, sets to this value will abort the session
              (2) TFTP requested
              (3) TFTP transferring
              (4) TFTP programming FLASH - unit will reset 
              (5) TFTP fail: session aborted by user or error condition
              (6) TFTP fail: host no reply -  verify TFTP profile and host
              (7) TFTP fail: file not found - verify file name and location
              (8) TFTP fail: invalid file - file rejected by unit as inappropriate
              (9) TFTP fail: corrupt file - session terminated due to checksum error
              (10) TFTP transfer successful and file has been verified"
          ::= {sfrapCfgTftpTable 6}

sfrapCfgTftpNumBytes OBJECT-TYPE
          SYNTAX Counter
          ACCESS      read-only
          STATUS      mandatory
          DESCRIPTION
            "The number of Bytes from the ROM image that have been 
             TFTP'd to the unit"
          ::= {sfrapCfgTftpTable 7}


--
--       The SNMP Configuration Table
--              This table contains the Configuration for the SNMP
--              support on the sfrap DSU.

sfrapCfgSnmpTable OBJECT IDENTIFIER ::= { sfrapCfgMgmtTable 3 }

sfrapCfgSnmpFrTrap   OBJECT-TYPE
         SYNTAX      INTEGER
         {
             enabled        (1),
             disabled       (2)
         }
         ACCESS      read-write
         STATUS      mandatory
         DESCRIPTION
            "Controls whether or not the Frame Relay DLCI
             status change traps are issued.  These traps are
             sfrapDLCIActiveTrap and sfrapDLCIInactiveTrap.
             When sfrapCfgSnmpFrTrap is enabled (1), a trap
             will be sent each time an individual DLCI changes
             status between active and inactive. When
             sfrapCfgSnmpFrTrap is disabled (2), the traps
             are not sent."
         ::= { sfrapCfgSnmpTable 1 }

sfrapCfgSnmpTrapMuting    OBJECT-TYPE
          SYNTAX      INTEGER (0..10080)
          ACCESS      read-write
          STATUS      mandatory
          DESCRIPTION
             "Controls whether Traps are Sent or Muted. If traps
              are Muted then a single trap (#75) will be periodically
              issued by the unit at the programmed frequency. If Muting
              is Disabled then the full set of Trap events are reported
              accordingly.
              (0) Disable Trap Muting
              (30-10080) Trap Muting frequency in minutes."
         ::= { sfrapCfgSnmpTable 3 }

sfrapCfgSnmpUtilTrapEnable  OBJECT-TYPE
         SYNTAX      INTEGER
         {
             enable        (1),
             disable       (2)
         }
         ACCESS      read-write
         STATUS      mandatory
         DESCRIPTION
            "Enables or disables the sending of per-DLCI
             utilization traps.
             (1) enable utilization traps
             (2) disable utilization traps"
         ::= { sfrapCfgSnmpTable 6 }
     
sfrapCfgSnmpMgrClearN   OBJECT-TYPE
        SYNTAX  INTEGER
        ACCESS  write-only
        STATUS  mandatory
        DESCRIPTION
           " Deletes the number of entries in the sfrapCfgSnmpMgrTable
             indicated by the value.  If the value is a positive number
             the entries will be deleted starting from the first entry.
             If the value is negative the entries will be deleted 
             starting from the last entry. "
        ::= { sfrapCfgSnmpTable 7 }
         
sfrapCfgSnmpMgrTable   OBJECT-TYPE
         SYNTAX   SEQUENCE OF SfrapCfgSnmpMgrEntry
         ACCESS   not-accessible
         STATUS   mandatory
         DESCRIPTION
            "The table of SNMP manager profiles to which
             traps are sent. In all managed modes an SNMP
             trap mangager's ip address is required as a 
             minimum. Additionally for Piggyback managed
             units the DLCI and interface must also be 
             configured appropriately. For Local, Remote
             and SLIP-based management, the DLCI and
             interface are implied and need not be 
             configured as part of this profile."
          ::= { sfrapCfgSnmpTable 2 }

sfrapCfgSnmpMgrEntry   OBJECT-TYPE
         SYNTAX   SfrapCfgSnmpMgrEntry
         ACCESS   not-accessible
         STATUS   mandatory
         DESCRIPTION
            "The IP address of a SNMP manager to receive this node's TRAPs."
         INDEX { sfrapCfgSnmpMgrIndex }
            ::= { sfrapCfgSnmpMgrTable 1 }

SfrapCfgSnmpMgrEntry ::=
         SEQUENCE {
             sfrapCfgSnmpMgrIndex       INTEGER,
             sfrapCfgSnmpMgrIP          IpAddress,
             sfrapCfgSnmpMgrInterface   INTEGER,
             sfrapCfgSnmpMgrDlci        INTEGER
         }

sfrapCfgSnmpMgrIndex OBJECT-TYPE
         SYNTAX   INTEGER
         ACCESS   read-only
         STATUS   mandatory
         DESCRIPTION
            "The index to the list of SNMP managers receiving TRAPs."
         ::= { sfrapCfgSnmpMgrEntry 1 }

sfrapCfgSnmpMgrIP   OBJECT-TYPE
         SYNTAX      IpAddress
         ACCESS      read-write
         STATUS      mandatory
         DESCRIPTION
            "The IP address of a SNMP manager to receive this node's TRAPs.
             Setting this value to 0.0.0.0 will disable the issuance of
             traps to the indexed manager."
         ::= { sfrapCfgSnmpMgrEntry 2 }

sfrapCfgSnmpMgrInterface OBJECT-TYPE
         SYNTAX      INTEGER
         {
              to-dte-interface (1),
              to-dce-interface (2),
              slip-interface   (3)
         }
         ACCESS      read-write
         STATUS      mandatory
         DESCRIPTION
            "The interface out which the indexed trap manager can be
             reached. This entry is required in Piggyback and Bi-directional 
             in-band managed applications. In Local, Remote and SLIP-based
             applications, the interface is known and this parameter is
             ignored.
             (1) Traps sent out DTE interface for this manager
             (2) Traps sent out WAN interface for this manager
             (3) Traps sent out SLIP interface (async maint port)

             When the node is configured for SLIP, a GET on this MIB
             object will return slip-interface(3) and a SET of this MIB
             object to slip-interface(3) is allowed but unnecessary.

             When the node is not configured for SLIP, this MIB
             object can be SET to dte-interface(1) or to dce-interface(2);
             slip-interface(3) would be rejected."
         ::= { sfrapCfgSnmpMgrEntry 3 }

sfrapCfgSnmpMgrDlci OBJECT-TYPE
         SYNTAX      INTEGER
         ACCESS      read-write
         STATUS      mandatory
         DESCRIPTION
            "The DLCI out which the indexed trap manager can be
             reached. This entry is required in Piggyback in-band 
             managed applications. In Private in-band applications
             the DLCI is known and Sets to this parameter will be 
             ignored. In SLIP mode the DLCI is not applicable,
             Sets will be ignored and a -1 will be returned as the 
             DLCI value."
         ::= { sfrapCfgSnmpMgrEntry 4 }

--
--       The Communication Port Configuration Table
--              This table contains the Communications port configuration.

sfrapCfgCommTable OBJECT IDENTIFIER ::= { sfrapCfgMgmtTable 4 }

sfrapCfgCommMode      OBJECT-TYPE
     SYNTAX      INTEGER
     {
         vt100     (1),
         slip      (2)
     }
     ACCESS      read-write
     STATUS      mandatory
     DESCRIPTION
        "The protocol running on the Maintenance/Comm port (console).
         Setting this to SLIP mode will automatically disable
         in-band management if it's enabled.
         (1) VT100 for directly attached async terminal
         (2) SLIP - Serial Line IP out-of-band management"
     ::= { sfrapCfgCommTable 1 }

sfrapCfgCommBaud OBJECT-TYPE
     SYNTAX      INTEGER
     {
         baud-2400   (2),
         baud-9600   (4),
         baud-19200  (5),
         baud-38400  (6)
     }
     ACCESS      read-write
     STATUS      mandatory
     DESCRIPTION
        "Asynchronous baud rate for the Maintenance/Comm port 
         (Console). This must be configured to match either the 
         VT100 compatible terminal or the SLIP Terminal Server 
         depending upon the Comm port mode. 
         (2) baud-2400 
         (4) baud-9600
         (5) baud-19200
         (6) baud-38400"
     ::= { sfrapCfgCommTable 2 }

sfrapCfgCommDataBits OBJECT-TYPE
     SYNTAX      INTEGER
     {
         databits-7 (1),
         databits-8 (2)
     }
     ACCESS      read-write
     STATUS      mandatory
     DESCRIPTION
        "Asynchronous data format for the Maintenance/Comm port 
         (Console). This must be configured to match either the 
         VT100 compatible terminal or the SLIP Terminal Server 
         depending upon the Comm port mode.
         (1) 7 databits per character
         (2) 8 databits per character"
     ::= { sfrapCfgCommTable 3 }

sfrapCfgCommStopBits OBJECT-TYPE
     SYNTAX      INTEGER
     {
         stopbits-1   (1),
         stopbits-1-5 (2),
         stopbits-2   (3)
     }
     ACCESS      read-write
     STATUS      mandatory
     DESCRIPTION
        "Asynchronous intercharacter protocol for the Maintenance/Comm 
         port (Console). This must be configured to match either the 
         VT100 compatible terminal or the SLIP Terminal Server 
         depending upon the Comm port mode.
         (1) 1 stopbit 
         (2) 1.5 stopbits 
         (3) 3 stopbits"
     ::= { sfrapCfgCommTable 4 }

sfrapCfgCommParity OBJECT-TYPE
     SYNTAX      INTEGER
     {
         no-parity   (1),
         odd-parity  (2),
         even-parity (3)
     }
     ACCESS      read-write
     STATUS      mandatory
     DESCRIPTION
        "Asynchronous parity checking protocol for the 
         Maintenance/Comm port (Console). This must be configured 
         to match either the VT100 compatible terminal or the SLIP 
         Terminal Server depending upon the Comm port mode.  
         (1) no parity
         (2) odd-parity 
         (3) even-parity"
     ::= { sfrapCfgCommTable 5 }

sfrapCfgCommFlowCtrl OBJECT-TYPE
     SYNTAX      INTEGER
     {
         no-flow-control (1)
     }
     ACCESS      read-write
     STATUS      mandatory
     DESCRIPTION
        "Flow Control for this Communication port.  Values
         are off-flow-control (1)."
     ::= { sfrapCfgCommTable 6 }


--
--       The DLCI Configuration Table
--              This table contains the Configuration for DLCI support.

sfrapCfgFrDLCITable OBJECT IDENTIFIER ::= { sfrapCfgMgmtTable 5 }

sfrapCfgFrDLCIMode  OBJECT-TYPE
          SYNTAX      INTEGER
          {
              inactive        (1),
              local-to-dte    (2),
              remote-to-dce   (3),
              bidirectional   (4),
              piggyback       (5),
              fixedDCE        (6)
          }
          ACCESS      read-write
          STATUS      mandatory
          DESCRIPTION
             "In-band Frame Relay management mode. A variety of options
              exist which are differentiated by how PVCs can be provisioned
              to manage the unit and the resulting impact to the logical
              processing of Link Management Protocol messages (LMI spoofing 
              and sourcing). The unit is designed to support these management 
              modes even in non-provisioned or failed frame relay networks.
              This setting also has implications upon how networking protocols 
              such as ARP and InARP are handled by the unit. 
              (1) inactive: in-band management is not enabled
              (2) local DLCI mode: in-band managed using a private dedicated DLCI 
                  accessible via the TO-DTE only. A DLCI value is configured 
                  which, through LMI spoofing, will only be visible to the DTE 
                  equipment and need not be provisioned on the WAN. All traffic on
                  this DLCI will be terminated by the unit.
              (3) remote DLCI mode: in-band managed using a private dedicated DLCI 
                  accessible via the WAN port only. A DLCI value is configured 
                  which, through LMI spoofing, will only be visible from the WAN 
                  side and will not be seen by any DTE equipment. All traffic on
                  this DLCI will be terminated by the unit.
              (4) bidirectional mode: in-band managed using a private dedicated DLCI 
                  accessible through either port. A DLCI value is configured 
                  which is expected to be fully provisioned in the frame relay 
                  network but dedicated to the management function of this particular 
                  unit. All traffic on this DLCI will be terminated by the unit.
              (5) piggyback mode: in-band managed using any DLCI on any interface. A
                  DLCI value is defined that becomes the default DLCI that will be
                  maintained by the unit during network or LMI failure conditions. 
                  The unit will terminate and respond accordingly to management and
                  networking data while transparently passing on user data.
              (6) fixed DCE mode: special mode of operation to support frame relay
                  applications that do not include a switch (frame relay DCE). The 
                  unit will independently respond to LMI requests on each interface
                  and will provision the configured DLCI to each Frame Relay DTE device.
                  Except for this, the unit behaves like piggyback."
          ::=  { sfrapCfgFrDLCITable 1 }

sfrapCfgFrDLCIValue  OBJECT-TYPE
          SYNTAX      INTEGER (16..63487)
          ACCESS      read-write
          STATUS      mandatory
          DESCRIPTION
             "If in-band management is being used this DLCI value should be defined. 
              In all modes of in-band management with the LMI Sourcing feature enabled 
              the unit may provision this DLCI during LMI failure to facilitate management 
              access. In Private modes (Local, Remote, and Bidirectional) this is the 
              dedicated DLCI for management data and address resolution protocols - all 
              other traffic on this DLCI will be discarded. In Piggyback mode this DLCI 
              is treated like all others except during LMI failure sourcing when it may
              be provisioned by the unit. In Piggyback mode if InARP is enabled on a single 
              DLCI then this value defines that DLCI."
          ::= { sfrapCfgFrDLCITable 2 }

sfrapCfgFrDLCIEncap   OBJECT-TYPE
          SYNTAX      INTEGER
          {
              rfc1490        (1),
              rfc1490snap    (2),
              auto           (3),
              cisco          (4)
          }
          ACCESS      read-write
          STATUS      mandatory
          DESCRIPTION
             "This is the protocol used for enacapsulating and formatting
              ip data for Frame Relay transmission. This setting is specific
              to management data to and from the unit.
              (1) RFC1490 - per IETF standard with Network Level 
                  Protocol ID (NLPID) set for IP encapsulation.
              (2) RFC1490 SNAP/IP - per IETF standard with NLPID set 
                  for Sub-Network Access Protocol (SNAP).
              (3) auto - adjusts to either of these encapsulation techniques
                  as required. 
              (4) Cisco - proprietary encapsulation (4-byte header)."
          ::= { sfrapCfgFrDLCITable 3 }

sfrapCfgFrDLCIMgmtDE   OBJECT-TYPE
          SYNTAX      INTEGER
          {
              no-DE-bit-0     (1),
              yes-DE-bit-1    (2)
          }
          ACCESS      read-write
          STATUS      mandatory
          DESCRIPTION
        "Provides user control over the state of the Frame Relay Discard
         Eligibility bit of all management frames generated by
         the unit. Frames marked DE=1 are more likely to be dropped in a 
         congested Frame Relay network than those that are DE=0. Heavily 
         congested circumstances can cause both to be dropped. Additionally,
         frames marked DE=0 may get re-marked to DE=1 by intervening
         equipment.
         (1) DE bit cleared to 0: frame is not discard eligible
         (2) DE bit set to 1: frame is discard eligible"
          ::= { sfrapCfgFrDLCITable 4 }

--
--       The Application Configuration Table
--              This table contains the Application (system) Configuration.

sfrapCfgAppTable   OBJECT IDENTIFIER ::= { sfrapConfiguration 2 }

sfrapCfgAppCircuitId    OBJECT-TYPE
          SYNTAX      DisplayString (SIZE (0..30))
          ACCESS      read-write
          STATUS      mandatory
          DESCRIPTION
             "Alphanumeric circuit identifier may be provided by the service 
              provider for reference or assigned arbitrarily per user
              requirements."
          ::= { sfrapCfgAppTable 2 }

sfrapCfgAppType    OBJECT-TYPE
          SYNTAX      INTEGER
          {
               dedicated   (1),
               frame-relay (2)   
          } 
          ACCESS      read-write
          STATUS      mandatory
          DESCRIPTION
             "This unit provides many features specifically adapted 
              to Frame Relay transmission links; this includes diagnostic 
              utilities, statistical analysis, protocol trends, quality of 
              service reporting, and in-band SNMP management. If the unit 
              will be operating in a Frame Relay network the Application Type
              must be set to Frame Relay to enable these features. To 
              operate in a non-Frame Relay network or to bypass this feature
              set the unit may be placed in Dedicated mode and will emulate a
              more familiar DSU/CSU. Note - changing this value will 
              automatically change the Application Format setting and vice 
              versa.
              (1) dedicated: protocol-independent transparent DSU/CSU
              (2) Frame Relay: Frame and protocol aware DSU/CSU"
          ::= { sfrapCfgAppTable 3 }

sfrapCfgAppFormat OBJECT-TYPE
          SYNTAX      INTEGER
          {
               cbo         (1),
               hdlc        (2)
          }
          ACCESS      read-write
          STATUS      mandatory
          DESCRIPTION
              "Refer to Application Type. Frame Relay is based upon
               HDLC framing. To operate in a Frame Relay application
               the Format must be set for HDLC. To operate in a
               protocol-independent application the Format must be 
               set for Constant Bit Operation (CBO). Note - changing 
               this value will automatically change the Application 
               Type setting and vice versa
               (1) CBO: protocol-independent transparent DSU/CSU
               (2) HDLC: Frame and protocol aware DSU/CSU"
     ::= { sfrapCfgAppTable 4 }

sfrapCfgAppLpbkTimeout OBJECT-TYPE
          SYNTAX      INTEGER (0..1440)
          ACCESS      read-write
          STATUS      mandatory
          DESCRIPTION
             "The length of time a service-impacting loopback
              or diagnostic utility may run before automatically 
              returning to normal operation. This setting will
              override any alternatively timed tests (such as 
              VBERT).
              (0) Loopbak Timeout Disabled
              (1-1440) Loopback Timeout"
     ::= { sfrapCfgAppTable 5 }

sfrapCfgAppTxClkmode OBJECT-TYPE
          SYNTAX      INTEGER
          {
               normal-timing   (1),
               invert-TO-DCE   (2),
               invert-TO-DTE   (3),
               invert-timing   (4)
          }               
          ACCESS      read-write
          STATUS      mandatory
          DESCRIPTION
             "This MIB object is being obsoleted.
              The mode in which the TO-DTE and TO-DCE Transmit
              clocks are set to.  The transmit clocks can either
              be normal or inverted.  Here are the choices:
               1:Normal-timing   both TO-DTE & TO-DCE are set normal
               2:Invert-TO-DCE   the TO-DCE clock is inverted
               3:Invert-TO-DTE   the TO-DTE clock is inverted
               4:Invert-timing   both TO-DTE & TO-DCE are inverted."
     ::= { sfrapCfgAppTable 6 }
     
sfrapCfgAppTxtiming    OBJECT-TYPE
     SYNTAX      INTEGER  
     {
        loop-1                (1),
        loop-2                (2),
        source-tt         (3)
     }
     ACCESS        read-write
     STATUS        mandatory
     DESCRIPTION
      "Serial Transmit Timing mode. Loop-1 (1) uses the clock  
      returned from the TO-DTE (TT/TCE) to sample tx data, Loop-2 (2) 
      uses the clock (ST/TC) generated by the node to sample tx 
      data. Sourced-tt (3) occurs when the unit is configured for Loop-1
      and the clock returned from the TO-DTE (TT/TCE)is not present. The unit
      will use the (ST/TC) to sample tx data."
    ::= { sfrapCfgAppTable 7 }

sfrapCfgAppOperationMode    OBJECT-TYPE
      SYNTAX      INTEGER  
     {
        tap                        (1),
        inband                     (2)
     }
     ACCESS        read-write
     STATUS        mandatory
     DESCRIPTION
           "Describes the Operational Mode of the SFRAP:
               (1) cut-through   used to place unit in cut-thru
               (2) inband        used to place unit in inband."
     ::= { sfrapCfgAppTable 8 }

sfrapCfgAppCutthruTimeout OBJECT-TYPE
          SYNTAX      INTEGER (0..1440)
          ACCESS      read-write
          STATUS      mandatory
          DESCRIPTION
             "The amount of time Cuthtru mode may run before
              timing out and automatically terminating.
              The timeout is in minutes and a value of 0
              means no timeout."
     ::= { sfrapCfgAppTable 9 }


sfrapCfgAppPerfBuffLimit OBJECT-TYPE
          SYNTAX      INTEGER (0..512)
          ACCESS      read-write
          STATUS      mandatory
          DESCRIPTION
             "This value controls the throttling mechanism
              used to determine the optimum level of statistical
              processing versus manageability of the unit. The
              lower the value (1 - 128), the unit becomes more
              responsive to management commands during very heavy
              utilization at the possible expense of statistical 
              accuracy.  The larger the value (129 - 512), the more 
              accurate the SFRAP performs statistical analysis of the 
              frames but management may seem slow or unresponsive 
              during periods of very heavy link utilization.
              NOTE: A value of 0 disables statistical processing entirely."
      ::= { sfrapCfgAppTable 10 }
--
--       The DTE Configuration Table
--              This table contains the Configuration information
--              for the TO-DTE and TO-DCE ports.

sfrapCfgDteTable   OBJECT-TYPE
         SYNTAX   SEQUENCE OF SfrapCfgDteEntry
         ACCESS   not-accessible
         STATUS   mandatory
         DESCRIPTION
            "The table of DTE port configurations."
         ::= { sfrapConfiguration 4 }

sfrapCfgDteEntry   OBJECT-TYPE
         SYNTAX   SfrapCfgDteEntry
         ACCESS   not-accessible
         STATUS   mandatory
         DESCRIPTION
            "A configuration entry for a DTE port."
         INDEX { sfrapCfgDteIndex }
            ::= { sfrapCfgDteTable 1 }

SfrapCfgDteEntry ::=
         SEQUENCE {
             sfrapCfgDteIndex             INTEGER,
             sfrapCfgDteIntfType          INTEGER,
             sfrapCfgDteTxClockMode       INTEGER,
             sfrapCfgDteRxClockMode       INTEGER,
             sfrapCfgDteRtsC              INTEGER
         }

sfrapCfgDteIndex         OBJECT-TYPE  
     SYNTAX       INTEGER
     {
         to-dte   (1),
         to-dce   (2)
     }
     ACCESS       read-only
     STATUS       mandatory
     DESCRIPTION
     "Selects which DTE port."
     ::= { sfrapCfgDteEntry 99 }

sfrapCfgDteIntfType    OBJECT-TYPE
     SYNTAX      INTEGER  
     {
         intf-v35       (3),
         intf-rs449     (4),
         intf-x21       (5)
     }
     ACCESS        read-only
     STATUS        mandatory
     DESCRIPTION
      "Gets the electrical interface for the DTE port."
     ::= { sfrapCfgDteEntry 1 }

sfrapCfgDteTxClockMode    OBJECT-TYPE
     SYNTAX      INTEGER  
     {
        clock-normal    (1),
        clock-invert    (2)
     }
     ACCESS        read-write
     STATUS        mandatory
     DESCRIPTION
        "This selection controls how the unit internally latches 
         the transmit data from the DTE. Normal will sample
         data with the rising edge of the selected TX Clock, 
         Invert will sample data with the falling edge of the 
         selected TX Clock. The TX Clock is selected using 
         CfgDteTiming. This clock invertion is most useful when 
         loop-2 timing is used - particularly at higher rates 
         and with long cable runs. Only in rare circumstances 
         will clock-invert be used with loop-1 timing. If the 
         DTE Interface TX statistics are indicating excessive 
         crc errors or aborts then changing this setting may have
         some benefit.
         (1) normal
         (2) invert"
    ::= { sfrapCfgDteEntry 3 }

sfrapCfgDteRxClockMode    OBJECT-TYPE
     SYNTAX      INTEGER  
     {
        clock-normal    (1),
        clock-invert    (2),
        clock-auto      (3)
     }
     ACCESS        read-write
     STATUS        mandatory
     DESCRIPTION
        "Clock-normal samples data with the rising edge of the 
         selected rx clock, clock-invert samples data with the 
         falling edge of the selected rx clock,auto-sense forces
         hardware automated clock selection. The rx clock is 
         selected using CfgDteTiming. This clock invertion is 
         most useful when loop-2 timing is used. Only in rare 
         circumstances will clock-invert (2) be used with loop-1 
         timing. (3)Auto-sense can only be used on the TO-DTE 
         interface.  Auto-sense automatically determines what 
         kind of clocking to use on the TO-DTE interface. THIS 
         OBJECT IS OBSOLETE ON THE TO-DCE INTERFACE"
    ::= { sfrapCfgDteEntry 21 }

sfrapCfgDteRtsC         OBJECT-TYPE  
     SYNTAX       INTEGER
     {
         signal-assumed-active (1),
         signal-monitored      (2)
     }
     ACCESS       read-write
     STATUS       mandatory
     DESCRIPTION
     "Controls the reporting of the status of the To-DTE port's
      Request to Send (RTS) and Control (C) control signals,
      specifically the generation of traps in response to control
      signal state changes. If Signal Assumed Active, the unit
      will ignore the actual status and always report this signal
      Active. If Signal Monitored, the unit will reflect the status
      as driven by the To-DTE; as such, Traps will be generated
      due to change of state (these may be useful for a network 
      manager's assessment of interface status.
      (1) Signal Assumed Active
      (2) Signal Monitored"
    ::= { sfrapCfgDteEntry 22 }

--
--       The FrameRelay Configuration Table
--              This table contains the Configuration for the Frame Relay
--              support on the sfrap DSU.


sfrapCfgFrTable OBJECT IDENTIFIER ::= { sfrapConfiguration 5 }

sfrapCfgFrAddrLen  OBJECT-TYPE
          SYNTAX      INTEGER
          {
              twobytes       (1),
              threebytes     (2),
              fourbytes      (3)
          }
          ACCESS      read-write
          STATUS      mandatory
          DESCRIPTION
             "Defines the size of the DLCI address field of the Frame Relay
              header. This setting must correspond to the Frame Relay 
              transmission format; typically Two bytes.
              (1) two byte DLCI address field
              (2) three byte DLCI address field
              (3) four byte DLCI address field"         
          ::= { sfrapCfgFrTable 1 }
 
sfrapCfgFrCrcMode  OBJECT-TYPE
          SYNTAX      INTEGER
          {
              discard        (1),
              passthru       (2)
          }
          ACCESS      read-write
          STATUS      mandatory
          DESCRIPTION
             "This defines the manner in which the unit handles HDLC
              protocol errors (crc errors) in a Frame Relay application. 
              If Discard is selected the unit will respond to an errored 
              frame by aborting the frame if transmission has begun; or 
              simply discarding it if transmission has not begun. If 
              Passthru is selected the unit will transmit the entire frame 
              but will place an incorrect crc in it to preserve the error 
              indication.
              (1) discard
              (2) passthru"
          ::= { sfrapCfgFrTable 2 }

sfrapCfgFrLmiType  OBJECT-TYPE
          SYNTAX      INTEGER
          {
              annexd         (1),
              annexa         (2),
              type1          (3),
              autosense      (4)
          }
          ACCESS      read-write
          STATUS      mandatory
          DESCRIPTION
        "The LMI type used in a Frame Relay application. This setting
         must match the attached Frame Relay device configuration. 
         Annex-A and Annex-D use DLCI 0, and Type 1 uses DLCI 1023.
         Type 1 is alternatively referred to as Cisco, Group of four, 
         or simply LMI. Annex-D may be referred to as ANSI T1.617.
         Annex-A may be referred to as ITU or CCITT Q.933. Auto-sense
         will either use the most recently detected LMI type or, in 
         the absence of any LMI, will attempt to instigate LMI 
         communications using each protocol.     
         (1) Annnex-A: conforms to ITU (CCITT) Q.933 annex A
         (2) Annnex-D: conforms to ANSI T1.617 annex D
         (3) Type 1: conforms to the original LMI as developed by 
             the Group of Four
         (4) Auto-sense: unit will attempt to detect and synchronize
             to the LMI type of the attached equipment."
          ::= { sfrapCfgFrTable 3 }

sfrapCfgFrLmiInactivityTimeout  OBJECT-TYPE
          SYNTAX      INTEGER (0..255)
          ACCESS      read-write
          STATUS      mandatory
          DESCRIPTION
        "Timer used by the unit to determine that an attached device is
         not participating in the LMI protocol and that the unit should 
         attempt to source LMI. This timer also controls the length of 
         time that the LMI sourcing state machine remains in a particular 
         state as it attempts to locate an LMI peer.
         (0) LMI Sourcing disabled
         (2-255) LMI Inactivity timeout"
          ::= { sfrapCfgFrTable 4 }

sfrapCfgFrLmiKeepaliveTimeout  OBJECT-TYPE
          SYNTAX      INTEGER (2..255)
          ACCESS      read-write
          STATUS      mandatory
          DESCRIPTION
        "Timer used by the unit to determine the frequency at which Status
         Enquiries are issued during LMI sourcing states where the unit is 
         emulating a Frame Relay DTE device.
         (2-255) length of time between sending enquiries (in seconds)"
          ::= { sfrapCfgFrTable 5 }

sfrapCfgFrAddrResMode OBJECT-TYPE
         SYNTAX      INTEGER
         {
              inactive (1),
              arp      (2),
              inarp    (3),
              both     (4)
         }
         ACCESS      read-write
         STATUS      mandatory
         DESCRIPTION
            "Enable ARP (2), INARP (3), both (4), or neither (1)."
         ::= { sfrapCfgFrTable 6 }

sfrapCfgFrAddrResDlcis OBJECT-TYPE
         SYNTAX      INTEGER
         {
              single        (1),
              multiple      (2),
              todcemulti    (3),
              todtemulti    (4)
         }
         ACCESS      read-write
         STATUS      mandatory
         DESCRIPTION
            "Address Resolution Dlcis determines which dlcis are
             used for address resolution.  The choices include
             using the configured management dlci only (1), all
             dlcis (2), all dlcis on the To-DCE port (3) or all
             dlcis on the To-DTE port (4).  In the last two cases,
             the management dlci is used on the other port.
             Multiple DLCI support only applies to piggyback mode;
             in other management modes, only the configured
             management dlci is used."
         ::= { sfrapCfgFrTable 9 }


sfrapCfgFrAddrResInarpTimer OBJECT-TYPE
         SYNTAX      INTEGER (5..86400)
         ACCESS      read-write
         STATUS      mandatory
         DESCRIPTION
            "The frequency of INARP requests in seconds
             from 5 seconds to 86400 seconds (24 hours)."
         ::= { sfrapCfgFrTable 7 }


sfrapCfgFrLmiFullStatus  OBJECT-TYPE
          SYNTAX      INTEGER (0..3600)
          ACCESS      read-write
          STATUS      mandatory
          DESCRIPTION
             "Timer used by the unit to determine if an LMI Full Status
              Report is missing. In the absence of a Full Status report
              for the duration defined by this timer, the unit will
              declared all DLCI's status INACTIVE and begin logging
              down time. Data passage is not interfered with.
              (0) Full Status Timer is disabled
              (20-3600) Full Status Report Timeout in seconds."
          ::= { sfrapCfgFrTable 8 }

--
--       The VNIP Configuration Table
--              This table contains the Configuration for the VNIP
--              protocol support on the sfrap DSU.

sfrapCfgVnipTable OBJECT IDENTIFIER ::= { sfrapConfiguration 6 }

   sfrapCfgVnipMode OBJECT-TYPE
         SYNTAX      INTEGER
         {
              inactive (1),
              to-dte   (2),
              to-dce   (3),
              both     (4)
         }
         ACCESS      read-write
         STATUS      mandatory
         DESCRIPTION
            "This setting configures the unit for VNIP topology support on
             a per-interface basis. Establishing a VNIP topology is a
             fundamental prerequisite to applying the VNIP feature set which 
             includes PVC-based delay measurement, diagnostics, and congestion
             monitoring. With VNIP enabled on an interface the unit
             will attempt to locate VNIP peers out that port. As peers are 
             discovered and logged the unit will report the topology it has 
             learned on its opposite interface. If VNIP is inactive on one
             interface it will not engage in any VNIP dialog; however it will 
             continue to listen for topology messages on the inactive interface
             and will reflect these messages out the opposite interface if VNIP 
             is enabled. With VNIP inactive on both interfaces the unit will 
             transparently pass all VNIP messages. The topology database includes
             ip addresses, DLCI values, and the number of VNIP hops in between.
             (1) Topology Inactive: VNIP messages pass through unit
             (2) Topology Enabled on TO-DTE only: unit logs VNIP peers seen
                 out the TO-DTE interface. Unit listens for topology reports
                 from the WAN but doesn't generate any towards the WAN. Will 
                 report learned WAN topology towards the TO-DTE.
             (3) Topology Enabled on WAN only: unit logs VNIP peers seen
                 out the WAN interface. Unit listens for topology reports
                 from the TO-DTE but doesn't generate any towards the TO-DTE. Will 
                 report learned TO-DTE topology towards the WAN.
             (4) Topolgy Enabled on Both TO-DTE and WAN: Unit logs VNIP peers
                 seen out both interfaces and generates TO-DTE topolgy reports 
                 towards the WAN and vice versa."
         ::= { sfrapCfgVnipTable 1 }

   sfrapCfgVnipInitTimer OBJECT-TYPE
         SYNTAX      INTEGER (5..86400)
         ACCESS      read-write
         STATUS      mandatory
         DESCRIPTION
           "VNIP peer to peer communications are initiated following
            the detection of a VNIP Hello message. The unit will
            periodically issue this message out interfaces that have 
            VNIP enabled until a Hello response is received. Following 
            the reception of the Hello response, the unit will stop 
            issuing Hello messahges on that DLCI/interface and generate 
            periodic topology reports at the VNIP Keep Alive frequency. 
            The unit will generate periodic Hello messages, at the 
            InitTimer frequency if no Hello responses are ever detected 
            or a topology message not been detected within the time period 
            defined by the VNIP Inactivity timer.
            (5-86400) VNIP Hello frequency (in seconds)"
         ::= { sfrapCfgVnipTable 2 }

   sfrapCfgVnipTxTimer OBJECT-TYPE
         SYNTAX      INTEGER (5..86400)
         ACCESS      read-write
         STATUS      mandatory
         DESCRIPTION
            "The frequency of hello messages sent
             to neighbor(s) in seconds from
             5 seconds to 86400 seconds (24 hours)."
         ::= { sfrapCfgVnipTable 3 }

   sfrapCfgVnipRxTimer OBJECT-TYPE
         SYNTAX      INTEGER (5..86400)
         ACCESS      read-write
         STATUS      mandatory
         DESCRIPTION
            "The timeout on receiving a hello message
             from a neighbor in seconds from
             5 seconds to 86400 seconds (24 hours)."
         ::= { sfrapCfgVnipTable 4 }


   sfrapCfgVnipTransitDelayFrequency OBJECT-TYPE
         SYNTAX      INTEGER (15..86400)
         ACCESS      read-write
         STATUS      mandatory
         DESCRIPTION
            "Transit Delay measurements may be enabled between any DLCI
             peers that have been logged through the topology protocol.
             Delay messages are issued at this frequency and results are
             recorded. Transit delay measures the round-trip network
             delay between two VNIP peers (internal unit latencies are
             not part of the measurement). Traps may be optionally generated 
             if a delay threshold is exceeded.
             (15-86400): Transit Delay message frequency (in seconds)"
         ::= { sfrapCfgVnipTable 5 }


   sfrapCfgTransitDelayTable   OBJECT-TYPE
         SYNTAX   SEQUENCE OF SfrapCfgTransitDelayEntry
         ACCESS   not-accessible
         STATUS   mandatory
         DESCRIPTION
            "The table defining the transit delay measurement profile for
             each of the learned VNIP peers. As peers are located and 
             logged into the topology database, a default transit delay
             profile is assumed. The default is to enable transit delay
             to all hops located out the interface. A DLCI's transit
             delay profile cannot be modified unless the DLCI has been
             discovered through the VNIP topology protocol."
         ::= { sfrapCfgVnipTable 20 }

      sfrapCfgTransitDelayEntry OBJECT-TYPE
          SYNTAX      SfrapCfgTransitDelayEntry
          ACCESS      not-accessible
          STATUS      mandatory
          DESCRIPTION
             "A VNIP Transit Delay configuration entry for a particular 
              DLCI on a particular interface. A DLCI's transit delay 
              profile cannot be modified unless the DLCI has been
              discovered through the VNIP topology protocol"
          INDEX { sfrapCfgTransitDelayInterface, sfrapCfgTransitDelayDlciValue }
          ::= { sfrapCfgTransitDelayTable 1 }

      SfrapCfgTransitDelayEntry ::=
          SEQUENCE
          {
               sfrapCfgTransitDelayInterface         INTEGER,
               sfrapCfgTransitDelayDlciValue         INTEGER,
               sfrapCfgTransitDelayNumHops           INTEGER,
               sfrapCfgTransitDelayRcvSummaryCancel  INTEGER,
               sfrapCfgTransitDelayThreshold         INTEGER
          }

      sfrapCfgTransitDelayInterface OBJECT-TYPE
         SYNTAX      INTEGER
         {
              to-dte-interface (1),
              to-dce-interface (2)
         }
         ACCESS      read-write
         STATUS      mandatory
         DESCRIPTION
              "The interface being configured for VNIP
               Transit Delay, either to-dte-interface (1)
               or to-dce-interface (2).  This table is
               indexed by {interface,dlci}."
         ::= { sfrapCfgTransitDelayEntry 1 }

      sfrapCfgTransitDelayDlciValue    OBJECT-TYPE
          SYNTAX      INTEGER 
          ACCESS      read-write
          STATUS      mandatory
          DESCRIPTION
             "This is the DLCI being configured for VNIP Transit 
              Delay. If topology is enabled, each interface will contain 
              a database of VNIP peers organized by DLCI value and 
              Number of Hops."
          ::= { sfrapCfgTransitDelayEntry 2 }

      sfrapCfgTransitDelayNumHops    OBJECT-TYPE
          SYNTAX      INTEGER (0..255)
          ACCESS      read-write
          STATUS      mandatory
          DESCRIPTION
             "VNIP topolgy may include multiple units on a given
              DLCI/interface. The topology logs the number of 
              intermediate VNIP peers between units (Hops). This 
              setting determines which peers on a DLCI are participating
              in delay measurements.
              (0) All hops
              (1-254) individually addressable delay measurement
                  between any two peers.
              (255) Furthest hop only"
          ::= { sfrapCfgTransitDelayEntry 4 }

      sfrapCfgTransitDelayRcvSummaryCancel    OBJECT-TYPE
          SYNTAX      INTEGER 
          {
               enable-rsc  (1),
               disable-rsc (2)
          }
          ACCESS      read-write
          STATUS      mandatory
          DESCRIPTION
             "Controls the Receive Summary Cancellation feature of VNIP 
              Transit Delay on this interface/DLCI. Every Transit Delay
              measurement exchange includes a follow-up message from the 
              initiator with the delay results. If RSC is enabled, a unit
              will log results based upon this summary message and will 
              not issue its next scheduled delay measurement. With RSC 
              disabled, the unit will not use the summary message and 
              will always issue its regularly scheduled message based on
              the delay frequency timer. The purpose of this feature is to
              reduce traffic introduced by VNIP. In a typical peer-to-peer
              transit delay measurement where both ends are concurrently
              conducting transit delay measurements it's recommended that 
              one end have RSC enabled and one end disabled."
          ::= { sfrapCfgTransitDelayEntry 5 }

      sfrapCfgTransitDelayThreshold    OBJECT-TYPE
          SYNTAX      INTEGER (0..86400000)
          ACCESS      read-write
          STATUS      mandatory
          DESCRIPTION
             "Specifies a transit delay threshold for this DLCI/interface.
              When the transit delay exceeds the threshold, a TRAP is sent. 
              The threshold may be set from one millisecond to 24 hours.
              A value of 0 will prevent a TRAP from being sent.
              (0): Transit delay threshold trap disabled for this DLCI/interface
              (1-86400000): delay threshhold. Any delay measurements exceeding
                  this result will generate a trap."
          ::= { sfrapCfgTransitDelayEntry 6 }


   sfrapCfgTDDeleteTable   OBJECT-TYPE
         SYNTAX   SEQUENCE OF SfrapCfgTDDeleteEntry
         ACCESS   not-accessible
         STATUS   mandatory
         DESCRIPTION
            "The table allows the user to disable transit delay measurements
             for a specific DLCI on a particular interface."
         ::= { sfrapCfgVnipTable 21 }

      sfrapCfgTDDeleteEntry OBJECT-TYPE
          SYNTAX      SfrapCfgTDDeleteEntry
          ACCESS      not-accessible
          STATUS      mandatory
          DESCRIPTION
             "Disables VNIP Transit Delay for a particular interface and DLCI." 
          INDEX { sfrapCfgTDDeleteInterface }
          ::= { sfrapCfgTDDeleteTable 1 }

      SfrapCfgTDDeleteEntry ::=
          SEQUENCE
          {
               sfrapCfgTDDeleteInterface    INTEGER,
               sfrapCfgTDDeleteDlciValue    INTEGER
          }

      sfrapCfgTDDeleteInterface OBJECT-TYPE
         SYNTAX      INTEGER
         {
              to-dte-interface (1),
              to-dce-interface (2)
         }
         ACCESS      not-accessible
         STATUS      mandatory
         DESCRIPTION
            "Transit delay can be disabled for a given DLCI on
             either interface. This indexes the interface. 
             Setting this index and the associated DLCI index
             will disable transit delay on that combination."
         ::= { sfrapCfgTDDeleteEntry 1 }

      sfrapCfgTDDeleteDlciValue    OBJECT-TYPE
         SYNTAX      INTEGER 
         ACCESS      write-only
         STATUS      mandatory
         DESCRIPTION
            "The DLCI chosen to be deleted from the specified
             interface-side of the VNIP Transit Delay
             configuration table. This table is indexed by
             {interface}. To delete an entry in the
             sfrapCfgTransitDelayTable, specify the interface
             as the index and set the dlci."
          ::= { sfrapCfgTDDeleteEntry 2 }

   sfrapCfgTransitDelayTableClear  OBJECT-TYPE
         SYNTAX      INTEGER
         {
               clear-table   (1)
         }
         ACCESS      write-only
         STATUS      mandatory
         DESCRIPTION
            "The sfrapCfgTransitDelayTable is cleared.
             (1) clear the table "
         ::= { sfrapCfgVnipTable 22 }


--       The Frame Relay Performance Configuration
--              A group of configuration tables supporting frame relay
--              performance measurement on the sfrap DSU.

sfrapCfgFrPerf OBJECT IDENTIFIER ::= { sfrapConfiguration 7 }

  sfrapCfgFrPerfDlciNamesTable   OBJECT-TYPE
          SYNTAX      SEQUENCE OF SfrapCfgFrPerfDlciNamesEntry
          ACCESS      not-accessible
          STATUS      mandatory
          DESCRIPTION
             "This table allows the user to configure DLCI
              specific parameters such as Names, CIR, and EIR. 
              Additionally, any DLCIs configured with these
              parameters will be added into the Short Term 
              statistics database next time its cleared."
          ::= { sfrapCfgFrPerf 1 }

      sfrapCfgFrPerfDlciNamesEntry OBJECT-TYPE
          SYNTAX      SfrapCfgFrPerfDlciNamesEntry
          ACCESS      not-accessible
          STATUS      mandatory
          DESCRIPTION
             "A table entry indexed by DLCI, containing
              a DLCI, a DLCI name, a CIR, and how the
              CIR value was obtained." 
          INDEX { sfrapCfgFrPerfDlciNamesDlciValue }
          ::= { sfrapCfgFrPerfDlciNamesTable 1 }

      SfrapCfgFrPerfDlciNamesEntry ::=
          SEQUENCE
          {
             sfrapCfgFrPerfDlciNamesDlciValue     INTEGER,
             sfrapCfgFrPerfDlciNamesDlciName      DisplayString (SIZE (0..15)),
             sfrapCfgFrPerfDlciNamesCirValue      INTEGER,
             sfrapCfgFrPerfDlciNamesCirType       INTEGER,
             sfrapCfgFrPerfDlciNamesUtilThreshold INTEGER,
             sfrapCfgFrPerfDlciNamesEirValue      INTEGER
          } 

      sfrapCfgFrPerfDlciNamesDlciValue    OBJECT-TYPE
          SYNTAX      INTEGER 
          ACCESS      read-write
          STATUS      mandatory
          DESCRIPTION
             "A DLCI selected for customized configuration and to 
              be added to short term statistics collection (if it
              wasn't already there)."
          ::= { sfrapCfgFrPerfDlciNamesEntry 1 }

      sfrapCfgFrPerfDlciNamesDlciName   OBJECT-TYPE
          SYNTAX      DisplayString (SIZE (0..15))
          ACCESS      read-write
          STATUS      mandatory
          DESCRIPTION
             "A user-specifiable name for an individual DLCI."
          ::= { sfrapCfgFrPerfDlciNamesEntry 2 }

      sfrapCfgFrPerfDlciNamesCirValue    OBJECT-TYPE
          SYNTAX      INTEGER 
          ACCESS      read-write
          STATUS      mandatory
          DESCRIPTION
             "The CIR value for an individual DLCI. This
              value is used in the calculation utilization
              as a percentage of CIR. If the CIR is reported 
              in the LMI message then the reported value will
              override this configured entry. In the absence
              of LMI CIR and a configured CIR, the unit will
              assume that teh CIR is the DTE Line Rate."
          ::= { sfrapCfgFrPerfDlciNamesEntry 3 }

      sfrapCfgFrPerfDlciNamesCirType    OBJECT-TYPE
          SYNTAX      INTEGER 
          {
               cir-acquired-from-lmi  (1),
               cir-configured-by-user (2),
               cir-is-datarate        (3)
          }
          ACCESS      read-only
          STATUS      mandatory
          DESCRIPTION
             "The source of the CIR value for this DLCI.
              If CIR for a DLCI is part of the LMI message
              then this LMI supplied CIR will override any 
              defined CIR. If CIR is not part of LMI and
              has not been explicitly defined by the user
              it will default to the TO-DTE Line Rate.
              (1) CIR reported in LMI Full Status message
              (2) CIR configured by user
              (3) CIR defaulted to TO-DTE Line Rate"
          ::= { sfrapCfgFrPerfDlciNamesEntry 4 }

      sfrapCfgFrPerfDlciNamesUtilThreshold  OBJECT-TYPE
          SYNTAX      INTEGER  (0..100) 
          ACCESS      read-write
          STATUS      mandatory
          DESCRIPTION
             "The threshold for generating a utilization 
              threshold trap as a percentage of the CIR.  
              If the utilization percentage is above this 
              threshold for more than 
              sfrapCfgFrPerfDlciUtilThreshold number of
              sfrapCfgFrPerfTimersSTInterval's a
              sfrapPvc(Rx/Tx)UtilizationExceeded trap
              will be issued.  If the If the utilization 
              percentage falls below this threshold for 
              more than sfrapCfgFrPerfDlciUtilThreshold 
              number of sfrapCfgFrPerfTimersSTInterval's a
              sfrapPvc(Rx/Tx)UtilizationExceeded trap
              will be issued."
          ::= { sfrapCfgFrPerfDlciNamesEntry 5}

      sfrapCfgFrPerfDlciNamesEirValue    OBJECT-TYPE
          SYNTAX      INTEGER 
          ACCESS      read-write
          STATUS      mandatory
          DESCRIPTION
             "The EIR value for an individual DLCI. In the 
              absence of a configured EIR, the unit will
              assume that the EIR is the DTE Line Rate."
          ::= { sfrapCfgFrPerfDlciNamesEntry 6 }

         
   sfrapCfgFrPerfDlciNamesDelete   OBJECT-TYPE
          SYNTAX      INTEGER 
          ACCESS      write-only
          STATUS      mandatory
          DESCRIPTION
             "Setting this object with a specific DLCI value
              will remove the DLCI form the DLCI-specific
              parameters database."
          ::= { sfrapCfgFrPerf 2 }

  sfrapCfgFrPerfTimers OBJECT IDENTIFIER ::= { sfrapCfgFrPerf 3 }

      sfrapCfgFrPerfTimersSTInterval   OBJECT-TYPE
          SYNTAX      INTEGER (3..60)
          ACCESS      read-write
          STATUS      mandatory
          DESCRIPTION
            "The interval in seconds to collect short term
             statistics before moving the current counts into the
             previous counts and starting current from zeros.
             The range is 3 to 60 seconds."
          ::= { sfrapCfgFrPerfTimers 1 }

      sfrapCfgFrPerfTimersLTInterval   OBJECT-TYPE
          SYNTAX      INTEGER (4..3600)
          ACCESS      read-write
          STATUS      mandatory
          DESCRIPTION
             "Long term statistics maintain 96 contiguous intervals
              of configurable protocol per DLCI statistics. This value
              is the window size of each interval. Adjusting this value
              will change the overall length of time that the 96 intervals
              will span.
             (4-3600): long term statsistics collection interval"
          ::= { sfrapCfgFrPerfTimers 2 }

   sfrapCfgFrPerfUserProtocolsTable   OBJECT-TYPE
          SYNTAX      SEQUENCE OF SfrapCfgFrPerfUserProtocolsEntry
          ACCESS      not-accessible
          STATUS      mandatory
          DESCRIPTION
             "This table allows the user to select TCP/UDP ports 
              for statistics collection.  Tx and Rx byte counts
              will collected on the specified ports.  These ports
              are selectable as protocols in the long term
              statistics filter and are displayed with the other
              protocols in the short term statistics."
          ::= { sfrapCfgFrPerf 4 }

      sfrapCfgFrPerfUserProtocolsEntry OBJECT-TYPE
          SYNTAX      SfrapCfgFrPerfUserProtocolsEntry
          ACCESS      not-accessible
          STATUS      mandatory
          DESCRIPTION
             "An index and TCP/UDP port number pair." 
          INDEX { sfrapCfgFrPerfUserProtocolsIndex }
          ::= { sfrapCfgFrPerfUserProtocolsTable 1 }

      SfrapCfgFrPerfUserProtocolsEntry ::=
          SEQUENCE
          {
               sfrapCfgFrPerfUserProtocolsIndex     INTEGER,
               sfrapCfgFrPerfUserProtocolsPortNum   INTEGER
          } 

      sfrapCfgFrPerfUserProtocolsIndex    OBJECT-TYPE
          SYNTAX      INTEGER 
          ACCESS      read-only
          STATUS      mandatory
          DESCRIPTION
             "An index. Beginning with index 1, the range is defined 
              in SysNumUserProtocols"
          ::= { sfrapCfgFrPerfUserProtocolsEntry 1 }

      sfrapCfgFrPerfUserProtocolsPortNum   OBJECT-TYPE
          SYNTAX      INTEGER
          ACCESS      read-write
          STATUS      mandatory
          DESCRIPTION
            "Tx and Rx byte counts will be collected on
             the user-specifiable TCP/UDP port number.
             (0) port not defined
             (1-65535): IP TCP/UDP protocol port number."
          ::= { sfrapCfgFrPerfUserProtocolsEntry 2 }

   sfrapCfgFrPerfLTDlciFilterTable       OBJECT-TYPE
          SYNTAX      SEQUENCE OF SfrapCfgFrPerfLTDlciFilterEntry
          ACCESS      not-accessible
          STATUS      mandatory
          DESCRIPTION
             "Long term statistics can only be collected
              on a limited number of DLCIs. The value of
              SysLTFNumDlcis defines the maximum number of
              DLCIs that can be included in the Long Term
              Statistics. Once one or more DLCIs are added
              to Long Term Stats, the user may assign a 
              set of protocols that will be monitored across
              all of the Long Term DLCIs."
          ::= { sfrapCfgFrPerf 5 }

      sfrapCfgFrPerfLTDlciFilterEntry OBJECT-TYPE
          SYNTAX      SfrapCfgFrPerfLTDlciFilterEntry
          ACCESS      not-accessible
          STATUS      mandatory
          DESCRIPTION
             "An index and DLCI number pair." 
          INDEX { sfrapCfgFrPerfLTDlciFilterIndex }
          ::= { sfrapCfgFrPerfLTDlciFilterTable 1 }

      SfrapCfgFrPerfLTDlciFilterEntry ::=
          SEQUENCE
          {
               sfrapCfgFrPerfLTDlciFilterIndex     INTEGER,
               sfrapCfgFrPerfLTDlciFilterDlciNum   INTEGER
          } 

      sfrapCfgFrPerfLTDlciFilterIndex    OBJECT-TYPE
          SYNTAX      INTEGER 
          ACCESS      read-only
          STATUS      mandatory
          DESCRIPTION
             "An index. Beginning with index 1, the maximum is 
              defined by the value of SysLTFNumDlcis."
          ::= { sfrapCfgFrPerfLTDlciFilterEntry 1 }

      sfrapCfgFrPerfLTDlciFilterDlciNum   OBJECT-TYPE
          SYNTAX      INTEGER
          ACCESS      read-write
          STATUS      mandatory
          DESCRIPTION
             "Setting a DLCI value here will add that DLCI into
              the Long term statistics database (associated with 
              its index) and it will be monitored for the protocol 
              activity defined in the Long Term Protocol filter."
          ::= { sfrapCfgFrPerfLTDlciFilterEntry 2 }


   sfrapCfgFrPerfLTProtocolFilterTable   OBJECT-TYPE
          SYNTAX      SEQUENCE OF SfrapCfgFrPerfLTProtocolFilterEntry
          ACCESS      not-accessible
          STATUS      mandatory
          DESCRIPTION
             "Long term statistics can only be collected
              on a limited number of protocols. The maximum
              number of Long Term Protoocls are defined by 
              SysLTFNumProtocols. This table allows the user to 
              configure those protocols."
          ::= { sfrapCfgFrPerf 6 }

      sfrapCfgFrPerfLTProtocolFilterEntry OBJECT-TYPE
          SYNTAX      SfrapCfgFrPerfLTProtocolFilterEntry
          ACCESS      not-accessible
          STATUS      mandatory
          DESCRIPTION
             "An index and protocol pair." 
          INDEX { sfrapCfgFrPerfLTProtocolFilterIndex }
          ::= { sfrapCfgFrPerfLTProtocolFilterTable 1 }

      SfrapCfgFrPerfLTProtocolFilterEntry ::=
          SEQUENCE
          {
               sfrapCfgFrPerfLTProtocolFilterIndex      INTEGER,
               sfrapCfgFrPerfLTProtocolFilterProtocol   INTEGER
          } 

      sfrapCfgFrPerfLTProtocolFilterIndex    OBJECT-TYPE
          SYNTAX      INTEGER 
          ACCESS      read-only
          STATUS      mandatory
          DESCRIPTION
             "An index. Beginning with index 1, the maximum is 
              defined by the value of SysLTFNumProtocols."
          ::= { sfrapCfgFrPerfLTProtocolFilterEntry 1 }

      sfrapCfgFrPerfLTProtocolFilterProtocol   OBJECT-TYPE
          SYNTAX      INTEGER
          {
            ip-tx-bc                    (1),
            ip-rx-bc                    (2),
            tcp-ip-tx-bc                (3),
            tcp-ip-rx-bc                (4),
            ftp-tcp-ip-tx-bc            (5),
            ftp-tcp-ip-rx-bc            (6),
            telnet-tcp-ip-tx-bc         (7),
            telnet-tcp-ip-rx-bc         (8),
            smtp-tcp-ip-tx-bc           (9),
            smtp-tcp-ip-rx-bc           (10),
--          tftp-tcp-ip-tx-bc           (11),
--          tftp-tcp-ip-rx-bc           (12),
            http-tcp-ip-tx-bc           (13),
            http-tcp-ip-rx-bc           (14),
            netbios-ssn-tcp-ip-tx-bc    (15),
            netbios-ssn-tcp-ip-rx-bc    (16),
--          snmp-tcp-ip-tx-bc           (17),
--          snmp-tcp-ip-rx-bc           (18),
--          snmptrap-tcp-ip-tx-bc       (19),
--          snmptrap-tcp-ip-rx-bc       (20),
            udp-ip-tx-bc                (21),
            udp-ip-rx-bc                (22),
--          ftp-udp-ip-tx-bc            (23),
--          ftp-udp-ip-rx-bc            (24),
--          telnet-udp-ip-tx-bc         (25),
--          telnet-udp-ip-rx-bc         (26),
--          smtp-udp-ip-tx-bc           (27),
--          smtp-udp-ip-rx-bc           (28),
            tftp-udp-ip-tx-bc           (29),
            tftp-udp-ip-rx-bc           (30),
--          http-udp-ip-tx-bc           (31),
--          http-udp-ip-rx-bc           (32),
            netbios-dgm-udp-ip-tx-bc    (33),
            netbios-dgm-udp-ip-rx-bc    (34),
            snmp-udp-ip-tx-bc           (35),
            snmp-udp-ip-rx-bc           (36),
            snmptrap-udp-ip-tx-bc       (37),
            snmptrap-udp-ip-rx-bc       (38),
            rip-udp-ip-tx-bc            (39),
            rip-udp-ip-rx-bc            (40),
            icmp-ip-tx-bc               (41),
            icmp-ip-rx-bc               (42),
            echorep-icmp-ip-tx-bc       (43),
            echorep-icmp-ip-rx-bc       (44),
            dest-unr-icmp-ip-tx-bc      (45),
            dest-unr-icmp-ip-rx-bc      (46),
            src-quench-icmp-ip-tx-bc    (47),
            src-quench-icmp-ip-rx-bc    (48),
            redirect-icmp-ip-tx-bc      (49),
            redirect-icmp-ip-rx-bc      (50),
            echoreq-icmp-ip-tx-bc       (51),
            echoreq-icmp-ip-rx-bc       (52),
            time-excd-icmp-ip-tx-bc     (53),
            time-excd-icmp-ip-rx-bc     (54),
            param-prob-icmp-ip-tx-bc    (55),
            param-prob-icmp-ip-rx-bc    (56),
            timestamp-req-icmp-ip-tx-bc (57),
            timestamp-req-icmp-ip-rx-bc (58),
            timestamp-rep-icmp-ip-tx-bc (59),
            timestamp-rep-icmp-ip-rx-bc (60),
            addr-mask-req-icmp-ip-tx-bc (61),
            addr-mask-req-icmp-ip-rx-bc (62),
            addr-mask-rep-icmp-ip-tx-bc (63),
            addr-mask-rep-icmp-ip-rx-bc (64),
            pkt-too-big-icmp-ip-tx-bc   (65),
            pkt-too-big-icmp-ip-rx-bc   (66),
            gp-mem-query-icmp-ip-tx-bc  (67),
            gp-mem-query-icmp-ip-rx-bc  (68),
            gp-mem-report-icmp-ip-tx-bc (69),
            gp-mem-report-icmp-ip-rx-bc (70),
            gp-mem-reduct-icmp-ip-tx-bc (71),
            gp-mem-reduct-icmp-ip-rx-bc (72),
            ospf-ip-tx-bc               (73),
            ospf-ip-rx-bc               (74),
            other-ip-tx-bc              (75),
            other-ip-rx-bc              (76),
            ipx-tx-bc                   (77),
            ipx-rx-bc                   (78),
            spx-ipx-tx-bc               (79),
            spx-ipx-rx-bc               (80),
            ncp-ipx-tx-bc               (81),
            ncp-ipx-rx-bc               (82),
            sap-ipx-tx-bc               (83),
            sap-ipx-rx-bc               (84),
            rip-ipx-tx-bc               (85),
            rip-ipx-rx-bc               (86),
            netbios-ipx-tx-bc           (87),
            netbios-ipx-rx-bc           (88),
            other-ipx-tx-bc             (89),
            other-ipx-rx-bc             (90),
            arp-tx-bc                   (91),
            arp-rx-bc                   (92),
            arp-req-tx-bc               (93),
            arp-req-rx-bc               (94),
            arp-rep-tx-bc               (95),
            arp-rep-rx-bc               (96),
            rarp-req-tx-bc              (97),
            rarp-req-rx-bc              (98),
            rarp-rep-tx-bc              (99),
            rarp-rep-rx-bc              (100),
            inarp-req-tx-bc             (101),
            inarp-req-rx-bc             (102),
            inarp-rep-tx-bc             (103),
            inarp-rep-rx-bc             (104),
            sna-tx-bc                   (105),
            sna-rx-bc                   (106),
            sna-subarea-tx-bc           (107),
            sna-subarea-rx-bc           (108),
            sna-periph-tx-bc            (109),
            sna-periph-rx-bc            (110),
            sna-appn-tx-bc              (111),
            sna-appn-rx-bc              (112),
            sna-netbios-tx-bc           (113),
            sna-netbios-rx-bc           (114),
            cisco-tx-bc                 (115),
            cisco-rx-bc                 (116),
            other-tx-bc                 (117),
            other-rx-bc                 (118),
            user-defined-1-tx-bc        (119),
            user-defined-1-rx-bc        (120),
            user-defined-2-tx-bc        (121),
            user-defined-2-rx-bc        (122),
            user-defined-3-tx-bc        (123),
            user-defined-3-rx-bc        (124),
            user-defined-4-tx-bc        (125),
            user-defined-4-rx-bc        (126),
            thru-byte-tx-bc             (127),
            thru-byte-rx-bc             (128),
            thru-frame-tx-c             (129),
            thru-frame-rx-c             (130),
            thru-fecn-tx-c              (131),
            thru-fecn-rx-c              (132),
            thru-becn-tx-c              (133),
            thru-becn-rx-c              (134),
            thru-de-tx-c                (135),
            thru-de-rx-c                (136),

            cir-percent-range1-tx-bc    (137),
            cir-percent-range1-rx-bc    (138),
            cir-percent-range2-tx-bc    (139),
            cir-percent-range2-rx-bc    (140),
            cir-percent-range3-tx-bc    (141),
            cir-percent-range3-rx-bc    (142),
            cir-percent-range4-tx-bc    (143),
            cir-percent-range4-rx-bc    (144),
            cir-percent-range5-tx-bc    (145),
            cir-percent-range5-rx-bc    (146),
            cir-percent-range6-tx-bc    (147),
            cir-percent-range6-rx-bc    (148),
            cir-percent-range7-tx-bc    (149),
            cir-percent-range7-rx-bc    (150),
            cir-percent-range8-tx-bc    (151),
            cir-percent-range8-rx-bc    (152),
            lmi-tx-bc                   (153),
            lmi-rx-bc                   (154),
            lmi-livo-enq-tx-bc          (155),
            lmi-livo-enq-rx-bc          (156),
            lmi-livo-stat-tx-bc         (157),
            lmi-livo-stat-rx-bc         (158),
            lmi-full-enq-tx-bc          (159),
            lmi-full-enq-rx-bc          (160),
            lmi-full-stat-tx-bc         (161),
            lmi-full-stat-rx-bc         (162),
            lmi-other-tx-bc             (163),
            lmi-other-rx-bc             (164),
            total-uptime                (165),
            total-downtime              (166),
            igrp-tx-bc                  (167),
            igrp-rx-bc                  (168),
            vnip-tx-bc                  (169),
            vnip-rx-bc                  (170),
            annex-g-tx-bc               (171),
            annex-g-rx-bc               (172),

            delete-entry                (-1)
          }
          ACCESS      read-write
          STATUS      mandatory
          DESCRIPTION
             "Long term statistics will be collected on
              the user-specifiable protocol. Setting a -1 
              remove the indexed protocol from the filter."
          ::= { sfrapCfgFrPerfLTProtocolFilterEntry 2 }

      sfrapCfgFrPerfDlciDefaultUtilThreshold  OBJECT-TYPE
          SYNTAX      INTEGER  (0..100) 
          ACCESS      read-write
          STATUS      mandatory
          DESCRIPTION
             "The default threshold for generating a 
              utilization threshold trap as a percentage 
              of the CIR. This value is used for 
              sfrapCfgFrPerfDlciNamesUtilThreshold when
              a DLCI is first discovered. "
          ::= { sfrapCfgFrPerf 7 }

   sfrapCfgFrPerfDlciUtilDuration  OBJECT-TYPE
          SYNTAX      INTEGER (0..65535) 
          ACCESS      read-write
          STATUS      mandatory
          DESCRIPTION
             "The number of Short Term Intervals that a
              DLCI's utilization as a percentage of CIR
              must be above or below the value of
           sfrapCfgFrPerfDlciUtilThreshold before a
              sfrapPvc(Rx/Tx)UtilizationExceededTrap or
              sfrapPvc(Rx/Tx)UtilizationClearedTrap is
              issued. "
          ::= { sfrapCfgFrPerf 8 }

  sfrapCfgFrPerfDlciNamesTableClear  OBJECT-TYPE
         SYNTAX       INTEGER
         {            
            clear-table                (1),
            clear-table-keep-stats     (2)
         }
          ACCESS      write-only
          STATUS      mandatory
          DESCRIPTION
             "Clears the smperCfgFrPerfDlciNamesTable
              (1) clear the table or (2) clear the table
              but don't remove the dlcis from the short
              term statistics."
          ::= { sfrapCfgFrPerf 9 }
         
  sfrapCfgFrPerfUserProtocolsTableClear  OBJECT-TYPE
         SYNTAX       INTEGER
         {            
            clear-table     (1)
         }
          ACCESS      write-only
          STATUS      mandatory
          DESCRIPTION
             " Clears the sfrapCfgFrPerfUserProtocolsTable
               (1) clear the table "
          ::= { sfrapCfgFrPerf 10 }
         
  sfrapCfgFrPerfLTDlciFilterTableClear  OBJECT-TYPE
         SYNTAX       INTEGER
         {            
            clear-table     (1)
         }
          ACCESS      write-only
          STATUS      mandatory
          DESCRIPTION
             " Clears the sfrapCfgFrPerfLTDlciFilterTable
               (1) clear the table "
          ::= { sfrapCfgFrPerf 11 }
         
  sfrapCfgFrPerfLTProtocolFilterTableClear  OBJECT-TYPE
         SYNTAX       INTEGER
         {            
            clear-table     (1)
         }
          ACCESS      write-only
          STATUS      mandatory
          DESCRIPTION
             " Clears the sfrapCfgFrPerfLTProtocolFilterTable
               (1) clear the table "
          ::= { sfrapCfgFrPerf 12 }
         
  sfrapCfgFrPerfUnprovDlcisDelete  OBJECT-TYPE
         SYNTAX       INTEGER
         {            
            delete-unprov     (1)
         }
          ACCESS      write-only
          STATUS      mandatory
          DESCRIPTION
             "Delete all unprovisioned and Not-In-LMI dlcis
              (1) delete all unprovisioned "
          ::= { sfrapCfgFrPerf 13 }
         

  sfrapCfgSecurityTable OBJECT IDENTIFIER ::= { sfrapConfiguration 8 }

      sfrapCfgTelnetCliPassword   OBJECT-TYPE
          SYNTAX      DisplayString (SIZE (0..8))
          ACCESS      read-write
          STATUS      mandatory
          DESCRIPTION
             "The password needed to start a
              CLI (Command Line Interface) session
              using either a terminal connected to the
              unit or Telnet."
          ::= { sfrapCfgSecurityTable 1 }

      sfrapCfgTftpPassword   OBJECT-TYPE
          SYNTAX      DisplayString (SIZE (0..8))
          ACCESS      read-write
          STATUS      mandatory
          DESCRIPTION
             "The password needed to initiate a TFTP download."
          ::= { sfrapCfgSecurityTable 2 }

      sfrapCfgCliPassword   OBJECT-TYPE
          SYNTAX      DisplayString (SIZE (0..8))
          ACCESS      read-write
          STATUS      mandatory
          DESCRIPTION
             "OBSOLETE: The Telnet and CLI passwords
              are one and the same.  Use the above
              sfrapCfgTelnetCliLcdPassword to log into
              the CLI (Command Line Interface)."
          ::= { sfrapCfgSecurityTable 3 }

      sfrapCfgGetCommunityString   OBJECT-TYPE
          SYNTAX      DisplayString (SIZE (0..15))
          ACCESS      read-write
          STATUS      mandatory
          DESCRIPTION
             "The community string for doing SNMP GETs. The unit
              will respond to GETs that use either this string or
              the SET community string. All others will be rejected
              and a trap will be generated. String is case sensitive."
          ::= { sfrapCfgSecurityTable 5 }

      sfrapCfgSetCommunityString   OBJECT-TYPE
          SYNTAX      DisplayString (SIZE (0..15))
          ACCESS      read-write
          STATUS      mandatory
          DESCRIPTION
             "The community string for doing SNMP SETs. The unit 
              will reject SETs with any other coimmunity string
              and will generate a trap. String is case sensitive."
          ::= { sfrapCfgSecurityTable 6 }



sfrapCfgLock   OBJECT-TYPE
     SYNTAX      INTEGER (1..600)
     ACCESS      write-only
     STATUS      mandatory
     DESCRIPTION
        "Request to start configuration download and lock out any 
         other means of configuring the unit. The integer passed in
         represents the time out period  in seconds between sets. 
         A set to this object will fail if the unit is already in a 
         configuration locked state."
     ::= { sfrapConfiguration 12 }

sfrapCfgLockID   OBJECT-TYPE
     SYNTAX      IpAddress
     ACCESS      read-only
     STATUS      mandatory
     DESCRIPTION
        "Returns the IP Address of  the management station currently 
         in control of configuration. A unit that is not in a 
         configuration locked state will return  0.0.0.0" 
     ::= { sfrapConfiguration 13 }

sfrapCfgID   OBJECT-TYPE
     SYNTAX      DisplayString (SIZE (0..8))
     ACCESS      read-write
     STATUS      mandatory
     DESCRIPTION
        "A read of this object returns the Current Configuration ID 
         string. A write sets  the Configuration ID string. The 
         string contains a starting character to indicate the last 
         configuration source C = Envisage N = CLI/TELNET L = LCD 
         S= other SNMP management station  and a unique 7 integer 
         value to differentiate configurations between common sources. 
         A value of *STARTUP indicates the configuration has been 
         defaulted. A write will only be accepted from the management 
         station that has successfully obtained the configuration lock" 
     ::= { sfrapConfiguration 14 }

sfrapCfgStatus   OBJECT-TYPE
     SYNTAX      INTEGER
     {
        in-progress                (1),
        success                    (2),
        datarate-density-conflict  (3),
        bandwidth-allocation-error (4),
        general-error              (5),
        timeout                    (6),
        aborted-by-user            (7)
     }
     ACCESS      read-only
     STATUS      mandatory
     DESCRIPTION
        "The status of a configuration install is reported here.
         On startup, a status of success will be reported.
         (1) The configuration has been locked and an update or
             unlock command has not been received.
         (2) An update command has been received and the configuration
             has been validated as consistent; .
         (3) An update command has been received but the DTE port 
             datarate is not compatible with the density.
         (4) An update command has been received but the number of
             channels to be allocated will not fit in the available
             channels.
         (5) An update command has been received but there is an
             error in the configuration that is not a 
             datarate-density-conflict or bandwidth-allocation-error.
         (6) The time between consecutive set requests exceeded the
             timeout sent with the sfrapCfgLock command.
         (7) The user sent a sfrapCfgUnlock command before a 
             sfrapCfgUpdate command.  This usually means that one
             of the sets in the configuration failed. "
     ::= { sfrapConfiguration 15 }

sfrapCfgUnlock   OBJECT-TYPE
     SYNTAX      INTEGER 
     {
        un-lock (1)
     }
     ACCESS      write-only
     STATUS      mandatory
     DESCRIPTION
        "The management station sets this variable to complete 
         the configuration install process. Un-lock (1) notifies 
         the agent to remove the lock on configuring the unit
          without updating the configuration."
     ::= { sfrapConfiguration 16 }


sfrapCfgUpdate   OBJECT-TYPE
     SYNTAX      INTEGER 
     {
        update (1)
     }
     ACCESS      write-only
     STATUS      mandatory
     DESCRIPTION
        "The management station sets this variable to complete 
         the configuration install process. Update (1) notifies 
         the agent to start the update process within the unit."
     ::= { sfrapConfiguration 17 }


-- =============================
-- ==    DIAGNOSTIC group     ==
-- =============================

sfrapDiagnostics  OBJECT IDENTIFIER ::= { sfrap 3 }

--
--       The Diagnostics/Unit Table
--              This table contains the objects for unit level diagnostics
--              on the SFRAP DSU.

sfrapDiagUnitTable OBJECT IDENTIFIER ::= { sfrapDiagnostics 1 }

sfrapDiagUnitLocLoop OBJECT-TYPE
          SYNTAX      INTEGER 
          {
               enable-loopback-mode  (1),
               disable-loopback-mode (2)
          }
          ACCESS      read-write
          STATUS      mandatory
          DESCRIPTION
             "Controls a bi-directional unit loopback. Data 
              is received from either interface, processed, 
              and transmitted back towards the same interface. 
              When configured for Frame Relay operation the unit 
              will preserve the LMI path and maintain managed access
              during this loopback. In Frame Relay mode, only valid 
              HDLC frames are looped back (pseudorandom test patterns
              will be dropped).
              (1) enable unit loopback
              (2) disable unit loopback"
          ::= { sfrapDiagUnitTable 1 }

sfrapDiagUnitReset OBJECT-TYPE
          SYNTAX      INTEGER 
          {
               reset-unit (1)
          }
          ACCESS      write-only
          STATUS      mandatory
          DESCRIPTION
             "Enables the operator to remotely reset the unit.
              Using this command will cause the unit to terminate
              all its connections and drop data."
          ::= { sfrapDiagUnitTable 2 }

sfrapDiagUnitTimeRemaining OBJECT-TYPE
          SYNTAX      TimeTicks
          ACCESS      read-only
          STATUS      mandatory
          DESCRIPTION
             "The remaining time on the active loopback
              before the loopback times out. The time is
              in hundredths of seconds (TimeTicks)."
          ::= { sfrapDiagUnitTable 3 }


sfrapDiagUnitCutThru OBJECT-TYPE
          SYNTAX      INTEGER 
          {
               enable-cutthru-mode  (1),
               disable-cutthru-mode (2)
          }
          ACCESS      read-write
          STATUS      mandatory
          DESCRIPTION
             "Enables the operator to control and examine the 
             UNIT Cut Through mode.  This diagnostic occurs on
             the TO-DTE and TO-DCE transmit and receive logic.
             The unit will transmit To-DTE data onto the TO-DCE
             port without any intervention by the processor.  If the
             CutThruTimeout is greater than 0, then the cut-thru
             diagnostic will time out after that interval (in minutes).
             (same as Tap Mode operation - see CfgAppOperationMode)."
          ::= { sfrapDiagUnitTable 4 }

sfrapDiagUnitCutThruTimeRemaining OBJECT-TYPE
          SYNTAX      TimeTicks
          ACCESS      read-only
          STATUS      mandatory
          DESCRIPTION
             "The remaining time on the active loopback
              before the loopback times out. The time is
              in hundredths of seconds (TimeTicks)."
          ::= { sfrapDiagUnitTable 5 }


-- DTE:   sfrapDiagDteTable { sfrapDiagnostics 3 }
--
--       The sfrapDiagDteTable
--              This table contains the TO-DTE and TO-DCE diagnostics.
--
sfrapDiagDteTable     OBJECT-TYPE
         SYNTAX   SEQUENCE OF SfrapDiagDteEntry
         ACCESS   not-accessible
         STATUS   mandatory
         DESCRIPTION
            "The table of DTE port diagnostics."
         ::= { sfrapDiagnostics 3 }

sfrapDiagDteEntry   OBJECT-TYPE
         SYNTAX   SfrapDiagDteEntry
         ACCESS   not-accessible
         STATUS   mandatory
         DESCRIPTION
            "An diagnostic entry for a DTE port."
         INDEX { sfrapDiagDteIndex }
            ::= { sfrapDiagDteTable 1 }

SfrapDiagDteEntry ::=
          SEQUENCE {
              sfrapDiagDteIndex            INTEGER,
              sfrapDiagDteLclLpbk          INTEGER,
              sfrapDiagDteTimeRemaining    TimeTicks
          }

sfrapDiagDteIndex         OBJECT-TYPE  
          SYNTAX       INTEGER
          {
              to-dte   (1),
              to-dce   (2)
          }
          ACCESS       read-only
          STATUS       mandatory
          DESCRIPTION
          "Selects which DTE port."
          ::= { sfrapDiagDteEntry 99 }

sfrapDiagDteLclLpbk OBJECT-TYPE
          SYNTAX      INTEGER
          {
               enable-loopback-mode  (1),
               disable-loopback-mode (2)
          }
          ACCESS      read-write
          STATUS      mandatory
          DESCRIPTION
             "Controls the DTE loopback state. This is a 
              bi-directional loopback state where both the
              DTE and WAN ports are placed in line loopback. 
              All data received on each interface is sent back
              out the respective interface regardless of format
              or content. In Frame Relay applications the unit 
              will not preserve the LMI path during this diagnostic 
              and in-band management will not operate.
              (1) enable payload loopback
              (2) disable payload loopback"
          ::= { sfrapDiagDteEntry 3 }


sfrapDiagDteTimeRemaining OBJECT-TYPE
          SYNTAX      TimeTicks
          ACCESS      read-only
          STATUS      mandatory
          DESCRIPTION
             "The remaining time on the active loopback
              before the loopback times out and disables
              itself. The time is in hundredths of seconds
              (TimeTicks)."
          ::= { sfrapDiagDteEntry 13 }


--
--       The sfrapDiagVnipTable
--              This table contains the VNIP level diagnostics of the SFRAP CSU.
--
--
sfrapDiagVnipTable  OBJECT-TYPE
      SYNTAX   SEQUENCE OF SFRAPDiagVnipEntry
      ACCESS   not-accessible
      STATUS   mandatory
      DESCRIPTION
         " Table of Diagnostics performed with the VNIP protocol"
      ::= { sfrapDiagnostics 6 }

    sfrapDiagVnipEntry OBJECT-TYPE
        SYNTAX   SFRAPDiagVnipEntry
        ACCESS   not-accessible
        STATUS   mandatory
        DESCRIPTION
           "VNIP VLOOP and VBERT diagnostic profile. Initiating
            these tests require an established and stable VNIP topology
            on an interface. Once the topology is in place, the user
            can execute a PVC-based diagnostic between this unit and
            any indexed entry in the topology table. The index into the 
            topology table for a particular interface is required."
        INDEX {sfrapDiagVnipInterface, sfrapDiagVnipIndex}
         ::= { sfrapDiagVnipTable 1 }

    SFRAPDiagVnipEntry ::=
          SEQUENCE {
                sfrapDiagVnipInterface          INTEGER,
                sfrapDiagVnipIndex              INTEGER,
                sfrapDiagVnipDlci               INTEGER,
                sfrapDiagVnipIpAddr             IpAddress,
                sfrapDiagVLOOP                  INTEGER,
                sfrapDiagVBERT                  INTEGER,
                sfrapDiagVBERTRate              INTEGER,
                sfrapDiagVBERTSize              INTEGER,
                sfrapDiagVBERTPktPercent        INTEGER,
                sfrapDiagVBERTTestPeriod        INTEGER
          }

sfrapDiagVnipInterface OBJECT-TYPE
   SYNTAX      INTEGER
   {
        dte-interface (1),
        t1-interface (2)
   }
   ACCESS      read-write
   STATUS      mandatory
   DESCRIPTION
      "The interface out which a PVC-based VNIP diagnostic
       will be run. This must be an interface with a valid 
       and stable VNIP topology for a VNIP Diagnostic."
   ::= { sfrapDiagVnipEntry 1 }

sfrapDiagVnipIndex OBJECT-TYPE
    SYNTAX      INTEGER
    ACCESS      read-write
    STATUS      mandatory
    DESCRIPTION
       "The index to the external VNIP peer as presented by the VNIP
        topology database for the given interface. Refer to 
        VnipTopologyTable to determine the index of the remote peer."
    ::= { sfrapDiagVnipEntry 2 }

sfrapDiagVnipDlci    OBJECT-TYPE
    SYNTAX      INTEGER
    ACCESS      read-only
    STATUS      mandatory
    DESCRIPTION
       "This is the DLCI value for the given interface/index
        combination. This comes from the VniptTopologyTable."
    ::= { sfrapDiagVnipEntry 3 }

sfrapDiagVnipIpAddr   OBJECT-TYPE
    SYNTAX      IpAddress
    ACCESS      read-only
    STATUS      mandatory
    DESCRIPTION
       "This is the ip address for the given interface/index
        combination. This comes from the VniptTopologyTable."
    ::= { sfrapDiagVnipEntry 4 }

sfrapDiagVLOOP OBJECT-TYPE
    SYNTAX      INTEGER
    {
         start-test         (1),
         stop-test          (2)
    }
    ACCESS      write-only
    STATUS      mandatory
    DESCRIPTION
       "Controls execution of the Vnip Logical Loopback (VLOOP) test. 
        VLOOP is designed as an intrusive test and customer data 
        on the DLCI-under-test will be discarded. The VLOOP test includes
        a timed VBERT test and is run using the profile configured within 
        this table.
        (1) start VLOOP test 
        (2) stop VLOOP test (override VBERT test duration)"
    ::= { sfrapDiagVnipEntry 5 }

 
sfrapDiagVBERT OBJECT-TYPE
    SYNTAX      INTEGER
    {
         start     (1),
         stop      (2)
    }
    ACCESS      write-only
    STATUS      mandatory
    DESCRIPTION
       "Controls execution of the Vnip Virtual Bit Eror Rate (VBERT) test. 
        VBERT is designed to be a non-intrusive test and will attempt to
        statistically multiplex VBERT test data and customer data on the
        DLCI-under-test. However, VBERT data is given priority over customer
        data when the selected VBERT volume causes internal congestion. 
        The test is run using the profile configured within this table.
        (1) start test 
        (2) stop test (override VBERT test duration)"
    ::= { sfrapDiagVnipEntry 6 }



sfrapDiagVBERTRate  OBJECT-TYPE
    SYNTAX      INTEGER (8000..2048000)
    ACCESS      read-write
    STATUS      mandatory
    DESCRIPTION
       "Specifies the throughput bit rate applied by VBERT or 
        VLOOP to the DLCI-under-test. For TO-DTE Rates or configured
        CIR up to 64K the maximum VBERT rate is either the TO-DTE data
        rate or 110% of CIR (which ever is less). For TO-DTE Rates or
        configured CIR greater than 64K, the maximum VBERT rate is 
        75% of the TO-DTE data rate or 110% of CIR (which ever is less). 
        Note that selecting rates that approach line rate will impact 
        neighboring PVCs.
        (8000-1152000): VBERT/VLOOP data rate (in bits per second)."
    ::= { sfrapDiagVnipEntry 7 }


sfrapDiagVBERTSize  OBJECT-TYPE
    SYNTAX      INTEGER 
    {
       pkt-size-64      (64),
       pkt-size-128     (128),
       pkt-size-256     (256),
       pkt-size-512     (512),
       pkt-size-1024    (1024),
       pkt-size-2048    (2048)
    }
    ACCESS      read-write
    STATUS      mandatory
    DESCRIPTION
       "Specifies the size of framed data that will be used
        during the VBERT test, measures in Bytes.
         (64)     64-byte frames
         (128)   128-byte frames
         (256)   256-byte frames
         (512)   512-byte frames
         (1024) 1024-byte frames
         (2048) 2048-byte frames"
    ::= { sfrapDiagVnipEntry 8 }


sfrapDiagVBERTPktPercent  OBJECT-TYPE
    SYNTAX      INTEGER 
    {
       zero-percent        (0),
       twentyFive-percent  (25),
       fifty-percent       (50),
       seventyFive-percent (75),
       oneHundred-percent  (100)
    }
    ACCESS      read-write
    STATUS      mandatory
    DESCRIPTION
        "Specifies percentage of VBERT packets that will have the
         Frame Relay Discard Eligibility bit set. Frames with this
         bit set may be more likley to get dropped in a congested
         network.
         (0) 0%  of the test frames are marked discard eligible
         (25) 25% of the test frames are marked discard eligible
         (50) 50% of the test frames are marked discard eligible
         (75) 75% of the test frames are marked discard eligible
         (100) 100% of the test frames are marked discard eligible"
    ::= { sfrapDiagVnipEntry 9 }

sfrapDiagVBERTTestPeriod  OBJECT-TYPE
    SYNTAX      INTEGER (10..1440)
    ACCESS      read-write
    STATUS      mandatory
    DESCRIPTION
       "Specifies the duration of a VBERT test. Note that VBERT is 
        subjected to the unit's Loopback Timer and will be terminated 
        by whichever timer expires first.
        (10-1440): VBERT time duration in seconds"
    ::= { sfrapDiagVnipEntry 10 }

sfrapDiagTxClockDetect OBJECT-TYPE
    SYNTAX      INTEGER 
    {
      initiate-clock-detect  (1),
      terminate-clock-detect (2)
    }
    ACCESS      read-write
    STATUS      mandatory
    DESCRIPTION
       "Enables the operator to activate clock detection
        on the TO-DCE Transmit clock.  Clock detection
        can be stopped by issuing the terminate command."
    ::= { sfrapDiagnostics 7 }


-- =========================
-- ==    STATUS group     ==
-- =========================

sfrapStatus  OBJECT IDENTIFIER ::= { sfrap 4 }

--
--      LED Status
--
--         The current status of the SFRAP front-panel LED indicators.
--
sfrapStatusLedTable   OBJECT IDENTIFIER ::= { sfrapStatus 4 }

sfrapStatusLedOpStatusLED   OBJECT-TYPE
     SYNTAX  INTEGER
     {
        greenLED-high-speed-mode          (1),
        blinkgreenLED-low-speed-mode      (2),
        yellowLED-test-mode               (3),
        redLED-alarm-mode                 (4),
        blinkredLED-cut-through-mode      (5)
     }
     ACCESS  read-only
     STATUS  mandatory
     DESCRIPTION
      "Status of the Operation Mode LED."
     ::= { sfrapStatusLedTable 1 }

sfrapStatusLedToDTETxLED   OBJECT-TYPE
     SYNTAX  INTEGER
     {
        offLED-inactive                   (1),
        greenLED-tx-data-receiving        (2)
     }
     ACCESS  read-only
     STATUS  mandatory
     DESCRIPTION
      "Status of the TO-DTE TxD LED."
     ::= { sfrapStatusLedTable 2 }
     
sfrapStatusLedToDTERxLED   OBJECT-TYPE
     SYNTAX  INTEGER
     {
        offLED-inactive                   (1),
        greenLED-rx-data-receiving        (2)
     }
     ACCESS  read-only
     STATUS  mandatory
     DESCRIPTION
      "Status of the TO-DTE RxD LED."
     ::= { sfrapStatusLedTable 3 }

sfrapStatusLedRtsLED   OBJECT-TYPE
     SYNTAX  INTEGER
     {
        greenLED-rts-active               (1),
        offLED-rts-inactive               (2)
     }
     ACCESS  read-only
     STATUS  mandatory
     DESCRIPTION
      "Status of the RTS Signal LED."
     ::= { sfrapStatusLedTable 4 }

sfrapStatusLedCtsLED   OBJECT-TYPE
     SYNTAX  INTEGER
     {
        greenLED-cts-active               (1),
        offLED-cts-inactive               (2)
     }
     ACCESS  read-only
     STATUS  mandatory
     DESCRIPTION
      "Status of the CTS Signal LED."
     ::= { sfrapStatusLedTable 5 }
        
sfrapStatusLedDsrLED   OBJECT-TYPE
     SYNTAX  INTEGER
     {
        greenLED-dsr-active               (1),
        offLED-dsr-inactive               (2)
     }
     ACCESS  read-only
     STATUS  mandatory
     DESCRIPTION
      "Status of the DSR Signal LED."
     ::= { sfrapStatusLedTable 7 }
        
sfrapStatusLedDcdLED   OBJECT-TYPE
     SYNTAX  INTEGER
     {
        greenLED-dcd-active               (1),
        offLED-dcd-inactive               (2)
     }
     ACCESS  read-only
     STATUS  mandatory
     DESCRIPTION
      "Status of the DCD Signal LED."
     ::= { sfrapStatusLedTable 8 }

sfrapStatusLedToDCETxLED   OBJECT-TYPE
     SYNTAX  INTEGER
     {
        offLED-inactive                   (1),
        greenLED-tx-data-receiving        (2)
     }
     ACCESS  read-only
     STATUS  mandatory
     DESCRIPTION
      "Status of the TO-DCE TxD LED."
     ::= { sfrapStatusLedTable 9 }
     
sfrapStatusLedToDCERxLED   OBJECT-TYPE
     SYNTAX  INTEGER
     {
        offLED-inactive                   (1),
        greenLED-rx-data-receiving        (2)
     }
     ACCESS  read-only
     STATUS  mandatory
     DESCRIPTION
      "Status of the TO-DCE RxD LED."
     ::= { sfrapStatusLedTable 10 }
  
sfrapStatusLedLmiErrLED   OBJECT-TYPE
     SYNTAX  INTEGER
     {
        offLED-lmi-active-state           (1),
        yellowLED-lmi-error-state         (2),
        blinkyellowLED-lmi-source-state   (3)
     }
     ACCESS  read-only
     STATUS  mandatory
     DESCRIPTION
      "Status of the LMI Error LED."
     ::= { sfrapStatusLedTable 15 }
        
sfrapStatusLedFrmActLED   OBJECT-TYPE
     SYNTAX  INTEGER
     {
        greenLED-frm-active               (1),
        offLED-frm-inactive               (2)
     }
     ACCESS  read-only
     STATUS  mandatory
     DESCRIPTION
      "Status of the Frame Activity LED."
     ::= { sfrapStatusLedTable 16 }
     
sfrapStatusLedCtrlLED   OBJECT-TYPE
     SYNTAX  INTEGER
     {
        yellowLED-ctrl-active            (1),
        offLED-ctrl-inactive             (2)
     }
     ACCESS  read-only
     STATUS  mandatory
     DESCRIPTION
      "Status of the X.21 Control Signal LED.
       Only applicable when in X.21."
     ::= { sfrapStatusLedTable 17 }

sfrapStatusLedIndLED   OBJECT-TYPE
     SYNTAX  INTEGER
     {
        yellowLED-ind-active              (1),
        offLED-ind-inactive               (2)
     }
     ACCESS  read-only
     STATUS  mandatory
     DESCRIPTION
      "Status of the X.21 Indication Signal LED.
       Only applicable when in X.21."
     ::= { sfrapStatusLedTable 18 }
          
sfrapStatusAllLEDs   OBJECT-TYPE
     SYNTAX  DisplayString (SIZE (0..10))
     ACCESS  read-only
     STATUS  mandatory
     DESCRIPTION
        "Status of all ten SFRAP LEDs, encoded in a string.
             'F'    off
             '5'    green
             '0'    yellow
             'A'    red
             '7'    blinking green and off
             '3'    blinking yellow and off
             'B'    blinking red and off
             '4'    blinking green and yellow
             '6'    blinking green and red
             '8'    blinking yellow and red

         Positionally, the 13 letters are SFRAP Op Mode,
         TO-DCE Rx, TO-DCE Tx, RTS, CTS, DCD, DSR,
         LMI Error, Frame Activity, Ctrl, Ind, TO-DTE Rx, TO-DTE Tx."
     ::= { sfrapStatusLedTable 14 }
     

--
--      Dipswitch Status
--
--         The current status of the SFRAP front-panel dipswitches. 
--
sfrapStatusDipswitchTable   OBJECT IDENTIFIER ::= { sfrapStatus 10 }

sfrapStatusDipswitchCutthru   OBJECT-TYPE
     SYNTAX  INTEGER
     {
        switch-up       (1),
        switch-down     (2),
        na              (3)
     }
     ACCESS  read-only
     STATUS  mandatory
     DESCRIPTION
      "Status of the Operation Mode LED."
     ::= { sfrapStatusDipswitchTable 1 }
     
sfrapStatusDipswitchToDteLpbk   OBJECT-TYPE
     SYNTAX  INTEGER
     {
        switch-up          (1),
        switch-down        (2),
        na                 (3)
     }
     ACCESS  read-only
     STATUS  mandatory
     DESCRIPTION
      "Status of the TO-DTE TxD LED."
     ::= { sfrapStatusDipswitchTable 2 }

sfrapStatusDipswitchToDceLpbk   OBJECT-TYPE
     SYNTAX  INTEGER
     {
        switch-up                (1),
        switch-down              (2),
        na                       (3)
     }
     ACCESS  read-only
     STATUS  mandatory
     DESCRIPTION
      "Status of the TO-DTE RxD LED."
     ::= { sfrapStatusDipswitchTable 3 }
     
sfrapStatusDipswitchUnused   OBJECT-TYPE
     SYNTAX  INTEGER
     {
        switch-up                (1),
        switch-down              (2),
        na                       (3)
     }
     ACCESS  read-only
     STATUS  mandatory
     DESCRIPTION
      "Status of the RTS Signal LED."
     ::= { sfrapStatusDipswitchTable 4 }

sfrapStatusDipswitchIntfMode1   OBJECT-TYPE
     SYNTAX  INTEGER
     {
        switch-up                (1),
        switch-down              (2),
        na                       (3)
     }
     ACCESS  read-only
     STATUS  mandatory
     DESCRIPTION
      "Status of the RTS Signal LED."
     ::= { sfrapStatusDipswitchTable 5 }

sfrapStatusDipswitchIntfMode2   OBJECT-TYPE
     SYNTAX  INTEGER
     {
        switch-up                (1),
        switch-down              (2),
        na                       (3)
     }
     ACCESS  read-only
     STATUS  mandatory
     DESCRIPTION
      "Status of the RTS Signal LED."
     ::= { sfrapStatusDipswitchTable 6 }
--        
--        
--
--      DTE Status 
--
--         The current status of the TO-DTE and TO-DCE ports.
--

sfrapStatusDteTable   OBJECT-TYPE
         SYNTAX   SEQUENCE OF SfrapStatusDteEntry
         ACCESS   not-accessible
         STATUS   mandatory
         DESCRIPTION
            "The table of DTE port statuses."
         ::= { sfrapStatus 7 }

sfrapStatusDteEntry   OBJECT-TYPE
         SYNTAX   SfrapStatusDteEntry
         ACCESS   not-accessible
         STATUS   mandatory
         DESCRIPTION
            "An status entry for a DTE port."
         INDEX { sfrapStatusDteIndex }
            ::= { sfrapStatusDteTable 1 }

SfrapStatusDteEntry ::=
         SEQUENCE {
             sfrapStatusDteIndex       INTEGER,
             sfrapStatusDteMode        INTEGER,
             sfrapStatusDteRts         INTEGER,
             sfrapStatusDteDtr         INTEGER,
             sfrapStatusDteDcd         INTEGER,
             sfrapStatusDteDsr         INTEGER,
             sfrapStatusDteCts         INTEGER,
             sfrapStatusDteSendtiming  INTEGER,
             sfrapStatusDteRxtiming    INTEGER,
             sfrapStatusDteTermtiming  INTEGER,
             sfrapStatusDteCtrl        INTEGER,
             sfrapStatusDteInd         INTEGER
         }

sfrapStatusDteIndex         OBJECT-TYPE  
     SYNTAX       INTEGER
     {
         to-dte   (1),
         to-dce   (2)
     }
     ACCESS       read-only
     STATUS       mandatory
     DESCRIPTION
     "Selects which DTE port."
     ::= { sfrapStatusDteEntry 99 }                                 

sfrapStatusDteMode   OBJECT-TYPE
     SYNTAX  INTEGER
     {
        no-connections (1),
        active         (2),
        test           (3)
     }
     ACCESS  read-only
     STATUS  mandatory
     DESCRIPTION
      "Status of the port. no-connections (1) indicates
      the port has no connections. Active (2) indicates 
      connections and data mode. Test (3) indicates
      connections and diagnostic state for that port."
     ::= { sfrapStatusDteEntry 1 }

sfrapStatusDteRts   OBJECT-TYPE
     SYNTAX  INTEGER
     {
        on  (1),
        off (2),
        na  (3)
     }
     ACCESS  read-only
     STATUS  mandatory
     DESCRIPTION
      "Status of the RTS signal on the port:
       on (1) and off (2)."
     ::= { sfrapStatusDteEntry 2 }

sfrapStatusDteDtr   OBJECT-TYPE
     SYNTAX  INTEGER
     {
        on  (1),
        off (2),
        na  (3)
     }
     ACCESS  read-only
     STATUS  mandatory
     DESCRIPTION
      "Status of the DTR signal on the port:
       on (1) and off (2)."
     ::= { sfrapStatusDteEntry 3 }

sfrapStatusDteDcd OBJECT-TYPE
     SYNTAX      INTEGER
     {
          on   (1),
          off  (2),
          na   (3)
     }
     ACCESS      read-only
     STATUS      mandatory
     DESCRIPTION
        "Whether the DCD signal on the port is on (1) or off (2)."
     ::= { sfrapStatusDteEntry 4 }

sfrapStatusDteDsr OBJECT-TYPE
     SYNTAX      INTEGER
     {
          on   (1),
          off  (2),
          na   (3)
     }
     ACCESS      read-only
     STATUS      mandatory
     DESCRIPTION
        "Whether the DSR signal on the port is on (1) or off (2)."
     ::= { sfrapStatusDteEntry 5 }

sfrapStatusDteCts OBJECT-TYPE
     SYNTAX      INTEGER
     {
          on   (1),
          off  (2),
          na   (3)
     }
     ACCESS      read-only
     STATUS      mandatory
     DESCRIPTION
        "Whether the CTS signal on the port is on (1) or off (2)."
     ::= { sfrapStatusDteEntry 6 }
     
sfrapStatusDteSendtiming OBJECT-TYPE
     SYNTAX      INTEGER
     {
          present      (1),
          not-present  (2),
          na           (3)
     }
     ACCESS      read-only
     STATUS      mandatory
     DESCRIPTION
        "Whether Send Timing is (1)present or (2)not-present 
        on the interface."
     ::= { sfrapStatusDteEntry 7 }

sfrapStatusDteRxtiming OBJECT-TYPE
     SYNTAX      INTEGER
     {
          present      (1),
          not-present  (2),
          na           (3)
     }
     ACCESS      read-only
     STATUS      mandatory
     DESCRIPTION
        "Whether Receive Timing is (1)present or (2)not-present 
        on the interface."
     ::= { sfrapStatusDteEntry 8 }

sfrapStatusDteTermtiming OBJECT-TYPE
     SYNTAX      INTEGER
     {
          present      (1),
          not-present  (2),
          na           (3)
     }
     ACCESS      read-only
     STATUS      mandatory
     DESCRIPTION
        "Whether Terminal Timing is (1)present or (2)not-present 
        on the interface."
     ::= { sfrapStatusDteEntry 9 }

sfrapStatusDteCtrl OBJECT-TYPE
     SYNTAX      INTEGER
     {
          on      (1),
          off     (2),
          na      (3)
     }
     ACCESS      read-only
     STATUS      mandatory
     DESCRIPTION
        "The status of the Control lead when using X.21"
     ::= { sfrapStatusDteEntry 10 }


sfrapStatusDteInd OBJECT-TYPE
     SYNTAX      INTEGER
     {
          on      (1),
          off     (2),
          na      (3)
     }
     ACCESS      read-only
     STATUS      mandatory
     DESCRIPTION
        "The status of the Indication lead when using X.21"
     ::= { sfrapStatusDteEntry 11 }

--
--     Table of peers discovered by VNIP
--

sfrapVnipTopologyTable   OBJECT-TYPE
      SYNTAX   SEQUENCE OF SfrapVnipTopologyEntry
      ACCESS   not-accessible
      STATUS   mandatory
      DESCRIPTION
         "Topology of peers discovered via VNIP, organized
          by the interface (DATA1 or DATA2) from which they were
          discovered and an entry number or index. The
          topology is of limited size per interface."
      ::= { sfrapStatus 2 }

      sfrapVnipTopologyEntry OBJECT-TYPE
          SYNTAX   SfrapVnipTopologyEntry
          ACCESS   not-accessible
          STATUS   mandatory
          DESCRIPTION
             "The DLCI, IP address, and number of hops
              for a particular node, discovered via VNIP
              off of an interface (DATA1 or DATA2).  The entry
              may also have transit delay measurements
              for the particular node."
         INDEX { sfrapVnipTopologyInterface, sfrapVnipTopologyIndex }
         ::= { sfrapVnipTopologyTable 1 }

      SfrapVnipTopologyEntry ::=
          SEQUENCE {
              sfrapVnipTopologyInterface          INTEGER,
              sfrapVnipTopologyIndex              INTEGER,
              sfrapVnipTopologyDlci               INTEGER,
              sfrapVnipTopologyIpAddr             IpAddress,
              sfrapVnipTopologyNumHops            INTEGER,
              sfrapVnipTopologyLocalDlci          INTEGER,
              sfrapVnipTopoTDNumSamples           Counter,
              sfrapVnipTopoTDAvgDelay             Counter,
              sfrapVnipTopoTDMaxDelay             Counter,
              sfrapVnipTopoTDMinDelay             Counter,
              sfrapVnipTopoTDLastDelay            Counter,
              sfrapVnipTopoVLOOPStatus            INTEGER,
              sfrapVnipTopoVBERTStatus            INTEGER,
              sfrapVnipTopoVBertTxDESetFrames     Counter,
              sfrapVnipTopoVBertRxDESetFrames     Counter,
              sfrapVnipTopoVBertTxDEClrFrames     Counter,
              sfrapVnipTopoVBertRxDEClrFrames     Counter,
              sfrapVnipTopoVBertTransitDelayMax   Counter,
              sfrapVnipTopoVBertTransitDelayAvg   Counter,
              sfrapVnipTopoVBertTimeElapse        TimeTicks,
              sfrapVnipTopoVBertPerUtilCIR        INTEGER,
              sfrapVnipTopoVBertPerUtilEIR        INTEGER
          }

      sfrapVnipTopologyInterface OBJECT-TYPE
          SYNTAX      INTEGER
          {
               data1-interface (1),
               data2-interface (2)
          }
          ACCESS      read-only
          STATUS      mandatory
          DESCRIPTION
             "The interface off of which the peer was
              discovered.  Topology is discovered by
              sending VNIP messages out each interface.
              Nodes discovered via a particular interface
              are kept in a list associated with that
              interface."
          ::= { sfrapVnipTopologyEntry 1 }

      sfrapVnipTopologyIndex OBJECT-TYPE
          SYNTAX      INTEGER
          ACCESS      read-only
          STATUS      mandatory
          DESCRIPTION
             "The number of this discovered peer in the list
              of nodes for this interface. For each interface,
              the nodes are numbered 1 through n."
          ::= { sfrapVnipTopologyEntry 2 }

      sfrapVnipTopologyDlci    OBJECT-TYPE
          SYNTAX      INTEGER 
          ACCESS      read-only
          STATUS      mandatory
          DESCRIPTION
            "The DLCI of the discovered neighboring peer.
             This may be different from the local DLCI."
         ::= { sfrapVnipTopologyEntry 3 }

      sfrapVnipTopologyIpAddr   OBJECT-TYPE
          SYNTAX      IpAddress
          ACCESS      read-only
          STATUS      mandatory
          DESCRIPTION
             "The IP address for the discovered peer."
          ::= { sfrapVnipTopologyEntry 4 }
 
      sfrapVnipTopologyNumHops OBJECT-TYPE
          SYNTAX      INTEGER
          ACCESS      read-only
          STATUS      mandatory
          DESCRIPTION
             "The discovered peer is this number of hops away."
          ::= { sfrapVnipTopologyEntry 5 }
 
      sfrapVnipTopologyLocalDlci OBJECT-TYPE
          SYNTAX      INTEGER
          ACCESS      read-only
          STATUS      mandatory
          DESCRIPTION
            "The DLCI of this node over which the remote peer
             was discovered."
          ::= { sfrapVnipTopologyEntry 6 }

      sfrapVnipTopoTDNumSamples  OBJECT-TYPE
          SYNTAX      Counter
          ACCESS      read-only
          STATUS      mandatory
          DESCRIPTION
            "The number of transit delay samples collected."
          ::= { sfrapVnipTopologyEntry 10 }

      sfrapVnipTopoTDAvgDelay  OBJECT-TYPE
          SYNTAX      Counter
          ACCESS      read-only
          STATUS      mandatory
          DESCRIPTION
            "The average transit delay between this
             node and the remote peer."
          ::= { sfrapVnipTopologyEntry 11 }

      sfrapVnipTopoTDMaxDelay  OBJECT-TYPE
          SYNTAX      Counter
          ACCESS      read-only
          STATUS      mandatory
          DESCRIPTION
            "The maximum transit delay between this
             node and the remote peer."
          ::= { sfrapVnipTopologyEntry 12 }

      sfrapVnipTopoTDMinDelay  OBJECT-TYPE
          SYNTAX      Counter
          ACCESS      read-only
          STATUS      mandatory
          DESCRIPTION
            "The minimum transit delay between this
             node and the remote peer."
          ::= { sfrapVnipTopologyEntry 13 }

      sfrapVnipTopoTDLastDelay  OBJECT-TYPE
          SYNTAX      Counter
          ACCESS      read-only
          STATUS      mandatory
          DESCRIPTION
            "The most recent transit delay measured between
             this node and the remote peer."
          ::= { sfrapVnipTopologyEntry 14 }



      sfrapVnipTopoVLOOPStatus   OBJECT-TYPE
          SYNTAX      INTEGER
          {
               loopback-enable (1),
               loopback-disable (2)
          }
          ACCESS      read-only
          STATUS      mandatory
          DESCRIPTION
             "This selection displays the status of the VNIP Loopback
              This loopback is initiated by the remote node, causing
              this node to loop data back to the remote node."
          ::= { sfrapVnipTopologyEntry  15 }
      

      sfrapVnipTopoVBERTStatus  OBJECT-TYPE
          SYNTAX      INTEGER
          {
               off            (1),
               testing        (2),
               test-failed    (3),
               test-completed (4),
               in-test        (5)
          }
          ACCESS      read-only
          STATUS      mandatory
          DESCRIPTION
             "Displays the current status of the VBERT test, values are
              off(1): no test has run or the entry has been cleared, 
              testing(2): the entry is generating VBERT packets, 
              in-test(5): the entry is on the receiving end of VBERT packets
              test-completed(4): a test has run and is finished results are complete
              test-failed(3): the request for a test on this entry failed"
          ::= { sfrapVnipTopologyEntry 16 }
  

      sfrapVnipTopoVBertTxDESetFrames   OBJECT-TYPE
          SYNTAX      Counter
          ACCESS      read-only
          STATUS      mandatory
          DESCRIPTION
             "Displays the number of Frames transmitted during VBERT Test that
              had the Discard Eligibility indicator bit set."
          ::= { sfrapVnipTopologyEntry  17 }


     
      sfrapVnipTopoVBertRxDESetFrames OBJECT-TYPE
          SYNTAX      Counter
          ACCESS      read-only
          STATUS      mandatory
          DESCRIPTION
             "Displays the number of Frames received during VBERT Test that 
              had the Discard Eligibility indicator bit set."
          ::= { sfrapVnipTopologyEntry  18 }
      
      
      
      sfrapVnipTopoVBertTxDEClrFrames   OBJECT-TYPE
          SYNTAX      Counter
          ACCESS      read-only
          STATUS      mandatory
          DESCRIPTION
             "Displays the number of Frames transmitted during VBERT Test that
              had the Discard Eligibility indicator bit cleared."
          ::= { sfrapVnipTopologyEntry  19 }
      
      
      sfrapVnipTopoVBertRxDEClrFrames OBJECT-TYPE
          SYNTAX      Counter
          ACCESS      read-only
          STATUS      mandatory
          DESCRIPTION
             "Displays the number of Frames received during VBERT Test that 
              had the Discard Eligibility indicator bit cleared."
          ::= { sfrapVnipTopologyEntry  20 }
      
      sfrapVnipTopoVBertTransitDelayMax OBJECT-TYPE
          SYNTAX      Counter
          ACCESS      read-only
          STATUS      mandatory
          DESCRIPTION
             "The maximum transit delay between this
              node and the remote peer during the VBERT test."
          ::= { sfrapVnipTopologyEntry  21 }
      
       
      sfrapVnipTopoVBertTransitDelayAvg OBJECT-TYPE
          SYNTAX      Counter
          ACCESS      read-only
          STATUS      mandatory
          DESCRIPTION
             "The average transit delay between this
              node and the remote peer during the VBERT test."
          ::= { sfrapVnipTopologyEntry  22 }
      
      sfrapVnipTopoVBertTimeElapse OBJECT-TYPE
          SYNTAX      TimeTicks
          ACCESS      read-only
          STATUS      mandatory
          DESCRIPTION
             "Elapsed time since VBERT test was started or cleared."
          ::= { sfrapVnipTopologyEntry  23 }


      sfrapVnipTopoVBertPerUtilCIR OBJECT-TYPE
          SYNTAX      INTEGER
          ACCESS      read-only
          STATUS      mandatory
          DESCRIPTION
             " The calculated percent of CIR utilization during a VBERT test,
               this value is only valid after a test is complete not during."
          ::= { sfrapVnipTopologyEntry 24 }


      sfrapVnipTopoVBertPerUtilEIR OBJECT-TYPE
          SYNTAX      INTEGER
          ACCESS      read-only
          STATUS      mandatory
          DESCRIPTION
             " The calculated percent of EIR utilization during a VBERT test,
               this value is only valid after a test is complete not during."
          ::= { sfrapVnipTopologyEntry 25 }


sfrapVnipTransitDelayClear    OBJECT-TYPE
          SYNTAX      INTEGER
          {
              clear-transit-delay (1)
          }
          ACCESS      write-only
          STATUS      mandatory
          DESCRIPTION
             "Allows the user to clear all the VNIP Transit Delay
              data collected in the VNIP topology database."
          ::= { sfrapStatus 5 }

sfrapLmiSourcing OBJECT-TYPE
         SYNTAX      INTEGER
         {
              initializing (1),
              passthrough  (2),
              user-to-dte  (3),
              user-to-dce  (4),
              ntwk-to-dte  (5),
              ntwk-to-dce  (6),
              disabled     (7),
              both-ports   (8)
         }
         ACCESS      read-only
         STATUS      mandatory
         DESCRIPTION
            "What type of LMI sourcing is being done: initializing (1),
             passthrough (2), emulating a user device on the To-DTE (3),
             emulating a user device on the To-DCE (4), emulating a
             network device on the To-DTE (5), emulating a network device
             on the To-DCE (6), disabled (7), or emulating a switch by
             responding to both ports (8)."
         ::= { sfrapStatus 6 }


sfrapVBertClear    OBJECT-TYPE
          SYNTAX      INTEGER
          {
              clear-vbert (1)
          }
          ACCESS      write-only
          STATUS      mandatory
          DESCRIPTION
             "Allows the user to clear all the VBERT data
              collected in the VNIP topology database as long as 
              the entry is not in a test status."
      ::= { sfrapStatus 11 }

--
--      Management Status 
--
--         The current status of the InBand Mangement configuration. 
--         This section is intended to display information of how the
--         node is configured for InBand Management.
--

sfrapStatusMgmtTable   OBJECT IDENTIFIER ::= { sfrapStatus 3 }

sfrapStatusMgmtChannel   OBJECT-TYPE
     SYNTAX  INTEGER
     {
        none             (1),
        slip             (2), 
        private-dlci     (3),
        piggyback-dlci   (4)
     }
     ACCESS  read-only
     STATUS  mandatory
     DESCRIPTION
        "This is the method in which the unit is configured for
         SNMP management access.
         (1) None: SNMP management disabled
         (2) SLIP: out-of-band management via asynchronous Serial Line IP
         (3) Private DLCI: in-band management using a private DLCI that 
             is dedicated solely to this unit's management.
         (4) Piggyback DLCI: in-band management using any DLCI optionally
             multiplexing both management and user data."
    ::= {sfrapStatusMgmtTable 1}                

sfrapStatusMgmtInterface   OBJECT-TYPE
     SYNTAX  INTEGER
     {
        comm             (1),
        local-to-dte     (2), 
        remote-to-dce    (3),
        local-and-remote (4)
     }
     ACCESS  read-only
     STATUS  mandatory
     DESCRIPTION
        "This is the port(s) on which the management traffic will appear.
         (1) Async Maintenance(Comm)/Console port - SLIP mode
         (2) Local TO-DTE interface: unit is configured for Private Local 
             DLCI mode
         (3) Remote WAN Interface: unit is confiogured for Private Remote
             DLCI mode
         (4) TO-DTE and WAN Interfaces: unit is configured for either Piggyback
             Bidirectional mode."
     ::= {sfrapStatusMgmtTable 2}                

sfrapStatusMgmtInterfaceStatus   OBJECT-TYPE
     SYNTAX  INTEGER
     {
        active     (1),
        inactive   (2), 
        alarm      (3)
     }
     ACCESS  read-only
     STATUS  mandatory
     DESCRIPTION
        "This is the status of the port(s) on which
         the management traffic will appear.
         (1) Active: port or DLCI is configured and status is okay
         (2) Inactive: port or DLCI is declared out of service 
         (3) Alarm: port or DLCI is experiencing an alarm condition that may
             interefere with management access  "
     ::= {sfrapStatusMgmtTable 3}                

sfrapStatusMgmtDefaultDLCINo   OBJECT-TYPE
     SYNTAX  INTEGER
     ACCESS  read-only
     STATUS  mandatory
     DESCRIPTION
        "This is the DLCI for the PVC that is defined for the
        Management port.  All traffic using this DLCI in the Frame
        Replay packet will be destined for the InBand Management task."
     ::= {sfrapStatusMgmtTable 4}                

sfrapStatusMgmtDefaultDLCIStatus   OBJECT-TYPE
     SYNTAX  INTEGER
     {
        na              (1),
        dlci-active     (2), 
        dlci-inactive   (3)
     }
     ACCESS  read-only
     STATUS  mandatory
     DESCRIPTION
        "This is the status of the default management DLCI.
         (1) not applicable: SLIP mode or management is disabled
         (2) DLCI Active: default DLCI is active in the LMI full 
             status response.
         (3) DLCI Inactive: default DLCI is not active in the LMI full 
             status response."
     ::= {sfrapStatusMgmtTable 5}                

sfrapStatusClockRate               OBJECT-TYPE
      SYNTAX      INTEGER (0..2048000)
      ACCESS      read-only
      STATUS      mandatory
      DESCRIPTION
         "This is the value in Kbps of the Receive Clock Frequency,
         for both the TO-DTE and TO-DCE ports."   
         ::= { sfrapStatus 8 }

sfrapStatusToDteRxClockMode OBJECT-TYPE
     SYNTAX      INTEGER
     {
          clock-normal      (1),
          clock-invert      (2),
          clock-auto-normal (3),
          clock-auto-invert (4)
     }
     ACCESS      read-only
     STATUS      mandatory
     DESCRIPTION
        "The status of the Receive clocking mode."
     ::= { sfrapStatus   9 }

sfrapStatusLmiAutosense   OBJECT-TYPE
     SYNTAX  INTEGER
     {
        disabled            (1),
        searching           (2),
        learned-annex-d     (3),
        learned-annex-a     (4),
        learned-type1       (5)
     }
     ACCESS  read-only
     STATUS  mandatory
     DESCRIPTION
        "This indicates the current status of LMI Auto Sensing if 
         it's enabled.
         (1) Disabled: LMI is configured as Type 1, Annex-D, or Annex-A
         (2) Searching: unit is attempting to determine the LMI type of
             the attached equipment by issuing LMI messages of each LMI 
             type and searching for responses.
         (3) Learned Annex-D: unit has successfully detected Annex-D LMI
             (ANSI T1.617 Annex D)
         (4) Learned Annex-A: unit has successfully detected Annex-A LMI
             (ITU/CCITT Q.933 Annex A)
         (5) Learned Type 1: unit has successfully detected Type 1 LMI
             (Cisco, Group of four, LMI)"
     ::= { sfrapStatus 12 }
     
sfrapStatusTxClockDetect OBJECT-TYPE
          SYNTAX  INTEGER
          {
              inactive              (1),
              initiate              (2),
              trying-cut-thru       (3),
              failed-cut-thru       (4),
              trying-inband-norm    (5),
              success-inband-norm   (6),
              failed-inband-norm    (7),
              trying-inband-invert  (8),
              success-inband-invert (9),
              failed-inband         (10),
              terminate             (11)
          }
          ACCESS  read-only
          STATUS  mandatory
          DESCRIPTION
             "This selection displays the status of the TO-DCE
              transmit clock auto detection process.
              (1)inactive - The Auto Detect option was not
              selected.
              (2)initiate - The Auto Detect option was selected
              and is initializing.
              (3)trying-cut-thru - The Auto Detect option is trying
              to verify the integrity of the TO-DCE transmit clock
              mode selected in Cut Through mode
              (4)failed-cut-thru - This mechanism has detected that the
              LMI integrity check has failed.
              (5)trying-inband-normal - The Auto Detection mechanism
              has set the TO-DCE Tx clock to normal timing and is
              performing the link integrity check, to determine if this
              selection is correct
              (6)success-inband-norm - The Auto Detection mechanism has
              determined that the TO-DCE Tx clock timing is successful
              in normal mode.
              (7)trying-inband-invert - The Auto Detection mechanism
              has determined that the TO-DCE clock mode failed using
              normal timing, now it has inverted the clock.
              (8)success-inband-invert - The mechanism has decided that
              the TO-DCE Tx clock needs to be inverted.
              (9)failed-in-band - Neither Normal or Invert timing was
              successful.
              (10)terminated - The Auto Detection mechanism has been
              terminated."

         ::= { sfrapStatus 13 }

-- =========================
-- ==  PERFORMANCE group  ==
-- =========================

sfrapPerformance  OBJECT IDENTIFIER ::= { sfrap 5 }

   --    1  PerfMgmtIp                          sfrap
   --    2  PerfThruput                         sfrap
   --          1  sfrapPerfThruputPerIntfTable  sfrap
   --          2  sfrapPerfThruputPerDlciTable  sfrap
   --          3  sfrapPerfThruputCommands      sfrap
   --    3  PerfNetworkShortTerm                sfrap
   --    4  PerfNetworkLongTerm                 sfrap
   --    5  PerfFRStatsCollectionStatus         sfrap

--
--    IP protocol stack statistics - a reflection of some MIB-2 variables
--

sfrapPerfMgmtIp   OBJECT IDENTIFIER ::= { sfrapPerformance 2 }

sfrapPerfMgmtIpIFStatsTable OBJECT IDENTIFIER ::= { sfrapPerfMgmtIp 1 }

          sfrapPerfMgmtIpIFInOctets OBJECT-TYPE
              SYNTAX  Counter
              ACCESS  read-only
              STATUS  mandatory
              DESCRIPTION
                      "The count of all octets received.
                       Same as ifInOctets in mib-2."
              ::= { sfrapPerfMgmtIpIFStatsTable 1 }

          sfrapPerfMgmtIpIFInErrors OBJECT-TYPE
              SYNTAX  Counter
              ACCESS  read-only
              STATUS  mandatory
              DESCRIPTION
                      "The count of packets received that could
                       not be delivered because of errors.
                       Same as ifInErrors in mib-2."
              ::= { sfrapPerfMgmtIpIFStatsTable 2 }

          sfrapPerfMgmtIpIFOutOctets OBJECT-TYPE
              SYNTAX  Counter
              ACCESS  read-only
              STATUS  mandatory
              DESCRIPTION
                      "The count of all octets transmitted.
                       Same as ifOutOctets in mib-2."
              ::= { sfrapPerfMgmtIpIFStatsTable 3 }

          sfrapPerfMgmtIpIFOperStatus OBJECT-TYPE
              SYNTAX  INTEGER 
              {
                  up(1),
                  down(2),
                  testing(3)
              }
              ACCESS  read-only
              STATUS  mandatory
              DESCRIPTION
                      "The current operational state.
                       Same as ifOperStatus in mib-2."
              ::= { sfrapPerfMgmtIpIFStatsTable 4 }

   sfrapPerfMgmtIpIPStatsTable OBJECT IDENTIFIER ::= { sfrapPerfMgmtIp 2 }

          sfrapPerfMgmtIpIPInRcv OBJECT-TYPE
              SYNTAX  Counter
              ACCESS  read-only
              STATUS  mandatory
              DESCRIPTION
                      "The count of all datagrams received.
                       Same as ipInReceives in mib-2."
              ::= { sfrapPerfMgmtIpIPStatsTable 1 }

          sfrapPerfMgmtIpIPInHdrErr OBJECT-TYPE
              SYNTAX  Counter
              ACCESS  read-only
              STATUS  mandatory
              DESCRIPTION
                      "The count of datagrams received that were
                       discarded because of errors in their IP headers.
                       Same as ipInHdrErrors in mib-2."
              ::= { sfrapPerfMgmtIpIPStatsTable 2 }

          sfrapPerfMgmtIpIPInAddrErr OBJECT-TYPE
              SYNTAX  Counter
              ACCESS  read-only
              STATUS  mandatory
              DESCRIPTION
                      "The count of datagrams received that were
                       discarded because unexpected or invalid IP
                       addresses in their IP headers.
                       Same as ipInAddrErrors in mib-2."
              ::= { sfrapPerfMgmtIpIPStatsTable 3 }

          sfrapPerfMgmtIpIPInProtUnk OBJECT-TYPE
              SYNTAX  Counter
              ACCESS  read-only
              STATUS  mandatory
              DESCRIPTION
                      "The count of datagrams received that were
                       discarded because of unsupported protocols.
                       Same as ipInUnknownProtos in mib-2."
              ::= { sfrapPerfMgmtIpIPStatsTable 4 }

          sfrapPerfMgmtIpIPInDscrd OBJECT-TYPE
              SYNTAX  Counter
              ACCESS  read-only
              STATUS  mandatory
              DESCRIPTION
                      "The count of datagrams received that were
                       discarded for reasons other than a problem with
                       the datagram. Same as ipInDiscards in mib-2."
              ::= { sfrapPerfMgmtIpIPStatsTable 5 }

          sfrapPerfMgmtIpIPInDlvrs OBJECT-TYPE
              SYNTAX  Counter
              ACCESS  read-only
              STATUS  mandatory
              DESCRIPTION
                      "The count of datagrams received that were
                       delivered to IP client-protocols.
                       Same as ipInDelivers in mib-2."
              ::= { sfrapPerfMgmtIpIPStatsTable 6 }

          sfrapPerfMgmtIpIPOutRqst OBJECT-TYPE
              SYNTAX  Counter
              ACCESS  read-only
              STATUS  mandatory
              DESCRIPTION
                      "The count of all outgoing datagrams
                       originating in this node.
                       Same as ipOutRequests in mib-2."
              ::= { sfrapPerfMgmtIpIPStatsTable 7 }

          sfrapPerfMgmtIpIPOutDscrd OBJECT-TYPE
              SYNTAX  Counter
              ACCESS  read-only
              STATUS  mandatory
              DESCRIPTION
                      "The count of outgoing datagrams that were
                       discarded for reasons other than a problem with
                       the datagram. Same as ipOutDiscards in mib-2."
              ::= { sfrapPerfMgmtIpIPStatsTable 8 }

          sfrapPerfMgmtIpIPOutNoRt OBJECT-TYPE
              SYNTAX  Counter
              ACCESS  read-only
              STATUS  mandatory
              DESCRIPTION
                      "The count of outgoing datagrams that were
                       discarded because no route could be found
                       for transmission.
                       Same as ipOutNoRoutes in mib-2."
              ::= { sfrapPerfMgmtIpIPStatsTable 9 }


   sfrapPerfMgmtIpICMPStatsTable OBJECT IDENTIFIER ::= { sfrapPerfMgmtIp 3 }

          sfrapPerfMgmtIpICMPInMsgs OBJECT-TYPE
              SYNTAX  Counter
              ACCESS  read-only
              STATUS  mandatory
              DESCRIPTION
                      "The count of all ICMP messages received.
                       Same as icmpInMsgs in mib-2."
              ::= { sfrapPerfMgmtIpICMPStatsTable 1 }

          sfrapPerfMgmtIpICMPInErrors OBJECT-TYPE
              SYNTAX  Counter
              ACCESS  read-only
              STATUS  mandatory
              DESCRIPTION
                      "The count of ICMP messages received with
                       errors. Same as icmpInErrors in mib-2."
              ::= { sfrapPerfMgmtIpICMPStatsTable 2 }

          sfrapPerfMgmtIpICMPInDestUnreachs OBJECT-TYPE
              SYNTAX  Counter
              ACCESS  read-only
              STATUS  mandatory
              DESCRIPTION
                      "The count of ICMP Destination Unreachable
                       messages received.
                       Same as icmpInDestUnreachs in mib-2."
              ::= { sfrapPerfMgmtIpICMPStatsTable 3 }

          sfrapPerfMgmtIpICMPInTimeExcds OBJECT-TYPE
              SYNTAX  Counter
              ACCESS  read-only
              STATUS  mandatory
              DESCRIPTION
                      "The count of ICMP Time Exceeded messages
                       received.
                       Same as icmpInTimeExcds in mib-2."
              ::= { sfrapPerfMgmtIpICMPStatsTable 4 }

          sfrapPerfMgmtIpICMPInParmProbs OBJECT-TYPE
              SYNTAX  Counter
              ACCESS  read-only
              STATUS  mandatory
              DESCRIPTION
                      "The count of ICMP Parameter Problem messages
                       received.
                       Same as icmpInParmProbs in mib-2."
              ::= { sfrapPerfMgmtIpICMPStatsTable 5 }

          sfrapPerfMgmtIpICMPInRedirects OBJECT-TYPE
              SYNTAX  Counter
              ACCESS  read-only
              STATUS  mandatory
              DESCRIPTION
                      "The count of ICMP Redirect messages received.
                       Same as icmpInRedirects in mib-2."
              ::= { sfrapPerfMgmtIpICMPStatsTable 6 }

          sfrapPerfMgmtIpICMPInEchos OBJECT-TYPE
              SYNTAX  Counter
              ACCESS  read-only
              STATUS  mandatory
              DESCRIPTION
                      "The count of ICMP Echo messages received.
                       Same as icmpInEchos in mib-2."
              ::= { sfrapPerfMgmtIpICMPStatsTable 7 }

          sfrapPerfMgmtIpICMPInEchoReps OBJECT-TYPE
              SYNTAX  Counter
              ACCESS  read-only
              STATUS  mandatory
              DESCRIPTION
                      "The count of ICMP Echo Reply messages received.
                       Same as icmpInEchoReps in mib-2."
              ::= { sfrapPerfMgmtIpICMPStatsTable 8 }

          sfrapPerfMgmtIpICMPOutMsgs OBJECT-TYPE
              SYNTAX  Counter
              ACCESS  read-only
              STATUS  mandatory
              DESCRIPTION
                      "The count of all outgoing ICMP messages
                       originating in this node.
                       Same as icmpOutMsgs in mib-2."
              ::= { sfrapPerfMgmtIpICMPStatsTable 9 }

          sfrapPerfMgmtIpICMPOutErrors OBJECT-TYPE
              SYNTAX  Counter
              ACCESS  read-only
              STATUS  mandatory
              DESCRIPTION
                      "The count of outgoing ICMP messages not
                       transmitted due problems found by the ICMP layer.                                        which this entity did
                       Same as icmpOutErrors in mib-2."
              ::= { sfrapPerfMgmtIpICMPStatsTable 10 }

          sfrapPerfMgmtIpICMPOutDestUnreachs OBJECT-TYPE
              SYNTAX  Counter
              ACCESS  read-only
              STATUS  mandatory
              DESCRIPTION
                      "The count of outgoing ICMP Destination Unreachable
                       messages.
                       Same as icmpOutDestUnreachs in mib-2."
              ::= { sfrapPerfMgmtIpICMPStatsTable 11 }

          sfrapPerfMgmtIpICMPOutParmProbs OBJECT-TYPE
              SYNTAX  Counter
              ACCESS  read-only
              STATUS  mandatory
              DESCRIPTION
                      "The count of outgoing ICMP Parameter Problem
                       messages.
                       Same as icmpOutParmProbs in mib-2."
              ::= { sfrapPerfMgmtIpICMPStatsTable 12 }

          sfrapPerfMgmtIpICMPOutRedirects OBJECT-TYPE
              SYNTAX  Counter
              ACCESS  read-only
              STATUS  mandatory
              DESCRIPTION
                      "The count of outgoing ICMP Redirect messages.
                       Same as icmpOutRedirects in mib-2."
              ::= { sfrapPerfMgmtIpICMPStatsTable 13 }

          sfrapPerfMgmtIpICMPOutEchos OBJECT-TYPE
              SYNTAX  Counter
              ACCESS  read-only
              STATUS  mandatory
              DESCRIPTION
                      "The count of outgoing ICMP Echo messages.
                       Same as icmpOutEchos in mib-2."
              ::= { sfrapPerfMgmtIpICMPStatsTable 14 }

          sfrapPerfMgmtIpICMPOutEchoReps OBJECT-TYPE
              SYNTAX  Counter
              ACCESS  read-only
              STATUS  mandatory
              DESCRIPTION
                      "The count of outgoing ICMP Echo Reply messages.
                       Same as icmpOutEchoReps in mib-2."
              ::= { sfrapPerfMgmtIpICMPStatsTable 15 }

   sfrapPerfMgmtIpUDPStatsTable OBJECT IDENTIFIER ::= { sfrapPerfMgmtIp 4 }

          sfrapPerfMgmtIpUDPInDatagrams OBJECT-TYPE
              SYNTAX  Counter
              ACCESS  read-only
              STATUS  mandatory
              DESCRIPTION
                 "The count of all UDP datagrams received that are 
                  addressed as management frames for this unit. Same 
                  as udpInDatagrams in mib-2."
              ::= { sfrapPerfMgmtIpUDPStatsTable 1 }

          sfrapPerfMgmtIpUDPOutDatagrams OBJECT-TYPE
              SYNTAX  Counter
              ACCESS  read-only
              STATUS  mandatory
              DESCRIPTION
                      "The count of all UDP datagrams generated by
                       this unit. Same as udpOutDatagrams in mib-2."
              ::= { sfrapPerfMgmtIpUDPStatsTable 2 }

          sfrapPerfMgmtIpUDPNoPorts OBJECT-TYPE
              SYNTAX  Counter
              ACCESS  read-only
              STATUS  mandatory
              DESCRIPTION
                 "The count of all UDP datagrams received that are 
                  addressed as management frames for this unit with 
                  no application at the destination port. Same as 
                  udpNoPorts in mib-2."
              ::= { sfrapPerfMgmtIpUDPStatsTable 3 }


   sfrapPerfMgmtIpTCPStatsTable OBJECT IDENTIFIER ::= { sfrapPerfMgmtIp 5 }

          sfrapPerfMgmtIpTCPActiveOpens OBJECT-TYPE
              SYNTAX  Counter
              ACCESS  read-only
              STATUS  mandatory
              DESCRIPTION
                 "The count of the times TCP connections specific to this 
                  unit have made a direct state transition from CLOSED to 
                  SYN-SENT. Same as tcpActiveOpens in mib-2."
              ::= { sfrapPerfMgmtIpTCPStatsTable 1 }

          sfrapPerfMgmtIpTCPPassiveOpens OBJECT-TYPE
              SYNTAX  Counter
              ACCESS  read-only
              STATUS  mandatory
              DESCRIPTION
                 "The count of the times TCP connections specific to 
                  this unit have made a direct state transition from 
                  CLOSED to SYN-RCVD. Same as tcpPassiveOpens in mib-2."
              ::= { sfrapPerfMgmtIpTCPStatsTable 2 }

          sfrapPerfMgmtIpTCPAttemptFails OBJECT-TYPE
              SYNTAX  Counter
              ACCESS  read-only
              STATUS  mandatory
              DESCRIPTION
                 "The count of the times TCP connections specific to this unit
                  have made a direct state transition from SYN-SENT or SYN-RCVD
                  to CLOSED state, plus the count of the times TCP connections 
                  have made a direct state transition from SYN-RCVD to LISTEN.
                  Same as tcpAttemptFails in mib-2."
              ::= { sfrapPerfMgmtIpTCPStatsTable 3 }

          sfrapPerfMgmtIpTCPCurrEstab OBJECT-TYPE
              SYNTAX  Gauge
              ACCESS  read-only
              STATUS  mandatory
              DESCRIPTION
                 "The count of the TCP connections specific to this unit
                  in state ESTABLISHED or CLOSE-WAIT. Same as tcpCurrEstab 
                  in mib-2."
              ::= { sfrapPerfMgmtIpTCPStatsTable 4 }

          sfrapPerfMgmtIpTCPInSegs OBJECT-TYPE
              SYNTAX  Counter
              ACCESS  read-only
              STATUS  mandatory
              DESCRIPTION
                 "The count of all the segments received that are 
                  addressed as management frames for this unit.
                  Same as tcpInSegs in mib-2."
              ::= { sfrapPerfMgmtIpTCPStatsTable 5 }

          sfrapPerfMgmtIpTCPOutSegs OBJECT-TYPE
              SYNTAX  Counter
              ACCESS  read-only
              STATUS  mandatory
              DESCRIPTION
                 "The count of all the segments generated from this unit.
                  Same as tcpOutSegs in mib-2."
              ::= { sfrapPerfMgmtIpTCPStatsTable 6 }


--
--       The sfrap Performance Thruput Table
--              This table contains Thruput statistics for the TO-DTE port
--              and the TO-DCE port.  This table does NOT contain any PVC 
--              DLCI thruput statistics.
--

sfrapPerfThruput   OBJECT IDENTIFIER ::= { sfrapPerformance 3 }

--
--       The DLCI Statistics Table
--              This table contains the DLCI Statistics (layer 2).

   Index ::= INTEGER

sfrapPerfThruputPerIntfTable  OBJECT-TYPE
     SYNTAX  SEQUENCE OF  SfrapPerfThruputPerIntfEntry
     ACCESS  not-accessible
     STATUS  mandatory
     DESCRIPTION
        "The throughput per interface table. These values are accumulated
         across all DLCIs."
     ::= { sfrapPerfThruput 1 }

sfrapPerfThruputPerIntfEntry  OBJECT-TYPE
     SYNTAX  SfrapPerfThruputPerIntfEntry
     ACCESS  not-accessible
     STATUS  mandatory
     DESCRIPTION
        "An entry in the throughput per interface table."
     INDEX   { sfrapPerfThruputPerIntfIndex }
     ::= { sfrapPerfThruputPerIntfTable 1 }

SfrapPerfThruputPerIntfEntry ::=
     SEQUENCE {
        sfrapPerfThruputPerIntfIndex       INTEGER, 
        sfrapPerfThruputPerIntfRxByteCnt   Counter,
        sfrapPerfThruputPerIntfTxByteCnt   Counter,
        sfrapPerfThruputPerIntfRxFrameCnt  Counter,
        sfrapPerfThruputPerIntfTxFrameCnt  Counter,
        sfrapPerfThruputPerIntfRxCrcErrCnt Counter,
        sfrapPerfThruputPerIntfRxAbortCnt  Counter,
        sfrapPerfThruputPerIntfRxBpvCnt    Counter
     }

   sfrapPerfThruputPerIntfIndex    OBJECT-TYPE
          SYNTAX      INTEGER
          {
             to-dte   (1),
             to-dce   (2)
          }
          ACCESS      read-only
          STATUS      mandatory
          DESCRIPTION
             "Interface for which the statistics apply.
              (1) TO-DTE interface
              (2) TO-DCE interface"
          ::= { sfrapPerfThruputPerIntfEntry 1 }

   sfrapPerfThruputPerIntfRxByteCnt    OBJECT-TYPE
          SYNTAX      Counter 
          ACCESS      read-only
          STATUS      mandatory
          DESCRIPTION
             "The number of framed bytes that have been received
              on this interface."
          ::= { sfrapPerfThruputPerIntfEntry 2 }

   sfrapPerfThruputPerIntfTxByteCnt    OBJECT-TYPE
             SYNTAX      Counter
             ACCESS      read-only
             STATUS      mandatory
             DESCRIPTION
                "The number of framed bytes that have been transmitted
                 on this interface."
             ::= { sfrapPerfThruputPerIntfEntry 3 }

   sfrapPerfThruputPerIntfRxFrameCnt    OBJECT-TYPE
             SYNTAX      Counter 
             ACCESS      read-only
             STATUS      mandatory
             DESCRIPTION
                "The number of frames that have been received
                 on this interface."
             ::= { sfrapPerfThruputPerIntfEntry 4 }

   sfrapPerfThruputPerIntfTxFrameCnt    OBJECT-TYPE
             SYNTAX      Counter 
             ACCESS      read-only
             STATUS      mandatory
             DESCRIPTION
                "The number of frames that have been transmitted
                 on this interface."
             ::= { sfrapPerfThruputPerIntfEntry 5 }

   sfrapPerfThruputPerIntfRxCrcErrCnt  OBJECT-TYPE
             SYNTAX      Counter 
             ACCESS      read-only
             STATUS      mandatory
             DESCRIPTION
                "The number of frames with CRC errors received
                 on this interface."
            ::= { sfrapPerfThruputPerIntfEntry 6 }

   sfrapPerfThruputPerIntfRxAbortCnt   OBJECT-TYPE
             SYNTAX      Counter 
             ACCESS      read-only
             STATUS      mandatory
             DESCRIPTION
                "The number of aborted frames received
                 on this interface."
            ::= { sfrapPerfThruputPerIntfEntry 7 }

   sfrapPerfThruputPerIntfRxBpvCnt   OBJECT-TYPE
             SYNTAX      Counter 
             ACCESS      read-only
             STATUS      mandatory
             DESCRIPTION
                "The number of BPV errors received
                 on this interface."
            ::= { sfrapPerfThruputPerIntfEntry 8 }


   sfrapPerfThruputPerDlciTable OBJECT-TYPE
         SYNTAX   SEQUENCE OF SfrapPerfThruputPerDlciEntry
         ACCESS   not-accessible
         STATUS   mandatory
         DESCRIPTION
            "Layer 2 statistics on a per-DLCI basis. Transmit direction
             is from TO-DTE to WAN and receive direction is from the WAN
             towards the TO-DTE."
         ::= { sfrapPerfThruput 2 }

         sfrapPerfThruputPerDlciEntry OBJECT-TYPE
             SYNTAX   SfrapPerfThruputPerDlciEntry
             ACCESS   not-accessible
             STATUS   mandatory
             DESCRIPTION
                "The Statistics for a particular Data Link
                 Connection Management Interface (DLCI)."
            INDEX { sfrapPerfThruputPerDlciIndex,
                    sfrapPerfThruputPerDlciValue }
            ::= { sfrapPerfThruputPerDlciTable 1 }

         SfrapPerfThruputPerDlciEntry ::=
             SEQUENCE {
                 sfrapPerfThruputPerDlciIndex               Index,
                 sfrapPerfThruputPerDlciValue               INTEGER,
                 sfrapPerfThruputPerDlciCreateTime          INTEGER,
                 sfrapPerfThruputPerDlciChangeTime          INTEGER,
                 sfrapPerfThruputPerDlciRxByte              Counter,
                 sfrapPerfThruputPerDlciTxByte              Counter,
                 sfrapPerfThruputPerDlciRxFrame             Counter,
                 sfrapPerfThruputPerDlciTxFrame             Counter,
                 sfrapPerfThruputPerDlciRxFecn              Counter,
                 sfrapPerfThruputPerDlciRxBecn              Counter,
                 sfrapPerfThruputPerDlciRxDe                Counter,
                 sfrapPerfThruputPerDlciTxDe                Counter,
                 sfrapPerfThruputPerDlciRxThruput           INTEGER,
                 sfrapPerfThruputPerDlciTxThruput           INTEGER,
                 sfrapPerfThruputPerDlciCIR                 INTEGER,
                 sfrapPerfThruputPerDlciUptime              INTEGER,
                 sfrapPerfThruputPerDlciDowntime            INTEGER,
                 sfrapPerfThruputPerDlciCirType             INTEGER,
                 sfrapPerfThruputPerDlciPvcState            INTEGER,
                 sfrapPerfThruputPerDlciOutageCount         Counter,
                 sfrapPerfThruputPerDlciAvailability        INTEGER,
                 sfrapPerfThruputPerDlciMTBSO               INTEGER,
                 sfrapPerfThruputPerDlciMTTSR               INTEGER,
                 sfrapPerfThruputPerDlciEncapType           INTEGER,
                 sfrapPerfThruputPerDlciRxUtilizationStatus INTEGER,
                 sfrapPerfThruputPerDlciTxUtilizationStatus INTEGER,
                 sfrapPerfThruputPerDlciEIR                 INTEGER
             }

   sfrapPerfThruputPerDlciIndex OBJECT-TYPE
             SYNTAX   Index
             ACCESS   read-only
             STATUS   mandatory
             DESCRIPTION
                "This value must be in the range 1-3.
                 Other than that, this value is ignored as
                 all three will return the same result."
            ::= { sfrapPerfThruputPerDlciEntry 1 }

   sfrapPerfThruputPerDlciValue    OBJECT-TYPE
             SYNTAX      INTEGER 
             ACCESS      read-only
             STATUS      mandatory
             DESCRIPTION
                "The DLCI value in which the Statistics are associated."
            ::= { sfrapPerfThruputPerDlciEntry 2 }

   sfrapPerfThruputPerDlciCreateTime    OBJECT-TYPE
             SYNTAX      INTEGER 
             ACCESS      read-only
             STATUS      mandatory
             DESCRIPTION
                "The amount of time elapsed since this DLCI was first
                 detected through traffic sensing or in an LMI message 
                 (in seconds)."
            ::= { sfrapPerfThruputPerDlciEntry 3 }

   sfrapPerfThruputPerDlciChangeTime    OBJECT-TYPE
             SYNTAX      INTEGER 
             ACCESS      read-only
             STATUS      mandatory
             DESCRIPTION
                "The amount of elapsed time since this DLCI last
                 changed state from active to inactive or vice versa
                 (in seconds)."
            ::= { sfrapPerfThruputPerDlciEntry 4 }

   sfrapPerfThruputPerDlciRxByte    OBJECT-TYPE
             SYNTAX      Counter 
             ACCESS      read-only
             STATUS      mandatory
             DESCRIPTION
                "The number of bytes that have been received from
                 the WAN towards the DTE on this DLCI. This count
                 will include any frames that are terminated by the 
                 unit and do not pass through to the opposite interface 
                 (management and networking data)."
            ::= { sfrapPerfThruputPerDlciEntry 5 }

   sfrapPerfThruputPerDlciTxByte    OBJECT-TYPE
             SYNTAX      Counter
             ACCESS      read-only
             STATUS      mandatory
             DESCRIPTION
                "The number of bytes that have been transmitted from the
                 TO-DTE towards the WAN on this DLCI. This count
                 will include any frames that are terminated by the 
                 unit and do not pass through to the opposite interface 
                 (management and networking data)."
       ::= { sfrapPerfThruputPerDlciEntry 6 }

   sfrapPerfThruputPerDlciRxFrame    OBJECT-TYPE
             SYNTAX      Counter
             ACCESS      read-only
             STATUS      mandatory
             DESCRIPTION
                "The number of frames that have been received from
                 the WAN towards to the DTE on this DLCI. This count
                 will include any frames that are terminated by the 
                 unit and do not pass through to the opposite interface 
                 (management and networking data)."
            ::= { sfrapPerfThruputPerDlciEntry 7 }

   sfrapPerfThruputPerDlciTxFrame    OBJECT-TYPE
             SYNTAX      Counter
             ACCESS      read-only
             STATUS      mandatory
             DESCRIPTION
                "The number of frames that have been transmitted from the
                 TO-DTE towards the WAN on this DLCI. This count
                 will include any frames that are terminated by the 
                 unit and do not pass through to the opposite interface 
                 (management and networking data)."
            ::= { sfrapPerfThruputPerDlciEntry 8 }

   sfrapPerfThruputPerDlciRxFecn    OBJECT-TYPE
             SYNTAX      Counter
             ACCESS      read-only
             STATUS      mandatory
             DESCRIPTION
                "The number of frames received from the WAN towards the TO-DTE 
                 that have had the Forward Explict Congestion Notification 
                 (FECN) bit set on this DLCI. This count will include any 
                 frames that are terminated by the unit and do not pass 
                 through to the opposite interface (management and networking 
                 data)."
            ::= { sfrapPerfThruputPerDlciEntry 9 }

   sfrapPerfThruputPerDlciRxBecn    OBJECT-TYPE
             SYNTAX      Counter
             ACCESS      read-only
             STATUS      mandatory
             DESCRIPTION
                "The number of frames received from the WAN towards the TO-DTE 
                 that have had the Backward Explict Congestion Notification 
                 (BECN) bit set on this DLCI. This count will include any 
                 frames that are terminated by the unit and do not pass 
                 through to the opposite interface (management and networking 
                 data)."
            ::= { sfrapPerfThruputPerDlciEntry 10 }

   sfrapPerfThruputPerDlciRxDe    OBJECT-TYPE
             SYNTAX      Counter
             ACCESS      read-only
             STATUS      mandatory
             DESCRIPTION
                "The number of frames received from the WAN towards the TO-DTE 
                 that have had the Discard Eligibility (DE) bit set on 
                 this DLCI. This count will include any frames that are 
                 terminated by the unit and do not pass through to the 
                 opposite interface (management and networking data)."
            ::= { sfrapPerfThruputPerDlciEntry 11 }

   sfrapPerfThruputPerDlciTxDe    OBJECT-TYPE
             SYNTAX      Counter
             ACCESS      read-only
             STATUS      mandatory
             DESCRIPTION
                "The number of frames transmit towards the WAN from the TO-DTE 
                 that have had the Discard Eligibility (DE) bit set on 
                 this DLCI. This count will include any frames that are 
                 terminated by the unit and do not pass through to the 
                 opposite interface (management and networking data)."
            ::= { sfrapPerfThruputPerDlciEntry 12 }

   sfrapPerfThruputPerDlciRxThruput    OBJECT-TYPE
             SYNTAX      INTEGER
             ACCESS      read-only
             STATUS      mandatory
             DESCRIPTION
                "The number of bits/sec received from the WAN on this 
                 DLCI. This count will include any frames that are 
                 terminated by the unit and do not pass through to the 
                 opposite interface (management and networking data)."
            ::= { sfrapPerfThruputPerDlciEntry 13 }

   sfrapPerfThruputPerDlciTxThruput    OBJECT-TYPE
             SYNTAX      INTEGER
             ACCESS      read-only
             STATUS      mandatory
             DESCRIPTION
                "The number of bits/sec transmit to the WAN on this 
                 DLCI. This count will include any frames that are 
                 terminated by the unit and do not pass through to 
                 the opposite interface (management and networking data)."
            ::= { sfrapPerfThruputPerDlciEntry 14 }

   sfrapPerfThruputPerDlciCIR    OBJECT-TYPE
             SYNTAX      INTEGER
             ACCESS      read-only
             STATUS      mandatory
             DESCRIPTION
                "The Committed Information Rate (CIR) for this DLCI.
                 This can come form one of three sources: From the LMI
                 Full Status Response, configured by the user, or 
                 the DTE line rate (default)."
            ::= { sfrapPerfThruputPerDlciEntry 15 }

   sfrapPerfThruputPerDlciCirType    OBJECT-TYPE
             SYNTAX      INTEGER 
             {
               cir-acquired-from-lmi  (1),
               cir-configured-by-user (2),
               cir-is-dte-datarate    (3)
             }
             ACCESS      read-only
             STATUS      mandatory
             DESCRIPTION
               "The source of the CIR value for this DLCI. 
                (1) CIR acquired from LMI message. Will override user
                    configured CIR. This feature is not supported by all
                    Frame Relay DCE (switches).
                (2) CIR configured by user.
                (3) CIR is DTE Line Rate. Default if CIR is not set
                    by one of the other methods."
            ::= { sfrapPerfThruputPerDlciEntry 18 }

   sfrapPerfThruputPerDlciUptime    OBJECT-TYPE
             SYNTAX      INTEGER 
             ACCESS      read-only
             STATUS      mandatory
             DESCRIPTION
                "The total amount of time that the DLCI has been up as
                 reported by the LMI Full Status Response (in seconds)."
            ::= { sfrapPerfThruputPerDlciEntry 16 }

   sfrapPerfThruputPerDlciDowntime    OBJECT-TYPE
             SYNTAX      INTEGER 
             ACCESS      read-only
             STATUS      mandatory
             DESCRIPTION
                "The total amount of time that the DLCI has been declared
                 down (in seconds). A DLCI is Down if it's explicitly 
                 declared Inactive through LMI or if it's missing from the 
                 LMI Full Status message or if there is no Full Status 
                 message at all."
            ::= { sfrapPerfThruputPerDlciEntry 17 }

   sfrapPerfThruputPerDlciPvcState   OBJECT-TYPE
             SYNTAX       INTEGER
             {
               pvc-active        (1),
               pvc-inactive      (2),
               pvc-unprovisioned (3),
               pvc-not-in-lmi    (4),
               pvc-lmi-timeout   (5),
               pvc-undetermined  (6)
             }
             ACCESS      read-only
             STATUS      mandatory
             DESCRIPTION
                "The current state of the DLCI:
                 (1) DLCI marked active in last full status LMI
                 (2) DLCI in last full status LMI but not marked active
                 (3) DLCI has never been seen in a full status LMI
                 (4) DLCI was seen at least once in a full status LMI
                     but was not in the last full status LMI
                 (5) the full status LMI has timed out; all previously
                     active or inactive DLCIs are changed to this state
                 (6) DLCI was detected in the traffic stream and a full
                     status LMI has not been received so the state cannot
                     be determined yet. "
            ::= { sfrapPerfThruputPerDlciEntry 19 }
         
   sfrapPerfThruputPerDlciOutageCount   OBJECT-TYPE
              SYNTAX      Counter
              ACCESS      read-only
              STATUS      mandatory
              DESCRIPTION
                 "The number of times the smperPerfThruputPerDlciPvcState
                  transitions from pvc-active or pvc-undetermined to one
                  of the other (inactive) states. "
             ::= { sfrapPerfThruputPerDlciEntry 20 }

   sfrapPerfThruputPerDlciAvailability    OBJECT-TYPE
             SYNTAX      INTEGER
             ACCESS      read-only
             STATUS      mandatory
             DESCRIPTION
                "The measure of the percentage time the DLCI is
                 available: UpTime/CreateTime or zero if CreateTime
                 = 0. (in 1/1000 per cent; i.e. availability = 1000 
                 converts to 1%). "
            ::= { sfrapPerfThruputPerDlciEntry 21 }

   sfrapPerfThruputPerDlciMTBSO    OBJECT-TYPE
             SYNTAX      INTEGER
             ACCESS      read-only
             STATUS      mandatory
             DESCRIPTION
                "Mean Time Between Service Outages: UpTime/OutageCount
                 or zero if OutageCount = 0 (in seconds). "
            ::= { sfrapPerfThruputPerDlciEntry 22 }

   sfrapPerfThruputPerDlciMTTSR    OBJECT-TYPE
             SYNTAX      INTEGER
             ACCESS      read-only
             STATUS      mandatory
             DESCRIPTION
                "Mean Time to ServiceRestoral: DownTime/OutageCount
                 or zero if OutageCount = 0 (in seconds). "
            ::= { sfrapPerfThruputPerDlciEntry 23 }

   sfrapPerfThruputPerDlciEncapType   OBJECT-TYPE
             SYNTAX      INTEGER
             {
                encap-na      (1),
                encap-1490    (2),
                encap-cisco   (3),
                encap-annex-g (4),
                encap-other   (5)
             }
             ACCESS      read-only
             STATUS      mandatory
             DESCRIPTION
                "The encapsulation protocol seen in the last frame
                 analyzed on this DLCI:
                 (1) DLCI is the LMI DLCI or no frames have been
                     analyzed
                 (2) The encapsulation is per rfc1490
                 (3) The encapsulation is per Cisco proprietary
                 (4) The encapsulation is per Annex-G (X.25 over
                     frame relay)
                 (5) The encapsulation is not one of the above. "
            ::= { sfrapPerfThruputPerDlciEntry 24 }

   sfrapPerfThruputPerDlciRxUtilizationStatus OBJECT-TYPE
             SYNTAX      INTEGER
             {
                clear                  (1),
                over-threshold         (2),
                alarm                  (3),
                alarm-under-threshold  (4)
             }
             ACCESS      read-only
             STATUS      mandatory
             DESCRIPTION
                "The status of the per-DLCI utilization
                 alarm in the receive direction.
                 (1) there is no alarm condition; utilization
                     is under the configured CIR percentage
                     threshold; if traps are enabled and the 
                     alarm had been previously triggered, a
                     utilization alarm clear trap will be sent.
                 (2) the utilization has been over the configured 
                     CIR percentage threshold for less than the
                     configured duration.
                 (3) the utilization has been over the configured 
                     CIR percentage threshold for more than the
                     configured duration; if traps are enabled
                     a utilization exceeded trap will be sent.
                 (4) the utilization has been under the configured 
                     CIR percentage threshold for less than the
                     configured duration. "
            ::= { sfrapPerfThruputPerDlciEntry 25 }
             
   sfrapPerfThruputPerDlciTxUtilizationStatus OBJECT-TYPE
             SYNTAX      INTEGER
             {
                clear                  (1),
                over-threshold         (2),
                alarm                  (3),
                alarm-under-threshold  (4)
             }
             ACCESS      read-only
             STATUS      mandatory
             DESCRIPTION
                "The status of the per-DLCI utilization
                 alarm in the transmit direction.
                 (1) there is no alarm condition; utilization
                     is under the configured CIR percentage
                     threshold; if traps are enabled and the 
                     alarm had been previously triggered, a
                     utilization alarm clear trap will be sent.
                 (2) the utilization has been over the configured 
                     CIR percentage threshold for less than the
                     configured duration.
                 (3) the utilization has been over the configured 
                     CIR percentage threshold for more than the
                     configured duration; if traps are enabled
                     a utilization exceeded trap will be sent.
                 (4) the utilization has been under the configured 
                     CIR percentage threshold for less than the
                     configured duration. "
             ::= { sfrapPerfThruputPerDlciEntry 26 }
             
   sfrapPerfThruputPerDlciEIR    OBJECT-TYPE
             SYNTAX      INTEGER
             ACCESS      read-only
             STATUS      mandatory
             DESCRIPTION
                "The Excess Information Rate.  This is defined to
                 be the maximum rate traffic is (supposed to be)
                 allowed to burst to."
            ::= { sfrapPerfThruputPerDlciEntry 27 }
             


sfrapPerfThruputCommands OBJECT IDENTIFIER ::= { sfrapPerfThruput 3 }

   sfrapPerfThruputCmdClearToDteStats    OBJECT-TYPE
          SYNTAX      INTEGER
          {
              clear-statistics (1)
          }
          ACCESS      write-only
          STATUS      mandatory
          DESCRIPTION
             "Allows the user to zero out all the interface statistics in
              the TO-DTE portion of the ThruputPerIntf statistics table.
              (1) Clear TO-DTE interface statistics command."
          ::= { sfrapPerfThruputCommands 1 }
          
   sfrapPerfThruputCmdClearToDceStats    OBJECT-TYPE
          SYNTAX      INTEGER
          {
              clear-statistics (1)
          }
          ACCESS      write-only
          STATUS      mandatory
          DESCRIPTION
             "Allows the user to zero out all the interface statistics in
              the WAN portion of the ThruputPerIntf statistics table.
              (1) Clear WAN interface statistics command."
          ::= { sfrapPerfThruputCommands 2 }
          
   sfrapPerfThruputCmdClearAllIntfStats    OBJECT-TYPE
          SYNTAX      INTEGER
          {
              clear-statistics (1)
          }
          ACCESS      write-only
          STATUS      mandatory
          DESCRIPTION
             "Allows the user to zero out all the statistics in
              the ThruputPerIntf statistics table."
          ::= { sfrapPerfThruputCommands 3 }

   sfrapPerfThruputCmdClearDlciStats    OBJECT-TYPE
          SYNTAX      INTEGER
          {
              clear-statistics (1)
          }
          ACCESS      write-only
          STATUS      mandatory
          DESCRIPTION
             "Allows the user to zero out all the per-DLCI statistics
              in the ThruputPerDlci statistics table and the the short 
              term statistics tables.
              (1) Clear layer 2 per-DLCI statistics command."
          ::= { sfrapPerfThruputCommands 4 }

   sfrapPerfThruputCmdClearAllStats    OBJECT-TYPE
          SYNTAX      INTEGER
          {
              clear-statistics (1)
          }
          ACCESS      write-only
          STATUS      mandatory
          DESCRIPTION
             "Allows the user to zero out all the statistics
              in the ThruputPerIntf and ThruputPerDlci statistics
              tables and in the short term statistics tables.
              (1) Clear all interface and layer 2 per-DLCI statistics."
          ::= { sfrapPerfThruputCommands 5 }

   sfrapPerfThruputCmdRemoveStsDlci    OBJECT-TYPE
          SYNTAX      INTEGER
          ACCESS      write-only
          STATUS      mandatory
          DESCRIPTION
             "Allows the user to remove a Dlci from the short term 
              statistics tables."
          ::= { sfrapPerfThruputCommands 6 }

   sfrapPerfThruputCmdReplaceDlciTable    OBJECT-TYPE
          SYNTAX      SEQUENCE OF SfrapPerfThruputCmdReplaceDlciEntry
          ACCESS      not-accessible
          STATUS      mandatory
          DESCRIPTION
             "Allows the user to replace one DLCI in the short-term
              statistics table with another one."
          ::= { sfrapPerfThruputCommands 7 }

       sfrapPerfThruputCmdReplaceDlciEntry   OBJECT-TYPE
          SYNTAX      SfrapPerfThruputCmdReplaceDlciEntry
          ACCESS      not-accessible
          STATUS      mandatory
          DESCRIPTION
             "Allows the user to replace one DLCI in the short-term
              statistics table with another one."
          INDEX { sfrapPerfThruputCmdReplaceDlciValue }
          ::= { sfrapPerfThruputCmdReplaceDlciTable 1 }

       SfrapPerfThruputCmdReplaceDlciEntry ::=
          SEQUENCE {
             sfrapPerfThruputCmdReplaceDlciValue     INTEGER,
             sfrapPerfThruputCmdReplaceDlciNewValue  INTEGER
          }
            
          sfrapPerfThruputCmdReplaceDlciValue  OBJECT-TYPE
             SYNTAX      INTEGER
             ACCESS      read-only
             STATUS      mandatory
             DESCRIPTION
                "A Dlci that is in the short-term stats table.  Index by
                 this Dlci value to identify the statistics entry to be
                 replaced."
             ::= { sfrapPerfThruputCmdReplaceDlciEntry 1 }

          sfrapPerfThruputCmdReplaceDlciNewValue  OBJECT-TYPE
             SYNTAX      INTEGER
             ACCESS      write-only
             STATUS      mandatory
             DESCRIPTION
                "A Dlci that is to replace another in the short-term stats 
                 table.  Index by this Dlci value to identify the statistics 
                 entry to do the replacing."
             ::= { sfrapPerfThruputCmdReplaceDlciEntry 2 }

   sfrapPerfThruputCmdAvailabilityStsDlciReset    OBJECT-TYPE
          SYNTAX      INTEGER
          ACCESS      write-only
          STATUS      mandatory
          DESCRIPTION
             "Allows the user to reset the availability
              statistics of an individual Dlci within
              the short-term stats table."
          ::= { sfrapPerfThruputCommands 8 }

   sfrapPerfThruputCmdAvailabilityStsDlciResetAll    OBJECT-TYPE
          SYNTAX      INTEGER
          ACCESS      write-only
          STATUS      mandatory
          DESCRIPTION
             "Allows the user to reset the availability
              statistics of all Dlci's within the short-term
              stats table."
          ::= { sfrapPerfThruputCommands 9 }

   sfrapPerfThruputCmdCountsStsDlciReset    OBJECT-TYPE
          SYNTAX      INTEGER
          ACCESS      write-only
          STATUS      mandatory
          DESCRIPTION
             "Allows the user to reset the count 
              statistics of an individual Dlci within
              the short-term stats table."
          ::= { sfrapPerfThruputCommands 10 }

   sfrapPerfThruputCmdCountsStsDlciResetAll    OBJECT-TYPE
          SYNTAX      INTEGER
          ACCESS      write-only
          STATUS      mandatory
          DESCRIPTION
             "Allows the user to reset the count
              statistics of all Dlci's within the short-term
              stats table."
          ::= { sfrapPerfThruputCommands 11 }

   sfrapPerfThruputCmdAllStsDlciReset    OBJECT-TYPE
          SYNTAX      INTEGER
          ACCESS      write-only
          STATUS      mandatory
          DESCRIPTION
             "Allows the user to reset both the count 
              and availability statistics of an individual Dlci within
              the short-term stats table."
          ::= { sfrapPerfThruputCommands 12 }

   sfrapPerfThruputCmdAllStsDlciResetAll    OBJECT-TYPE
          SYNTAX      INTEGER
          ACCESS      write-only
          STATUS      mandatory
          DESCRIPTION
             "Allows the user to reset both the count and the
              availability statistics of all Dlci's within the short-term
              stats table."
          ::= { sfrapPerfThruputCommands 13 }



sfrapPerfNetworkShortTerm OBJECT IDENTIFIER ::= { sfrapPerformance 4 }

   --  Network Layer Short Term Statistics for each DLCI.

   sfrapPerfNetwProtoPerDlciTable OBJECT-TYPE
         SYNTAX   SEQUENCE OF SfrapPerfNetwProtoPerDlciEntry
         ACCESS   not-accessible
         STATUS   mandatory
         DESCRIPTION
            "The Short Term Statistics on the Network Layer
             protocol for each DLCI. These are protocol-based
             per-DLCI statistics. The Short Term model maintains
             three intervals: current, previous, and cumulative
             totals. Interval duration is defined by the Short Term
             Timer (CfgFrPerfTimersSTInterval)."
         ::= { sfrapPerfNetworkShortTerm 1 }

         sfrapPerfNetwProtoPerDlciEntry OBJECT-TYPE
             SYNTAX   SfrapPerfNetwProtoPerDlciEntry
             ACCESS   not-accessible
             STATUS   mandatory
             DESCRIPTION
                "The Network Layer Short Term Statistics
                 for a particular DLCI. This table organizes
                 statistics by high-layer network protocol."
            INDEX { sfrapPerfNetwProtoPerDlciInterval,
                    sfrapPerfNetwProtoPerDlciValue }
            ::= { sfrapPerfNetwProtoPerDlciTable 1 }

         SfrapPerfNetwProtoPerDlciEntry ::=
             SEQUENCE {
                 sfrapPerfNetwProtoPerDlciInterval  INTEGER,
                 sfrapPerfNetwProtoPerDlciValue     INTEGER,
                 sfrapPerfNetwProtoPerDlciRxTotal   Counter,
                 sfrapPerfNetwProtoPerDlciTxTotal   Counter,
                 sfrapPerfNetwProtoPerDlciRxIp      Counter,
                 sfrapPerfNetwProtoPerDlciTxIp      Counter,
                 sfrapPerfNetwProtoPerDlciRxIpx     Counter,
                 sfrapPerfNetwProtoPerDlciTxIpx     Counter,
                 sfrapPerfNetwProtoPerDlciRxSna     Counter,
                 sfrapPerfNetwProtoPerDlciTxSna     Counter,
                 sfrapPerfNetwProtoPerDlciRxArp     Counter,
                 sfrapPerfNetwProtoPerDlciTxArp     Counter,
                 sfrapPerfNetwProtoPerDlciRxCisco   Counter,
                 sfrapPerfNetwProtoPerDlciTxCisco   Counter,
                 sfrapPerfNetwProtoPerDlciRxOther   Counter,
                 sfrapPerfNetwProtoPerDlciTxOther   Counter,
                 sfrapPerfNetwProtoPerDlciRxVnip    Counter,
                 sfrapPerfNetwProtoPerDlciTxVnip    Counter,
                 sfrapPerfNetwProtoPerDlciRxAnnexG  Counter,
                 sfrapPerfNetwProtoPerDlciTxAnnexG  Counter
               }

      sfrapPerfNetwProtoPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfNetwProtoPerDlciEntry 1 }

      sfrapPerfNetwProtoPerDlciValue    OBJECT-TYPE
             SYNTAX      INTEGER 
             ACCESS      read-only
             STATUS      mandatory
             DESCRIPTION
                "The DLCI value with which the Statistics are associated."
            ::= { sfrapPerfNetwProtoPerDlciEntry 2 }

      sfrapPerfNetwProtoPerDlciRxTotal    OBJECT-TYPE
             SYNTAX      Counter 
             ACCESS      read-only
             STATUS      mandatory
             DESCRIPTION
                "The total number of received Network Layer bytes
                 that have been counted on this DLCI."
            ::= { sfrapPerfNetwProtoPerDlciEntry 3 }

      sfrapPerfNetwProtoPerDlciTxTotal    OBJECT-TYPE
             SYNTAX      Counter
             ACCESS      read-only
             STATUS      mandatory
             DESCRIPTION
                "The total number of transmitted Network Layer bytes
                 that have been counted on this DLCI."
            ::= { sfrapPerfNetwProtoPerDlciEntry 4 }

      sfrapPerfNetwProtoPerDlciRxIp    OBJECT-TYPE
             SYNTAX      Counter
             ACCESS      read-only
             STATUS      mandatory
             DESCRIPTION
                "The number of received IP bytes
                 that have been counted on this DLCI."
            ::= { sfrapPerfNetwProtoPerDlciEntry 5 }

      sfrapPerfNetwProtoPerDlciTxIp    OBJECT-TYPE
             SYNTAX      Counter
             ACCESS      read-only
             STATUS      mandatory
             DESCRIPTION
                "The number of transmitted IP bytes
                 that have been counted on this DLCI."
            ::= { sfrapPerfNetwProtoPerDlciEntry 6 }

      sfrapPerfNetwProtoPerDlciRxIpx    OBJECT-TYPE
             SYNTAX      Counter
             ACCESS      read-only
             STATUS      mandatory
             DESCRIPTION
                "The number of received IPX bytes
                 that have been counted on this DLCI."
            ::= { sfrapPerfNetwProtoPerDlciEntry 7 }

      sfrapPerfNetwProtoPerDlciTxIpx    OBJECT-TYPE
             SYNTAX      Counter
             ACCESS      read-only
             STATUS      mandatory
             DESCRIPTION
                "The number of transmitted IPX bytes
                 that have been counted on this DLCI."
            ::= { sfrapPerfNetwProtoPerDlciEntry 8 }

      sfrapPerfNetwProtoPerDlciRxSna    OBJECT-TYPE
             SYNTAX      Counter
             ACCESS      read-only
             STATUS      mandatory
             DESCRIPTION
                "The number of received SNA bytes
                 that have been counted on this DLCI."
            ::= { sfrapPerfNetwProtoPerDlciEntry 9 }

      sfrapPerfNetwProtoPerDlciTxSna    OBJECT-TYPE
             SYNTAX      Counter
             ACCESS      read-only
             STATUS      mandatory
             DESCRIPTION
                "The number of transmitted SNA bytes
                 that have been counted on this DLCI."
            ::= { sfrapPerfNetwProtoPerDlciEntry 10 }

      sfrapPerfNetwProtoPerDlciRxArp    OBJECT-TYPE
             SYNTAX      Counter
             ACCESS      read-only
             STATUS      mandatory
             DESCRIPTION
                "The number of received ARP bytes
                 that have been counted on this DLCI."
            ::= { sfrapPerfNetwProtoPerDlciEntry 11 }

      sfrapPerfNetwProtoPerDlciTxArp    OBJECT-TYPE
             SYNTAX      Counter
             ACCESS      read-only
             STATUS      mandatory
             DESCRIPTION
                "The number of transmitted ARP bytes
                 that have been counted on this DLCI."
            ::= { sfrapPerfNetwProtoPerDlciEntry 12 }

      sfrapPerfNetwProtoPerDlciRxCisco    OBJECT-TYPE
             SYNTAX      Counter
             ACCESS      read-only
             STATUS      mandatory
             DESCRIPTION
                "The number of received Cisco protocol bytes
                 that have been counted on this DLCI."
            ::= { sfrapPerfNetwProtoPerDlciEntry 13 }

      sfrapPerfNetwProtoPerDlciTxCisco    OBJECT-TYPE
             SYNTAX      Counter
             ACCESS      read-only
             STATUS      mandatory
             DESCRIPTION
                "The number of transmitted Cisco protocol bytes
                 that have been counted on this DLCI."
            ::= { sfrapPerfNetwProtoPerDlciEntry 14 }

      sfrapPerfNetwProtoPerDlciRxOther    OBJECT-TYPE
             SYNTAX      Counter
             ACCESS      read-only
             STATUS      mandatory
             DESCRIPTION
                "The number of received bytes on this DLCI
                 from protocols that are not counted elsewhere
                 in this table."
            ::= { sfrapPerfNetwProtoPerDlciEntry 15 }

      sfrapPerfNetwProtoPerDlciTxOther    OBJECT-TYPE
             SYNTAX      Counter
             ACCESS      read-only
             STATUS      mandatory
             DESCRIPTION
                "The number of transmitted bytes on this DLCI
                 from protocols that are not counted elsewhere
                 in this table."
            ::= { sfrapPerfNetwProtoPerDlciEntry 16 }

      sfrapPerfNetwProtoPerDlciRxVnip    OBJECT-TYPE
             SYNTAX      Counter 
             ACCESS      read-only
             STATUS      mandatory
             DESCRIPTION
                "The number of received VNIP protocol bytes
                 that have been counted on this DLCI."
            ::= { sfrapPerfNetwProtoPerDlciEntry 17 }

      sfrapPerfNetwProtoPerDlciTxVnip    OBJECT-TYPE
             SYNTAX      Counter 
             ACCESS      read-only
             STATUS      mandatory
             DESCRIPTION
                "The number of transmitted VNIP protocol bytes
                 that have been counted on this DLCI."
            ::= { sfrapPerfNetwProtoPerDlciEntry 18 }

      sfrapPerfNetwProtoPerDlciRxAnnexG  OBJECT-TYPE
             SYNTAX      Counter 
             ACCESS      read-only
             STATUS      mandatory
             DESCRIPTION
                "The number of received Annex G protocol 
                 bytes that have been counted on this DLCI."
            ::= { sfrapPerfNetwProtoPerDlciEntry 19 }

      sfrapPerfNetwProtoPerDlciTxAnnexG  OBJECT-TYPE
             SYNTAX      Counter 
             ACCESS      read-only
             STATUS      mandatory
             DESCRIPTION
                "The number of transmitted Annex G protocol 
                 bytes that have been counted on this DLCI."
            ::= { sfrapPerfNetwProtoPerDlciEntry 20 }



   --  Network Layer Short Term Statistics totals.

   sfrapPerfNetwProtoTotalTable OBJECT-TYPE
         SYNTAX   SEQUENCE OF SfrapPerfNetwProtoTotalEntry
         ACCESS   not-accessible
         STATUS   mandatory
         DESCRIPTION
            "The Short Term Statistics on Network Layer
            protocols summed across all DLCIs."
         ::= { sfrapPerfNetworkShortTerm 2 }

         sfrapPerfNetwProtoTotalEntry OBJECT-TYPE
             SYNTAX   SfrapPerfNetwProtoTotalEntry
             ACCESS   not-accessible
             STATUS   mandatory
             DESCRIPTION
                "The Network Layer Short Term Statistics
                 for a particular DLCI."
            INDEX { sfrapPerfNetwProtoTotalInterval }
            ::= { sfrapPerfNetwProtoTotalTable 1 }

         SfrapPerfNetwProtoTotalEntry ::=
             SEQUENCE {
                 sfrapPerfNetwProtoTotalInterval  INTEGER,
                 sfrapPerfNetwProtoTotalRxTotal   Counter,
                 sfrapPerfNetwProtoTotalTxTotal   Counter,
                 sfrapPerfNetwProtoTotalRxIp      Counter,
                 sfrapPerfNetwProtoTotalTxIp      Counter,
                 sfrapPerfNetwProtoTotalRxIpx     Counter,
                 sfrapPerfNetwProtoTotalTxIpx     Counter,
                 sfrapPerfNetwProtoTotalRxSna     Counter,
                 sfrapPerfNetwProtoTotalTxSna     Counter,
                 sfrapPerfNetwProtoTotalRxArp     Counter,
                 sfrapPerfNetwProtoTotalTxArp     Counter,
                 sfrapPerfNetwProtoTotalRxCisco   Counter,
                 sfrapPerfNetwProtoTotalTxCisco   Counter,
                 sfrapPerfNetwProtoTotalRxOther   Counter,
                 sfrapPerfNetwProtoTotalTxOther   Counter,
                 sfrapPerfNetwProtoTotalRxVnip    Counter,
                 sfrapPerfNetwProtoTotalTxVnip    Counter,
                 sfrapPerfNetwProtoTotalRxAnnexG  Counter,
                 sfrapPerfNetwProtoTotalTxAnnexG  Counter
               }

      sfrapPerfNetwProtoTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfNetwProtoTotalEntry 1 }

      sfrapPerfNetwProtoTotalRxTotal    OBJECT-TYPE
             SYNTAX      Counter 
             ACCESS      read-only
             STATUS      mandatory
             DESCRIPTION
                "The total number of received Network Layer bytes
                 that have been counted across all DLCIs."
            ::= { sfrapPerfNetwProtoTotalEntry 3 }

      sfrapPerfNetwProtoTotalTxTotal    OBJECT-TYPE
             SYNTAX      Counter 
             ACCESS      read-only
             STATUS      mandatory
             DESCRIPTION
                "The total number of transmitted Network Layer bytes
                 that have been counted across all DLCIs."
            ::= { sfrapPerfNetwProtoTotalEntry 4 }

      sfrapPerfNetwProtoTotalRxIp    OBJECT-TYPE
             SYNTAX      Counter 
             ACCESS      read-only
             STATUS      mandatory
             DESCRIPTION
                "The number of received IP bytes
                 that have been counted across all DLCIs."
            ::= { sfrapPerfNetwProtoTotalEntry 5 }

      sfrapPerfNetwProtoTotalTxIp    OBJECT-TYPE
             SYNTAX      Counter
             ACCESS      read-only
             STATUS      mandatory
             DESCRIPTION
                "The number of transmitted IP bytes
                 that have been counted across all DLCIs."
            ::= { sfrapPerfNetwProtoTotalEntry 6 }

      sfrapPerfNetwProtoTotalRxIpx    OBJECT-TYPE
             SYNTAX      Counter
             ACCESS      read-only
             STATUS      mandatory
             DESCRIPTION
                "The number of received IPX bytes
                 that have been counted across all DLCIs."
            ::= { sfrapPerfNetwProtoTotalEntry 7 }

      sfrapPerfNetwProtoTotalTxIpx    OBJECT-TYPE
             SYNTAX      Counter
             ACCESS      read-only
             STATUS      mandatory
             DESCRIPTION
                "The number of transmitted IPX bytes
                 that have been counted across all DLCIs."
            ::= { sfrapPerfNetwProtoTotalEntry 8 }

      sfrapPerfNetwProtoTotalRxSna    OBJECT-TYPE
             SYNTAX      Counter
             ACCESS      read-only
             STATUS      mandatory
             DESCRIPTION
                "The number of received SNA bytes
                 that have been counted across all DLCIs."
            ::= { sfrapPerfNetwProtoTotalEntry 9 }

      sfrapPerfNetwProtoTotalTxSna    OBJECT-TYPE
             SYNTAX      Counter
             ACCESS      read-only
             STATUS      mandatory
             DESCRIPTION
                "The number of transmitted SNA bytes
                 that have been counted across all DLCIs."
            ::= { sfrapPerfNetwProtoTotalEntry 10 }

      sfrapPerfNetwProtoTotalRxArp    OBJECT-TYPE
             SYNTAX      Counter
             ACCESS      read-only
             STATUS      mandatory
             DESCRIPTION
                "The number of received ARP bytes
                 that have been counted across all DLCIs."
            ::= { sfrapPerfNetwProtoTotalEntry 11 }

      sfrapPerfNetwProtoTotalTxArp    OBJECT-TYPE
             SYNTAX      Counter
             ACCESS      read-only
             STATUS      mandatory
             DESCRIPTION
                "The number of transmitted ARP bytes
                 that have been counted across all DLCIs."
            ::= { sfrapPerfNetwProtoTotalEntry 12 }

      sfrapPerfNetwProtoTotalRxCisco    OBJECT-TYPE
             SYNTAX      Counter
             ACCESS      read-only
             STATUS      mandatory
             DESCRIPTION
                "The number of received Cisco protocol bytes
                 that have been counted across all DLCIs."
            ::= { sfrapPerfNetwProtoTotalEntry 13 }

      sfrapPerfNetwProtoTotalTxCisco    OBJECT-TYPE
             SYNTAX      Counter
             ACCESS      read-only
             STATUS      mandatory
             DESCRIPTION
                "The number of transmitted Cisco protocol bytes
                 that have been counted across all DLCIs."
            ::= { sfrapPerfNetwProtoTotalEntry 14 }

      sfrapPerfNetwProtoTotalRxOther    OBJECT-TYPE
             SYNTAX      Counter
             ACCESS      read-only
             STATUS      mandatory
             DESCRIPTION
                "The number of received bytes across all DLCIs
                 from protocols that are not counted elsewhere
                 in this table."
            ::= { sfrapPerfNetwProtoTotalEntry 15 }

      sfrapPerfNetwProtoTotalTxOther   OBJECT-TYPE
             SYNTAX      Counter
             ACCESS      read-only
             STATUS      mandatory
             DESCRIPTION
                "The number of transmitted bytes across all DLCIs
                 from protocols that are not counted elsewhere
                 in this table."
            ::= { sfrapPerfNetwProtoTotalEntry 16 }

      sfrapPerfNetwProtoTotalRxVnip    OBJECT-TYPE
             SYNTAX      Counter 
             ACCESS      read-only
             STATUS      mandatory
             DESCRIPTION
                "The number of received VNIP protocol bytes
                 that have been counted across all DLCIs."
            ::= { sfrapPerfNetwProtoTotalEntry 17 }

      sfrapPerfNetwProtoTotalTxVnip    OBJECT-TYPE
             SYNTAX      Counter 
             ACCESS      read-only
             STATUS      mandatory
             DESCRIPTION
                "The number of transmitted VNIP protocol bytes
                 that have been counted across all DLCIs."
            ::= { sfrapPerfNetwProtoTotalEntry 18 }

      sfrapPerfNetwProtoTotalRxAnnexG  OBJECT-TYPE
             SYNTAX      Counter 
             ACCESS      read-only
             STATUS      mandatory
             DESCRIPTION
                "The number of received Annex G protocol bytes
                 that have been counted across all DLCIs."
            ::= { sfrapPerfNetwProtoTotalEntry 19 }

      sfrapPerfNetwProtoTotalTxAnnexG  OBJECT-TYPE
             SYNTAX      Counter 
             ACCESS      read-only
             STATUS      mandatory
             DESCRIPTION
                "The number of transmitted Annex G protocol bytes
                 that have been counted across all DLCIs."
            ::= { sfrapPerfNetwProtoTotalEntry 20 }


   --  IP Short Term Statistics for each DLCI.

   sfrapPerfIpPerDlciTable OBJECT-TYPE
         SYNTAX   SEQUENCE OF SfrapPerfIpPerDlciEntry
         ACCESS   not-accessible
         STATUS   mandatory
         DESCRIPTION
            "The Short Term Statistics on the IP
            protocol for each DLCI."
         ::= { sfrapPerfNetworkShortTerm 3 }

         sfrapPerfIpPerDlciEntry OBJECT-TYPE
             SYNTAX   SfrapPerfIpPerDlciEntry
             ACCESS   not-accessible
             STATUS   mandatory
             DESCRIPTION
                "The IP Short Term Statistics for a particular DLCI."
            INDEX { sfrapPerfIpPerDlciInterval, sfrapPerfIpPerDlciValue }
            ::= { sfrapPerfIpPerDlciTable 1 }

         SfrapPerfIpPerDlciEntry ::=
             SEQUENCE {
                 sfrapPerfIpPerDlciInterval  INTEGER,
                 sfrapPerfIpPerDlciValue     INTEGER,
                 sfrapPerfIpPerDlciRxTotal   Counter,
                 sfrapPerfIpPerDlciTxTotal   Counter,
                 sfrapPerfIpPerDlciRxTcp     Counter,
                 sfrapPerfIpPerDlciTxTcp     Counter,
                 sfrapPerfIpPerDlciRxUdp     Counter,
                 sfrapPerfIpPerDlciTxUdp     Counter,
                 sfrapPerfIpPerDlciRxIcmp    Counter,
                 sfrapPerfIpPerDlciTxIcmp    Counter,
                 sfrapPerfIpPerDlciRxOther   Counter,
                 sfrapPerfIpPerDlciTxOther   Counter,
                 sfrapPerfIpPerDlciRxIgrp    Counter,
                 sfrapPerfIpPerDlciTxIgrp    Counter
               }

      sfrapPerfIpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfIpPerDlciEntry 1 }

      sfrapPerfIpPerDlciValue    OBJECT-TYPE
             SYNTAX      INTEGER 
             ACCESS      read-only
             STATUS      mandatory
             DESCRIPTION
                "The DLCI value with which the Statistics are associated."
            ::= { sfrapPerfIpPerDlciEntry 2 }

      sfrapPerfIpPerDlciRxTotal    OBJECT-TYPE
             SYNTAX      Counter 
             ACCESS      read-only
             STATUS      mandatory
             DESCRIPTION
                "The total number of received IP bytes
                 that have been counted on this DLCI."
            ::= { sfrapPerfIpPerDlciEntry 3 }

      sfrapPerfIpPerDlciTxTotal    OBJECT-TYPE
             SYNTAX      Counter
             ACCESS      read-only
             STATUS      mandatory
             DESCRIPTION
                "The total number of transmitted IP bytes
                 that have been counted on this DLCI."
            ::= { sfrapPerfIpPerDlciEntry 4 }

      sfrapPerfIpPerDlciRxTcp    OBJECT-TYPE
             SYNTAX      Counter
             ACCESS      read-only
             STATUS      mandatory
             DESCRIPTION
                "The number of received TCP over IP bytes
                 that have been counted on this DLCI."
            ::= { sfrapPerfIpPerDlciEntry 5 }

      sfrapPerfIpPerDlciTxTcp    OBJECT-TYPE
             SYNTAX      Counter
             ACCESS      read-only
             STATUS      mandatory
             DESCRIPTION
                "The number of transmitted TCP over IP bytes
                 that have been counted on this DLCI."
            ::= { sfrapPerfIpPerDlciEntry 6 }

      sfrapPerfIpPerDlciRxUdp    OBJECT-TYPE
             SYNTAX      Counter
             ACCESS      read-only
             STATUS      mandatory
             DESCRIPTION
                "The number of received UDP over IP bytes
                 that have been counted on this DLCI."
            ::= { sfrapPerfIpPerDlciEntry 7 }

      sfrapPerfIpPerDlciTxUdp    OBJECT-TYPE
             SYNTAX      Counter
             ACCESS      read-only
             STATUS      mandatory
             DESCRIPTION
                "The number of transmitted UDP over IP bytes
                 that have been counted on this DLCI."
            ::= { sfrapPerfIpPerDlciEntry 8 }

      sfrapPerfIpPerDlciRxIcmp    OBJECT-TYPE
             SYNTAX      Counter
             ACCESS      read-only
             STATUS      mandatory
             DESCRIPTION
                "The number of received ICMP over IP bytes
                 that have been counted on this DLCI."
            ::= { sfrapPerfIpPerDlciEntry 9 }

      sfrapPerfIpPerDlciTxIcmp    OBJECT-TYPE
             SYNTAX      Counter
             ACCESS      read-only
             STATUS      mandatory
             DESCRIPTION
                "The number of transmitted ICMP over IP bytes
                 that have been counted on this DLCI."
            ::= { sfrapPerfIpPerDlciEntry 10 }

      sfrapPerfIpPerDlciRxOther    OBJECT-TYPE
             SYNTAX      Counter
             ACCESS      read-only
             STATUS      mandatory
             DESCRIPTION
                "The number of received bytes on this DLCI
                 from protocols over IP that are not counted
                 elsewhere in this table."
            ::= { sfrapPerfIpPerDlciEntry 11 }

      sfrapPerfIpPerDlciTxOther    OBJECT-TYPE
             SYNTAX      Counter
             ACCESS      read-only
             STATUS      mandatory
             DESCRIPTION
                "The number of transmitted bytes on this DLCI
                 from protocols over IP that are not counted
                 elsewhere in this table."
            ::= { sfrapPerfIpPerDlciEntry 12 }

      sfrapPerfIpPerDlciRxIgrp    OBJECT-TYPE
             SYNTAX      Counter 
             ACCESS      read-only
             STATUS      mandatory
             DESCRIPTION
                "The number of received IGRP over IP bytes
                 that have been counted on this DLCI."
            ::= { sfrapPerfIpPerDlciEntry 13 }

      sfrapPerfIpPerDlciTxIgrp    OBJECT-TYPE
             SYNTAX      Counter 
             ACCESS      read-only
             STATUS      mandatory
             DESCRIPTION
                "The number of transmitted IGRP over IP bytes
                 that have been counted on this DLCI."
            ::= { sfrapPerfIpPerDlciEntry 14 }


   --  IP Short Term Statistics totals.

   sfrapPerfIpTotalTable OBJECT-TYPE
         SYNTAX   SEQUENCE OF SfrapPerfIpTotalEntry
         ACCESS   not-accessible
         STATUS   mandatory
         DESCRIPTION
            "The Short Term Statistics on the IP
            protocol across all DLCIs."
         ::= { sfrapPerfNetworkShortTerm 4 }

         sfrapPerfIpTotalEntry OBJECT-TYPE
             SYNTAX   SfrapPerfIpTotalEntry
             ACCESS   not-accessible
             STATUS   mandatory
             DESCRIPTION
                "The IP Short Term Statistics across all DLCIs."
            INDEX { sfrapPerfIpTotalInterval }
            ::= { sfrapPerfIpTotalTable 1 }

         SfrapPerfIpTotalEntry ::=
             SEQUENCE {
                 sfrapPerfIpTotalInterval INTEGER,
                 sfrapPerfIpTotalRxTotal  Counter,
                 sfrapPerfIpTotalTxTotal  Counter,
                 sfrapPerfIpTotalRxTcp    Counter,
                 sfrapPerfIpTotalTxTcp    Counter,
                 sfrapPerfIpTotalRxUdp    Counter,
                 sfrapPerfIpTotalTxUdp    Counter,
                 sfrapPerfIpTotalRxIcmp   Counter,
                 sfrapPerfIpTotalTxIcmp   Counter,
                 sfrapPerfIpTotalRxOther  Counter,
                 sfrapPerfIpTotalTxOther  Counter,
                 sfrapPerfIpTotalRxIgrp   Counter,
                 sfrapPerfIpTotalTxIgrp   Counter
               }

      sfrapPerfIpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfIpTotalEntry 1 }

      sfrapPerfIpTotalRxTotal    OBJECT-TYPE
             SYNTAX      Counter
             ACCESS      read-only
             STATUS      mandatory
             DESCRIPTION
                "The total number of received IP bytes
                 that have been counted across all DLCIs."
            ::= { sfrapPerfIpTotalEntry 3 }

      sfrapPerfIpTotalTxTotal    OBJECT-TYPE
             SYNTAX      Counter
             ACCESS      read-only
             STATUS      mandatory
             DESCRIPTION
                "The total number of transmitted IP bytes
                 that have been counted across all DLCIs."
            ::= { sfrapPerfIpTotalEntry 4 }

      sfrapPerfIpTotalRxTcp    OBJECT-TYPE
             SYNTAX      Counter
             ACCESS      read-only
             STATUS      mandatory
             DESCRIPTION
                "The number of received TCP over IP bytes
                 that have been counted across all DLCIs."
            ::= { sfrapPerfIpTotalEntry 5 }

      sfrapPerfIpTotalTxTcp    OBJECT-TYPE
             SYNTAX      Counter
             ACCESS      read-only
             STATUS      mandatory
             DESCRIPTION
                "The number of transmitted TCP over IP bytes
                 that have been counted across all DLCIs."
            ::= { sfrapPerfIpTotalEntry 6 }

      sfrapPerfIpTotalRxUdp    OBJECT-TYPE
             SYNTAX      Counter
             ACCESS      read-only
             STATUS      mandatory
             DESCRIPTION
                "The number of received UDP over IP bytes
                 that have been counted across all DLCIs."
            ::= { sfrapPerfIpTotalEntry 7 }

      sfrapPerfIpTotalTxUdp    OBJECT-TYPE
             SYNTAX      Counter
             ACCESS      read-only
             STATUS      mandatory
             DESCRIPTION
                "The number of transmitted UDP over IP bytes
                 that have been counted across all DLCIs."
            ::= { sfrapPerfIpTotalEntry 8 }

      sfrapPerfIpTotalRxIcmp    OBJECT-TYPE
             SYNTAX      Counter
             ACCESS      read-only
             STATUS      mandatory
             DESCRIPTION
                "The number of received ICMP over IP bytes
                 that have been counted  across all DLCIs."
            ::= { sfrapPerfIpTotalEntry 9 }

      sfrapPerfIpTotalTxIcmp    OBJECT-TYPE
             SYNTAX      Counter
             ACCESS      read-only
             STATUS      mandatory
             DESCRIPTION
                "The number of transmitted ICMP over IP bytes
                 that have been counted across all DLCIs."
            ::= { sfrapPerfIpTotalEntry 10 }

      sfrapPerfIpTotalRxOther    OBJECT-TYPE
             SYNTAX      Counter
             ACCESS      read-only
             STATUS      mandatory
             DESCRIPTION
                "The number of received bytes across all DLCIs
                 from protocols over IP that are not counted
                 elsewhere in this table."
            ::= { sfrapPerfIpTotalEntry 11 }

      sfrapPerfIpTotalTxOther    OBJECT-TYPE
             SYNTAX      Counter
             ACCESS      read-only
             STATUS      mandatory
             DESCRIPTION
                "The number of transmitted bytes across all DLCIs.
                 from protocols over IP that are not counted
                 elsewhere in this table."
            ::= { sfrapPerfIpTotalEntry 12 }

      sfrapPerfIpTotalRxIgrp    OBJECT-TYPE
             SYNTAX      Counter 
             ACCESS      read-only
             STATUS      mandatory
             DESCRIPTION
                "The number of received IGRP over IP bytes
                 that have been counted across all DLCIs."
            ::= { sfrapPerfIpTotalEntry 13 }

      sfrapPerfIpTotalTxIgrp    OBJECT-TYPE
             SYNTAX      Counter 
             ACCESS      read-only
             STATUS      mandatory
             DESCRIPTION
                "The number of transmitted IGRP over IP bytes
                 that have been counted across all DLCIs."
            ::= { sfrapPerfIpTotalEntry 14 }


   --  ICMP Short Term Statistics for each DLCI.

   sfrapPerfIcmpPerDlciTable OBJECT-TYPE
         SYNTAX   SEQUENCE OF SfrapPerfIcmpPerDlciEntry
         ACCESS   not-accessible
         STATUS   mandatory
         DESCRIPTION
            "Short Term Statistics on the ICMP
             protocol for each DLCI."
         ::= { sfrapPerfNetworkShortTerm 5 }

         sfrapPerfIcmpPerDlciEntry OBJECT-TYPE
             SYNTAX   SfrapPerfIcmpPerDlciEntry
             ACCESS   not-accessible
             STATUS   mandatory
             DESCRIPTION
                "The ICMP Short Term Statistics for a particular DLCI."
            INDEX { sfrapPerfIcmpPerDlciInterval, sfrapPerfIcmpPerDlciValue }
            ::= { sfrapPerfIcmpPerDlciTable 1 }

         SfrapPerfIcmpPerDlciEntry ::=
             SEQUENCE {
                 sfrapPerfIcmpPerDlciInterval        INTEGER,
                 sfrapPerfIcmpPerDlciValue           INTEGER,
                 sfrapPerfIcmpPerDlciRxTotal         Counter,
                 sfrapPerfIcmpPerDlciTxTotal         Counter,
                 sfrapPerfIcmpPerDlciRxEchoRep       Counter,
                 sfrapPerfIcmpPerDlciTxEchoRep       Counter,
                 sfrapPerfIcmpPerDlciRxDestUnr       Counter,
                 sfrapPerfIcmpPerDlciTxDestUnr       Counter,
                 sfrapPerfIcmpPerDlciRxSrcQuench     Counter,
                 sfrapPerfIcmpPerDlciTxSrcQuench     Counter,
                 sfrapPerfIcmpPerDlciRxRedirect      Counter,
                 sfrapPerfIcmpPerDlciTxRedirect      Counter,
                 sfrapPerfIcmpPerDlciRxEchoReq       Counter,
                 sfrapPerfIcmpPerDlciTxEchoReq       Counter,
                 sfrapPerfIcmpPerDlciRxTimeExcd      Counter,
                 sfrapPerfIcmpPerDlciTxTimeExcd      Counter,
                 sfrapPerfIcmpPerDlciRxParamProb     Counter,
                 sfrapPerfIcmpPerDlciTxParamProb     Counter,
                 sfrapPerfIcmpPerDlciRxTimestpReq    Counter,
                 sfrapPerfIcmpPerDlciTxTimestpReq    Counter,
                 sfrapPerfIcmpPerDlciRxTimestpRep    Counter,
                 sfrapPerfIcmpPerDlciTxTimestpRep    Counter,
                 sfrapPerfIcmpPerDlciRxAddrMaskReq   Counter,
                 sfrapPerfIcmpPerDlciTxAddrMaskReq   Counter,
                 sfrapPerfIcmpPerDlciRxAddrMaskRep   Counter,
                 sfrapPerfIcmpPerDlciTxAddrMaskRep   Counter,
                 sfrapPerfIcmpPerDlciRxPktTooBig     Counter,
                 sfrapPerfIcmpPerDlciTxPktTooBig     Counter,
                 sfrapPerfIcmpPerDlciRxGmQuery       Counter,
                 sfrapPerfIcmpPerDlciTxGmQuery       Counter,
                 sfrapPerfIcmpPerDlciRxGmReport      Counter,
                 sfrapPerfIcmpPerDlciTxGmReport      Counter,
                 sfrapPerfIcmpPerDlciRxGmReduct      Counter,
                 sfrapPerfIcmpPerDlciTxGmReduct      Counter
            }

      sfrapPerfIcmpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfIcmpPerDlciEntry 1 }

      sfrapPerfIcmpPerDlciValue    OBJECT-TYPE
             SYNTAX      INTEGER 
            ACCESS      read-only
             STATUS      mandatory
             DESCRIPTION
                "The DLCI value in which the Statistics are associated."
            ::= { sfrapPerfIcmpPerDlciEntry 2 }

      sfrapPerfIcmpPerDlciRxTotal    OBJECT-TYPE
             SYNTAX      Counter
             ACCESS      read-only
             STATUS      mandatory
             DESCRIPTION
                "The total number of ICMP bytes that have been
                 counted on this DLCI."
            ::= { sfrapPerfIcmpPerDlciEntry 3 }

      sfrapPerfIcmpPerDlciTxTotal    OBJECT-TYPE
             SYNTAX      Counter
             ACCESS      read-only
               STATUS      mandatory
             DESCRIPTION
                "The total number of ICMP bytes that have been
                 counted on this DLCI."
            ::= { sfrapPerfIcmpPerDlciEntry 4 }

      sfrapPerfIcmpPerDlciRxEchoRep    OBJECT-TYPE
             SYNTAX      Counter
             ACCESS      read-only
             STATUS      mandatory
             DESCRIPTION
                "The number of bytes in ICMP ECHO replies
                 that have been counted on this DLCI."
            ::= { sfrapPerfIcmpPerDlciEntry 5 }

      sfrapPerfIcmpPerDlciTxEchoRep    OBJECT-TYPE
             SYNTAX      Counter
             ACCESS      read-only
               STATUS      mandatory
             DESCRIPTION
                "The number of bytes in ICMP ECHO replies
                 that have been counted on this DLCI."
            ::= { sfrapPerfIcmpPerDlciEntry 6 }

      sfrapPerfIcmpPerDlciRxDestUnr    OBJECT-TYPE
             SYNTAX      Counter
             ACCESS      read-only
             STATUS      mandatory
             DESCRIPTION
                "The number of bytes in ICMP destination unreachables
                 that have been counted on this DLCI."
            ::= { sfrapPerfIcmpPerDlciEntry 7 }

      sfrapPerfIcmpPerDlciTxDestUnr    OBJECT-TYPE
             SYNTAX      Counter
             ACCESS      read-only
               STATUS      mandatory
             DESCRIPTION
                "The number of bytes in ICMP destination unreachables
                 that have been counted on this DLCI."
            ::= { sfrapPerfIcmpPerDlciEntry 8 }

      sfrapPerfIcmpPerDlciRxSrcQuench    OBJECT-TYPE
             SYNTAX      Counter
             ACCESS      read-only
             STATUS      mandatory
             DESCRIPTION
                "The number of bytes in ICMP source quenches
                 that have been counted on this DLCI."
            ::= { sfrapPerfIcmpPerDlciEntry 9 }

      sfrapPerfIcmpPerDlciTxSrcQuench    OBJECT-TYPE
             SYNTAX      Counter
             ACCESS      read-only
             STATUS      mandatory
             DESCRIPTION
                "The number of bytes in ICMP source quenches
                 that have been counted on this DLCI."
            ::= { sfrapPerfIcmpPerDlciEntry 10 }

      sfrapPerfIcmpPerDlciRxRedirect    OBJECT-TYPE
             SYNTAX      Counter
             ACCESS      read-only
             STATUS      mandatory
             DESCRIPTION
                "The number of bytes in ICMP redirects
                 that have been counted on this DLCI."
            ::= { sfrapPerfIcmpPerDlciEntry 11 }

      sfrapPerfIcmpPerDlciTxRedirect    OBJECT-TYPE
             SYNTAX      Counter
             ACCESS      read-only
             STATUS      mandatory
             DESCRIPTION
                "The number of bytes in ICMP redirects
                 that have been counted on this DLCI."
            ::= { sfrapPerfIcmpPerDlciEntry 12 }

      sfrapPerfIcmpPerDlciRxEchoReq    OBJECT-TYPE
             SYNTAX      Counter
             ACCESS      read-only
             STATUS      mandatory
             DESCRIPTION
                "The number of bytes in ICMP ECHO requests
                 that have been counted on this DLCI."
            ::= { sfrapPerfIcmpPerDlciEntry 13 }

      sfrapPerfIcmpPerDlciTxEchoReq    OBJECT-TYPE
             SYNTAX      Counter
             ACCESS      read-only
             STATUS      mandatory
             DESCRIPTION
                "The number of bytes in ICMP ECHO requests
                 that have been counted on this DLCI."
            ::= { sfrapPerfIcmpPerDlciEntry 14 }

      sfrapPerfIcmpPerDlciRxTimeExcd    OBJECT-TYPE
             SYNTAX      Counter
             ACCESS      read-only
             STATUS      mandatory
             DESCRIPTION
                "The number of bytes in ICMP time exceededs
                 that have been counted on this DLCI."
            ::= { sfrapPerfIcmpPerDlciEntry 15 }

      sfrapPerfIcmpPerDlciTxTimeExcd    OBJECT-TYPE
             SYNTAX      Counter
             ACCESS      read-only
             STATUS      mandatory
             DESCRIPTION
                "The number of bytes in ICMP time exceededs
                 that have been counted on this DLCI."
            ::= { sfrapPerfIcmpPerDlciEntry 16 }

      sfrapPerfIcmpPerDlciRxParamProb    OBJECT-TYPE
             SYNTAX      Counter
             ACCESS      read-only
             STATUS      mandatory
             DESCRIPTION
                "The number of bytes in ICMP parameter problems
                 that have been counted on this DLCI."
            ::= { sfrapPerfIcmpPerDlciEntry 17 }

      sfrapPerfIcmpPerDlciTxParamProb    OBJECT-TYPE
             SYNTAX      Counter
             ACCESS      read-only
             STATUS      mandatory
             DESCRIPTION
                "The number of bytes in ICMP parameter problems
                 that have been counted on this DLCI."
            ::= { sfrapPerfIcmpPerDlciEntry 18 }

      sfrapPerfIcmpPerDlciRxTimestpReq    OBJECT-TYPE
             SYNTAX      Counter
             ACCESS      read-only
             STATUS      mandatory
             DESCRIPTION
                "The number of bytes in ICMP timestamp requests
                 that have been counted on this DLCI."
            ::= { sfrapPerfIcmpPerDlciEntry 19 }

      sfrapPerfIcmpPerDlciTxTimestpReq    OBJECT-TYPE
             SYNTAX      Counter
             ACCESS      read-only
             STATUS      mandatory
             DESCRIPTION
                "The number of bytes in ICMP timestamp requests
                 that have been counted on this DLCI."
            ::= { sfrapPerfIcmpPerDlciEntry 20 }

      sfrapPerfIcmpPerDlciRxTimestpRep    OBJECT-TYPE
             SYNTAX      Counter
             ACCESS      read-only
             STATUS      mandatory
             DESCRIPTION
                "The number of bytes in ICMP timestamp replies
                 that have been counted on this DLCI."
            ::= { sfrapPerfIcmpPerDlciEntry 21 }

      sfrapPerfIcmpPerDlciTxTimestpRep    OBJECT-TYPE
             SYNTAX      Counter
             ACCESS      read-only
             STATUS      mandatory
             DESCRIPTION
                "The number of bytes in ICMP timestamp replies
                 that have been counted on this DLCI."
            ::= { sfrapPerfIcmpPerDlciEntry 22 }

      sfrapPerfIcmpPerDlciRxAddrMaskReq    OBJECT-TYPE
             SYNTAX      Counter
             ACCESS      read-only
             STATUS      mandatory
             DESCRIPTION
                "The number of bytes in ICMP address mask requests
                 that have been counted on this DLCI."
            ::= { sfrapPerfIcmpPerDlciEntry 23 }

      sfrapPerfIcmpPerDlciTxAddrMaskReq    OBJECT-TYPE
             SYNTAX      Counter
             ACCESS      read-only
             STATUS      mandatory
             DESCRIPTION
                "The number of bytes in ICMP address mask requests
                 that have been counted on this DLCI."
            ::= { sfrapPerfIcmpPerDlciEntry 24 }

      sfrapPerfIcmpPerDlciRxAddrMaskRep    OBJECT-TYPE
             SYNTAX      Counter
             ACCESS      read-only
             STATUS      mandatory
             DESCRIPTION
                "The number of bytes in ICMP address mask replies
                 that have been counted on this DLCI."
            ::= { sfrapPerfIcmpPerDlciEntry 25 }

      sfrapPerfIcmpPerDlciTxAddrMaskRep    OBJECT-TYPE
             SYNTAX      Counter
             ACCESS      read-only
             STATUS      mandatory
             DESCRIPTION
                "The number of bytes in ICMP address mask replies
                 that have been counted on this DLCI."
            ::= { sfrapPerfIcmpPerDlciEntry 26 }

      sfrapPerfIcmpPerDlciRxPktTooBig    OBJECT-TYPE
             SYNTAX      Counter
             ACCESS      read-only
             STATUS      mandatory
             DESCRIPTION
                "The number of bytes in ICMP packet too bigs
                 that have been counted on this DLCI."
            ::= { sfrapPerfIcmpPerDlciEntry 27 }

      sfrapPerfIcmpPerDlciTxPktTooBig    OBJECT-TYPE
             SYNTAX      Counter
             ACCESS      read-only
             STATUS      mandatory
             DESCRIPTION
                "The number of bytes in ICMP packet too bigs
                 that have been counted on this DLCI."
            ::= { sfrapPerfIcmpPerDlciEntry 28 }

      sfrapPerfIcmpPerDlciRxGmQuery    OBJECT-TYPE
             SYNTAX      Counter
             ACCESS      read-only
             STATUS      mandatory
             DESCRIPTION
                "The number of bytes in ICMP group membership
                 queries that have been counted on this DLCI."
            ::= { sfrapPerfIcmpPerDlciEntry 29 }

      sfrapPerfIcmpPerDlciTxGmQuery    OBJECT-TYPE
             SYNTAX      Counter
             ACCESS      read-only
             STATUS      mandatory
             DESCRIPTION
                "The number of bytes in ICMP group membership
                 queries that have been counted on this DLCI."
            ::= { sfrapPerfIcmpPerDlciEntry 30 }

      sfrapPerfIcmpPerDlciRxGmReport    OBJECT-TYPE
             SYNTAX      Counter
             ACCESS      read-only
             STATUS      mandatory
             DESCRIPTION
                "The number of bytes in ICMP group membership
                 reports that have been counted on this DLCI."
            ::= { sfrapPerfIcmpPerDlciEntry 31 }

      sfrapPerfIcmpPerDlciTxGmReport    OBJECT-TYPE
             SYNTAX      Counter
             ACCESS      read-only
             STATUS      mandatory
             DESCRIPTION
                "The number of bytes in ICMP group membership
                 reports that have been counted on this DLCI."
            ::= { sfrapPerfIcmpPerDlciEntry 32 }

      sfrapPerfIcmpPerDlciRxGmReduct    OBJECT-TYPE
             SYNTAX      Counter
             ACCESS      read-only
             STATUS      mandatory
             DESCRIPTION
                "The number of bytes in ICMP group membership
                 reductions that have been counted on this DLCI."
            ::= { sfrapPerfIcmpPerDlciEntry 33 }

      sfrapPerfIcmpPerDlciTxGmReduct    OBJECT-TYPE
             SYNTAX      Counter
             ACCESS      read-only
             STATUS      mandatory
             DESCRIPTION
                "The number of bytes in ICMP group membership
                 reductions that have been counted on this DLCI."
            ::= { sfrapPerfIcmpPerDlciEntry 34 }


   --  ICMP Short Term Statistics totals.

   sfrapPerfIcmpTotalTable OBJECT-TYPE
         SYNTAX   SEQUENCE OF SfrapPerfIcmpTotalEntry
         ACCESS   not-accessible
         STATUS   mandatory
         DESCRIPTION
            "Short Term Statistics on the ICMP
             protocol across all DLCIs."
         ::= { sfrapPerfNetworkShortTerm 6 }

         sfrapPerfIcmpTotalEntry OBJECT-TYPE
             SYNTAX   SfrapPerfIcmpTotalEntry
             ACCESS   not-accessible
             STATUS   mandatory
             DESCRIPTION
                "The ICMP Short Term Statistics for a particular DLCI."
            INDEX { sfrapPerfIcmpTotalInterval }
            ::= { sfrapPerfIcmpTotalTable 1 }

         SfrapPerfIcmpTotalEntry ::=
             SEQUENCE {
                 sfrapPerfIcmpTotalInterval        INTEGER,
                 sfrapPerfIcmpTotalRxTotal         Counter,
                 sfrapPerfIcmpTotalTxTotal         Counter,
                 sfrapPerfIcmpTotalRxEchoRep       Counter,
                 sfrapPerfIcmpTotalTxEchoRep       Counter,
                 sfrapPerfIcmpTotalRxDestUnr       Counter,
                 sfrapPerfIcmpTotalTxDestUnr       Counter,
                 sfrapPerfIcmpTotalRxSrcQuench     Counter,
                 sfrapPerfIcmpTotalTxSrcQuench     Counter,
                 sfrapPerfIcmpTotalRxRedirect      Counter,
                 sfrapPerfIcmpTotalTxRedirect      Counter,
                 sfrapPerfIcmpTotalRxEchoReq       Counter,
                 sfrapPerfIcmpTotalTxEchoReq       Counter,
                 sfrapPerfIcmpTotalRxTimeExcd      Counter,
                 sfrapPerfIcmpTotalTxTimeExcd      Counter,
                 sfrapPerfIcmpTotalRxParamProb     Counter,
                 sfrapPerfIcmpTotalTxParamProb     Counter,
                 sfrapPerfIcmpTotalRxTimestpReq    Counter,
                 sfrapPerfIcmpTotalTxTimestpReq    Counter,
                 sfrapPerfIcmpTotalRxTimestpRep    Counter,
                 sfrapPerfIcmpTotalTxTimestpRep    Counter,
                 sfrapPerfIcmpTotalRxAddrMaskReq   Counter,
                 sfrapPerfIcmpTotalTxAddrMaskReq   Counter,
                 sfrapPerfIcmpTotalRxAddrMaskRep   Counter,
                 sfrapPerfIcmpTotalTxAddrMaskRep   Counter,
                 sfrapPerfIcmpTotalRxPktTooBig     Counter,
                 sfrapPerfIcmpTotalTxPktTooBig     Counter,
                 sfrapPerfIcmpTotalRxGmQuery       Counter,
                 sfrapPerfIcmpTotalTxGmQuery       Counter,
                 sfrapPerfIcmpTotalRxGmReport      Counter,
                 sfrapPerfIcmpTotalTxGmReport      Counter,
                 sfrapPerfIcmpTotalRxGmReduct      Counter,
                 sfrapPerfIcmpTotalTxGmReduct      Counter
            }

      sfrapPerfIcmpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfIcmpTotalEntry 1 }

      sfrapPerfIcmpTotalRxTotal    OBJECT-TYPE
             SYNTAX      Counter
             ACCESS      read-only
             STATUS      mandatory
             DESCRIPTION
                "The total number of ICMP bytes that have been
                 counted across all DLCIs."
            ::= { sfrapPerfIcmpTotalEntry 3 }

      sfrapPerfIcmpTotalTxTotal    OBJECT-TYPE
             SYNTAX      Counter
             ACCESS      read-only
               STATUS      mandatory
             DESCRIPTION
                "The total number of ICMP bytes that have been
                 counted across all DLCIs."
            ::= { sfrapPerfIcmpTotalEntry 4 }

      sfrapPerfIcmpTotalRxEchoRep    OBJECT-TYPE
             SYNTAX      Counter
             ACCESS      read-only
             STATUS      mandatory
             DESCRIPTION
                "The number of bytes in ICMP ECHO repies
                 that have been counted across all DLCIs."
            ::= { sfrapPerfIcmpTotalEntry 5 }

      sfrapPerfIcmpTotalTxEchoRep    OBJECT-TYPE
             SYNTAX      Counter
             ACCESS      read-only
               STATUS      mandatory
             DESCRIPTION
                "The number of bytes in ICMP ECHO repies
                 that have been counted across all DLCIs."
            ::= { sfrapPerfIcmpTotalEntry 6 }

      sfrapPerfIcmpTotalRxDestUnr    OBJECT-TYPE
             SYNTAX      Counter
             ACCESS      read-only
             STATUS      mandatory
             DESCRIPTION
                "The number of bytes in ICMP destination unreachables
                 that have been counted across all DLCIs."
            ::= { sfrapPerfIcmpTotalEntry 7 }

      sfrapPerfIcmpTotalTxDestUnr    OBJECT-TYPE
             SYNTAX      Counter
             ACCESS      read-only
               STATUS      mandatory
             DESCRIPTION
                "The number of bytes in ICMP destination unreachables
                 that have been counted across all DLCIs."
            ::= { sfrapPerfIcmpTotalEntry 8 }

      sfrapPerfIcmpTotalRxSrcQuench    OBJECT-TYPE
             SYNTAX      Counter
             ACCESS      read-only
             STATUS      mandatory
             DESCRIPTION
                "The number of bytes in ICMP source quenches
                 that have been counted across all DLCIs."
            ::= { sfrapPerfIcmpTotalEntry 9 }

      sfrapPerfIcmpTotalTxSrcQuench    OBJECT-TYPE
             SYNTAX      Counter
             ACCESS      read-only
             STATUS      mandatory
             DESCRIPTION
                "The number of bytes in ICMP source quenches
                 that have been counte across all DLCIs."
            ::= { sfrapPerfIcmpTotalEntry 10 }

      sfrapPerfIcmpTotalRxRedirect    OBJECT-TYPE
             SYNTAX      Counter
             ACCESS      read-only
             STATUS      mandatory
             DESCRIPTION
                "The number of bytes in ICMP redirects
                 that have been counte across all DLCIs."
            ::= { sfrapPerfIcmpTotalEntry 11 }

      sfrapPerfIcmpTotalTxRedirect    OBJECT-TYPE
             SYNTAX      Counter
             ACCESS      read-only
             STATUS      mandatory
             DESCRIPTION
                "The number of bytes in ICMP redirects
                 that have been counte across all DLCIs."
            ::= { sfrapPerfIcmpTotalEntry 12 }

      sfrapPerfIcmpTotalRxEchoReq    OBJECT-TYPE
             SYNTAX      Counter
             ACCESS      read-only
             STATUS      mandatory
             DESCRIPTION
                "The number of bytes in ICMP ECHO requests
                 that have been counted across all DLCIs."
            ::= { sfrapPerfIcmpTotalEntry 13 }

      sfrapPerfIcmpTotalTxEchoReq    OBJECT-TYPE
             SYNTAX      Counter
             ACCESS      read-only
             STATUS      mandatory
             DESCRIPTION
                "The number of bytes in ICMP ECHO requests
                 that have been counte across all DLCIs."
            ::= { sfrapPerfIcmpTotalEntry 14 }

      sfrapPerfIcmpTotalRxTimeExcd    OBJECT-TYPE
             SYNTAX      Counter
             ACCESS      read-only
             STATUS      mandatory
             DESCRIPTION
                "The number of bytes in ICMP time exceededs
                 that have been counted across all DLCIs."
            ::= { sfrapPerfIcmpTotalEntry 15 }

      sfrapPerfIcmpTotalTxTimeExcd    OBJECT-TYPE
             SYNTAX      Counter
             ACCESS      read-only
             STATUS      mandatory
             DESCRIPTION
                "The number of bytes in ICMP time exceededs
                 that have been counted across all DLCIs."
            ::= { sfrapPerfIcmpTotalEntry 16 }

      sfrapPerfIcmpTotalRxParamProb    OBJECT-TYPE
             SYNTAX      Counter
             ACCESS      read-only
             STATUS      mandatory
             DESCRIPTION
                "The number of bytes in ICMP parameter problems
                 that have been counted across all DLCIs."
            ::= { sfrapPerfIcmpTotalEntry 17 }

      sfrapPerfIcmpTotalTxParamProb    OBJECT-TYPE
             SYNTAX      Counter
             ACCESS      read-only
             STATUS      mandatory
             DESCRIPTION
                "The number of bytes in ICMP parameter problems
                 that have been counted across all DLCIs."
            ::= { sfrapPerfIcmpTotalEntry 18 }

      sfrapPerfIcmpTotalRxTimestpReq    OBJECT-TYPE
             SYNTAX      Counter
             ACCESS      read-only
             STATUS      mandatory
             DESCRIPTION
                "The number of bytes in ICMP timestamp requests
                 that have been counted across all DLCIs."
            ::= { sfrapPerfIcmpTotalEntry 19 }

      sfrapPerfIcmpTotalTxTimestpReq    OBJECT-TYPE
             SYNTAX      Counter
             ACCESS      read-only
             STATUS      mandatory
             DESCRIPTION
                "The number of bytes in ICMP timestamp requests
                 that have been counted across all DLCIs."
            ::= { sfrapPerfIcmpTotalEntry 20 }

      sfrapPerfIcmpTotalRxTimestpRep    OBJECT-TYPE
             SYNTAX      Counter
             ACCESS      read-only
             STATUS      mandatory
             DESCRIPTION
                "The number of bytes in ICMP timestamp replies
                 that have been counted across all DLCIs."
            ::= { sfrapPerfIcmpTotalEntry 21 }

      sfrapPerfIcmpTotalTxTimestpRep    OBJECT-TYPE
             SYNTAX      Counter
             ACCESS      read-only
             STATUS      mandatory
             DESCRIPTION
                "The number of bytes in ICMP timestamp replies
                 that have been counted across all DLCIs."
            ::= { sfrapPerfIcmpTotalEntry 22 }

      sfrapPerfIcmpTotalRxAddrMaskReq    OBJECT-TYPE
             SYNTAX      Counter
             ACCESS      read-only
             STATUS      mandatory
             DESCRIPTION
                "The number of bytes in ICMP address mask requests
                 that have been counted across all DLCIs."
            ::= { sfrapPerfIcmpTotalEntry 23 }

      sfrapPerfIcmpTotalTxAddrMaskReq    OBJECT-TYPE
             SYNTAX      Counter
             ACCESS      read-only
             STATUS      mandatory
             DESCRIPTION
                "The number of bytes in ICMP address mask requests
                 that have been counted across all DLCIs."
            ::= { sfrapPerfIcmpTotalEntry 24 }

      sfrapPerfIcmpTotalRxAddrMaskRep    OBJECT-TYPE
             SYNTAX      Counter
             ACCESS      read-only
             STATUS      mandatory
             DESCRIPTION
                "The number of bytes in ICMP address mask replies
                 that have been counted across all DLCIs."
            ::= { sfrapPerfIcmpTotalEntry 25 }

      sfrapPerfIcmpTotalTxAddrMaskRep    OBJECT-TYPE
             SYNTAX      Counter
             ACCESS      read-only
             STATUS      mandatory
             DESCRIPTION
                "The number of bytes in ICMP address mask replies
                 that have been counted across all DLCIs."
            ::= { sfrapPerfIcmpTotalEntry 26 }

      sfrapPerfIcmpTotalRxPktTooBig    OBJECT-TYPE
             SYNTAX      Counter
             ACCESS      read-only
             STATUS      mandatory
             DESCRIPTION
                "The number of bytes in ICMP packet too bigs
                 that have been counted across all DLCIs."
            ::= { sfrapPerfIcmpTotalEntry 27 }

      sfrapPerfIcmpTotalTxPktTooBig    OBJECT-TYPE
             SYNTAX      Counter
             ACCESS      read-only
             STATUS      mandatory
             DESCRIPTION
                "The number of bytes in ICMP packet too bigs
                 that have been counted across all DLCIs."
            ::= { sfrapPerfIcmpTotalEntry 28 }

      sfrapPerfIcmpTotalRxGmQuery    OBJECT-TYPE
             SYNTAX      Counter
             ACCESS      read-only
             STATUS      mandatory
             DESCRIPTION
                "The number of bytes in ICMP group membership
                 queries that have been counted across all DLCIs."
            ::= { sfrapPerfIcmpTotalEntry 29 }

      sfrapPerfIcmpTotalTxGmQuery    OBJECT-TYPE
             SYNTAX      Counter
             ACCESS      read-only
             STATUS      mandatory
             DESCRIPTION
                "The number of bytes in ICMP group membership
                 queries that have been counte across all DLCIs."
            ::= { sfrapPerfIcmpTotalEntry 30 }

      sfrapPerfIcmpTotalRxGmReport    OBJECT-TYPE
             SYNTAX      Counter
             ACCESS      read-only
             STATUS      mandatory
             DESCRIPTION
                "The number of bytes in ICMP group membership
                 reports that have been counted across all DLCIs."
            ::= { sfrapPerfIcmpTotalEntry 31 }

      sfrapPerfIcmpTotalTxGmReport    OBJECT-TYPE
             SYNTAX      Counter
             ACCESS      read-only
             STATUS      mandatory
             DESCRIPTION
                "The number of bytes in ICMP group membership
                 reports that have been counted across all DLCIs."
            ::= { sfrapPerfIcmpTotalEntry 32 }

      sfrapPerfIcmpTotalRxGmReduct    OBJECT-TYPE
             SYNTAX      Counter
             ACCESS      read-only
             STATUS      mandatory
             DESCRIPTION
                "The number of bytes in ICMP group membership
                 reductions that have been counted across all DLCIs."
            ::= { sfrapPerfIcmpTotalEntry 33 }

      sfrapPerfIcmpTotalTxGmReduct    OBJECT-TYPE
             SYNTAX      Counter
             ACCESS      read-only
             STATUS      mandatory
             DESCRIPTION
                "The number of bytes in ICMP group membership
                 reductions that have been counted across all DLCIs."
            ::= { sfrapPerfIcmpTotalEntry 34 }

   --  Application-level Short Term Statistics for each DLCI.

   sfrapPerfApplicationPerDlciTable OBJECT-TYPE
         SYNTAX   SEQUENCE OF SfrapPerfApplicationPerDlciEntry
         ACCESS   not-accessible
         STATUS   mandatory
         DESCRIPTION
            "The Short Term Statistics on the Application
            protocol for each DLCI."
         ::= { sfrapPerfNetworkShortTerm 7 }

         sfrapPerfApplicationPerDlciEntry OBJECT-TYPE
             SYNTAX   SfrapPerfApplicationPerDlciEntry
             ACCESS   not-accessible
             STATUS   mandatory
             DESCRIPTION
                "The Application Short Term Statistics for a particular DLCI."
            INDEX { sfrapPerfApplicationPerDlciInterval, 
                    sfrapPerfApplicationPerDlciValue }
            ::= { sfrapPerfApplicationPerDlciTable 1 }

         SfrapPerfApplicationPerDlciEntry ::=
             SEQUENCE {
                 sfrapPerfApplicationPerDlciInterval   INTEGER,
                 sfrapPerfApplicationPerDlciValue      INTEGER,
                 sfrapPerfApplicationPerDlciRxSnmp     Counter,
                 sfrapPerfApplicationPerDlciTxSnmp     Counter,
                 sfrapPerfApplicationPerDlciRxSnmpTrap Counter,
                 sfrapPerfApplicationPerDlciTxSnmpTrap Counter,
                 sfrapPerfApplicationPerDlciRxHttp     Counter,
                 sfrapPerfApplicationPerDlciTxHttp     Counter,
                 sfrapPerfApplicationPerDlciRxTelnet   Counter,
                 sfrapPerfApplicationPerDlciTxTelnet   Counter,
                 sfrapPerfApplicationPerDlciRxSmtp     Counter,
                 sfrapPerfApplicationPerDlciTxSmtp     Counter,
                 sfrapPerfApplicationPerDlciRxFtp      Counter,
                 sfrapPerfApplicationPerDlciTxFtp      Counter,
                 sfrapPerfApplicationPerDlciRxTftp     Counter,
                 sfrapPerfApplicationPerDlciTxTftp     Counter,
                 sfrapPerfApplicationPerDlciRxCustom1  Counter,
                 sfrapPerfApplicationPerDlciTxCustom1  Counter,
                 sfrapPerfApplicationPerDlciRxCustom2  Counter,
                 sfrapPerfApplicationPerDlciTxCustom2  Counter,
                 sfrapPerfApplicationPerDlciRxCustom3  Counter,
                 sfrapPerfApplicationPerDlciTxCustom3  Counter,
                 sfrapPerfApplicationPerDlciRxCustom4  Counter,
                 sfrapPerfApplicationPerDlciTxCustom4  Counter
               }

      sfrapPerfApplicationPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfApplicationPerDlciEntry 1 }

      sfrapPerfApplicationPerDlciValue    OBJECT-TYPE
             SYNTAX      INTEGER 
             ACCESS      read-only
             STATUS      mandatory
             DESCRIPTION
                "The DLCI value with which the Statistics are associated."
            ::= { sfrapPerfApplicationPerDlciEntry 2 }

      sfrapPerfApplicationPerDlciRxSnmp    OBJECT-TYPE
             SYNTAX      Counter
             ACCESS      read-only
             STATUS      mandatory
             DESCRIPTION
                "The number of received SNMP bytes
                 that have been counted on this DLCI."
            ::= { sfrapPerfApplicationPerDlciEntry 3 }

      sfrapPerfApplicationPerDlciTxSnmp    OBJECT-TYPE
             SYNTAX      Counter
             ACCESS      read-only
             STATUS      mandatory
             DESCRIPTION
                "The number of transmitted SNMP bytes
                 that have been counted on this DLCI."
            ::= { sfrapPerfApplicationPerDlciEntry 4 }

      sfrapPerfApplicationPerDlciRxSnmpTrap    OBJECT-TYPE
             SYNTAX      Counter
             ACCESS      read-only
             STATUS      mandatory
             DESCRIPTION
                "The number of received SNMP TRAP bytes
                 that have been counted on this DLCI."
            ::= { sfrapPerfApplicationPerDlciEntry 5 }

      sfrapPerfApplicationPerDlciTxSnmpTrap    OBJECT-TYPE
             SYNTAX      Counter
             ACCESS      read-only
             STATUS      mandatory
             DESCRIPTION
                "The number of transmitted SNMP TRAP bytes
                 that have been counted on this DLCI."
            ::= { sfrapPerfApplicationPerDlciEntry 6 }

      sfrapPerfApplicationPerDlciRxHttp    OBJECT-TYPE
             SYNTAX      Counter
             ACCESS      read-only
             STATUS      mandatory
             DESCRIPTION
                "The number of received HTTP bytes
                 that have been counted on this DLCI."
            ::= { sfrapPerfApplicationPerDlciEntry 7 }

      sfrapPerfApplicationPerDlciTxHttp    OBJECT-TYPE
             SYNTAX      Counter
             ACCESS      read-only
             STATUS      mandatory
             DESCRIPTION
                "The number of transmitted HTTP bytes
                 that have been counted on this DLCI."
            ::= { sfrapPerfApplicationPerDlciEntry 8 }

      sfrapPerfApplicationPerDlciRxTelnet    OBJECT-TYPE
             SYNTAX      Counter
             ACCESS      read-only
             STATUS      mandatory
             DESCRIPTION
                "The number of received Telnet bytes
                 that have been counted on this DLCI."
            ::= { sfrapPerfApplicationPerDlciEntry 9 }

      sfrapPerfApplicationPerDlciTxTelnet    OBJECT-TYPE
             SYNTAX      Counter
             ACCESS      read-only
             STATUS      mandatory
             DESCRIPTION
                "The number of transmitted Telnet bytes
                 that have been counted on this DLCI."
            ::= { sfrapPerfApplicationPerDlciEntry 10 }

      sfrapPerfApplicationPerDlciRxSmtp    OBJECT-TYPE
             SYNTAX      Counter
             ACCESS      read-only
             STATUS      mandatory
             DESCRIPTION
                "The number of received SMTP bytes
                 that have been counted on this DLCI."
            ::= { sfrapPerfApplicationPerDlciEntry 11 }

      sfrapPerfApplicationPerDlciTxSmtp    OBJECT-TYPE
             SYNTAX      Counter
             ACCESS      read-only
             STATUS      mandatory
             DESCRIPTION
                "The number of transmitted SMTP bytes
                 that have been counted on this DLCI."
            ::= { sfrapPerfApplicationPerDlciEntry 12 }

      sfrapPerfApplicationPerDlciRxFtp    OBJECT-TYPE
             SYNTAX      Counter
             ACCESS      read-only
             STATUS      mandatory
             DESCRIPTION
                "The number of received FTP bytes
                 that have been counted on this DLCI."
            ::= { sfrapPerfApplicationPerDlciEntry 13 }

      sfrapPerfApplicationPerDlciTxFtp    OBJECT-TYPE
             SYNTAX      Counter
             ACCESS      read-only
             STATUS      mandatory
             DESCRIPTION
                "The number of transmitted FTP bytes
                 that have been counted on this DLCI."
            ::= { sfrapPerfApplicationPerDlciEntry 14 }

      sfrapPerfApplicationPerDlciRxTftp    OBJECT-TYPE
             SYNTAX      Counter
             ACCESS      read-only
             STATUS      mandatory
             DESCRIPTION
                "The number of received TFTP bytes
                 that have been counted on this DLCI."
            ::= { sfrapPerfApplicationPerDlciEntry 15 }

      sfrapPerfApplicationPerDlciTxTftp    OBJECT-TYPE
             SYNTAX      Counter
             ACCESS      read-only
             STATUS      mandatory
             DESCRIPTION
                "The number of transmitted TFTP bytes
                 that have been counted on this DLCI."
            ::= { sfrapPerfApplicationPerDlciEntry 16 }

      sfrapPerfApplicationPerDlciRxCustom1    OBJECT-TYPE
             SYNTAX      Counter
             ACCESS      read-only
             STATUS      mandatory
             DESCRIPTION
                "The number of received bytes of
                 User Defined Protocol #1 that have
                 been counted on this DLCI."
            ::= { sfrapPerfApplicationPerDlciEntry 17 }

      sfrapPerfApplicationPerDlciTxCustom1    OBJECT-TYPE
             SYNTAX      Counter
             ACCESS      read-only
             STATUS      mandatory
             DESCRIPTION
                "The number of transmitted bytes of
                 User Defined Protocol #1 that have
                 been counted on this DLCI."
            ::= { sfrapPerfApplicationPerDlciEntry 18 }

      sfrapPerfApplicationPerDlciRxCustom2    OBJECT-TYPE
             SYNTAX      Counter
             ACCESS      read-only
             STATUS      mandatory
             DESCRIPTION
                "The number of received bytes of
                 User Defined Protocol #2 that have
                 been counted on this DLCI."
            ::= { sfrapPerfApplicationPerDlciEntry 19 }

      sfrapPerfApplicationPerDlciTxCustom2    OBJECT-TYPE
             SYNTAX      Counter
             ACCESS      read-only
             STATUS      mandatory
             DESCRIPTION
                "The number of transmitted bytes of
                 User Defined Protocol #2 that have
                 been counted on this DLCI."
            ::= { sfrapPerfApplicationPerDlciEntry 20 }

      sfrapPerfApplicationPerDlciRxCustom3    OBJECT-TYPE
             SYNTAX      Counter
             ACCESS      read-only
             STATUS      mandatory
             DESCRIPTION
                "The number of received bytes of
                 User Defined Protocol #3 that have
                 been counted on this DLCI."
            ::= { sfrapPerfApplicationPerDlciEntry 21 }

      sfrapPerfApplicationPerDlciTxCustom3    OBJECT-TYPE
             SYNTAX      Counter
             ACCESS      read-only
             STATUS      mandatory
             DESCRIPTION
                "The number of transmitted bytes of
                 User Defined Protocol #3 that have
                 been counted on this DLCI."
            ::= { sfrapPerfApplicationPerDlciEntry 22 }

      sfrapPerfApplicationPerDlciRxCustom4    OBJECT-TYPE
             SYNTAX      Counter
             ACCESS      read-only
             STATUS      mandatory
             DESCRIPTION
                "The number of received bytes of
                 User Defined Protocol #4 that have
                 been counted on this DLCI."
            ::= { sfrapPerfApplicationPerDlciEntry 23 }

      sfrapPerfApplicationPerDlciTxCustom4    OBJECT-TYPE
             SYNTAX      Counter
             ACCESS      read-only
             STATUS      mandatory
             DESCRIPTION
                "The number of transmitted bytes of
                 User Defined Protocol #4 that have
                 been counted on this DLCI."
            ::= { sfrapPerfApplicationPerDlciEntry 24 }



   --  Application-level Short Term Statistics totals.

   sfrapPerfApplicationTotalTable OBJECT-TYPE
         SYNTAX   SEQUENCE OF SfrapPerfApplicationTotalEntry
         ACCESS   not-accessible
         STATUS   mandatory
         DESCRIPTION
            "The Short Term Statistics on the Application
            protocol across all DLCIs."
         ::= { sfrapPerfNetworkShortTerm 8 }

         sfrapPerfApplicationTotalEntry OBJECT-TYPE
             SYNTAX   SfrapPerfApplicationTotalEntry
             ACCESS   not-accessible
             STATUS   mandatory
             DESCRIPTION
                "The Application Short Term Statistics for a particular DLCI."
            INDEX { sfrapPerfApplicationTotalInterval }
            ::= { sfrapPerfApplicationTotalTable 1 }

         SfrapPerfApplicationTotalEntry ::=
             SEQUENCE {
                 sfrapPerfApplicationTotalInterval   INTEGER,
                 sfrapPerfApplicationTotalRxSnmp     Counter,
                 sfrapPerfApplicationTotalTxSnmp     Counter,
                 sfrapPerfApplicationTotalRxSnmpTrap Counter,
                 sfrapPerfApplicationTotalTxSnmpTrap Counter,
                 sfrapPerfApplicationTotalRxHttp     Counter,
                 sfrapPerfApplicationTotalTxHttp     Counter,
                 sfrapPerfApplicationTotalRxTelnet   Counter,
                 sfrapPerfApplicationTotalTxTelnet   Counter,
                 sfrapPerfApplicationTotalRxSmtp     Counter,
                 sfrapPerfApplicationTotalTxSmtp     Counter,
                 sfrapPerfApplicationTotalRxFtp      Counter,
                 sfrapPerfApplicationTotalTxFtp      Counter,
                 sfrapPerfApplicationTotalRxTftp     Counter,
                 sfrapPerfApplicationTotalTxTftp     Counter,
                 sfrapPerfApplicationTotalRxCustom1  Counter,
                 sfrapPerfApplicationTotalTxCustom1  Counter,
                 sfrapPerfApplicationTotalRxCustom2  Counter,
                 sfrapPerfApplicationTotalTxCustom2  Counter,
                 sfrapPerfApplicationTotalRxCustom3  Counter,
                 sfrapPerfApplicationTotalTxCustom3  Counter,
                 sfrapPerfApplicationTotalRxCustom4  Counter,
                 sfrapPerfApplicationTotalTxCustom4  Counter
               }

      sfrapPerfApplicationTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfApplicationTotalEntry 1 }

      sfrapPerfApplicationTotalRxSnmp    OBJECT-TYPE
             SYNTAX      Counter
             ACCESS      read-only
             STATUS      mandatory
             DESCRIPTION
                "The number of received SNMP bytes
                 that have been counted across all DLCIs."
            ::= { sfrapPerfApplicationTotalEntry 3 }

      sfrapPerfApplicationTotalTxSnmp    OBJECT-TYPE
             SYNTAX      Counter
             ACCESS      read-only
             STATUS      mandatory
             DESCRIPTION
                "The number of transmitted SNMP bytes
                 that have been counted across all DLCIs."
            ::= { sfrapPerfApplicationTotalEntry 4 }

      sfrapPerfApplicationTotalRxSnmpTrap    OBJECT-TYPE
             SYNTAX      Counter
             ACCESS      read-only
             STATUS      mandatory
             DESCRIPTION
                "The number of received SNMP TRAP bytes
                 that have been counted across all DLCIs."
            ::= { sfrapPerfApplicationTotalEntry 5 }

      sfrapPerfApplicationTotalTxSnmpTrap    OBJECT-TYPE
             SYNTAX      Counter
             ACCESS      read-only
             STATUS      mandatory
             DESCRIPTION
                "The number of transmitted SNMP TRAP bytes
                 that have been counted across all DLCIs."
            ::= { sfrapPerfApplicationTotalEntry 6 }

      sfrapPerfApplicationTotalRxHttp    OBJECT-TYPE
             SYNTAX      Counter
             ACCESS      read-only
             STATUS      mandatory
             DESCRIPTION
                "The number of received HTTP bytes
                 that have been counted across all DLCIs."
            ::= { sfrapPerfApplicationTotalEntry 7 }

      sfrapPerfApplicationTotalTxHttp    OBJECT-TYPE
             SYNTAX      Counter
             ACCESS      read-only
             STATUS      mandatory
             DESCRIPTION
                "The number of transmitted HTTP bytes
                 that have been counted across all DLCIs."
            ::= { sfrapPerfApplicationTotalEntry 8 }

      sfrapPerfApplicationTotalRxTelnet    OBJECT-TYPE
             SYNTAX      Counter
             ACCESS      read-only
             STATUS      mandatory
             DESCRIPTION
                "The number of received Telnet bytes
                 that have been counted across all DLCIs."
            ::= { sfrapPerfApplicationTotalEntry 9 }

      sfrapPerfApplicationTotalTxTelnet    OBJECT-TYPE
             SYNTAX      Counter
             ACCESS      read-only
             STATUS      mandatory
             DESCRIPTION
                "The number of transmitted Telnet bytes
                 that have been counted across all DLCIs."
            ::= { sfrapPerfApplicationTotalEntry 10 }

      sfrapPerfApplicationTotalRxSmtp    OBJECT-TYPE
             SYNTAX      Counter
             ACCESS      read-only
             STATUS      mandatory
             DESCRIPTION
                "The number of received SMTP bytes
                 that have been counted across all DLCIs."
            ::= { sfrapPerfApplicationTotalEntry 11 }

      sfrapPerfApplicationTotalTxSmtp    OBJECT-TYPE
             SYNTAX      Counter
             ACCESS      read-only
             STATUS      mandatory
             DESCRIPTION
                "The number of transmitted SMTP bytes
                 that have been counted across all DLCIs."
            ::= { sfrapPerfApplicationTotalEntry 12 }

      sfrapPerfApplicationTotalRxFtp    OBJECT-TYPE
             SYNTAX      Counter
             ACCESS      read-only
             STATUS      mandatory
             DESCRIPTION
                "The number of received FTP bytes
                 that have been counted across all DLCIs."
            ::= { sfrapPerfApplicationTotalEntry 13 }

      sfrapPerfApplicationTotalTxFtp    OBJECT-TYPE
             SYNTAX      Counter
             ACCESS      read-only
             STATUS      mandatory
             DESCRIPTION
                "The number of transmitted FTP bytes
                 that have been counted across all DLCIs."
            ::= { sfrapPerfApplicationTotalEntry 14 }

      sfrapPerfApplicationTotalRxTftp    OBJECT-TYPE
             SYNTAX      Counter
             ACCESS      read-only
             STATUS      mandatory
             DESCRIPTION
                "The number of received TFTP bytes
                 that have been counted across all DLCIs."
            ::= { sfrapPerfApplicationTotalEntry 15 }

      sfrapPerfApplicationTotalTxTftp    OBJECT-TYPE
             SYNTAX      Counter
             ACCESS      read-only
             STATUS      mandatory
             DESCRIPTION
                "The number of transmitted TFTP bytes
                 that have been counted across all DLCIs."
            ::= { sfrapPerfApplicationTotalEntry 16 }

      sfrapPerfApplicationTotalRxCustom1    OBJECT-TYPE
             SYNTAX      Counter
             ACCESS      read-only
             STATUS      mandatory
             DESCRIPTION
                "The number of received bytes of
                 User Defined Protocol #1 that have
                 been counted across all DLCIs."
            ::= { sfrapPerfApplicationTotalEntry 17 }

      sfrapPerfApplicationTotalTxCustom1    OBJECT-TYPE
             SYNTAX      Counter
             ACCESS      read-only
             STATUS      mandatory
             DESCRIPTION
                "The number of transmitted bytes of
                 User Defined Protocol #1 that have
                 been counted across all DLCIs."
            ::= { sfrapPerfApplicationTotalEntry 18 }

      sfrapPerfApplicationTotalRxCustom2    OBJECT-TYPE
             SYNTAX      Counter
             ACCESS      read-only
             STATUS      mandatory
             DESCRIPTION
                "The number of received bytes of
                 User Defined Protocol #2 that have
                 been counted across all DLCIs."
            ::= { sfrapPerfApplicationTotalEntry 19 }

      sfrapPerfApplicationTotalTxCustom2    OBJECT-TYPE
             SYNTAX      Counter
             ACCESS      read-only
             STATUS      mandatory
             DESCRIPTION
                "The number of transmitted bytes of
                 User Defined Protocol #2 that have
                 been counted across all DLCIs."
            ::= { sfrapPerfApplicationTotalEntry 20 }

      sfrapPerfApplicationTotalRxCustom3    OBJECT-TYPE
             SYNTAX      Counter
             ACCESS      read-only
             STATUS      mandatory
             DESCRIPTION
                "The number of received bytes of
                 User Defined Protocol #3 that have
                 been counted across all DLCIs."
            ::= { sfrapPerfApplicationTotalEntry 21 }

      sfrapPerfApplicationTotalTxCustom3    OBJECT-TYPE
             SYNTAX      Counter
             ACCESS      read-only
             STATUS      mandatory
             DESCRIPTION
                "The number of transmitted bytes of
                 User Defined Protocol #3 that have
                 been counted across all DLCIs."
            ::= { sfrapPerfApplicationTotalEntry 22 }

      sfrapPerfApplicationTotalRxCustom4    OBJECT-TYPE
             SYNTAX      Counter
             ACCESS      read-only
             STATUS      mandatory
             DESCRIPTION
                "The number of received bytes of
                 User Defined Protocol #4 that have
                 been counted across all DLCIs."
            ::= { sfrapPerfApplicationTotalEntry 23 }

      sfrapPerfApplicationTotalTxCustom4    OBJECT-TYPE
             SYNTAX      Counter
             ACCESS      read-only
             STATUS      mandatory
             DESCRIPTION
                "The number of transmitted bytes of
                 User Defined Protocol #4 that have
                 been counted across all DLCIs."
            ::= { sfrapPerfApplicationTotalEntry 24 }


   --  Routing Short Term Statistics for each DLCI.

   sfrapPerfRoutingPerDlciTable OBJECT-TYPE
         SYNTAX   SEQUENCE OF SfrapPerfRoutingPerDlciEntry
         ACCESS   not-accessible
         STATUS   mandatory
         DESCRIPTION
            "The Short Term Statistics on the Routing
            protocol for each DLCI."
         ::= { sfrapPerfNetworkShortTerm 9 }

         sfrapPerfRoutingPerDlciEntry OBJECT-TYPE
             SYNTAX   SfrapPerfRoutingPerDlciEntry
             ACCESS   not-accessible
             STATUS   mandatory
             DESCRIPTION
                "The Routing Short Term Statistics for a particular DLCI."
            INDEX { sfrapPerfRoutingPerDlciInterval,
                    sfrapPerfRoutingPerDlciValue }
            ::= { sfrapPerfRoutingPerDlciTable 1 }

         SfrapPerfRoutingPerDlciEntry ::=
             SEQUENCE {
                 sfrapPerfRoutingPerDlciInterval  INTEGER,
                 sfrapPerfRoutingPerDlciValue     INTEGER,
                 sfrapPerfRoutingPerDlciRxOspf    Counter,
                 sfrapPerfRoutingPerDlciTxOspf    Counter,
                 sfrapPerfRoutingPerDlciRxRip     Counter,
                 sfrapPerfRoutingPerDlciTxRip     Counter,
                 sfrapPerfRoutingPerDlciRxNetbios Counter,
                 sfrapPerfRoutingPerDlciTxNetbios Counter
               }

      sfrapPerfRoutingPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfRoutingPerDlciEntry 1 }

      sfrapPerfRoutingPerDlciValue    OBJECT-TYPE
             SYNTAX      INTEGER 
             ACCESS      read-only
             STATUS      mandatory
             DESCRIPTION
                "The DLCI value with which the Statistics are associated."
            ::= { sfrapPerfRoutingPerDlciEntry 2 }


      sfrapPerfRoutingPerDlciRxOspf    OBJECT-TYPE
             SYNTAX      Counter
             ACCESS      read-only
             STATUS      mandatory
             DESCRIPTION
                "The number of received OSPF bytes
                 that have been counted on this DLCI."
            ::= { sfrapPerfRoutingPerDlciEntry 3 }

      sfrapPerfRoutingPerDlciTxOspf    OBJECT-TYPE
             SYNTAX      Counter
             ACCESS      read-only
             STATUS      mandatory
             DESCRIPTION
                "The number of transmitted OSPF bytes
                 that have been counted on this DLCI."
            ::= { sfrapPerfRoutingPerDlciEntry 4 }

      sfrapPerfRoutingPerDlciRxRip    OBJECT-TYPE
             SYNTAX      Counter
             ACCESS      read-only
             STATUS      mandatory
             DESCRIPTION
                "The number of received RIP bytes
                 that have been counted on this DLCI."
            ::= { sfrapPerfRoutingPerDlciEntry 5 }

      sfrapPerfRoutingPerDlciTxRip    OBJECT-TYPE
             SYNTAX      Counter
             ACCESS      read-only
             STATUS      mandatory
             DESCRIPTION
                "The number of transmitted RIP bytes
                 that have been counted on this DLCI."
            ::= { sfrapPerfRoutingPerDlciEntry 6 }

      sfrapPerfRoutingPerDlciRxNetbios    OBJECT-TYPE
             SYNTAX      Counter
             ACCESS      read-only
             STATUS      mandatory
             DESCRIPTION
                "The number of received Netbios bytes
                 that have been counted on this DLCI."
            ::= { sfrapPerfRoutingPerDlciEntry 7 }

      sfrapPerfRoutingPerDlciTxNetbios    OBJECT-TYPE
             SYNTAX      Counter
             ACCESS      read-only
             STATUS      mandatory
             DESCRIPTION
                "The number of transmitted Netbios bytes
                 that have been counted on this DLCI."
            ::= { sfrapPerfRoutingPerDlciEntry 8 }


   --  Routing Short Term Statistics totals.

   sfrapPerfRoutingTotalTable OBJECT-TYPE
         SYNTAX   SEQUENCE OF SfrapPerfRoutingTotalEntry
         ACCESS   not-accessible
         STATUS   mandatory
         DESCRIPTION
            "The Short Term Statistics on the Routing
            protocol across all DLCIs."
         ::= { sfrapPerfNetworkShortTerm 10 }

         sfrapPerfRoutingTotalEntry OBJECT-TYPE
             SYNTAX   SfrapPerfRoutingTotalEntry
             ACCESS   not-accessible
             STATUS   mandatory
             DESCRIPTION
                "The Routing Short Term Statistics for a particular DLCI."
            INDEX { sfrapPerfRoutingTotalInterval }
            ::= { sfrapPerfRoutingTotalTable 1 }

         SfrapPerfRoutingTotalEntry ::=
             SEQUENCE {
                 sfrapPerfRoutingTotalInterval  INTEGER,
                 sfrapPerfRoutingTotalRxOspf    Counter,
                 sfrapPerfRoutingTotalTxOspf    Counter,
                 sfrapPerfRoutingTotalRxRip     Counter,
                 sfrapPerfRoutingTotalTxRip     Counter,
                 sfrapPerfRoutingTotalRxNetbios Counter,
                 sfrapPerfRoutingTotalTxNetbios Counter
               }

      sfrapPerfRoutingTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfRoutingTotalEntry 1 }

      sfrapPerfRoutingTotalRxOspf    OBJECT-TYPE
             SYNTAX      Counter 
             ACCESS      read-only
             STATUS      mandatory
             DESCRIPTION
                "The number of received OSPF bytes
                 that have been counted across all DLCIs."
            ::= { sfrapPerfRoutingTotalEntry 3 }

      sfrapPerfRoutingTotalTxOspf    OBJECT-TYPE
             SYNTAX      Counter
             ACCESS      read-only
             STATUS      mandatory
             DESCRIPTION
                "The number of transmitted OSPF bytes
                 that have been counted across all DLCIs."
            ::= { sfrapPerfRoutingTotalEntry 4 }

      sfrapPerfRoutingTotalRxRip    OBJECT-TYPE
             SYNTAX      Counter
             ACCESS      read-only
             STATUS      mandatory
             DESCRIPTION
                "The number of received RIP bytes
                 that have been counted across all DLCIs."
            ::= { sfrapPerfRoutingTotalEntry 5 }

      sfrapPerfRoutingTotalTxRip    OBJECT-TYPE
             SYNTAX      Counter
             ACCESS      read-only
             STATUS      mandatory
             DESCRIPTION
                "The number of transmitted RIP bytes
                 that have been counted across all DLCIs."
            ::= { sfrapPerfRoutingTotalEntry 6 }

      sfrapPerfRoutingTotalRxNetbios    OBJECT-TYPE
             SYNTAX      Counter
             ACCESS      read-only
             STATUS      mandatory
             DESCRIPTION
                "The number of received Netbios bytes
                 that have been counted across all DLCIs."
            ::= { sfrapPerfRoutingTotalEntry 7 }

      sfrapPerfRoutingTotalTxNetbios    OBJECT-TYPE
             SYNTAX      Counter
             ACCESS      read-only
             STATUS      mandatory
             DESCRIPTION
                "The number of transmitted Netbios bytes
                 that have been counted across all DLCIs."
            ::= { sfrapPerfRoutingTotalEntry 8 }



   --  IPX Short Term Statistics for each DLCI.

   sfrapPerfIpxPerDlciTable OBJECT-TYPE
         SYNTAX   SEQUENCE OF SfrapPerfIpxPerDlciEntry
         ACCESS   not-accessible
         STATUS   mandatory
         DESCRIPTION
            "Short Term Statistics on the IPX
             protocol for each DLCI."
         ::= { sfrapPerfNetworkShortTerm 11 }

         sfrapPerfIpxPerDlciEntry OBJECT-TYPE
             SYNTAX   SfrapPerfIpxPerDlciEntry
             ACCESS   not-accessible
             STATUS   mandatory
             DESCRIPTION
                "The IPX Short Term Statistics for a particular DLCI."
            INDEX { sfrapPerfIpxPerDlciInterval, sfrapPerfIpxPerDlciValue }
            ::= { sfrapPerfIpxPerDlciTable 1 }

         SfrapPerfIpxPerDlciEntry ::=
             SEQUENCE {
                 sfrapPerfIpxPerDlciInterval   INTEGER,
                 sfrapPerfIpxPerDlciValue      INTEGER,
                 sfrapPerfIpxPerDlciRxTotal    Counter,
                 sfrapPerfIpxPerDlciTxTotal    Counter,
                 sfrapPerfIpxPerDlciRxSpx      Counter,
                 sfrapPerfIpxPerDlciTxSpx      Counter,
                 sfrapPerfIpxPerDlciRxNcp      Counter,
                 sfrapPerfIpxPerDlciTxNcp      Counter,
                 sfrapPerfIpxPerDlciRxSap      Counter,
                 sfrapPerfIpxPerDlciTxSap      Counter,
                 sfrapPerfIpxPerDlciRxRip      Counter,
                 sfrapPerfIpxPerDlciTxRip      Counter,
                 sfrapPerfIpxPerDlciRxNetbios  Counter,
                 sfrapPerfIpxPerDlciTxNetbios  Counter,
                 sfrapPerfIpxPerDlciRxOther    Counter,
                 sfrapPerfIpxPerDlciTxOther    Counter
             }

      sfrapPerfIpxPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfIpxPerDlciEntry 1 }

      sfrapPerfIpxPerDlciValue    OBJECT-TYPE
             SYNTAX      INTEGER 
            ACCESS      read-only
             STATUS      mandatory
             DESCRIPTION
                "The DLCI value in which the Statistics are associated."
            ::= { sfrapPerfIpxPerDlciEntry 2 }

      sfrapPerfIpxPerDlciRxTotal    OBJECT-TYPE
             SYNTAX      Counter
             ACCESS      read-only
             STATUS      mandatory
             DESCRIPTION
                "The total number of IPX bytes
                 that have been counted on this DLCI."
            ::= { sfrapPerfIpxPerDlciEntry 3 }

      sfrapPerfIpxPerDlciTxTotal    OBJECT-TYPE
             SYNTAX      Counter
             ACCESS      read-only
             STATUS      mandatory
             DESCRIPTION
                "The total number of IPX bytes
                 that have been counted on this DLCI."
            ::= { sfrapPerfIpxPerDlciEntry 4 }

      sfrapPerfIpxPerDlciRxSpx    OBJECT-TYPE
             SYNTAX      Counter
             ACCESS      read-only
             STATUS      mandatory
             DESCRIPTION
                "The number of SPX over IPX bytes
                 that have been counted on this DLCI."
            ::= { sfrapPerfIpxPerDlciEntry 5 }

      sfrapPerfIpxPerDlciTxSpx    OBJECT-TYPE
             SYNTAX      Counter
             ACCESS      read-only
             STATUS      mandatory
             DESCRIPTION
                "The number of SPX over IPX bytes
                 that have been counted on this DLCI."
            ::= { sfrapPerfIpxPerDlciEntry 6 }

      sfrapPerfIpxPerDlciRxNcp    OBJECT-TYPE
             SYNTAX      Counter
             ACCESS      read-only
             STATUS      mandatory
             DESCRIPTION
                "The number of NCP over IPX bytes
                 that have been counted on this DLCI."
            ::= { sfrapPerfIpxPerDlciEntry 7 }

      sfrapPerfIpxPerDlciTxNcp    OBJECT-TYPE
             SYNTAX      Counter
             ACCESS      read-only
             STATUS      mandatory
             DESCRIPTION
                "The number of NCP over IPX bytes
                 that have been counted on this DLCI."
            ::= { sfrapPerfIpxPerDlciEntry 8 }

      sfrapPerfIpxPerDlciRxSap    OBJECT-TYPE
             SYNTAX      Counter
             ACCESS      read-only
             STATUS      mandatory
             DESCRIPTION
                "The number of SAP over IPX bytes
                 that have been counted on this DLCI."
            ::= { sfrapPerfIpxPerDlciEntry 9 }

      sfrapPerfIpxPerDlciTxSap    OBJECT-TYPE
             SYNTAX      Counter
             ACCESS      read-only
             STATUS      mandatory
             DESCRIPTION
                "The number of SAP over IPX bytes
                 that have been counted on this DLCI."
            ::= { sfrapPerfIpxPerDlciEntry 10 }

      sfrapPerfIpxPerDlciRxRip    OBJECT-TYPE
             SYNTAX      Counter
             ACCESS      read-only
             STATUS      mandatory
             DESCRIPTION
                "The number of RIP over IPX bytes
                 that have been counted on this DLCI."
            ::= { sfrapPerfIpxPerDlciEntry 11 }

      sfrapPerfIpxPerDlciTxRip    OBJECT-TYPE
             SYNTAX      Counter
             ACCESS      read-only
             STATUS      mandatory
             DESCRIPTION
                "The number of RIP over IPX bytes
                 that have been counted on this DLCI."
            ::= { sfrapPerfIpxPerDlciEntry 12 }

      sfrapPerfIpxPerDlciRxNetbios    OBJECT-TYPE
             SYNTAX      Counter
             ACCESS      read-only
             STATUS      mandatory
             DESCRIPTION
                "The number of NETBIOS over IPX bytes
                 that have been counted on this DLCI."
            ::= { sfrapPerfIpxPerDlciEntry 13 }

      sfrapPerfIpxPerDlciTxNetbios    OBJECT-TYPE
             SYNTAX      Counter
             ACCESS      read-only
             STATUS      mandatory
             DESCRIPTION
                "The number of NETBIOS over IPX bytes
                 that have been counted on this DLCI."
            ::= { sfrapPerfIpxPerDlciEntry 14 }

      sfrapPerfIpxPerDlciRxOther    OBJECT-TYPE
             SYNTAX      Counter
             ACCESS      read-only
             STATUS      mandatory
             DESCRIPTION
                "The number of received bytes on this DLCI
                 from protocols over IPX that are not counted
                 elsewhere in this table."
            ::= { sfrapPerfIpxPerDlciEntry 15 }

      sfrapPerfIpxPerDlciTxOther    OBJECT-TYPE
             SYNTAX      Counter
             ACCESS      read-only
             STATUS      mandatory
             DESCRIPTION
                "The number of transmitted bytes on this DLCI
                 from protocols over IPX that are not counted
                 elsewhere in this table."
            ::= { sfrapPerfIpxPerDlciEntry 16 }


   --  IPX Short Term Statistics totals.

   sfrapPerfIpxTotalTable OBJECT-TYPE
         SYNTAX   SEQUENCE OF SfrapPerfIpxTotalEntry
         ACCESS   not-accessible
         STATUS   mandatory
         DESCRIPTION
            "Short Term Statistics on the IPX
             protocol across all DLCIs."
         ::= { sfrapPerfNetworkShortTerm 12 }

         sfrapPerfIpxTotalEntry OBJECT-TYPE
             SYNTAX   SfrapPerfIpxTotalEntry
             ACCESS   not-accessible
             STATUS   mandatory
             DESCRIPTION
                "The IPX Short Term Statistics for a particular DLCI."
            INDEX { sfrapPerfIpxTotalInterval }
            ::= { sfrapPerfIpxTotalTable 1 }

         SfrapPerfIpxTotalEntry ::=
             SEQUENCE {
                 sfrapPerfIpxTotalInterval   INTEGER,
                 sfrapPerfIpxTotalRxTotal    Counter,
                 sfrapPerfIpxTotalTxTotal    Counter,
                 sfrapPerfIpxTotalRxSpx      Counter,
                 sfrapPerfIpxTotalTxSpx      Counter,
                 sfrapPerfIpxTotalRxNcp      Counter,
                 sfrapPerfIpxTotalTxNcp      Counter,
                 sfrapPerfIpxTotalRxSap      Counter,
                 sfrapPerfIpxTotalTxSap      Counter,
                 sfrapPerfIpxTotalRxRip      Counter,
                 sfrapPerfIpxTotalTxRip      Counter,
                 sfrapPerfIpxTotalRxNetbios  Counter,
                 sfrapPerfIpxTotalTxNetbios  Counter,
                 sfrapPerfIpxTotalRxOther    Counter,
                 sfrapPerfIpxTotalTxOther    Counter
             }

      sfrapPerfIpxTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfIpxTotalEntry 1 }

      sfrapPerfIpxTotalRxTotal    OBJECT-TYPE
             SYNTAX      Counter
             ACCESS      read-only
             STATUS      mandatory
             DESCRIPTION
                "The total number of IPX bytes
                 that have been counted across all DLCIs."
            ::= { sfrapPerfIpxTotalEntry 3 }

      sfrapPerfIpxTotalTxTotal    OBJECT-TYPE
             SYNTAX      Counter
             ACCESS      read-only
             STATUS      mandatory
             DESCRIPTION
                "The total number of IPX bytes
                 that have been counted across all DLCIs."
            ::= { sfrapPerfIpxTotalEntry 4 }

      sfrapPerfIpxTotalRxSpx    OBJECT-TYPE
             SYNTAX      Counter
             ACCESS      read-only
             STATUS      mandatory
             DESCRIPTION
                "The number of SPX over IPX bytes
                 that have been counted across all DLCIs."
            ::= { sfrapPerfIpxTotalEntry 5 }

      sfrapPerfIpxTotalTxSpx    OBJECT-TYPE
             SYNTAX      Counter
             ACCESS      read-only
             STATUS      mandatory
             DESCRIPTION
                "The number of SPX over IPX bytes
                 that have been counted across all DLCIs."
            ::= { sfrapPerfIpxTotalEntry 6 }

      sfrapPerfIpxTotalRxNcp    OBJECT-TYPE
             SYNTAX      Counter
             ACCESS      read-only
             STATUS      mandatory
             DESCRIPTION
                "The number of NCP over IPX bytes
                 that have been counted across all DLCIs."
            ::= { sfrapPerfIpxTotalEntry 7 }

      sfrapPerfIpxTotalTxNcp    OBJECT-TYPE
             SYNTAX      Counter
             ACCESS      read-only
             STATUS      mandatory
             DESCRIPTION
                "The number of NCP over IPX bytes
                 that have been counted across all DLCIs."
            ::= { sfrapPerfIpxTotalEntry 8 }

      sfrapPerfIpxTotalRxSap    OBJECT-TYPE
             SYNTAX      Counter
             ACCESS      read-only
             STATUS      mandatory
             DESCRIPTION
                "The number of SAP over IPX bytes
                 that have been counted across all DLCIs."
            ::= { sfrapPerfIpxTotalEntry 9 }

      sfrapPerfIpxTotalTxSap    OBJECT-TYPE
             SYNTAX      Counter
             ACCESS      read-only
             STATUS      mandatory
             DESCRIPTION
                "The number of SAP over IPX bytes
                 that have been counted across all DLCIs."
            ::= { sfrapPerfIpxTotalEntry 10 }

      sfrapPerfIpxTotalRxRip    OBJECT-TYPE
             SYNTAX      Counter
             ACCESS      read-only
             STATUS      mandatory
             DESCRIPTION
                "The number of RIP over IPX bytes
                 that have been counted across all DLCIs."
            ::= { sfrapPerfIpxTotalEntry 11 }

      sfrapPerfIpxTotalTxRip    OBJECT-TYPE
             SYNTAX      Counter
             ACCESS      read-only
             STATUS      mandatory
             DESCRIPTION
                "The number of RIP over IPX bytes
                 that have been counted across all DLCIs."
            ::= { sfrapPerfIpxTotalEntry 12 }

      sfrapPerfIpxTotalRxNetbios    OBJECT-TYPE
             SYNTAX      Counter
             ACCESS      read-only
             STATUS      mandatory
             DESCRIPTION
                "The number of NETBIOS over IPX bytes
                 that have been counted across all DLCIs."
            ::= { sfrapPerfIpxTotalEntry 13 }

      sfrapPerfIpxTotalTxNetbios    OBJECT-TYPE
             SYNTAX      Counter
             ACCESS      read-only
             STATUS      mandatory
             DESCRIPTION
                "The number of NETBIOS over IPX bytes
                 that have been counted across all DLCIs."
            ::= { sfrapPerfIpxTotalEntry 14 }

      sfrapPerfIpxTotalRxOther    OBJECT-TYPE
             SYNTAX      Counter
             ACCESS      read-only
             STATUS      mandatory
             DESCRIPTION
                "The number of received bytes across all DLCIs
                 from protocols over IPX that are not counted
                 elsewhere in this table."
            ::= { sfrapPerfIpxTotalEntry 15 }

      sfrapPerfIpxTotalTxOther    OBJECT-TYPE
             SYNTAX      Counter
             ACCESS      read-only
             STATUS      mandatory
             DESCRIPTION
                "The number of transmitted bytes across all DLCIs
                 from protocols over IPX that are not counted
                 elsewhere in this table."
            ::= { sfrapPerfIpxTotalEntry 16 }


   --  SNA Short Term Statistics for each DLCI.

   sfrapPerfSnaPerDlciTable OBJECT-TYPE
         SYNTAX   SEQUENCE OF SfrapPerfSnaPerDlciEntry
         ACCESS   not-accessible
         STATUS   mandatory
         DESCRIPTION
            "Short Term Statistics on the SNA
             protocol for each DLCI."
         ::= { sfrapPerfNetworkShortTerm 13 }

         sfrapPerfSnaPerDlciEntry OBJECT-TYPE
             SYNTAX   SfrapPerfSnaPerDlciEntry
             ACCESS   not-accessible
             STATUS   mandatory
             DESCRIPTION
                "The SNA Short Term Statistics for a particular DLCI."
            INDEX { sfrapPerfSnaPerDlciInterval, sfrapPerfSnaPerDlciValue }
            ::= { sfrapPerfSnaPerDlciTable 1 }

         SfrapPerfSnaPerDlciEntry ::=
             SEQUENCE {
                 sfrapPerfSnaPerDlciInterval        INTEGER,
                 sfrapPerfSnaPerDlciValue           INTEGER,
                 sfrapPerfSnaPerDlciRxTotal         Counter,
                 sfrapPerfSnaPerDlciTxTotal         Counter,
                 sfrapPerfSnaPerDlciRxSubarea       Counter,
                 sfrapPerfSnaPerDlciTxSubarea       Counter,
                 sfrapPerfSnaPerDlciRxPeriph        Counter,
                 sfrapPerfSnaPerDlciTxPeriph        Counter,
                 sfrapPerfSnaPerDlciRxAppn          Counter,
                 sfrapPerfSnaPerDlciTxAppn          Counter,
                 sfrapPerfSnaPerDlciRxNetbios       Counter,
                 sfrapPerfSnaPerDlciTxNetbios       Counter,
                 sfrapPerfSnaPerDlciRxOther         Counter,
                 sfrapPerfSnaPerDlciTxOther         Counter
            }

      sfrapPerfSnaPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfSnaPerDlciEntry 1 }

      sfrapPerfSnaPerDlciValue    OBJECT-TYPE
             SYNTAX      INTEGER 
             ACCESS      read-only
             STATUS      mandatory
             DESCRIPTION
                "The DLCI value in which the Statistics are associated."
            ::= { sfrapPerfSnaPerDlciEntry 2 }

      sfrapPerfSnaPerDlciRxTotal    OBJECT-TYPE
             SYNTAX      Counter
             ACCESS      read-only
             STATUS      mandatory
             DESCRIPTION
                "The total number of SNA bytes
                 that have been counted on this DLCI."
            ::= { sfrapPerfSnaPerDlciEntry 3 }

      sfrapPerfSnaPerDlciTxTotal    OBJECT-TYPE
             SYNTAX      Counter
             ACCESS      read-only
             STATUS      mandatory
             DESCRIPTION
                "The total number of SNA bytes
                 that have been counted on this DLCI."
            ::= { sfrapPerfSnaPerDlciEntry 4 }

      sfrapPerfSnaPerDlciRxSubarea    OBJECT-TYPE
             SYNTAX      Counter
             ACCESS      read-only
             STATUS      mandatory
             DESCRIPTION
                "The number of SNA Subarea bytes
                 that have been counted on this DLCI."
            ::= { sfrapPerfSnaPerDlciEntry 5 }

      sfrapPerfSnaPerDlciTxSubarea    OBJECT-TYPE
             SYNTAX      Counter
             ACCESS      read-only
             STATUS      mandatory
             DESCRIPTION
                "The number of SNA Subarea bytes
                 that have been counted on this DLCI."
            ::= { sfrapPerfSnaPerDlciEntry 6 }

      sfrapPerfSnaPerDlciRxPeriph    OBJECT-TYPE
             SYNTAX      Counter
             ACCESS      read-only
             STATUS      mandatory
             DESCRIPTION
                "The number of SNA Periph bytes
                 that have been counted on this DLCI."
            ::= { sfrapPerfSnaPerDlciEntry 7 }

      sfrapPerfSnaPerDlciTxPeriph    OBJECT-TYPE
             SYNTAX      Counter
             ACCESS      read-only
             STATUS      mandatory
             DESCRIPTION
                "The number of SNA Periph bytes
                 that have been counted on this DLCI."
            ::= { sfrapPerfSnaPerDlciEntry 8 }

      sfrapPerfSnaPerDlciRxAppn    OBJECT-TYPE
             SYNTAX      Counter
             ACCESS      read-only
             STATUS      mandatory
             DESCRIPTION
                "The number of SNA Appn bytes
                 that have been counted on this DLCI."
            ::= { sfrapPerfSnaPerDlciEntry 9 }

      sfrapPerfSnaPerDlciTxAppn    OBJECT-TYPE
             SYNTAX      Counter
             ACCESS      read-only
             STATUS      mandatory
             DESCRIPTION
                "The number of SNA Appn bytes
                 that have been counted on this DLCI."
            ::= { sfrapPerfSnaPerDlciEntry 10 }

      sfrapPerfSnaPerDlciRxNetbios    OBJECT-TYPE
             SYNTAX      Counter
             ACCESS      read-only
             STATUS      mandatory
             DESCRIPTION
                "The number of SNA Netbios bytes
                 that have been counted on this DLCI."
            ::= { sfrapPerfSnaPerDlciEntry 11 }

      sfrapPerfSnaPerDlciTxNetbios    OBJECT-TYPE
             SYNTAX      Counter
             ACCESS      read-only
             STATUS      mandatory
             DESCRIPTION
                "The number of SNA Netbios bytes
                 that have been counted on this DLCI."
            ::= { sfrapPerfSnaPerDlciEntry 12 }

      sfrapPerfSnaPerDlciRxOther    OBJECT-TYPE
             SYNTAX      Counter
             ACCESS      read-only
             STATUS      mandatory
             DESCRIPTION
                "The number of received bytes on this DLCI
                 from protocols over SNA that are not counted
                 elsewhere in this table."
            ::= { sfrapPerfSnaPerDlciEntry 13 }

      sfrapPerfSnaPerDlciTxOther    OBJECT-TYPE
             SYNTAX      Counter
             ACCESS      read-only
             STATUS      mandatory
             DESCRIPTION
                "The number of transmitted bytes on this DLCI
                 from protocols over SNA that are not counted
                 elsewhere in this table."
            ::= { sfrapPerfSnaPerDlciEntry 14 }


   --  SNA Short Term Statistics totals.

   sfrapPerfSnaTotalTable OBJECT-TYPE
         SYNTAX   SEQUENCE OF SfrapPerfSnaTotalEntry
         ACCESS   not-accessible
         STATUS   mandatory
         DESCRIPTION
            "Short Term Statistics on the SNA
             protocol across all DLCIs."
         ::= { sfrapPerfNetworkShortTerm 14 }

         sfrapPerfSnaTotalEntry OBJECT-TYPE
             SYNTAX   SfrapPerfSnaTotalEntry
             ACCESS   not-accessible
             STATUS   mandatory
             DESCRIPTION
                "The SNA Short Term Statistics for a particular DLCI."
            INDEX { sfrapPerfSnaTotalInterval }
            ::= { sfrapPerfSnaTotalTable 1 }

         SfrapPerfSnaTotalEntry ::=
             SEQUENCE {
                 sfrapPerfSnaTotalInterval        INTEGER,
                 sfrapPerfSnaTotalRxTotal         Counter,
                 sfrapPerfSnaTotalTxTotal         Counter,
                 sfrapPerfSnaTotalRxSubarea       Counter,
                 sfrapPerfSnaTotalTxSubarea       Counter,
                 sfrapPerfSnaTotalRxPeriph        Counter,
                 sfrapPerfSnaTotalTxPeriph        Counter,
                 sfrapPerfSnaTotalRxAppn          Counter,
                 sfrapPerfSnaTotalTxAppn          Counter,
                 sfrapPerfSnaTotalRxNetbios       Counter,
                 sfrapPerfSnaTotalTxNetbios       Counter,
                 sfrapPerfSnaTotalRxOther         Counter,
                 sfrapPerfSnaTotalTxOther         Counter
            }

      sfrapPerfSnaTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfSnaTotalEntry 1 }

      sfrapPerfSnaTotalRxTotal    OBJECT-TYPE
             SYNTAX      Counter
             ACCESS      read-only
             STATUS      mandatory
             DESCRIPTION
                "The total number of SNA bytes
                 that have been counted across all DLCIs."
            ::= { sfrapPerfSnaTotalEntry 3 }

      sfrapPerfSnaTotalTxTotal    OBJECT-TYPE
             SYNTAX      Counter
             ACCESS      read-only
             STATUS      mandatory
             DESCRIPTION
                "The total number of SNA bytes
                 that have been counted across all DLCIs."
            ::= { sfrapPerfSnaTotalEntry 4 }

      sfrapPerfSnaTotalRxSubarea    OBJECT-TYPE
             SYNTAX      Counter
             ACCESS      read-only
             STATUS      mandatory
             DESCRIPTION
                "The number of SNA Subarea bytes
                 that have been counted across all DLCIs."
            ::= { sfrapPerfSnaTotalEntry 5 }

      sfrapPerfSnaTotalTxSubarea    OBJECT-TYPE
             SYNTAX      Counter
             ACCESS      read-only
             STATUS      mandatory
             DESCRIPTION
                "The number of SNA Subarea bytes
                 that have been counted across all DLCIs."
            ::= { sfrapPerfSnaTotalEntry 6 }

      sfrapPerfSnaTotalRxPeriph    OBJECT-TYPE
             SYNTAX      Counter
             ACCESS      read-only
             STATUS      mandatory
             DESCRIPTION
                "The number of SNA Periph bytes
                 that have been counted across all DLCIs."
            ::= { sfrapPerfSnaTotalEntry 7 }

      sfrapPerfSnaTotalTxPeriph    OBJECT-TYPE
             SYNTAX      Counter
             ACCESS      read-only
             STATUS      mandatory
             DESCRIPTION
                "The number of SNA Periph bytes
                 that have been counted across all DLCIs."
            ::= { sfrapPerfSnaTotalEntry 8 }

      sfrapPerfSnaTotalRxAppn    OBJECT-TYPE
             SYNTAX      Counter
             ACCESS      read-only
             STATUS      mandatory
             DESCRIPTION
                "The number of SNA Appn bytes
                 that have been counted across all DLCIs."
            ::= { sfrapPerfSnaTotalEntry 9 }

      sfrapPerfSnaTotalTxAppn    OBJECT-TYPE
             SYNTAX      Counter
             ACCESS      read-only
             STATUS      mandatory
             DESCRIPTION
                "The number of SNA Appn bytes
                 that have been counted across all DLCIs."
            ::= { sfrapPerfSnaTotalEntry 10 }

      sfrapPerfSnaTotalRxNetbios    OBJECT-TYPE
             SYNTAX      Counter
             ACCESS      read-only
             STATUS      mandatory
             DESCRIPTION
                "The number of SNA Netbios bytes
                 that have been counted across all DLCIs."
            ::= { sfrapPerfSnaTotalEntry 11 }

      sfrapPerfSnaTotalTxNetbios    OBJECT-TYPE
             SYNTAX      Counter
             ACCESS      read-only
             STATUS      mandatory
             DESCRIPTION
                "The number of SNA Netbios bytes
                 that have been counted across all DLCIs."
            ::= { sfrapPerfSnaTotalEntry 12 }

      sfrapPerfSnaTotalRxOther    OBJECT-TYPE
             SYNTAX      Counter
             ACCESS      read-only
             STATUS      mandatory
             DESCRIPTION
                "The number of received bytes across all DLCIs
                 from protocols over SNA that are not counted
                 elsewhere in this table."
            ::= { sfrapPerfSnaTotalEntry 13 }

      sfrapPerfSnaTotalTxOther    OBJECT-TYPE
             SYNTAX      Counter
             ACCESS      read-only
             STATUS      mandatory
             DESCRIPTION
                "The number of transmitted bytes across all DLCIs
                 from protocols over SNA that are not counted
                 elsewhere in this table."
            ::= { sfrapPerfSnaTotalEntry 14 }


   --  ARP Short Term Statistics for each DLCI.

   sfrapPerfArpPerDlciTable OBJECT-TYPE
         SYNTAX   SEQUENCE OF SfrapPerfArpPerDlciEntry
         ACCESS   not-accessible
         STATUS   mandatory
         DESCRIPTION
            "Short Term Statistics on the ARP
             protocol for each DLCI."
         ::= { sfrapPerfNetworkShortTerm 15 }

         sfrapPerfArpPerDlciEntry OBJECT-TYPE
             SYNTAX   SfrapPerfArpPerDlciEntry
             ACCESS   not-accessible
             STATUS   mandatory
             DESCRIPTION
                "The ARP Short Term Statistics for a particular DLCI."
            INDEX { sfrapPerfArpPerDlciInterval, sfrapPerfArpPerDlciValue }
            ::= { sfrapPerfArpPerDlciTable 1 }

         SfrapPerfArpPerDlciEntry ::=
             SEQUENCE {
                 sfrapPerfArpPerDlciInterval        INTEGER,
                 sfrapPerfArpPerDlciValue           INTEGER,
                 sfrapPerfArpPerDlciRxTotal         Counter,
                 sfrapPerfArpPerDlciTxTotal         Counter,
                 sfrapPerfArpPerDlciRxArpReq        Counter,
                 sfrapPerfArpPerDlciTxArpReq        Counter,
                 sfrapPerfArpPerDlciRxArpRep        Counter,
                 sfrapPerfArpPerDlciTxArpRep        Counter,
                 sfrapPerfArpPerDlciRxRarpReq       Counter,
                 sfrapPerfArpPerDlciTxRarpReq       Counter,
                 sfrapPerfArpPerDlciRxRarpRep       Counter,
                 sfrapPerfArpPerDlciTxRarpRep       Counter,
                 sfrapPerfArpPerDlciRxInarpReq      Counter,
                 sfrapPerfArpPerDlciTxInarpReq      Counter,
                 sfrapPerfArpPerDlciRxInarpRep      Counter,
                 sfrapPerfArpPerDlciTxInarpRep      Counter,
                 sfrapPerfArpPerDlciRxOther         Counter,
                 sfrapPerfArpPerDlciTxOther         Counter
            }

      sfrapPerfArpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfArpPerDlciEntry 1 }

      sfrapPerfArpPerDlciValue    OBJECT-TYPE
             SYNTAX      INTEGER 
            ACCESS      read-only
             STATUS      mandatory
             DESCRIPTION
                "The DLCI value in which the Statistics are associated."
            ::= { sfrapPerfArpPerDlciEntry 2 }

      sfrapPerfArpPerDlciRxTotal    OBJECT-TYPE
             SYNTAX      Counter
             ACCESS      read-only
             STATUS      mandatory
             DESCRIPTION
                "The total number of ARP bytes
                 that have been counted on this DLCI."
            ::= { sfrapPerfArpPerDlciEntry 3 }

      sfrapPerfArpPerDlciTxTotal    OBJECT-TYPE
             SYNTAX      Counter
             ACCESS      read-only
             STATUS      mandatory
             DESCRIPTION
                "The total number of ARP bytes
                 that have been counted on this DLCI."
            ::= { sfrapPerfArpPerDlciEntry 4 }

      sfrapPerfArpPerDlciRxArpReq    OBJECT-TYPE
             SYNTAX      Counter
             ACCESS      read-only
             STATUS      mandatory
             DESCRIPTION
                "The number of ARP request bytes
                 that have been counted on this DLCI."
            ::= { sfrapPerfArpPerDlciEntry 5 }

      sfrapPerfArpPerDlciTxArpReq    OBJECT-TYPE
             SYNTAX      Counter
             ACCESS      read-only
             STATUS      mandatory
             DESCRIPTION
                "The number of ARP request bytes
                 that have been counted on this DLCI."
            ::= { sfrapPerfArpPerDlciEntry 6 }

      sfrapPerfArpPerDlciRxArpRep    OBJECT-TYPE
             SYNTAX      Counter
             ACCESS      read-only
             STATUS      mandatory
             DESCRIPTION
                "The number of ARP reply bytes
                 that have been counted on this DLCI."
            ::= { sfrapPerfArpPerDlciEntry 7 }

      sfrapPerfArpPerDlciTxArpRep    OBJECT-TYPE
             SYNTAX      Counter
             ACCESS      read-only
             STATUS      mandatory
             DESCRIPTION
                "The number of ARP reply bytes
                 that have been counted on this DLCI."
            ::= { sfrapPerfArpPerDlciEntry 8 }

      sfrapPerfArpPerDlciRxRarpReq    OBJECT-TYPE
             SYNTAX      Counter
             ACCESS      read-only
             STATUS      mandatory
             DESCRIPTION
                "The number of RARP request bytes
                 that have been counted on this DLCI."
            ::= { sfrapPerfArpPerDlciEntry 9 }

      sfrapPerfArpPerDlciTxRarpReq    OBJECT-TYPE
             SYNTAX      Counter
             ACCESS      read-only
             STATUS      mandatory
             DESCRIPTION
                "The number of RARP request bytes
                 that have been counted on this DLCI."
            ::= { sfrapPerfArpPerDlciEntry 10 }

      sfrapPerfArpPerDlciRxRarpRep    OBJECT-TYPE
             SYNTAX      Counter
             ACCESS      read-only
             STATUS      mandatory
             DESCRIPTION
                "The number of RARP reply bytes
                 that have been counted on this DLCI."
            ::= { sfrapPerfArpPerDlciEntry 11 }

      sfrapPerfArpPerDlciTxRarpRep    OBJECT-TYPE
             SYNTAX      Counter
             ACCESS      read-only
             STATUS      mandatory
             DESCRIPTION
                "The number of RARP reply bytes
                 that have been counted on this DLCI."
            ::= { sfrapPerfArpPerDlciEntry 12 }

      sfrapPerfArpPerDlciRxInarpReq    OBJECT-TYPE
             SYNTAX      Counter
             ACCESS      read-only
             STATUS      mandatory
             DESCRIPTION
                "The number of INARP request bytes
                 that have been counted on this DLCI."
            ::= { sfrapPerfArpPerDlciEntry 13 }

      sfrapPerfArpPerDlciTxInarpReq    OBJECT-TYPE
             SYNTAX      Counter
             ACCESS      read-only
             STATUS      mandatory
             DESCRIPTION
                "The number of INARP request bytes
                 that have been counted on this DLCI."
            ::= { sfrapPerfArpPerDlciEntry 14 }

      sfrapPerfArpPerDlciRxInarpRep    OBJECT-TYPE
             SYNTAX      Counter
             ACCESS      read-only
             STATUS      mandatory
             DESCRIPTION
                "The number of INARP reply bytes
                 that have been counted on this DLCI."
            ::= { sfrapPerfArpPerDlciEntry 15 }

      sfrapPerfArpPerDlciTxInarpRep    OBJECT-TYPE
             SYNTAX      Counter
             ACCESS      read-only
             STATUS      mandatory
             DESCRIPTION
                "The number of INARP reply bytes
                 that have been counted on this DLCI."
            ::= { sfrapPerfArpPerDlciEntry 16 }

      sfrapPerfArpPerDlciRxOther    OBJECT-TYPE
             SYNTAX      Counter
             ACCESS      read-only
             STATUS      mandatory
             DESCRIPTION
                "The number of received bytes on this DLCI
                 from ARP message types that are not counted
                 elsewhere in this table."
            ::= { sfrapPerfArpPerDlciEntry 17 }

      sfrapPerfArpPerDlciTxOther    OBJECT-TYPE
             SYNTAX      Counter
             ACCESS      read-only
             STATUS      mandatory
             DESCRIPTION
                "The number of transmitted bytes on this DLCI
                 from ARP message types that are not counted
                 elsewhere in this table."
            ::= { sfrapPerfArpPerDlciEntry 18 }


   --  ARP Short Term Statistics totals.

   sfrapPerfArpTotalTable OBJECT-TYPE
         SYNTAX   SEQUENCE OF SfrapPerfArpTotalEntry
         ACCESS   not-accessible
         STATUS   mandatory
         DESCRIPTION
            "Short Term Statistics on the ARP
             protocol across all DLCIs."
         ::= { sfrapPerfNetworkShortTerm 16 }

         sfrapPerfArpTotalEntry OBJECT-TYPE
             SYNTAX   SfrapPerfArpTotalEntry
             ACCESS   not-accessible
             STATUS   mandatory
             DESCRIPTION
                "The ARP Short Term Statistics for a particular DLCI."
            INDEX { sfrapPerfArpTotalInterval }
            ::= { sfrapPerfArpTotalTable 1 }

         SfrapPerfArpTotalEntry ::=
             SEQUENCE {
                 sfrapPerfArpTotalInterval        INTEGER,
                 sfrapPerfArpTotalRxTotal         Counter,
                 sfrapPerfArpTotalTxTotal         Counter,
                 sfrapPerfArpTotalRxArpReq        Counter,
                 sfrapPerfArpTotalTxArpReq        Counter,
                 sfrapPerfArpTotalRxArpRep        Counter,
                 sfrapPerfArpTotalTxArpRep        Counter,
                 sfrapPerfArpTotalRxRarpReq       Counter,
                 sfrapPerfArpTotalTxRarpReq       Counter,
                 sfrapPerfArpTotalRxRarpRep       Counter,
                 sfrapPerfArpTotalTxRarpRep       Counter,
                 sfrapPerfArpTotalRxInarpReq      Counter,
                 sfrapPerfArpTotalTxInarpReq      Counter,
                 sfrapPerfArpTotalRxInarpRep      Counter,
                 sfrapPerfArpTotalTxInarpRep      Counter,
                 sfrapPerfArpTotalRxOther         Counter,
                 sfrapPerfArpTotalTxOther         Counter
            }

      sfrapPerfArpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfArpTotalEntry 1 }

      sfrapPerfArpTotalRxTotal    OBJECT-TYPE
             SYNTAX      Counter
             ACCESS      read-only
             STATUS      mandatory
             DESCRIPTION
                "The total number of ARP bytes
                 that have been counted across all DLCIs."
            ::= { sfrapPerfArpTotalEntry 3 }

      sfrapPerfArpTotalTxTotal    OBJECT-TYPE
             SYNTAX      Counter
             ACCESS      read-only
             STATUS      mandatory
             DESCRIPTION
                "The total number of ARP bytes
                 that have been counted across all DLCIs."
            ::= { sfrapPerfArpTotalEntry 4 }

      sfrapPerfArpTotalRxArpReq    OBJECT-TYPE
             SYNTAX      Counter
             ACCESS      read-only
             STATUS      mandatory
             DESCRIPTION
                "The number of ARP request bytes
                 that have been counted across all DLCIs."
            ::= { sfrapPerfArpTotalEntry 5 }

      sfrapPerfArpTotalTxArpReq    OBJECT-TYPE
             SYNTAX      Counter
             ACCESS      read-only
             STATUS      mandatory
             DESCRIPTION
                "The number of ARP request bytes
                 that have been counted across all DLCIs."
            ::= { sfrapPerfArpTotalEntry 6 }

      sfrapPerfArpTotalRxArpRep    OBJECT-TYPE
             SYNTAX      Counter
             ACCESS      read-only
             STATUS      mandatory
             DESCRIPTION
                "The number of ARP reply bytes
                 that have been counted across all DLCIs."
            ::= { sfrapPerfArpTotalEntry 7 }

      sfrapPerfArpTotalTxArpRep    OBJECT-TYPE
             SYNTAX      Counter
             ACCESS      read-only
             STATUS      mandatory
             DESCRIPTION
                "The number of ARP reply bytes
                 that have been counted across all DLCIs."
            ::= { sfrapPerfArpTotalEntry 8 }

      sfrapPerfArpTotalRxRarpReq    OBJECT-TYPE
             SYNTAX      Counter
             ACCESS      read-only
             STATUS      mandatory
             DESCRIPTION
                "The number of RARP request bytes
                 that have been counted across all DLCIs."
            ::= { sfrapPerfArpTotalEntry 9 }

      sfrapPerfArpTotalTxRarpReq    OBJECT-TYPE
             SYNTAX      Counter
             ACCESS      read-only
             STATUS      mandatory
             DESCRIPTION
                "The number of RARP request bytes
                 that have been counted across all DLCIs."
            ::= { sfrapPerfArpTotalEntry 10 }

      sfrapPerfArpTotalRxRarpRep    OBJECT-TYPE
             SYNTAX      Counter
             ACCESS      read-only
             STATUS      mandatory
             DESCRIPTION
                "The number of RARP reply bytes
                 that have been counted across all DLCIs."
            ::= { sfrapPerfArpTotalEntry 11 }

      sfrapPerfArpTotalTxRarpRep    OBJECT-TYPE
             SYNTAX      Counter
             ACCESS      read-only
             STATUS      mandatory
             DESCRIPTION
                "The number of RARP reply bytes
                 that have been counted across all DLCIs."
            ::= { sfrapPerfArpTotalEntry 12 }

      sfrapPerfArpTotalRxInarpReq    OBJECT-TYPE
             SYNTAX      Counter
             ACCESS      read-only
             STATUS      mandatory
             DESCRIPTION
                "The number of INARP request bytes
                 that have been counted across all DLCIs."
            ::= { sfrapPerfArpTotalEntry 13 }

      sfrapPerfArpTotalTxInarpReq    OBJECT-TYPE
             SYNTAX      Counter
             ACCESS      read-only
             STATUS      mandatory
             DESCRIPTION
                "The number of INARP request bytes
                 that have been counted across all DLCIs."
            ::= { sfrapPerfArpTotalEntry 14 }

      sfrapPerfArpTotalRxInarpRep    OBJECT-TYPE
             SYNTAX      Counter
             ACCESS      read-only
             STATUS      mandatory
             DESCRIPTION
                "The number of INARP reply bytes
                 that have been counted across all DLCIs."
            ::= { sfrapPerfArpTotalEntry 15 }

      sfrapPerfArpTotalTxInarpRep    OBJECT-TYPE
             SYNTAX      Counter
             ACCESS      read-only
             STATUS      mandatory
             DESCRIPTION
                "The number of INARP reply bytes
                 that have been counted across all DLCIs."
            ::= { sfrapPerfArpTotalEntry 16 }

      sfrapPerfArpTotalRxOther    OBJECT-TYPE
             SYNTAX      Counter
             ACCESS      read-only
             STATUS      mandatory
             DESCRIPTION
                "The number of received bytes across all DLCIs
                 from ARP message types that are not counted
                 elsewhere in this table."
            ::= { sfrapPerfArpTotalEntry 17 }

      sfrapPerfArpTotalTxOther    OBJECT-TYPE
             SYNTAX      Counter
             ACCESS      read-only
             STATUS      mandatory
             DESCRIPTION
                "The number of transmitted bytes across all DLCIs
                 from ARP message types that are not counted
                 elsewhere in this table."
            ::= { sfrapPerfArpTotalEntry 18 }



   --  LMI Statistics for each DLCI.

   sfrapPerfLmiPerDlciTable OBJECT-TYPE
         SYNTAX   SEQUENCE OF  SfrapPerfLmiPerDlciEntry
         ACCESS   not-accessible
         STATUS   mandatory
         DESCRIPTION
            "Short Term Statistics on LMI protocol for each DLCI."
         ::= { sfrapPerfNetworkShortTerm  17 }

         sfrapPerfLmiPerDlciEntry OBJECT-TYPE
             SYNTAX   SfrapPerfLmiPerDlciEntry
             ACCESS   not-accessible
             STATUS   mandatory
             DESCRIPTION
                "The LMI Short Term Statistics for a particular DLCI."
             INDEX { sfrapPerfLmiPerDlciInterval, sfrapPerfLmiPerDlciValue }
             ::= { sfrapPerfLmiPerDlciTable 1 }

         SfrapPerfLmiPerDlciEntry ::=
             SEQUENCE {
                 sfrapPerfLmiPerDlciInterval            INTEGER,
                 sfrapPerfLmiPerDlciValue               INTEGER,
                 sfrapPerfLmiPerDlciRxTotalByteCnt      Counter,
                 sfrapPerfLmiPerDlciTxTotalByteCnt      Counter,
                 sfrapPerfLmiPerDlciRxLivoEnqByteCnt    Counter,
                 sfrapPerfLmiPerDlciTxLivoEnqByteCnt    Counter,
                 sfrapPerfLmiPerDlciRxLivoStatByteCnt   Counter,
                 sfrapPerfLmiPerDlciTxLivoStatByteCnt   Counter,
                 sfrapPerfLmiPerDlciRxFullEnqByteCnt    Counter,
                 sfrapPerfLmiPerDlciTxFullEnqByteCnt    Counter,
                 sfrapPerfLmiPerDlciRxFullStatByteCnt   Counter,
                 sfrapPerfLmiPerDlciTxFullStatByteCnt   Counter,
                 sfrapPerfLmiPerDlciRxOtherByteCnt      Counter,
                 sfrapPerfLmiPerDlciTxOtherByteCnt      Counter
            }

      sfrapPerfLmiPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfLmiPerDlciEntry 1 }

      sfrapPerfLmiPerDlciValue    OBJECT-TYPE
             SYNTAX      INTEGER 
             ACCESS      read-only
             STATUS      mandatory
             DESCRIPTION
                "The DLCI value with which the Statistics are associated."
            ::= { sfrapPerfLmiPerDlciEntry 2 }

      sfrapPerfLmiPerDlciRxTotalByteCnt    OBJECT-TYPE
             SYNTAX      Counter 
             ACCESS      read-only
             STATUS      mandatory
             DESCRIPTION
                "The total number of received LMI bytes
                 counted on this DLCI."
            ::= { sfrapPerfLmiPerDlciEntry 3 }

      sfrapPerfLmiPerDlciTxTotalByteCnt    OBJECT-TYPE
             SYNTAX      Counter 
             ACCESS      read-only
             STATUS      mandatory
             DESCRIPTION
                "The total number of transmitted LMI bytes
                 counted on this DLCI."
            ::= { sfrapPerfLmiPerDlciEntry 4 }

      sfrapPerfLmiPerDlciRxLivoEnqByteCnt    OBJECT-TYPE
             SYNTAX      Counter  
             ACCESS      read-only
             STATUS      mandatory
             DESCRIPTION
                "The number of bytes received in Link Integrity
                 Verification Only (LIVO) enquiries on this DLCI."
            ::= { sfrapPerfLmiPerDlciEntry 5 }

      sfrapPerfLmiPerDlciTxLivoEnqByteCnt    OBJECT-TYPE
             SYNTAX      Counter  
             ACCESS      read-only
             STATUS      mandatory
             DESCRIPTION
                "The number of bytes transmitted in Link Integrity
                 Verification Only (LIVO) enquiries on this DLCI."
            ::= { sfrapPerfLmiPerDlciEntry 6 }

      sfrapPerfLmiPerDlciRxLivoStatByteCnt    OBJECT-TYPE
             SYNTAX      Counter  
             ACCESS      read-only
             STATUS      mandatory
             DESCRIPTION
                "The number of bytes received in Link Integrity
                 Verification Only (LIVO) statuses on this DLCI."
            ::= { sfrapPerfLmiPerDlciEntry 7 }

      sfrapPerfLmiPerDlciTxLivoStatByteCnt    OBJECT-TYPE
             SYNTAX      Counter  
             ACCESS      read-only
             STATUS      mandatory
             DESCRIPTION
                "The number of bytes transmitted in Link Integrity
                 Verification Only (LIVO) statuses on this DLCI."
            ::= { sfrapPerfLmiPerDlciEntry 8 }

      sfrapPerfLmiPerDlciRxFullEnqByteCnt    OBJECT-TYPE
             SYNTAX      Counter  
             ACCESS      read-only
             STATUS      mandatory
             DESCRIPTION
                "The number of bytes received in 
                 Full Status enquiries on this DLCI."
            ::= { sfrapPerfLmiPerDlciEntry 9 }

      sfrapPerfLmiPerDlciTxFullEnqByteCnt    OBJECT-TYPE
             SYNTAX      Counter  
             ACCESS      read-only
             STATUS      mandatory
             DESCRIPTION
                "The number of bytes transmitted in 
                 Full Status enquiries on this DLCI."
            ::= { sfrapPerfLmiPerDlciEntry 10 }

      sfrapPerfLmiPerDlciRxFullStatByteCnt    OBJECT-TYPE
             SYNTAX      Counter  
             ACCESS      read-only
             STATUS      mandatory
             DESCRIPTION
                "The number of bytes received in 
                 Full Status messages on this DLCI."
            ::= { sfrapPerfLmiPerDlciEntry 11 }

      sfrapPerfLmiPerDlciTxFullStatByteCnt    OBJECT-TYPE
             SYNTAX      Counter  
             ACCESS      read-only
             STATUS      mandatory
             DESCRIPTION
                "The number of bytes transmitted in 
                 Full Status messages on this DLCI."
            ::= { sfrapPerfLmiPerDlciEntry 12 }

      sfrapPerfLmiPerDlciRxOtherByteCnt    OBJECT-TYPE
             SYNTAX      Counter  
             ACCESS      read-only
             STATUS      mandatory
             DESCRIPTION
                "The number of received bytes on this DLCI
                 from LMI protocols that are not counted
                 elsewhere (other than Total) in this table."
            ::= { sfrapPerfLmiPerDlciEntry 13 }

      sfrapPerfLmiPerDlciTxOtherByteCnt    OBJECT-TYPE
             SYNTAX      Counter  
             ACCESS      read-only
             STATUS      mandatory
             DESCRIPTION
                "The number of transmitted bytes on this DLCI
                 from LMI protocols that are not counted
                 elsewhere (other than Total) in this table."
            ::= { sfrapPerfLmiPerDlciEntry 14 }


   --  LMI Statistics for totals.

   sfrapPerfLmiTotalTable OBJECT-TYPE
         SYNTAX   SEQUENCE OF SfrapPerfLmiTotalEntry
         ACCESS   not-accessible
         STATUS   mandatory
         DESCRIPTION
            "Short Term Statistics on LMI protocol across all DLCIs."
         ::= { sfrapPerfNetworkShortTerm 18 }

         sfrapPerfLmiTotalEntry OBJECT-TYPE
             SYNTAX   SfrapPerfLmiTotalEntry
             ACCESS   not-accessible
             STATUS   mandatory
             DESCRIPTION
                "The LMI Short Term Statistics across all DLCIs."
             INDEX { sfrapPerfLmiTotalInterval }
             ::= { sfrapPerfLmiTotalTable 1 }

         SfrapPerfLmiTotalEntry ::=
             SEQUENCE {
                 sfrapPerfLmiTotalInterval            INTEGER,
                 sfrapPerfLmiTotalDlciValue           INTEGER,
                 sfrapPerfLmiTotalRxTotalByteCnt      Counter,
                 sfrapPerfLmiTotalTxTotalByteCnt      Counter,
                 sfrapPerfLmiTotalRxLivoEnqByteCnt    Counter,
                 sfrapPerfLmiTotalTxLivoEnqByteCnt    Counter,
                 sfrapPerfLmiTotalRxLivoStatByteCnt   Counter,
                 sfrapPerfLmiTotalTxLivoStatByteCnt   Counter,
                 sfrapPerfLmiTotalRxFullEnqByteCnt    Counter,
                 sfrapPerfLmiTotalTxFullEnqByteCnt    Counter,
                 sfrapPerfLmiTotalRxFullStatByteCnt   Counter,
                 sfrapPerfLmiTotalTxFullStatByteCnt   Counter,
                 sfrapPerfLmiTotalRxOtherByteCnt      Counter,
                 sfrapPerfLmiTotalTxOtherByteCnt      Counter
            }

      sfrapPerfLmiTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfLmiTotalEntry 1 }

      sfrapPerfLmiTotalDlciValue    OBJECT-TYPE
             SYNTAX      INTEGER 
             ACCESS      read-only
             STATUS      mandatory
             DESCRIPTION
                "OBSOLETE."
            ::= { sfrapPerfLmiTotalEntry 2 }

      sfrapPerfLmiTotalRxTotalByteCnt    OBJECT-TYPE
             SYNTAX      Counter  
             ACCESS      read-only
             STATUS      mandatory
             DESCRIPTION
                "The total number of received LMI bytes
                 counted across all DLCIs."
            ::= { sfrapPerfLmiTotalEntry 3 }

      sfrapPerfLmiTotalTxTotalByteCnt    OBJECT-TYPE
             SYNTAX      Counter  
             ACCESS      read-only
             STATUS      mandatory
             DESCRIPTION
                "The total number of transmitted LMI bytes
                 counted across all DLCIs."
            ::= { sfrapPerfLmiTotalEntry 4 }

      sfrapPerfLmiTotalRxLivoEnqByteCnt    OBJECT-TYPE
             SYNTAX      Counter  
             ACCESS      read-only
             STATUS      mandatory
             DESCRIPTION
                "The number of bytes received in Link Integrity
                 Verification Only (LIVO) enquiries across all DLCIs."
            ::= { sfrapPerfLmiTotalEntry 5 }

      sfrapPerfLmiTotalTxLivoEnqByteCnt    OBJECT-TYPE
             SYNTAX      Counter  
             ACCESS      read-only
             STATUS      mandatory
             DESCRIPTION
                "The number of bytes transmitted in Link Integrity
                 Verification Only (LIVO) enquiries across all DLCIs."
            ::= { sfrapPerfLmiTotalEntry 6 }

      sfrapPerfLmiTotalRxLivoStatByteCnt    OBJECT-TYPE
             SYNTAX      Counter  
             ACCESS      read-only
             STATUS      mandatory
             DESCRIPTION
                "The number of bytes received in Link Integrity
                 Verification Only (LIVO) enquiries across all DLCIs."
            ::= { sfrapPerfLmiTotalEntry 7 }

      sfrapPerfLmiTotalTxLivoStatByteCnt    OBJECT-TYPE
             SYNTAX      Counter  
             ACCESS      read-only
             STATUS      mandatory
             DESCRIPTION
                "The number of bytes transmitted in Link Integrity
                 Verification Only (LIVO) enquiries across all DLCIs."
            ::= { sfrapPerfLmiTotalEntry 8 }

      sfrapPerfLmiTotalRxFullEnqByteCnt    OBJECT-TYPE
             SYNTAX      Counter  
             ACCESS      read-only
             STATUS      mandatory
             DESCRIPTION
                "The number of bytes received in 
                 Full Status enquiries across all DLCIs."
            ::= { sfrapPerfLmiTotalEntry 9 }

      sfrapPerfLmiTotalTxFullEnqByteCnt    OBJECT-TYPE
             SYNTAX      Counter  
             ACCESS      read-only
             STATUS      mandatory
             DESCRIPTION
                "The number of bytes transmitted in 
                 Full Status enquiries across all DLCIs."
            ::= { sfrapPerfLmiTotalEntry 10 }

      sfrapPerfLmiTotalRxFullStatByteCnt    OBJECT-TYPE
             SYNTAX      Counter  
             ACCESS      read-only
             STATUS      mandatory
             DESCRIPTION
                "The number of bytes received in 
                 Full Status messages across all DLCIs."
            ::= { sfrapPerfLmiTotalEntry 11 }

      sfrapPerfLmiTotalTxFullStatByteCnt    OBJECT-TYPE
             SYNTAX      Counter  
             ACCESS      read-only
             STATUS      mandatory
             DESCRIPTION
                "The number of bytes transmitted in 
                 Full Status messages across all DLCIs."
            ::= { sfrapPerfLmiTotalEntry 12 }

      sfrapPerfLmiTotalRxOtherByteCnt    OBJECT-TYPE
             SYNTAX      Counter  
             ACCESS      read-only
             STATUS      mandatory
             DESCRIPTION
                "The number of received bytes across all DLCIs
                 from LMI protocols that are not counted
                 elsewhere (other than Total) in this table."
            ::= { sfrapPerfLmiTotalEntry 13 }

      sfrapPerfLmiTotalTxOtherByteCnt   OBJECT-TYPE
             SYNTAX      Counter  
             ACCESS      read-only
             STATUS      mandatory
             DESCRIPTION
                "The number of transmitted bytes across all DLCIs
                 from LMI protocols that are not counted
                 elsewhere (other than Total) in this table."
            ::= { sfrapPerfLmiTotalEntry 14 }


sfrapPerfNetworkLongTerm OBJECT IDENTIFIER ::= { sfrapPerformance 5 }

--
--       Long Term Statistics by DLCI, protocol, and interval.
--

   sfrapPerfNetwLongTermTable OBJECT-TYPE
         SYNTAX   SEQUENCE OF SfrapPerfNetwLongTermEntry
         ACCESS   not-accessible
         STATUS   mandatory
         DESCRIPTION
            "Long Term Statistics by DLCI, protocol, and interval.
             LT statistics are collected on a configurable set
             of DLCIs and protocols. There are 96 intervals maintained
             each with a duration defined by the Long Term Timer. 
             Interval 96 is the current window and Interval 1 is 
             furthest back in time (96xLT Timer seconds ago)."
         ::= { sfrapPerfNetworkLongTerm 1 }

         sfrapPerfNetwLongTermEntry OBJECT-TYPE
             SYNTAX   SfrapPerfNetwLongTermEntry
             ACCESS   not-accessible
             STATUS   mandatory
             DESCRIPTION
                "The Long Term Statistic for a particular DLCI,
                 protocol and interval."
            INDEX { sfrapPerfNetwLongTermDlci,
                    sfrapPerfNetwLongTermProtocol,
                    sfrapPerfNetwLongTermInterval }
            ::= { sfrapPerfNetwLongTermTable 1 }

         SfrapPerfNetwLongTermEntry ::=
             SEQUENCE {
                 sfrapPerfNetwLongTermDlci      INTEGER,
                 sfrapPerfNetwLongTermProtocol  INTEGER,
                 sfrapPerfNetwLongTermInterval  INTEGER,
                 sfrapPerfNetwLongTermValue     Counter
             }

         sfrapPerfNetwLongTermDlci    OBJECT-TYPE
             SYNTAX      INTEGER 
             ACCESS      read-only
             STATUS      mandatory
             DESCRIPTION
               "The DLCI monitored for the statistics. The Long
                Term DLCI filter must first be configured 
                (CfgFrPerfLTDlciFilterEntry)."
            ::= { sfrapPerfNetwLongTermEntry 1 }

         sfrapPerfNetwLongTermProtocol    OBJECT-TYPE
            SYNTAX      INTEGER
            {
               ip-tx-bc                    (1),
               ip-rx-bc                    (2),
               tcp-ip-tx-bc                (3),
               tcp-ip-rx-bc                (4),
               ftp-tcp-ip-tx-bc            (5),
               ftp-tcp-ip-rx-bc            (6),
               telnet-tcp-ip-tx-bc         (7),
               telnet-tcp-ip-rx-bc         (8),
               smtp-tcp-ip-tx-bc           (9),
               smtp-tcp-ip-rx-bc           (10),
--             tftp-tcp-ip-tx-bc           (11),
--             tftp-tcp-ip-rx-bc           (12),
               http-tcp-ip-tx-bc           (13),
               http-tcp-ip-rx-bc           (14),
               netbios-ssn-tcp-ip-tx-bc    (15),
               netbios-ssn-tcp-ip-rx-bc    (16),
--             snmp-tcp-ip-tx-bc           (17),
--             snmp-tcp-ip-rx-bc           (18),
--             snmptrap-tcp-ip-tx-bc       (19),
--             snmptrap-tcp-ip-rx-bc       (20),
               udp-ip-tx-bc                (21),
               udp-ip-rx-bc                (22),
--             ftp-udp-ip-tx-bc            (23),
--             ftp-udp-ip-rx-bc            (24),
--             telnet-udp-ip-tx-bc         (25),
--             telnet-udp-ip-rx-bc         (26),
--             smtp-udp-ip-tx-bc           (27),
--             smtp-udp-ip-rx-bc           (28),
               tftp-udp-ip-tx-bc           (29),
               tftp-udp-ip-rx-bc           (30),
--             http-udp-ip-tx-bc           (31),
--             http-udp-ip-rx-bc           (32),
               netbios-dgm-udp-ip-tx-bc    (33),
               netbios-dgm-udp-ip-rx-bc    (34),
               snmp-udp-ip-tx-bc           (35),
               snmp-udp-ip-rx-bc           (36),
               snmptrap-udp-ip-tx-bc       (37),
               snmptrap-udp-ip-rx-bc       (38),
               rip-udp-ip-tx-bc            (39),
               rip-udp-ip-rx-bc            (40),
               icmp-ip-tx-bc               (41),
               icmp-ip-rx-bc               (42),
               echorep-icmp-ip-tx-bc       (43),
               echorep-icmp-ip-rx-bc       (44),
               dest-unr-icmp-ip-tx-bc      (45),
               dest-unr-icmp-ip-rx-bc      (46),
               src-quench-icmp-ip-tx-bc    (47),
               src-quench-icmp-ip-rx-bc    (48),
               redirect-icmp-ip-tx-bc      (49),
               redirect-icmp-ip-rx-bc      (50),
               echoreq-icmp-ip-tx-bc       (51),
               echoreq-icmp-ip-rx-bc       (52),
               time-excd-icmp-ip-tx-bc     (53),
               time-excd-icmp-ip-rx-bc     (54),
               param-prob-icmp-ip-tx-bc    (55),
               param-prob-icmp-ip-rx-bc    (56),
               timestamp-req-icmp-ip-tx-bc (57),
               timestamp-req-icmp-ip-rx-bc (58),
               timestamp-rep-icmp-ip-tx-bc (59),
               timestamp-rep-icmp-ip-rx-bc (60),
               addr-mask-req-icmp-ip-tx-bc (61),
               addr-mask-req-icmp-ip-rx-bc (62),
               addr-mask-rep-icmp-ip-tx-bc (63),
               addr-mask-rep-icmp-ip-rx-bc (64),
               pkt-too-big-icmp-ip-tx-bc   (65),
               pkt-too-big-icmp-ip-rx-bc   (66),
               gp-mem-query-icmp-ip-tx-bc  (67),
               gp-mem-query-icmp-ip-rx-bc  (68),
               gp-mem-report-icmp-ip-tx-bc (69),
               gp-mem-report-icmp-ip-rx-bc (70),
               gp-mem-reduct-icmp-ip-tx-bc (71),
               gp-mem-reduct-icmp-ip-rx-bc (72),
               ospf-ip-tx-bc               (73),
               ospf-ip-rx-bc               (74),
               other-ip-tx-bc              (75),
               other-ip-rx-bc              (76),
               ipx-tx-bc                   (77),
               ipx-rx-bc                   (78),
               spx-ipx-tx-bc               (79),
               spx-ipx-rx-bc               (80),
               ncp-ipx-tx-bc               (81),
               ncp-ipx-rx-bc               (82),
               sap-ipx-tx-bc               (83),
               sap-ipx-rx-bc               (84),
               rip-ipx-tx-bc               (85),
               rip-ipx-rx-bc               (86),
               netbios-ipx-tx-bc           (87),
               netbios-ipx-rx-bc           (88),
               other-ipx-tx-bc             (89),
               other-ipx-rx-bc             (90),
               arp-tx-bc                   (91),
               arp-rx-bc                   (92),
               arp-req-tx-bc               (93),
               arp-req-rx-bc               (94),
               arp-rep-tx-bc               (95),
               arp-rep-rx-bc               (96),
               rarp-req-tx-bc              (97),
               rarp-req-rx-bc              (98),
               rarp-rep-tx-bc              (99),
               rarp-rep-rx-bc              (100),
               inarp-req-tx-bc             (101),
               inarp-req-rx-bc             (102),
               inarp-rep-tx-bc             (103),
               inarp-rep-rx-bc             (104),
               sna-tx-bc                   (105),
               sna-rx-bc                   (106),
               sna-subarea-tx-bc           (107),
               sna-subarea-rx-bc           (108),
               sna-periph-tx-bc            (109),
               sna-periph-rx-bc            (110),
               sna-appn-tx-bc              (111),
               sna-appn-rx-bc              (112),
               sna-netbios-tx-bc           (113),
               sna-netbios-rx-bc           (114),
               cisco-tx-bc                 (115),
               cisco-rx-bc                 (116),
               other-tx-bc                 (117),
               other-rx-bc                 (118),
               user-defined-1-tx-bc        (119),
               user-defined-1-rx-bc        (120),
               user-defined-2-tx-bc        (121),
               user-defined-2-rx-bc        (122),
               user-defined-3-tx-bc        (123),
               user-defined-3-rx-bc        (124),
               user-defined-4-tx-bc        (125),
               user-defined-4-rx-bc        (126),
               thru-byte-tx-bc             (127),
               thru-byte-rx-bc             (128),
               thru-frame-tx-c             (129),
               thru-frame-rx-c             (130),
               thru-fecn-tx-c              (131),
               thru-fecn-rx-c              (132),
               thru-becn-tx-c              (133),
               thru-becn-rx-c              (134),
               thru-de-tx-c                (135),
               thru-de-rx-c                (136),
             
               cir-percent-range1-tx-bc    (137),
               cir-percent-range1-rx-bc    (138),
               cir-percent-range2-tx-bc    (139),
               cir-percent-range2-rx-bc    (140),
               cir-percent-range3-tx-bc    (141),
               cir-percent-range3-rx-bc    (142),
               cir-percent-range4-tx-bc    (143),
               cir-percent-range4-rx-bc    (144),
               cir-percent-range5-tx-bc    (145),
               cir-percent-range5-rx-bc    (146),
               cir-percent-range6-tx-bc    (147),
               cir-percent-range6-rx-bc    (148),
               cir-percent-range7-tx-bc    (149),
               cir-percent-range7-rx-bc    (150),
               cir-percent-range8-tx-bc    (151),
               cir-percent-range8-rx-bc    (152),
               lmi-tx-bc                   (153),
               lmi-rx-bc                   (154),
               lmi-livo-enq-tx-bc          (155),
               lmi-livo-enq-rx-bc          (156),
               lmi-livo-stat-tx-bc         (157),
               lmi-livo-stat-rx-bc         (158),
               lmi-full-enq-tx-bc          (159),
               lmi-full-enq-rx-bc          (160),
               lmi-full-stat-tx-bc         (161),
               lmi-full-stat-rx-bc         (162),
               lmi-other-tx-bc             (163),
               lmi-other-rx-bc             (164),
               total-uptime                (165),
               total-downtime              (166),
               igrp-tx-bc                  (167),
               igrp-rx-bc                  (168),
               vnip-tx-bc                  (169),
               vnip-rx-bc                  (170),
               annex-g-tx-bc               (171),
               annex-g-rx-bc               (172)
            }
            ACCESS      read-only
            STATUS      mandatory
            DESCRIPTION
             "The type of protocol monitored for the statistics."
            ::= { sfrapPerfNetwLongTermEntry 2 }

         sfrapPerfNetwLongTermInterval    OBJECT-TYPE
             SYNTAX      INTEGER 
             ACCESS      read-only
             STATUS      mandatory
             DESCRIPTION
                "The time interval in which the value was collected.
                 Long Term statistis are maintained for 96 intervals 
                 with the interval duration defined by 
                 (CfgFrPerfTimersLTInterval)."
            ::= { sfrapPerfNetwLongTermEntry 3 }

         sfrapPerfNetwLongTermValue    OBJECT-TYPE
             SYNTAX      Counter
             ACCESS      read-only
             STATUS      mandatory
             DESCRIPTION
                "The statistic collected for the given DLCI and protocol
                 and within the given time interval."
            ::= { sfrapPerfNetwLongTermEntry 4 }


--
--       Long Term Statistics by DLCI: alternative method.
--

   sfrapPerfNetwLongTermAltTable OBJECT-TYPE
         SYNTAX   SEQUENCE OF SfrapPerfNetwLongTermAltEntry
         ACCESS   not-accessible
         STATUS   mandatory
         DESCRIPTION
            "This is an alternative method to access the database of
             long term statistics.  The statistics are indexed by DLCI
             and protocol and are returned in an OCTETSTRING."
         ::= { sfrapPerfNetworkLongTerm 2 }

         sfrapPerfNetwLongTermAltEntry   OBJECT-TYPE
             SYNTAX   SfrapPerfNetwLongTermAltEntry
             ACCESS   not-accessible
             STATUS   mandatory
             DESCRIPTION
                "The Long Term Statistic for a particular
                 DLCI and protocol."
            INDEX { sfrapPerfNetwLongTermAltDlci,
                    sfrapPerfNetwLongTermAltProtocol }
            ::= { sfrapPerfNetwLongTermAltTable 1 }

         SfrapPerfNetwLongTermAltEntry ::=
             SEQUENCE {
                 sfrapPerfNetwLongTermAltDlci      INTEGER,
                 sfrapPerfNetwLongTermAltProtocol  INTEGER,
                 sfrapPerfNetwLongTermAltArray     OCTET STRING
             }

         sfrapPerfNetwLongTermAltDlci    OBJECT-TYPE
             SYNTAX      INTEGER 
             ACCESS      read-only
             STATUS      mandatory
             DESCRIPTION
               "The DLCI monitored for the statistics."
            ::= { sfrapPerfNetwLongTermAltEntry 1 }

         sfrapPerfNetwLongTermAltProtocol   OBJECT-TYPE
             SYNTAX      INTEGER 
             {
                  ip-tx-bc                    (1),
                  ip-rx-bc                    (2),
                  tcp-ip-tx-bc                (3),
                  tcp-ip-rx-bc                (4),
                  ftp-tcp-ip-tx-bc            (5),
                  ftp-tcp-ip-rx-bc            (6),
                  telnet-tcp-ip-tx-bc         (7),
                  telnet-tcp-ip-rx-bc         (8),
                  smtp-tcp-ip-tx-bc           (9),
                  smtp-tcp-ip-rx-bc           (10),
--                tftp-tcp-ip-tx-bc           (11),
--                tftp-tcp-ip-rx-bc           (12),
                  http-tcp-ip-tx-bc           (13),
                  http-tcp-ip-rx-bc           (14),
                  netbios-ssn-tcp-ip-tx-bc    (15),
                  netbios-ssn-tcp-ip-rx-bc    (16),
--                snmp-tcp-ip-tx-bc           (17),
--                snmp-tcp-ip-rx-bc           (18),
--                snmptrap-tcp-ip-tx-bc       (19),
--                snmptrap-tcp-ip-rx-bc       (20),
                  udp-ip-tx-bc                (21),
                  udp-ip-rx-bc                (22),
--                ftp-udp-ip-tx-bc            (23),
--                ftp-udp-ip-rx-bc            (24),
--                telnet-udp-ip-tx-bc         (25),
--                telnet-udp-ip-rx-bc         (26),
--                smtp-udp-ip-tx-bc           (27),
--                smtp-udp-ip-rx-bc           (28),
                  tftp-udp-ip-tx-bc           (29),
                  tftp-udp-ip-rx-bc           (30),
--                http-udp-ip-tx-bc           (31),
--                http-udp-ip-rx-bc           (32),
                  netbios-dgm-udp-ip-tx-bc    (33),
                  netbios-dgm-udp-ip-rx-bc    (34),
                  snmp-udp-ip-tx-bc           (35),
                  snmp-udp-ip-rx-bc           (36),
                  snmptrap-udp-ip-tx-bc       (37),
                  snmptrap-udp-ip-rx-bc       (38),
                  rip-udp-ip-tx-bc            (39),
                  rip-udp-ip-rx-bc            (40),
                  icmp-ip-tx-bc               (41),
                  icmp-ip-rx-bc               (42),
                  echorep-icmp-ip-tx-bc       (43),
                  echorep-icmp-ip-rx-bc       (44),
                  dest-unr-icmp-ip-tx-bc      (45),
                  dest-unr-icmp-ip-rx-bc      (46),
                  src-quench-icmp-ip-tx-bc    (47),
                  src-quench-icmp-ip-rx-bc    (48),
                  redirect-icmp-ip-tx-bc      (49),
                  redirect-icmp-ip-rx-bc      (50),
                  echoreq-icmp-ip-tx-bc       (51),
                  echoreq-icmp-ip-rx-bc       (52),
                  time-excd-icmp-ip-tx-bc     (53),
                  time-excd-icmp-ip-rx-bc     (54),
                  param-prob-icmp-ip-tx-bc    (55),
                  param-prob-icmp-ip-rx-bc    (56),
                  timestamp-req-icmp-ip-tx-bc (57),
                  timestamp-req-icmp-ip-rx-bc (58),
                  timestamp-rep-icmp-ip-tx-bc (59),
                  timestamp-rep-icmp-ip-rx-bc (60),
                  addr-mask-req-icmp-ip-tx-bc (61),
                  addr-mask-req-icmp-ip-rx-bc (62),
                  addr-mask-rep-icmp-ip-tx-bc (63),
                  addr-mask-rep-icmp-ip-rx-bc (64),
                  pkt-too-big-icmp-ip-tx-bc   (65),
                  pkt-too-big-icmp-ip-rx-bc   (66),
                  gp-mem-query-icmp-ip-tx-bc  (67),
                  gp-mem-query-icmp-ip-rx-bc  (68),
                  gp-mem-report-icmp-ip-tx-bc (69),
                  gp-mem-report-icmp-ip-rx-bc (70),
                  gp-mem-reduct-icmp-ip-tx-bc (71),
                  gp-mem-reduct-icmp-ip-rx-bc (72),
                  ospf-ip-tx-bc               (73),
                  ospf-ip-rx-bc               (74),
                  other-ip-tx-bc              (75),
                  other-ip-rx-bc              (76),
                  ipx-tx-bc                   (77),
                  ipx-rx-bc                   (78),
                  spx-ipx-tx-bc               (79),
                  spx-ipx-rx-bc               (80),
                  ncp-ipx-tx-bc               (81),
                  ncp-ipx-rx-bc               (82),
                  sap-ipx-tx-bc               (83),
                  sap-ipx-rx-bc               (84),
                  rip-ipx-tx-bc               (85),
                  rip-ipx-rx-bc               (86),
                  netbios-ipx-tx-bc           (87),
                  netbios-ipx-rx-bc           (88),
                  other-ipx-tx-bc             (89),
                  other-ipx-rx-bc             (90),
                  arp-tx-bc                   (91),
                  arp-rx-bc                   (92),
                  arp-req-tx-bc               (93),
                  arp-req-rx-bc               (94),
                  arp-rep-tx-bc               (95),
                  arp-rep-rx-bc               (96),
                  rarp-req-tx-bc              (97),
                  rarp-req-rx-bc              (98),
                  rarp-rep-tx-bc              (99),
                  rarp-rep-rx-bc              (100),
                  inarp-req-tx-bc             (101),
                  inarp-req-rx-bc             (102),
                  inarp-rep-tx-bc             (103),
                  inarp-rep-rx-bc             (104),
                  sna-tx-bc                   (105),
                  sna-rx-bc                   (106),
                  sna-subarea-tx-bc           (107),
                  sna-subarea-rx-bc           (108),
                  sna-periph-tx-bc            (109),
                  sna-periph-rx-bc            (110),
                  sna-appn-tx-bc              (111),
                  sna-appn-rx-bc              (112),
                  sna-netbios-tx-bc           (113),
                  sna-netbios-rx-bc           (114),
                  cisco-tx-bc                 (115),
                  cisco-rx-bc                 (116),
                  other-tx-bc                 (117),
                  other-rx-bc                 (118),
                  user-defined-1-tx-bc        (119),
                  user-defined-1-rx-bc        (120),
                  user-defined-2-tx-bc        (121),
                  user-defined-2-rx-bc        (122),
                  user-defined-3-tx-bc        (123),
                  user-defined-3-rx-bc        (124),
                  user-defined-4-tx-bc        (125),
                  user-defined-4-rx-bc        (126),
                  thru-byte-tx-bc             (127),
                  thru-byte-rx-bc             (128),
                  thru-frame-tx-c             (129),
                  thru-frame-rx-c             (130),
                  thru-fecn-tx-c              (131),
                  thru-fecn-rx-c              (132),
                  thru-becn-tx-c              (133),
                  thru-becn-rx-c              (134),
                  thru-de-tx-c                (135),
                  thru-de-rx-c                (136),
            
                  cir-percent-range1-tx-bc    (137),
                  cir-percent-range1-rx-bc    (138),
                  cir-percent-range2-tx-bc    (139),
                  cir-percent-range2-rx-bc    (140),
                  cir-percent-range3-tx-bc    (141),
                  cir-percent-range3-rx-bc    (142),
                  cir-percent-range4-tx-bc    (143),
                  cir-percent-range4-rx-bc    (144),
                  cir-percent-range5-tx-bc    (145),
                  cir-percent-range5-rx-bc    (146),
                  cir-percent-range6-tx-bc    (147),
                  cir-percent-range6-rx-bc    (148),
                  cir-percent-range7-tx-bc    (149),
                  cir-percent-range7-rx-bc    (150),
                  cir-percent-range8-tx-bc    (151),
                  cir-percent-range8-rx-bc    (152),
                  lmi-tx-bc                   (153),
                  lmi-rx-bc                   (154),
                  lmi-livo-enq-tx-bc          (155),
                  lmi-livo-enq-rx-bc          (156),
                  lmi-livo-stat-tx-bc         (157),
                  lmi-livo-stat-rx-bc         (158),
                  lmi-full-enq-tx-bc          (159),
                  lmi-full-enq-rx-bc          (160),
                  lmi-full-stat-tx-bc         (161),
                  lmi-full-stat-rx-bc         (162),
                  lmi-other-tx-bc             (163),
                  lmi-other-rx-bc             (164),
                  total-uptime                (165),
                  total-downtime              (166),
                  igrp-tx-bc                  (167),
                  igrp-rx-bc                  (168),
                  vnip-tx-bc                  (169),
                  vnip-rx-bc                  (170),
                  annex-g-tx-bc               (171),
                  annex-g-rx-bc               (172)
             }
             ACCESS      read-only
             STATUS      mandatory
             DESCRIPTION
               "The protocol monitored for the statistics."
            ::= { sfrapPerfNetwLongTermAltEntry 2 }
      
         sfrapPerfNetwLongTermAltArray    OBJECT-TYPE
             SYNTAX      OCTET STRING
             ACCESS      read-only
             STATUS      mandatory
             DESCRIPTION
                "The statistic collected for the given DLCI and protocol."
            ::= { sfrapPerfNetwLongTermAltEntry 3 }


   sfrapPerfNetworkLongTermCommands OBJECT IDENTIFIER
            ::= { sfrapPerfNetworkLongTerm 3 }

   sfrapPerfNetworkLongTermCmdClear    OBJECT-TYPE
          SYNTAX      INTEGER
          {
              clear-statistics (1)
          }
          ACCESS      write-only
          STATUS      mandatory
          DESCRIPTION
             "Allows the user to zero out all the statistics in
              the long term statistics tables.
              (1) Clear all Long Term statistics"
          ::= { sfrapPerfNetworkLongTermCommands 1 }
          
sfrapPerfCirPercentUtilization OBJECT IDENTIFIER ::= { sfrapPerformance 6 }

--
--  CIR Percentage Statistics for each DLCI.
--

 sfrapPerfCirPercentUtilizationTable OBJECT-TYPE
         SYNTAX   SEQUENCE OF SfrapPerfCirPercentUtilizationEntry
         ACCESS   not-accessible
         STATUS   mandatory
         DESCRIPTION
            "Short Term Statistics on the percentage of CIR used
             on each DLCI.  Each short term statistics interval,
             the count of bytes transmitted and received is used
             to calculate the percentage of CIR used.  The byte
             count is then added to the appropriate bucket for
             the CIR percentage range."
         ::= { sfrapPerfCirPercentUtilization 1 }

 sfrapPerfCirPercentUtilizationEntry OBJECT-TYPE
             SYNTAX   SfrapPerfCirPercentUtilizationEntry
             ACCESS   not-accessible
             STATUS   mandatory
             DESCRIPTION
                "The CIR Percentage Statistics for a particular DLCI.
                 These calculations are done at the completion of each 
                 Short Term interval."
             INDEX { sfrapPerfCirPercentUtilizationInterval,
                     sfrapPerfCirPercentUtilizationDlciValue }
             ::= { sfrapPerfCirPercentUtilizationTable 1 }

         SfrapPerfCirPercentUtilizationEntry ::=
             SEQUENCE {
                 sfrapPerfCirPercentUtilizationInterval    INTEGER,
                 sfrapPerfCirPercentUtilizationDlciValue   INTEGER,
                 sfrapPerfCirRxPercentUtilizationRange1    INTEGER,
                 sfrapPerfCirRxPercentUtilizationRange2    INTEGER,
                 sfrapPerfCirRxPercentUtilizationRange3    INTEGER,
                 sfrapPerfCirRxPercentUtilizationRange4    INTEGER,
                 sfrapPerfCirRxPercentUtilizationRange5    INTEGER,
                 sfrapPerfCirRxPercentUtilizationRange6    INTEGER,
                 sfrapPerfCirRxPercentUtilizationRange7    INTEGER,
                 sfrapPerfCirRxPercentUtilizationRange8    INTEGER,
                 sfrapPerfCirTxPercentUtilizationRange1    INTEGER,
                 sfrapPerfCirTxPercentUtilizationRange2    INTEGER,
                 sfrapPerfCirTxPercentUtilizationRange3    INTEGER,
                 sfrapPerfCirTxPercentUtilizationRange4    INTEGER,
                 sfrapPerfCirTxPercentUtilizationRange5    INTEGER,
                 sfrapPerfCirTxPercentUtilizationRange6    INTEGER,
                 sfrapPerfCirTxPercentUtilizationRange7    INTEGER,
                 sfrapPerfCirTxPercentUtilizationRange8    INTEGER
            }

 sfrapPerfCirPercentUtilizationInterval OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { sfrapPerfCirPercentUtilizationEntry 1 }

 sfrapPerfCirPercentUtilizationDlciValue OBJECT-TYPE
             SYNTAX      INTEGER 
             ACCESS      read-only
             STATUS      mandatory
             DESCRIPTION
                "The DLCI value with which the Statistics are associated."
            ::= { sfrapPerfCirPercentUtilizationEntry 2 }

 sfrapPerfCirRxPercentUtilizationRange1 OBJECT-TYPE
             SYNTAX      INTEGER 
             ACCESS      read-only
             STATUS      mandatory
             DESCRIPTION
                "The number of short-term intervals during
                 which rx data throughput on this DLCI compared
                 to CIR was in range 1 (0% of CIR)."
            ::= { sfrapPerfCirPercentUtilizationEntry 21 }

 sfrapPerfCirRxPercentUtilizationRange2 OBJECT-TYPE
             SYNTAX      INTEGER 
             ACCESS      read-only
             STATUS      mandatory
             DESCRIPTION
                "The number of short-term intervals during
                 which rx data throughput on this DLCI compared
                 to CIR was in range 2 (1-10% of CIR)."
            ::= { sfrapPerfCirPercentUtilizationEntry 22 }

 sfrapPerfCirRxPercentUtilizationRange3 OBJECT-TYPE
             SYNTAX      INTEGER 
             ACCESS      read-only
             STATUS      mandatory
             DESCRIPTION
                "The number of short-term intervals during
                 which rx data throughput on this DLCI compared
                 to CIR was in range 3 (11-20% of CIR)."
            ::= { sfrapPerfCirPercentUtilizationEntry 23 }

 sfrapPerfCirRxPercentUtilizationRange4 OBJECT-TYPE
             SYNTAX      INTEGER 
             ACCESS      read-only
             STATUS      mandatory
             DESCRIPTION
                "The number of short-term intervals during
                 which rx data throughput on this DLCI compared
                 to CIR was in range 4 (21-50% of CIR)."
            ::= { sfrapPerfCirPercentUtilizationEntry 24 }

 sfrapPerfCirRxPercentUtilizationRange5 OBJECT-TYPE
             SYNTAX      INTEGER 
             ACCESS      read-only
             STATUS      mandatory
             DESCRIPTION
                "The number of short-term intervals during
                 which rx data throughput on this DLCI compared
                 to CIR was in range 5 (51-80% of CIR)."
            ::= { sfrapPerfCirPercentUtilizationEntry 25 }

 sfrapPerfCirRxPercentUtilizationRange6 OBJECT-TYPE
             SYNTAX      INTEGER 
             ACCESS      read-only
             STATUS      mandatory
             DESCRIPTION
                "The number of short-term intervals during
                 which rx data throughput on this DLCI compared
                 to CIR was in range 6 (81-100% of CIR)."
            ::= { sfrapPerfCirPercentUtilizationEntry 26 }

 sfrapPerfCirRxPercentUtilizationRange7 OBJECT-TYPE
             SYNTAX      INTEGER 
             ACCESS      read-only
             STATUS      mandatory
             DESCRIPTION
                "The number of short-term intervals during
                 which rx data throughput on this DLCI compared
                 to CIR was in range 7 (101-150% of CIR)."
            ::= { sfrapPerfCirPercentUtilizationEntry 27 }

 sfrapPerfCirRxPercentUtilizationRange8 OBJECT-TYPE
             SYNTAX      INTEGER 
             ACCESS      read-only
             STATUS      mandatory
             DESCRIPTION
                "The number of short-term intervals during
                 which rx data throughput on this DLCI compared
                 to CIR was in range 8 (> 150% of CIR)."
            ::= { sfrapPerfCirPercentUtilizationEntry 28 }

 sfrapPerfCirTxPercentUtilizationRange1 OBJECT-TYPE
             SYNTAX      INTEGER 
             ACCESS      read-only
             STATUS      mandatory
             DESCRIPTION
                "The number of short-term intervals during
                 which tx data throughput on this DLCI compared
                 to CIR was in range 1 (0% of CIR)."
            ::= { sfrapPerfCirPercentUtilizationEntry 41 }

 sfrapPerfCirTxPercentUtilizationRange2 OBJECT-TYPE
             SYNTAX      INTEGER 
             ACCESS      read-only
             STATUS      mandatory
             DESCRIPTION
                "The number of short-term intervals during
                 which tx data throughput on this DLCI compared
                 to CIR was in range 2 (1-10% of CIR)."
            ::= { sfrapPerfCirPercentUtilizationEntry 42 }

 sfrapPerfCirTxPercentUtilizationRange3 OBJECT-TYPE
             SYNTAX      INTEGER 
             ACCESS      read-only
             STATUS      mandatory
             DESCRIPTION
                "The number of short-term intervals during
                 which tx data throughput on this DLCI compared
                 to CIR was in range 3 (11-20% of CIR)."
            ::= { sfrapPerfCirPercentUtilizationEntry 43 }

 sfrapPerfCirTxPercentUtilizationRange4 OBJECT-TYPE
             SYNTAX      INTEGER 
             ACCESS      read-only
             STATUS      mandatory
             DESCRIPTION
                "The number of short-term intervals during
                 which tx data throughput on this DLCI compared
                 to CIR was in range 4 (21-50% of CIR)."
            ::= { sfrapPerfCirPercentUtilizationEntry 44 }

 sfrapPerfCirTxPercentUtilizationRange5 OBJECT-TYPE
             SYNTAX      INTEGER 
             ACCESS      read-only
             STATUS      mandatory
             DESCRIPTION
                "The number of short-term intervals during
                 which tx data throughput on this DLCI compared
                 to CIR was in range 5 (51-80% of CIR)."
            ::= { sfrapPerfCirPercentUtilizationEntry 45 }

 sfrapPerfCirTxPercentUtilizationRange6 OBJECT-TYPE
             SYNTAX      INTEGER 
             ACCESS      read-only
             STATUS      mandatory
             DESCRIPTION
                "The number of short-term intervals during
                 which tx data throughput on this DLCI compared
                 to CIR was in range 6 (81-100% o0f CIR)."
            ::= { sfrapPerfCirPercentUtilizationEntry 46 }

 sfrapPerfCirTxPercentUtilizationRange7 OBJECT-TYPE
             SYNTAX      INTEGER 
             ACCESS      read-only
             STATUS      mandatory
             DESCRIPTION
                "The number of short-term intervals during
                 which tx data throughput on this DLCI compared
                 to CIR was in range 7 (101-150% of CIR)."
            ::= { sfrapPerfCirPercentUtilizationEntry 47 }

 sfrapPerfCirTxPercentUtilizationRange8 OBJECT-TYPE
             SYNTAX      INTEGER 
             ACCESS      read-only
             STATUS      mandatory
             DESCRIPTION
                "The number of short-term intervals during
                 which tx data throughput on this DLCI compared
                 to CIR was in range 8 (> 150% of CIR)."
            ::= { sfrapPerfCirPercentUtilizationEntry 48 }


--
--  Current Utilization for each DLCI.
--

 sfrapPerfCurrentPerDlciUtilizationTable OBJECT-TYPE
         SYNTAX   SEQUENCE OF SfrapPerfCurrentPerDlciUtilizationEntry
         ACCESS   not-accessible
         STATUS   mandatory
         DESCRIPTION
            "The current measurement of utilization as a percentage
             of CIR on each DLCI.  Each short term statistics
             interval, the count of bytes transmitted and received
             is used to calculate the percentage of CIR used."
         ::= { sfrapPerfCirPercentUtilization 2 }

 sfrapPerfCurrentPerDlciUtilizationEntry OBJECT-TYPE
             SYNTAX SfrapPerfCurrentPerDlciUtilizationEntry
             ACCESS   not-accessible
             STATUS   mandatory
             DESCRIPTION
                "The utilization statistics for a particular DLCI."
             INDEX { sfrapPerfCurrentPerDlciUtilizationDlciValue }
             ::= { sfrapPerfCurrentPerDlciUtilizationTable 1 }

         SfrapPerfCurrentPerDlciUtilizationEntry ::=
             SEQUENCE {
                 sfrapPerfCurrentPerDlciUtilizationDlciValue  INTEGER,
                 sfrapPerfCurrentPerDlciRxUtilization         INTEGER,
                 sfrapPerfCurrentPerDlciTxUtilization         INTEGER,
                 sfrapPerfCurrentPerDlciAggregateUtilization  INTEGER
             }

 sfrapPerfCurrentPerDlciUtilizationDlciValue OBJECT-TYPE
             SYNTAX      INTEGER 
             ACCESS      read-only
             STATUS      mandatory
             DESCRIPTION
                "The DLCI value with which the Statistics are associated."
            ::= { sfrapPerfCurrentPerDlciUtilizationEntry 1 }

 sfrapPerfCurrentPerDlciRxUtilization OBJECT-TYPE
             SYNTAX      INTEGER 
             ACCESS      read-only
             STATUS      mandatory
             DESCRIPTION
                "The receive direction utilization as a
                 percentage of CIR."
            ::= { sfrapPerfCurrentPerDlciUtilizationEntry 2 }

 sfrapPerfCurrentPerDlciTxUtilization OBJECT-TYPE
             SYNTAX      INTEGER 
             ACCESS      read-only
             STATUS      mandatory
             DESCRIPTION
                "The transmit direction utilization as a
                 percentage of CIR."
            ::= { sfrapPerfCurrentPerDlciUtilizationEntry 3 }

 sfrapPerfCurrentPerDlciAggregateUtilization OBJECT-TYPE
             SYNTAX      INTEGER 
             ACCESS      read-only
             STATUS      mandatory
             DESCRIPTION
                "The aggregate utilization, the average
                 of the receive and transmit utilization
                 as a percentage of CIR."
            ::= { sfrapPerfCurrentPerDlciUtilizationEntry 4 }


--
--  Current Utilization for each interface and the unit as a whole.
--

sfrapPerfCurrentUnitUtilization OBJECT IDENTIFIER
            ::= { sfrapPerfCirPercentUtilization 3 }

 sfrapPerfCurrentDteUtilization OBJECT-TYPE
             SYNTAX      INTEGER 
             ACCESS      read-only
             STATUS      mandatory
             DESCRIPTION
                "The DTE interface utilization as a
                 percentage of line rate."
            ::= { sfrapPerfCurrentUnitUtilization 2 }

 sfrapPerfCurrentWanUtilization OBJECT-TYPE
             SYNTAX      INTEGER 
             ACCESS      read-only
             STATUS      mandatory
             DESCRIPTION
                "The WAN interface utilization as a
                 percentage of line rate."
            ::= { sfrapPerfCurrentUnitUtilization 3 }

 sfrapPerfCurrentAggregateUtilization OBJECT-TYPE
             SYNTAX      INTEGER 
             ACCESS      read-only
             STATUS      mandatory
             DESCRIPTION
                "The aggregate utilization of the unit,
                 the average of the DTE and WAN interface
                 utilizations as a percentage of line rate."
            ::= { sfrapPerfCurrentUnitUtilization 4 }



sfrapPerfFRStatsCollectionStatus  OBJECT IDENTIFIER ::= { sfrapPerformance 7 }

   sfrapPerfFRStatsCollection    OBJECT-TYPE
          SYNTAX      INTEGER
          {
              not-collecting-stats (1),
              collecting-stats     (2)
          }
          ACCESS      read-only
          STATUS      mandatory
          DESCRIPTION
             "Tells the GUI whether or not the Frame Relay Performance
              statistics are valid or not. This is a SFRAP Low Speed
              option, if the user's network bandwidth has exceeded the
              Low Speed boundary, then it is set to not-collecting-stats (1)
              all other cases it is set to collecting-stats (2)."
          ::= {sfrapPerfFRStatsCollectionStatus 1}
          


-- =============================
-- ==  SFRAP EVENT LOG group  ==
-- =============================
sfrapEventTrapLog      OBJECT IDENTIFIER ::= { sfrap 10 }

sfrapEventTrapLogTable              OBJECT-TYPE
        SYNTAX  SEQUENCE OF     SFRAPEventTrapLogEntry
        ACCESS  not-accessible
        STATUS  mandatory
        DESCRIPTION
            "This table contains the Event/Trap log.  The entries are
            indexed by sequence number."
        ::= { sfrapEventTrapLog 1}

    sfrapEventTrapLogEntry              OBJECT-TYPE
        SYNTAX  SFRAPEventTrapLogEntry
        ACCESS  not-accessible
        STATUS  mandatory
        DESCRIPTION
            "The event record for a particular event."
        INDEX {sfrapEventTrapLogSeqNum}
        ::= { sfrapEventTrapLogTable 1}

    SFRAPEventTrapLogEntry ::=
        SEQUENCE
        {
           sfrapEventTrapLogSeqNum        INTEGER,
           sfrapEventTrapLogGenericEvent  INTEGER,
           sfrapEventTrapLogSpecificEvent INTEGER,
           sfrapEventTrapLogTimeStamp     TimeTicks,
           sfrapEventTrapLogVarBind1      INTEGER,
           sfrapEventTrapLogVarBind2      INTEGER,
           sfrapEventTrapLogVarBind3      INTEGER
        }

    sfrapEventTrapLogSeqNum         OBJECT-TYPE
        SYNTAX  INTEGER
        ACCESS  read-only
        STATUS  mandatory
        DESCRIPTION
            "The sequence number associated with an event record."
        ::= {sfrapEventTrapLogEntry 1}

    sfrapEventTrapLogGenericEvent       OBJECT-TYPE
        SYNTAX  INTEGER
        ACCESS  read-only
        STATUS  mandatory
        DESCRIPTION
            "The SNMP generic trap or event number."
        ::= {sfrapEventTrapLogEntry 2}

    sfrapEventTrapLogSpecificEvent      OBJECT-TYPE
        SYNTAX  INTEGER
        ACCESS  read-only
        STATUS  mandatory
        DESCRIPTION
            "The SNMP specific trap or event sub-identifier number."
        ::= {sfrapEventTrapLogEntry 3}

    sfrapEventTrapLogTimeStamp      OBJECT-TYPE
        SYNTAX  TimeTicks
        ACCESS  read-only
        STATUS  mandatory
        DESCRIPTION
            "The SNMP trap timestamp."
        ::= {sfrapEventTrapLogEntry 4}

    sfrapEventTrapLogVarBind1           OBJECT-TYPE
        SYNTAX  INTEGER
        ACCESS  read-only
        STATUS  mandatory
        DESCRIPTION
            "Variable Binding 1 for this SNMP Trap event."
        ::= {sfrapEventTrapLogEntry 5}

    sfrapEventTrapLogVarBind2           OBJECT-TYPE
        SYNTAX  INTEGER
        ACCESS  read-only
        STATUS  mandatory
        DESCRIPTION
            "Variable Binding 2 for this SNMP Trap event."
        ::= {sfrapEventTrapLogEntry 6}

    sfrapEventTrapLogVarBind3           OBJECT-TYPE
        SYNTAX  INTEGER
        ACCESS  read-only
        STATUS  mandatory
        DESCRIPTION
            "Variable Binding 3 for this SNMP Trap event."
        ::= {sfrapEventTrapLogEntry 7}


    sfrapEventLogAltTable OBJECT-TYPE
         SYNTAX   SEQUENCE OF SFRAPEventLogAltEntry
         ACCESS   not-accessible
         STATUS   mandatory
         DESCRIPTION
            "This is an alternative method to access the database of the
             Event/Trap Log.  The database is indexed by Sequence Number
             and Event/Trap log's are returned  in an OCTETSTRING."
         ::= { sfrapEventTrapLog  2 }

        sfrapEventLogAltEntry   OBJECT-TYPE
            SYNTAX   SFRAPEventLogAltEntry
            ACCESS   not-accessible
            STATUS   mandatory
            DESCRIPTION
               "The Event/Trap Log for a particular sequence number."
           INDEX { sfrapEventLogAltSeqNum }
           ::= { sfrapEventLogAltTable 1 }

        SFRAPEventLogAltEntry ::=
            SEQUENCE {
                sfrapEventLogAltSeqNum               INTEGER,
                sfrapEventLogAltArray                OCTET STRING
                }

        sfrapEventLogAltSeqNum    OBJECT-TYPE
            SYNTAX      INTEGER
            ACCESS      read-only
            STATUS      mandatory
            DESCRIPTION
              "The Sequence Number monitored for the Event Log"
           ::= { sfrapEventLogAltEntry 1 }

        sfrapEventLogAltArray    OBJECT-TYPE
            SYNTAX      OCTET STRING
            ACCESS      read-only
            STATUS      mandatory
            DESCRIPTION
               "The Event / Trap log for the given sequence number."
           ::= { sfrapEventLogAltEntry 2 }

   sfrapEventLogCurrentSeqNum                 OBJECT-TYPE
        SYNTAX  INTEGER
        ACCESS  read-only
        STATUS  mandatory
        DESCRIPTION
            "The current index into the Event Log Table."
        ::= {sfrapEventTrapLog 3}


    sfrapEventLogFreeze                 OBJECT-TYPE
        SYNTAX  INTEGER
        {
            freeze      (1),
            un-freeze   (2)
        }
        ACCESS  write-only
        STATUS  mandatory
        DESCRIPTION
            "This freezes the Event/Trap Log. freeze(1) will 
             prevent Events / Traps from being entered into the database,
             un-freeze(2) will allow Events / Traps to be logged into the
             database. An event will be logged indicating a set of this
             entry"
        ::= { sfrapEventTrapLog 4}


    sfrapEventLogClear                  OBJECT-TYPE
        SYNTAX  INTEGER
        {
            clear   (1)
        }
        ACCESS  write-only
        STATUS  mandatory
        DESCRIPTION
            "This clears the Event/Trap Log."
        ::= { sfrapEventTrapLog 5}


-- =========================
-- ==        TRAPS        ==
-- =========================
--
--       Alarm types for the sfrap.
--       This is here for consistency in alarm/TRAP numbers.
--
--       This is a superset of alarm types and TRAPs.

sfrapAlarmType     OBJECT-TYPE
          SYNTAX      INTEGER
          {
               bad-config-in-set                 (1),
               config-local-update               (2),
               local-unit-loopback-enabled       (14),
               local-unit-loopback-disabled      (15),
               local-unit-loopback-failure       (16),
               local-dte-loopback-enabled        (17),
               local-dte-loopback-disabled       (18),
               local-dte-loopback-failure        (19),
               dlci-active                       (47),
               dlci-inactive                     (48),
               dlci-td-threshold                 (49),
               lmi-sourcing-change-passthru      (50),
               lmi-sourcing-change-user-dte      (51),
               lmi-sourcing-change-net-dte       (52),
               lmi-sourcing-change-user-net      (53),
               lmi-sourcing-change-net-net       (54),
               dte-signal-rts-on                 (55),
               dte-signal-rts-off                (56),
               dte-signal-dtr-on                 (57),
               dte-signal-dtr-off                (58),
               lmi-non-incr-seq-num-dte          (59),
               lmi-non-incr-seq-num-net          (60),
               lmi-seq-num-mismatch-dte          (61),
               lmi-seq-num-mismatch-net          (62),
               trap-muting-active                (75),
               trap-muting-inactive              (76),
               low-speed-exceeded                (80),
               low-speed-resumed                 (81),
               op-mode-cutthru-enabled           (82),
               op-mode-cutthru-disabled          (83),
               local-dte2-loopback-enabled       (84),
               local-dte2-loopback-disabled      (85),
               local-dte2-loopback-failure       (86),
               vloop-loop-up                     (90),
               vloop-loop-down                   (91),   
               vloop-up-via-remote               (92),
               vloop-down-via-remote             (93),
               vloop-failed                      (94),
               vbert-started                     (95),
               vbert-stopped                     (96),
               vbert-request-failed              (97),
               dte-signal-control-on             (100),
               dte-signal-control-off            (101),
               dte-signal-indicate-on            (102),
               dte-signal-indicate-off           (103),
               pvc-rx-utilization-exceeded       (138),
               pvc-tx-utilization-exceeded       (139),
               pvc-rx-utilization-cleared        (140),
               pvc-tx-utilization-cleared        (141),
               config-install-success            (142),
               tftp-requested                    (257),
               tftp-transferring                 (258),
               tftp-programming                  (259),
               tftp-aborted                      (260),
               tftp-success                      (261),
               tftp-host-unreachable             (262),
               tftp-no-file                      (263),
               tftp-invalid-file                 (264),
               tftp-corrupt-file                 (265)
          }
          ACCESS      read-only
          STATUS      mandatory
          DESCRIPTION
             "The alarm type of the most recent TRAP generated."
          ::= { sfrap 6 }

sfrapDLCINum     OBJECT-TYPE
          SYNTAX      INTEGER
          ACCESS      read-only
          STATUS      mandatory
          DESCRIPTION
             "The DLCI number for the most recent DLCI TRAP generated."
          ::= { sfrap 7 }

sfrapInterface     OBJECT-TYPE
          SYNTAX      INTEGER
          {
             to-dte   (1),
             to-dce   (2)
          }
          ACCESS      read-only
          STATUS      mandatory
          DESCRIPTION
             "The interface most recently reported in a TRAP."
          ::= { sfrap 8 }

sfrapIpAddress     OBJECT-TYPE
          SYNTAX      IpAddress
          ACCESS      read-only
          STATUS      mandatory
          DESCRIPTION
             "The IP address most recently reported in a TRAP."
          ::= { sfrap 9 }

sfrapPercentUtilization   OBJECT-TYPE
          SYNTAX      INTEGER
          ACCESS      read-only
          STATUS      mandatory
          DESCRIPTION
            "The percent utilization for a DLCI most recently
           reported in a TRAP."
         ::= { sfrap 11 }

sfrapUtilizationThreshold   OBJECT-TYPE
          SYNTAX      INTEGER
          ACCESS      read-only
          STATUS      mandatory
          DESCRIPTION
            "The percent utilization threshold for a DLCI most 
             recently reported in a TRAP."
         ::= { sfrap 12 }

sfrapCfgLockIpAddress   OBJECT-TYPE
          SYNTAX      INTEGER
          ACCESS      read-only
          STATUS      mandatory
          DESCRIPTION
            "The IP address of the management station locking 
              the configuration most recently reported in a TRAP."
         ::= { sfrap 13 }
          

sfrapTrap          TRAP-TYPE
          ENTERPRISE  sfrap
          VARIABLES   
          { 
               sfrapAlarmType
          }
          DESCRIPTION
             "A sfrapTrap trap signifies that the
             sending node had its `sfrapAlarmType`
             variable modified."
          ::= 0

sfrapBadConfigTrap          TRAP-TYPE
          ENTERPRISE  sfrap
          VARIABLES   
          { 
               sfrapAlarmType
          }
          DESCRIPTION
             "Unit has received a configuration
              update request through SNMP but the
              request was rejected due to an incorrect
              or inappropriate parameter."
          ::= 1

sfrapLocalConfigTrap          TRAP-TYPE
          ENTERPRISE  sfrap
          VARIABLES   
          { 
               sfrapAlarmType
          }
          DESCRIPTION
             "Unit configuration has been updated locally
              (console port or front panel keypad) or
              remotely (telnet)."
          ::= 2
 
 sfrapLocalUnitLoopbackEnabledTrap          TRAP-TYPE
          ENTERPRISE  sfrap
          VARIABLES   
          { 
               sfrapAlarmType
          }
          DESCRIPTION
             "Unit is in a bidirectional unit loopback. Data
              is received from either interface, processed, 
              and transmitted back towards the same interface. 
              When configured for Frame Relay operation the unit 
              will preserve the LMI path during this loopback. 
              In Frame Relay mode, only valid frames are looped 
              back (pseudorandom test patterns will be dropped)."
          ::= 14

sfrapLocalUnitLoopbackDisabledTrap          TRAP-TYPE
          ENTERPRISE  sfrap
          VARIABLES   
          { 
               sfrapAlarmType
          }
          DESCRIPTION
             "Bidirectional unit loopback path is removed."
          ::= 15

sfrapLocalUnitLoopbackFailedTrap          TRAP-TYPE
          ENTERPRISE  sfrap
          VARIABLES   
          { 
               sfrapAlarmType
          }
          DESCRIPTION
             "Bidirectional unit loopback request has been
              rejected by the unit. Typically, this is due 
              to the presence of another loopback condition."
          ::= 16

sfrapLocalToDteLoopbackEnabledTrap          TRAP-TYPE
          ENTERPRISE  sfrap
          VARIABLES   
          { 
               sfrapAlarmType
          }
          DESCRIPTION
             "Unit is in a bidirectional TO-DTE loopback. All
              data received at the TO-DTE interface is looped 
              back regardless of format or content (line 
              loopback). When configured for Frame Relay 
              operation the unit will not preserve the LMI 
              path during this loopback. Data received from 
              the TO-DCE is processed and transmitted back out 
              the TO-DCE. In Frame Relay mode, on the TO-DCE 
              interface, only valid frames are looped back 
              (pseudorandom test patterns will be dropped)."
          ::= 17

sfrapLocalToDteLoopbackDisabledTrap          TRAP-TYPE
          ENTERPRISE  sfrap
          VARIABLES   
          { 
               sfrapAlarmType
          }
          DESCRIPTION
             "Bidirectional TO-DTE loopback path is removed."
          ::= 18

sfrapLocalToDteLoopbackFailedTrap          TRAP-TYPE
          ENTERPRISE  sfrap
          VARIABLES   
          { 
               sfrapAlarmType
          }
          DESCRIPTION
             "Bidirectional TO-DTE loopback request has been
              rejected by the unit. Typically, this is due 
              to the presence of another loopback condition."
          ::= 19

sfrapDLCIActiveTrap          TRAP-TYPE
          ENTERPRISE  sfrap
          VARIABLES   
          { 
               sfrapAlarmType,
               sfrapDLCINum
          }
          DESCRIPTION
             "Unit is reporting this DLCI as active and
              provisioned. An active DLCI is one that is 
              explictly declared ACTIVE in an LMI Full 
              Status Response (typically coming from a 
              frame relay switch)."
          ::= 47

sfrapDLCIInactiveTrap          TRAP-TYPE
          ENTERPRISE  sfrap
          VARIABLES   
          { 
               sfrapAlarmType,
               sfrapDLCINum
          }
          DESCRIPTION
             "Unit is reporting this DLCI as inactive. An
              inactive DLCI is determined inactive one of two 
              ways: it is either explictly declared inactive
              in an LMI Full Status Response (typically coming 
              from a frame relay switch) or a Full Status 
              Response is not seen causing a Full Status Timer 
              expiry. Having the unit's full status timer too 
              low could result in the unit falsely declaring DLCIs 
              inactive (then active again). This does not interfere 
              with any data activity on the DLCI but could result
              in excessive traps."
          ::= 48

sfrapDLCITDThresholdTrap          TRAP-TYPE
          ENTERPRISE  sfrap
          VARIABLES   
          { 
               sfrapAlarmType,
               sfrapDLCINum,
               sfrapIpAddress
          }
          DESCRIPTION
             "VNIP has measured a round-trip transit delay on this
              PVC to this peer which exceeds the user-defined threshold."
          ::= 49

sfrapLmiSourcingChangePassthruTrap          TRAP-TYPE
          ENTERPRISE  sfrap
          VARIABLES   
          { 
               sfrapAlarmType
          }
          DESCRIPTION
             "Unit is not sourcing any LMI messages. If this
              state persists then LMI is up and the proper 
              handshaking is occurring independent of the unit. 
              This may also be a transient state if the unit 
              is in an LMI hunt mode. If this trap occurs 
              repeatedly, separated by other LMI sourcing states, 
              the unit is not seeing any of the expected LMI 
              messages from either interface. Check LMI type, 
              connectivity, and configuration of associated equipment."
          ::= 50

sfrapLmiSourcingChangeUserToDteTrap           TRAP-TYPE
          ENTERPRISE  sfrap
          VARIABLES   
          { 
               sfrapAlarmType
          }
          DESCRIPTION
             "Unit is acting as a source of LMI Status Requests
              (Link Integrity Verification, Keep Alive). If this 
              state persists then the equipment attached to the 
              TO-DTE interface is configured as a Frame Relay DCE 
              but a companion Frame Relay DTE device is not seen 
              out the TO-DCE. This could also be a transient state 
              if the unit is in an LMI hunt mode. If this trap 
              occurs repeatedly, separated by other LMI sourcing 
              states, the unit is not seeing any of the expected 
              LMI messages from either interface. Check LMI type, 
              connectivity, and configuration of associated equipment."
          ::= 51

sfrapLmiSourcingChangeNetToDteTrap            TRAP-TYPE
          ENTERPRISE  sfrap
          VARIABLES   
          { 
               sfrapAlarmType
          }
          DESCRIPTION
             "Unit is acting as a source of LMI Status Responses
              (Link Intergrity Verification, Keep Alive). If this 
              state persists then the equpiment attached to the 
              TO-DTE interface is configured as a Frame Relay DTE 
              but a companion Frame Relay DCE device is not seen 
              out the TO-DCE. This could also be a transient state 
              if the unit is in an LMI hunt mode. If this trap 
              occurs repeatedly, separated by other LMI sourcing 
              states, the unit is not seeing any of the expected 
              LMI messages from either interface. Check LMI type, 
              connectivity, and configuration of external equipment."
          ::= 52

sfrapLmiSourcingChangeUserToDceTrap           TRAP-TYPE
          ENTERPRISE  sfrap
          VARIABLES   
          { 
               sfrapAlarmType
          }
          DESCRIPTION
             "Unit is acting as a source of LMI Status Requests
              (Link Integrity Verification, Keep Alive). If this 
              state persists then the equipment attached to the 
              TO-DCE interface is configured as a Frame Relay DCE 
              but a companion Frame Relay DTE device is not seen 
              out the TO-DTE interface. This could also be a transient 
              state if the unit is in an LMI hunt mode. If this 
              trap occurs repeatedly, separated by other LMI 
              sourcing states, the unit is not seeing any of the 
              expected LMI messages from either interface. Check 
              LMI type, connectivity, and configuration of 
              associated equipment."
          ::= 53

sfrapLmiSourcingChangeNetToDceTrap            TRAP-TYPE
          ENTERPRISE  sfrap
          VARIABLES   
          { 
               sfrapAlarmType
          }
          DESCRIPTION
             "Unit is acting as a source of LMI Status Responses
              (Link Integrity Verification, Keep Alive). If this 
              state persists then the equipment attached to the 
              TO-DCE interface is configured as a Frame Relay DTE 
              but a companion Frame Relay DCE device is not seen 
              out the TO-DTE interface. This could also be a transient 
              state if the unit is in an LMI hunt mode. If this 
              trap occurs repeatedly, separated by other LMI sourcing 
              states, the unit is not seeing any of the expected 
              LMI messages from either interface. Check LMI type, 
              connectivity, and configuration of associated equipment."
          ::= 54

sfrapDteSignalRtsOnTrap                     TRAP-TYPE
          ENTERPRISE  sfrap
          VARIABLES   
          { 
               sfrapAlarmType
          }
          DESCRIPTION
             "Unit's DTE Request to Send (RTS) interface control
              signal is now active (on). This signal is presented 
              by the external DTE device. Unit may be configured 
              to ignore the state of this signal or to require 
              it for data transmission."
          ::= 55

sfrapDteSignalRtsOffTrap                    TRAP-TYPE
          ENTERPRISE  sfrap
          VARIABLES   
          { 
               sfrapAlarmType
          }
          DESCRIPTION
             "Unit's DTE Request to Send (RTS) interface control 
              signal is now inactive (off). This signal is presented 
              by the external DTE device. Unit may be configured 
              to ignore the state of this signal or to require it 
              for data transmission."
          ::= 56

sfrapDteSignalDtrOnTrap                     TRAP-TYPE
          ENTERPRISE  sfrap
          VARIABLES   
          { 
               sfrapAlarmType
          }
          DESCRIPTION
             "Unit's DTE Data Terminal Ready (DTR) interface control
              signal is now active (on). This signal is presented by the 
              external DTE device. The unit may be configured to ignore 
              the state of this signal or to require it for data transmission."
          ::= 57

sfrapDteSignalDtrOffTrap                    TRAP-TYPE
          ENTERPRISE  sfrap
          VARIABLES   
          { 
               sfrapAlarmType
          }
          DESCRIPTION
             "Unit's DTE Data Terminal Ready (DTR) interface control
              signal is now inactive (off). This signal is presented by 
              the external DTE device. Unit may be configured to ignore 
              the state of this signal or to require it for data 
              transmission."
          ::= 58

sfrapNonIncrLmiSeqNumToDteTrap           TRAP-TYPE
          ENTERPRISE  sfrap
          VARIABLES   
          { 
               sfrapAlarmType
          }
          DESCRIPTION
             "Unit has detected a non-incrementing LMI sequence number
              from the TO-DTE. A Status Enquiry or Status Response message 
              has been seen at the TO-DTE interface. The Link Integrity 
              information element's Send Sequence Number was not 
              incremented or was incremented more than once since the 
              last Send Sequence Number seen from the TO-DTE interface."
          ::= 59

sfrapNonIncrLmiSeqNumToDceTrap           TRAP-TYPE
          ENTERPRISE  sfrap
          VARIABLES   
          { 
               sfrapAlarmType
          }
          DESCRIPTION
             "Unit has detected a non-incrementing LMI sequence number
              from the TO-DCE. A Status Enquiry or Status Response message 
              has been seen at the TO-DCE interface. The Link Integrity 
              information element's Send Sequence Number was not 
              incremented or was incremented more than once since the 
              last Send Sequence Number seen from the TO-DCE interface."
          ::= 60

sfrapLmiSeqNumMismatchToDteTrap           TRAP-TYPE
          ENTERPRISE  sfrap
          VARIABLES   
          { 
               sfrapAlarmType
          }
          DESCRIPTION
             "Unit has detetcted an LMI sequence number mismatch from
              the TO-DTE. A Status Enquiry or Status Response message has 
              been seen at the TO-DTE interface. The Link Inetgrity information 
              element's Receive Sequence Number was not the most recent 
              Send Sequence number sent from the TO-DCE interface. "
          ::= 61

sfrapLmiSeqNumMismatchToDceTrap           TRAP-TYPE
          ENTERPRISE  sfrap
          VARIABLES   
          { 
               sfrapAlarmType
          }
          DESCRIPTION
             "Unit has detetcted an LMI sequence number mismatch from
              the TO-DCE. A Status Enquiry or Status Response message has 
              been seen at the TO-DCE interface. The Link Inetgrity information 
              element's Receive Sequence Number was not the most recent 
              Send Sequence number sent from the TO-DTE interface."
          ::= 62
          
sfrapTrapMutingActive           TRAP-TYPE
          ENTERPRISE  sfrap
          VARIABLES   
          { 
               sfrapAlarmType
          }
          DESCRIPTION
             "Trap generation is muted."
          ::= 75

sfrapTrapMutingInactive           TRAP-TYPE
          ENTERPRISE  sfrap
          VARIABLES   
          { 
               sfrapAlarmType
          }
          DESCRIPTION
             "Trap generation is re-enabled (muting disabled)."
          ::= 76

sfrapLowSpeedExceededTrap          TRAP-TYPE
          ENTERPRISE  sfrap
          VARIABLES   
          { 
               sfrapAlarmType
          }
          DESCRIPTION
             "The bandwidth has exceeded the maximum bandwidth
              for the Low Speed SFRAP.  Throttle your network
              bandwidth."
          ::= 80
          
sfrapLowSpeedResumedTrap          TRAP-TYPE
          ENTERPRISE  sfrap
          VARIABLES   
          { 
               sfrapAlarmType
          }
          DESCRIPTION
             "The bandwidth has is now under the maximum bandwidth
              for the Low Speed SFRAP.  Frame Relay processing
              will resume."
          ::= 81

sfrapOpModeCutThruEnabledTrap     TRAP-TYPE
          ENTERPRISE  sfrap
          VARIABLES   
          { 
               sfrapAlarmType
          }
          DESCRIPTION
             "The Unit has been put into Cut Through mode via the
              diagnostic.  The unit is now operating as if it were in
              Tap mode.  The processor is NOT transmitting data."
          ::= 82
          
sfrapOpModeCutThruDisabledTrap   TRAP-TYPE
          ENTERPRISE  sfrap
          VARIABLES   
          { 
               sfrapAlarmType
          }
          DESCRIPTION
             "The Unit has now resumed normal operation based upon the
              configured operation mode,Tap or Inband."
          ::= 83
          
sfrapLocalDte2LoopbackEnabledTrap          TRAP-TYPE
          ENTERPRISE  sfrap
          VARIABLES   
          { 
               sfrapAlarmType
          }
          DESCRIPTION
             "Local TO-DCE loopback enabled."
          ::= 84

sfrapLocalDte2LoopbackDisabledTrap          TRAP-TYPE
          ENTERPRISE  sfrap
          VARIABLES   
          { 
               sfrapAlarmType
          }
          DESCRIPTION
             "Local TO-DCE loopback disabled."
          ::= 85

sfrapLocalDte2LoopbackFailedTrap          TRAP-TYPE
          ENTERPRISE  sfrap
          VARIABLES   
          { 
               sfrapAlarmType
          }
          DESCRIPTION
             "Unable to do a local TO-DCE loopback."
          ::= 86


sfrapVloopUp         TRAP-TYPE
          ENTERPRISE  sfrap
          VARIABLES
          { 
               sfrapAlarmType,
               sfrapDLCINum,
               sfrapInterface
          }
          DESCRIPTION
             "A Vnip PVC loopback (VLOOP) request has been sent to
              a remote device on this DLCI out this interface. The
              remote unit should respond by looping all data received
              on this PVC back towards the unit that initiated this
              request. A PVC running VLOOP will not be running any
              user data."
          ::= 90

sfrapVloopDown         TRAP-TYPE
          ENTERPRISE  sfrap
          VARIABLES   
          { 
               sfrapAlarmType,
               sfrapDLCINum,
               sfrapInterface
          }
          DESCRIPTION
             "A Vnip PVC loopback (VLOOP) disable request has been
              sent to a remote device on this DLCI out this interface.
              The remote unit should respond by tearing down the
              logical loop on this DLCI."
          ::= 91 

sfrapVloopUpViaRemote     TRAP-TYPE
          ENTERPRISE  sfrap
          VARIABLES   
          { 
               sfrapAlarmType,
               sfrapDLCINum,
               sfrapInterface
          }
          DESCRIPTION
             "A Vnip PVC loopback (VLOOP) request has been received
              from a remote device on this DLCI on this interface.
              The unit will respond by looping all data received on
              this PVC back out the interface towards the unit that
              initiated the request." 
          ::= 92   

sfrapVloopDownViaRemote     TRAP-TYPE
          ENTERPRISE  sfrap
          VARIABLES   
          { 
               sfrapAlarmType,
               sfrapDLCINum,
               sfrapInterface
          }
          DESCRIPTION
             "A request to disable a Vnip PVC loopback (VLOOP) on
              this unit with the indicated DLCI and Interface has
              been received.  Usually this disable request is from
              the remote device that requested the VLOOP, however
              the request may also be due to a local event such as
              expiration of a locally configured loopback timeout.
              The unit will respond by tearing down the logical loop
              on this DLCI."
          ::= 93  

sfrapVloopRequestFailed       TRAP-TYPE
          ENTERPRISE  sfrap
          VARIABLES   
          { 
               sfrapAlarmType,
               sfrapDLCINum,
               sfrapInterface
          }
          DESCRIPTION
             "The request for a PVC loopback (VLOOP) has been rejected
              or did not complete."
          ::= 94

sfrapVbertStarted              TRAP-TYPE
          ENTERPRISE  sfrap
          VARIABLES   
          { 
               sfrapAlarmType,
               sfrapDLCINum,
               sfrapInterface
          }
          DESCRIPTION
             "A Vnip PVC error rate test (VBERT) has been started on
              this DLCI out this interface to a remote device. The
              VBERT test data will be statistically multiplexed in
              with user data, management data, and networking data.
              The destination peer will echo this test data back to
              the source producing a full-duplex volume-based timed
              test."
          ::= 95


sfrapVbertStopped              TRAP-TYPE
          ENTERPRISE  sfrap
          VARIABLES   
          { 
               sfrapAlarmType,
               sfrapDLCINum,
               sfrapInterface
          }   
          DESCRIPTION
             "A Vnip PVC BERT (VBERT) has been stopped on this DLCI 
              on this interface to a remote device."
          ::= 96

sfrapVbertRequestFailed       TRAP-TYPE
          ENTERPRISE  sfrap
          VARIABLES   
          { 
               sfrapAlarmType,
               sfrapDLCINum,
               sfrapInterface
          }   
          DESCRIPTION
             "The request for a PVC BERT (VBERT) on this DLCI 
              on this interface has been rejected."
          ::= 97

sfrapDteSignalControlOnTrap                     TRAP-TYPE
          ENTERPRISE  sfrap
          VARIABLES   
          { 
               sfrapAlarmType
          }
          DESCRIPTION
             "Unit's X.21 Control (C) DTE control signal
              is now active (on). This signal is presented 
              by the external DTE device."
          ::= 100

sfrapDteSignalControlOffTrap                    TRAP-TYPE
          ENTERPRISE  sfrap
          VARIABLES   
          { 
               sfrapAlarmType
          }
          DESCRIPTION
             "Unit's X.21 Control (C) DTE control signal
              is now inactive (off). This signal is presented 
              by the external DTE device."
          ::= 101

sfrapDteSignalIndicateOnTrap                     TRAP-TYPE
          ENTERPRISE  sfrap
          VARIABLES   
          { 
               sfrapAlarmType
          }
          DESCRIPTION
             "Unit's X.21 Indicate (I) DTE control signal
              is now active (on). This signal is presented 
              by the external DTE device."
          ::= 102

sfrapDteSignalIndicateOffTrap                    TRAP-TYPE
          ENTERPRISE  sfrap
          VARIABLES   
          { 
               sfrapAlarmType
          }
          DESCRIPTION
             "Unit's X.21 Indicate (I) DTE control signal
              is now inactive (off). This signal is presented 
              by the external DTE device."
          ::= 103

sfrapPvcRxUtilizationExceededTrap   TRAP-TYPE
          ENTERPRISE  sfrap
          VARIABLES   
          { 
               sfrapAlarmType,
               sfrapDLCINum,
               sfrapPercentUtilization,
               sfrapUtilizationThreshold
          }
          DESCRIPTION
             "Percent utilization threshold was exceeded for the
              defined number of Short Term Intervals in the
              reception direction on this DLCI. "
          ::= 138

sfrapPvcTxUtilizationExceededTrap   TRAP-TYPE
          ENTERPRISE  sfrap
          VARIABLES   
          { 
               sfrapAlarmType,
               sfrapDLCINum,
               sfrapPercentUtilization,
               sfrapUtilizationThreshold
          }
          DESCRIPTION
             "Percent utilization threshold was exceeded for the
              defined number of Short Term Intervals in the
              transmission direction on this DLCI. "
          ::= 139

sfrapPvcRxUtilizationClearedTrap   TRAP-TYPE
          ENTERPRISE  sfrap
          VARIABLES   
          { 
               sfrapAlarmType,
               sfrapDLCINum,
               sfrapPercentUtilization,
               sfrapUtilizationThreshold
          }
          DESCRIPTION
             "Percent utilization was below the threshold for the
              defined number of Short Term Intervals in the
              reception direction on this DLCI. "
          ::= 140

sfrapPvcTxUtilizationClearedTrap   TRAP-TYPE
          ENTERPRISE  sfrap
          VARIABLES   
          { 
               sfrapAlarmType,
               sfrapDLCINum,
               sfrapPercentUtilization,
               sfrapUtilizationThreshold
          }
          DESCRIPTION
             "Percent utilization was below the threshold for the
              defined number of Short Term Intervals in the
              transmission direction on this DLCI. "
          ::= 141

sfrapConfigInstallSuccess     TRAP-TYPE
          ENTERPRISE  sfrap
          VARIABLES   
          { 
               sfrapAlarmType,
               sfrapCfgLockIpAddress
          }
          DESCRIPTION
             "The configuration install process has successfully 
              completed. "
          ::= 142
          
sfrapTftpRequestedTrap            TRAP-TYPE
          ENTERPRISE  sfrap
          VARIABLES   
          { 
               sfrapAlarmType
          }
          DESCRIPTION
             "Unit has received a TFTP download request. TFTP is
              the preferred method for upgrading a unit's software 
              image."
          ::= 257

sfrapTftpTransferringTrap            TRAP-TYPE
          ENTERPRISE  sfrap
          VARIABLES   
          { 
               sfrapAlarmType
          }
          DESCRIPTION
             "Unit has established a TFTP session, found the file,
              and begun the transfer. The file must still be qualified 
              as appropriate for this unit."
          ::= 258

sfrapTftpProgrammingTrap            TRAP-TYPE
          ENTERPRISE  sfrap
          VARIABLES   
          { 
               sfrapAlarmType
          }
          DESCRIPTION
             "Unit has completed the TFTP transfer of a new software
              image which will next be programmed into non-volatile 
              flash memory."
          ::= 259

sfrapTftpAbortedTrap            TRAP-TYPE
          ENTERPRISE  sfrap
          VARIABLES   
          { 
               sfrapAlarmType
          }
          DESCRIPTION
             "Unit's TFTP session was established but the transfer was
              aborted by user intervention or an unrecoverable TFTP 
              protocol error."
          ::= 260

sfrapTftpSuccessTrap            TRAP-TYPE
          ENTERPRISE  sfrap
          VARIABLES   
          { 
               sfrapAlarmType
          }
          DESCRIPTION
             "Unit's TFTP download completed successfully. Flash
              devices will be programmed with a new image. Unit will stop
              passing data during the programming phase (less than a minute)
              and, upon completion, will reset and return to full operation
              using the new image."
          ::= 261

sfrapTftpHostUnreachableTrap    TRAP-TYPE
          ENTERPRISE  sfrap
          VARIABLES   
          { 
               sfrapAlarmType
          }
          DESCRIPTION
             "Unit could not establish a TFTP session with the
              designated server. Verify that the correct TFTP 
              ip address, TFTP DLCI and TFTP interface are 
              configured on the unit and also verify the TFTP 
              server confguration."
          ::= 262

sfrapTftpNoFileTrap             TRAP-TYPE
          ENTERPRISE  sfrap
          VARIABLES   
          { 
               sfrapAlarmType
          }
          DESCRIPTION
             "Unit could not locate the designated file on the TFTP
              server. Verify the correct TFTP filename is configured 
              on the unit and verify the location of this file on 
              the server (file name may be case sensitive)."
          ::= 263

sfrapTftpInvalidFileTrap        TRAP-TYPE
          ENTERPRISE  sfrap
          VARIABLES   
          { 
               sfrapAlarmType
          }
          DESCRIPTION
             "Unit had established a TFTP session and began transfer
              of the designated file. The unit aborted the transfer 
              after determining that the specified file is not 
              appropriate for this product (failed header verification)."
          ::= 264

sfrapTftpCorruptFileTrap        TRAP-TYPE
          ENTERPRISE  sfrap
          VARIABLES   
          { 
               sfrapAlarmType
          }
          DESCRIPTION
             "Unit transferred the designated file but aborted the
              operation due to a checksum error within the downloaded
              s-record file."
          ::= 265


END
