LEAN-MIB DEFINITIONS ::= BEGIN

 IMPORTS

    enterprises                                   FROM RFC1155-SMI

    MODULE-IDENTITY, OBJECT-TYPE,
    OBJECT-IDENTITY, NOTIFICATION-TYPE,
    Counter32, Integer32, IpAddress,
    TimeTicks                                     FROM SNMPv2-SMI

    DisplayString, PhysAddress,
    TimeStamp, RowStatus, TEXTUAL-CONVENTION      FROM SNMPv2-TC

    MODULE-COMPLIANCE, OBJECT-GROUP               FROM SNMPv2-CONF

    ifIndex                                       FROM RFC1213-MIB;

 tellabs MODULE-IDENTITY
      LAST-UPDATED "Wed Oct 11 15:08:08 BST 1995"
      ORGANIZATION "Tellabs Ltd., Shannon"
      CONTACT-INFO
            "   Brian O'Sullivan
                Tellabs,
                Shannon Industrial Estate,
                County Clare,
                Ireland.

                Tel: +353-61-471433 ext. 2406
                Fax: +353-61-471000/472004
                E-mail: brianos@shannon.tellabs.com."
      DESCRIPTION
               "The preliminary MIB module to describe generic objects for
                the Lean."
      ::= { enterprises 42 }

      IfIndex ::= TEXTUAL-CONVENTION
            STATUS  current
            DESCRIPTION
               "The value of this object identifies the
               interface for which this entry contains
               management information.  The value of this
               object for a particular interface has the same
               value as the ifIndex object, defined in RFC
               1213, for the same interface."
            SYNTAX Integer32


      leanMIB           OBJECT IDENTIFIER ::= { tellabs 1 }
      frnetservMIB      OBJECT IDENTIFIER ::= { leanMIB 1 }
      frnetservObjects  OBJECT IDENTIFIER ::= { frnetservMIB 1 }
      frnetservTraps    OBJECT IDENTIFIER ::= { frnetservMIB 2 }


 -- The Frame Relay Service Logical Port Group

 --  the Frame Relay Logical Port Group
 --  This table is an interface specific addendum
 --  to the generic ifTable from MIB-II.

frLportTable OBJECT-TYPE
 SYNTAX  SEQUENCE OF FrLportEntry
 MAX-ACCESS  not-accessible
 STATUS  current
 DESCRIPTION
         "The Frame Relay Logical Port Information table."
 ::= { frnetservObjects 1 }

frLportEntry OBJECT-TYPE
 SYNTAX  FrLportEntry
 MAX-ACCESS  not-accessible
 STATUS  current
 DESCRIPTION
          "An entry in the Frame Relay Logical Port
          Information table."
 INDEX   { ifIndex }
 ::= { frLportTable 1 }

FrLportEntry ::=
  SEQUENCE {
      frLportNumPlan
          INTEGER,
      frLportContact
          DisplayString,
      frLportLocation
          DisplayString,
      frLportType
          INTEGER,
      frLportAddrDLCILen
          INTEGER,
      frLportVCSigProtocol
          INTEGER,
      frLportVCSigPointer
          OBJECT IDENTIFIER
 }


 frLportNumPlan OBJECT-TYPE
     SYNTAX  INTEGER {
               other(1),
               e164(2),
               x121(3),
               none(4)
             }
     MAX-ACCESS  read-only
     STATUS  current
     DESCRIPTION
             "The value of this object identifies the network
             address numbering plan for this UNI/NNI logical
             port. The network address is the object
             ifPhysAddress. The value none implies that there
             is no ifPhysAddress.  The SNMP proxy-agent will
             return an octet string of zero length for
             ifPhysAddress. The value other means that an
             address has been assigned to this interface, but
             the numbering plan is not enumerated here."
     ::= { frLportEntry 1 }

 frLportContact OBJECT-TYPE
     SYNTAX  DisplayString (SIZE(0..255))
     MAX-ACCESS  read-only
     STATUS  current
     DESCRIPTION
             "The value of this object identifies the network
             contact for this UNI/NNI logical port."
     ::= { frLportEntry 2 }

 frLportLocation OBJECT-TYPE
     SYNTAX  DisplayString (SIZE(0..255))
     MAX-ACCESS  read-only
     STATUS  current
     DESCRIPTION
             "The value of this object identifies the Frame
             Relay network location for this UNI/NNI logical
             port."
     ::= { frLportEntry 3 }

 frLportType OBJECT-TYPE
     SYNTAX  INTEGER {
               uni(1),
               nni(2)
             }
     MAX-ACCESS  read-only
     STATUS  current
     DESCRIPTION
             "The value of this object identifies the type of
             network interface for this logical port."
     ::= { frLportEntry 4 }

 frLportAddrDLCILen OBJECT-TYPE
     SYNTAX  INTEGER {
      twoOctets10Bits(1),
      threeOctets10Bits(2),
      threeOctets16Bits(3),
      fourOctets17Bits(4),
      fourOctets23Bits(5)
    }
     MAX-ACCESS  read-only
     STATUS  current
     DESCRIPTION
             "The value of this object identifies the Q.922
             Address field length and DLCI length for this
             UNI/NNI logical port."
     ::= { frLportEntry 5 }

 frLportVCSigProtocol OBJECT-TYPE
     SYNTAX  INTEGER {
               none(1),
               lmi(2),
               ansiT1617D(3),
               ansiT1617B(4),
               ccittQ933A(5)
             }
     MAX-ACCESS  read-only
     STATUS  current
     DESCRIPTION
             "The value of this object identifies the Local
             In-Channel Signaling Protocol that is used for
             this frame relay UNI/NNI logical port."
     ::= { frLportEntry 6 }

 frLportVCSigPointer OBJECT-TYPE
     SYNTAX  OBJECT IDENTIFIER
     MAX-ACCESS  read-only
     STATUS  current
     DESCRIPTION
             "The value of this object is used as a pointer to
             the table that contains the Local In-Channel
             Signaling Protocol parameters and errors for this
             UNI/NNI logical port.  See the Frame Relay
             Management VC Signaling Parameters and Errors
             Group."
     ::= { frLportEntry 7 }


 -- the Frame Relay Management VC Signaling Group

 -- This Group contains managed objects for the
 -- Local In-Channel Signaling Parameters and
 -- for signaling errors.

 frMgtVCSigTable OBJECT-TYPE
     SYNTAX  SEQUENCE OF FrMgtVCSigEntry
     MAX-ACCESS  not-accessible
     STATUS  current
     DESCRIPTION
             "The Frame Relay Management VC Signaling
             Parameters and Errors table."
     ::= { frnetservObjects 2 }

 frMgtVCSigEntry OBJECT-TYPE
     SYNTAX  FrMgtVCSigEntry
     MAX-ACCESS  not-accessible
     STATUS  current
     DESCRIPTION
             "An entry in the Frame Relay Management VC
             Signaling Parameters Errors table."
     INDEX   { ifIndex }
     ::= { frMgtVCSigTable 1 }

 FrMgtVCSigEntry ::=
     SEQUENCE {
         frMgtVCSigProced
             INTEGER,
         frMgtVCSigUserN391
             INTEGER,
         frMgtVCSigUserN392
             INTEGER,
         frMgtVCSigUserN393
             INTEGER,
         frMgtVCSigUserT391
             INTEGER,
         frMgtVCSigNetN392
             INTEGER,
         frMgtVCSigNetN393
             INTEGER,
         frMgtVCSigNetT392
             INTEGER,
         frMgtVCSigNetnN4
             INTEGER,
         frMgtVCSigNetnT3
             INTEGER,
         frMgtVCSigUserLinkRelErrors
             Counter32,
         frMgtVCSigUserProtErrors
             Counter32,
         frMgtVCSigUserChanInactive
             Counter32,
         frMgtVCSigNetLinkRelErrors
             Counter32,
         frMgtVCSigNetProtErrors
             Counter32,
         frMgtVCSigNetChanInactive
             Counter32
 }


 frMgtVCSigProced OBJECT-TYPE
     SYNTAX  INTEGER {
               u2nnet(1),
               bidirect(2)
             }
     MAX-ACCESS  read-only
     STATUS  current
     DESCRIPTION
             "The value of this object identifies the Local
             In-Channel Signaling Procedure that is used for
             this UNI/NNI logical port.  The UNI/NNI logical
             port can be performing only user-to-network
             network-side procedures or bidirectional
             procedures."
     ::= { frMgtVCSigEntry 1 }

 frMgtVCSigUserN391 OBJECT-TYPE
     SYNTAX  INTEGER (1..255)
     MAX-ACCESS  read-only
     STATUS  current
     DESCRIPTION
             "The value of this object identifies the User-side
             N391 full status polling cycle value for this
             UNI/NNI logical port.  If the logical port is not
             performing user-side procedures, then this value
             is equal to noSuchName. This object applies to
             Q.933 Annex A and T1.617 Annex D."
     DEFVAL { 6 }
     ::= { frMgtVCSigEntry 2 }

 frMgtVCSigUserN392 OBJECT-TYPE
     SYNTAX  INTEGER (1..10)
     MAX-ACCESS  read-only
     STATUS  current
     DESCRIPTION
             "The value of this object identifies the User-side
             N392 error threshold value for this UNI/NNI
             logical port.  If the logical port is not
             performing user-side procedures, then this value
             is equal to noSuchName. This object applies to
             Q.933 Annex A and T1.617 Annex D."
     DEFVAL { 3 }
     ::= { frMgtVCSigEntry 3 }

 frMgtVCSigUserN393 OBJECT-TYPE
     SYNTAX  INTEGER (1..10)
     MAX-ACCESS  read-only
     STATUS  current
     DESCRIPTION
             "The value of this object identifies the User-side
             N393 monitored events count value for this UNI/NNI
             logical port.  If the logical port is not
             performing user-side procedures, then this value
             is equal to noSuchName. This object applies to
             Q.933 Annex A and T1.617 Annex D."
     DEFVAL { 4 }
     ::= { frMgtVCSigEntry 4 }

 frMgtVCSigUserT391 OBJECT-TYPE
     SYNTAX  INTEGER (5..30)
     MAX-ACCESS  read-only
     STATUS  current
     DESCRIPTION
             "The value of this object identifies the User-side
             T391 link integrity verification polling timer
             value for this UNI/NNI logical port.  If the
             logical port is not performing user-side
             procedures, then this value is equal to
             noSuchName. This object applies to Q.933 Annex A
             and T1.617 Annex D."
     DEFVAL { 10 }
     ::= { frMgtVCSigEntry 5 }

 frMgtVCSigNetN392 OBJECT-TYPE
     SYNTAX  INTEGER (1..10)
     MAX-ACCESS  read-only
     STATUS  current
     DESCRIPTION
             "The value of this object identifies the Network-
             side N392 error threshold value (nN2 for LMI) for
             this UNI/NNI logical port.  If the logical port is
             not performing network-side procedures, then this
             value is equal to noSuchName. This object applies
             to Q.933 Annex A, T1.617 Annex D and LMI."
     DEFVAL { 3 }
     ::= { frMgtVCSigEntry 6 }

 frMgtVCSigNetN393 OBJECT-TYPE
     SYNTAX  INTEGER (1..10)
     MAX-ACCESS  read-only
     STATUS  current
     DESCRIPTION
             "The value of this object identifies the Network-
             side N393 monitored events count value (nN3 for
             LMI) for this UNI/NNI logical port.  If the
             logical port is not performing network-side
             procedures, then this value is equal to
             noSuchName. This object applies to Q.933 Annex A,
             T1.617 Annex D and LMI."
     DEFVAL { 4 }
     ::= { frMgtVCSigEntry 7 }

 frMgtVCSigNetT392 OBJECT-TYPE
     SYNTAX  INTEGER (5..30)
     MAX-ACCESS  read-only
     STATUS  current
     DESCRIPTION
             "The value of this object identifies the Network-
             side T392 polling verification timer value (nT2
             for LMI)  for this UNI/NNI logical port.  If the
             logical port is not performing network-side
             procedures, then this value is equal to
             noSuchName. This object applies to Q.933 Annex A,
             T1.617 Annex D and LMI."
     DEFVAL { 15 }
     ::= { frMgtVCSigEntry 8 }

 frMgtVCSigNetnN4 OBJECT-TYPE
     SYNTAX  INTEGER (5..5)
     MAX-ACCESS  read-only
     STATUS  current
     DESCRIPTION
             "The value of this object identifies the Network-
             side nN4 maximum status enquires received value
             for this UNI/NNI logical port.  If the logical
             port is not performing network-side procedures or
             is not performing LMI procedures, then this value
             is equal to noSuchName. This object applies only
             to LMI and always has a value of 5."
     ::= { frMgtVCSigEntry 9 }

 frMgtVCSigNetnT3 OBJECT-TYPE
     SYNTAX  INTEGER (5 | 10 | 15 | 20 | 25 | 30)
     MAX-ACCESS  read-only
     STATUS  current
     DESCRIPTION
             "The value of this object identifies the Network-
             side nT3 timer (for nN4 status enquires received)
             value for this UNI/NNI logical port.  If the
             logical port is not performing network-side
             procedures or is not performing LMI procedures,
             then this value is equal to noSuchName. This
             object applies only to LMI."
     DEFVAL { 20 }
     ::= { frMgtVCSigEntry 10 }

 frMgtVCSigUserLinkRelErrors OBJECT-TYPE
     SYNTAX  Counter32
     MAX-ACCESS  read-only
     STATUS  current
     DESCRIPTION
             "The number of user-side local in-channel
             signaling link reliability errors (i.e., non-
             receipt of Status/Status Enquiry messages or
             invalid sequence numbers in a Link Integrity
             Verification Information Element) for this UNI/NNI
             logical port.  If the logical port is not
             performing user-side procedures, then this value
             is equal to noSuchName."
     ::= { frMgtVCSigEntry 11 }

 frMgtVCSigUserProtErrors OBJECT-TYPE
     SYNTAX  Counter32
     MAX-ACCESS  read-only
     STATUS  current
     DESCRIPTION
             "The number of user-side local in-channel
             signaling protocol errors (i.e., protocol
             discriminator, message type, call reference, and
             mandatory information element errors) for this
             UNI/NNI logical port.  If the logical port is not
             performing user-side procedures, then this value
             is equal to noSuchName."
     ::= { frMgtVCSigEntry 12 }

 frMgtVCSigUserChanInactive OBJECT-TYPE
     SYNTAX  Counter32
     MAX-ACCESS  read-only
     STATUS  current
     DESCRIPTION
             "The number of times the user-side channel was
             declared inactive (i.e., N392 errors in N393
             events) for this UNI/NNI logical port. If the
             logical port is not performing user-side
             procedures, then this value is equal to
             noSuchName."
     ::= { frMgtVCSigEntry 13 }

 frMgtVCSigNetLinkRelErrors OBJECT-TYPE
     SYNTAX  Counter32
     MAX-ACCESS  read-only
     STATUS  current
     DESCRIPTION
             "The number of network-side local in-channel
             signaling link reliability errors (i.e., non-
             receipt of Status/Status Enquiry messages or
             invalid sequence numbers in a Link Integrity
             Verification Information Element) for this UNI/NNI
             logical port.  If the logical port is not
             performing network-side procedures, then this
             value is equal to noSuchName."
     ::= { frMgtVCSigEntry 14 }

 frMgtVCSigNetProtErrors OBJECT-TYPE
     SYNTAX  Counter32
     MAX-ACCESS  read-only
     STATUS  current
     DESCRIPTION
             "The number of network-side local in-channel
             signaling protocol errors (i.e., protocol
             discriminator, message type, call reference, and
             mandatory information element errors) for this
             UNI/NNI logical port.  If the logical port is not
             performing network-side procedures, then this
             value is equal to noSuchName."
     ::= { frMgtVCSigEntry 15 }

 frMgtVCSigNetChanInactive OBJECT-TYPE
     SYNTAX  Counter32
     MAX-ACCESS  read-only
     STATUS  current
     DESCRIPTION
             "The number of times the network-side channel was
             declared inactive (i.e., N392 errors in N393
             events) for this UNI/NNI logical port.  If the
             logical port is not performing network-side
             procedures, then this value is equal to
             noSuchName."
     ::= { frMgtVCSigEntry 16 }



 -- The PVC End-Point Group

 -- This table is used to identify the traffic parameters
 -- for a bi-directional PVC segment end-point, and it also
 -- provides statistics for a PVC segment
 -- end-point.

 -- A PVC segment end-point is identified by a UNI/NNI
 -- logical port index value and DLCI index value.

 -- If the Frame Relay service provider allows
 -- the Frame Relay CNM subscriber to create, modify
 -- or delete PVCs using SNMP, then this table is used to identify
 -- and reserve
 -- the requested traffic parameters of each
 -- PVC segment end-point.  The Connection table
 -- is used to "connect" the end-points together.
 -- Not all implementations will support the
 -- capability of creating/modifying/deleting
 -- PVCs using SNMP as a feature of Frame Relay
 -- CNM service.

 -- Uni-directional PVCs are modeled with zero
 -- valued traffic parameters in one of the
 -- directions (In or Out direction) in this table.

 -- To create a PVC, the following procedures
 -- shall be followed:
 -- 1). Create the entries for the PVC segment endpoints in the
 --     frPVCEndptTable by specifying the traffic parameters
 --     for the bi-directional PVC segment endpoints.
 --     As shown in the figure, a point-to-point PVC has
 --     two endpoints, thus two entries in this table.
 --     Uni-directional PVCs are modeled
 --     with zero valued traffic parameters in one
 --     direction; all the `In' direction parameters
 --     for one Frame Relay PVC End-point or
 --     all the `Out' direction
 --     parameters for the other Frame Relay PVC
 --     End-point.



 --     In    ____________________________________ Out
 --    >>>>>>|                                   |>>>>>>>>
 --    ______| Frame Relay Network               |__________
 --     Out  |                                   |  In
 --    <<<<<<|                                   |<<<<<<<<
 --          |___________________________________|
 --  Frame Relay PVC                            Frame Relay
 --   End-point                                 PVC  End-point

 -- 2). Go to the Frame Relay Connection Group.
 --

 -- The Frame Relay PVC End-point Table

 frPVCEndptTable OBJECT-TYPE
     SYNTAX  SEQUENCE OF FrPVCEndptEntry
     MAX-ACCESS  not-accessible
     STATUS  current
     DESCRIPTION
             "The Frame Relay PVC End-Point table.  This table
             is used to model a PVC end-point.  This table
             contains the traffic parameters and statistics for
             a PVC end-point."
     ::= { frnetservObjects 3 }

 frPVCEndptEntry OBJECT-TYPE
     SYNTAX  FrPVCEndptEntry
     MAX-ACCESS  not-accessible
     STATUS  current
     DESCRIPTION
             "An entry in the Frame Relay PVC Endpoint table."
     INDEX   { ifIndex, frPVCEndptDLCIIndex }
     ::= { frPVCEndptTable 1 }

 FrPVCEndptEntry ::=
     SEQUENCE {
         frPVCEndptDLCIIndex
             Integer32,
         frPVCEndptInMaxFrameSize
             Integer32,
         frPVCEndptInBc
             Integer32,
         frPVCEndptInBe
             Integer32,
         frPVCEndptInCIR
            Integer32,
         frPVCEndptOutMaxFrameSize
             Integer32,
         frPVCEndptOutBc
             Integer32,
         frPVCEndptOutBe
             Integer32,
         frPVCEndptOutCIR
             Integer32,
         frPVCEndptConnectIdentifier
             Integer32,
         frPVCEndptRowStatus
             RowStatus,
         frPVCEndptRcvdSigStatus
             INTEGER,
         frPVCEndptInFrames
             Counter32,
         frPVCEndptOutFrames
             Counter32,
         frPVCEndptInDEFrames
             Counter32,
         frPVCEndptInExcessFrames
             Counter32,
         frPVCEndptOutExcessFrames
             Counter32,
         frPVCEndptInDiscards
             Counter32,
         frPVCEndptInOctets
             Counter32,
         frPVCEndptOutOctets
             Counter32
     }


 frPVCEndptDLCIIndex OBJECT-TYPE
     SYNTAX  Integer32
     MAX-ACCESS  not-accessible
     STATUS  current
     DESCRIPTION
             "The value of this object is equal to the DLCI
             value for this PVC end-point."
     ::= { frPVCEndptEntry 1 }

 frPVCEndptInMaxFrameSize OBJECT-TYPE
     SYNTAX  Integer32
     MAX-ACCESS  read-create
     STATUS  current
     DESCRIPTION
             "The value of this object is the size in octets of
             the largest frame relay information field for this
             PVC end-point in the ingress direction (into the
             frame relay network).  The value of
             frPVCEndptInMaxFrameSize must be less than or
             equal to the corresponding ifMtu for this Frame
             Relay UNI/NNI logical port."
     ::= { frPVCEndptEntry 2 }

 frPVCEndptInBc OBJECT-TYPE
     SYNTAX  Integer32
     MAX-ACCESS  read-create
     STATUS  current
     DESCRIPTION
             "The value of this object is equal to the
             committed burst size (Bc) parameter (measured in
             bits) for this PVC end-point in the ingress
             direction (into the frame relay network)."
     ::= { frPVCEndptEntry 3 }

 frPVCEndptInBe OBJECT-TYPE
     SYNTAX  Integer32
     MAX-ACCESS  read-create
     STATUS  current
     DESCRIPTION
             "The value of this object is equal to the excess
             burst size (Be) parameter (measured in bits) for
             this PVC end-point in the ingress direction (into
             the frame relay network)."
     ::= { frPVCEndptEntry 4 }

 frPVCEndptInCIR OBJECT-TYPE
     SYNTAX  Integer32
     MAX-ACCESS  read-create
     STATUS  current
     DESCRIPTION
             "The value of this object is equal to the
             committed information rate (CIR) parameter
             (measured in bits per second) for this PVC end-
             point in the ingress direction (into the frame
             relay network)."
     ::= { frPVCEndptEntry 5 }

 frPVCEndptOutMaxFrameSize OBJECT-TYPE
     SYNTAX  Integer32
     MAX-ACCESS  read-create
     STATUS  current
     DESCRIPTION
             "The value of this object is the size in octets of
             the largest frame relay information field for this
             PVC end-point in the egress direction (out of the
             frame relay network).  The value of
             frPVCEndptOutMaxFrameSize must be less than or
             equal to the corresponding ifMtu for this Frame
             Relay UNI/NNI logical port."
     ::= { frPVCEndptEntry 6 }

 frPVCEndptOutBc OBJECT-TYPE
     SYNTAX  Integer32
     MAX-ACCESS  read-create
     STATUS  current
     DESCRIPTION
             "The value of this object is equal to the
             committed burst size (Bc) parameter (measured in
             bits) for this PVC end-point in the egress
             direction (out of the frame relay network)."
     ::= { frPVCEndptEntry 7 }

 frPVCEndptOutBe OBJECT-TYPE
     SYNTAX  Integer32
     MAX-ACCESS  read-create
     STATUS  current
     DESCRIPTION
             "The value of this object is equal to the excess
             burst size (Be) parameter (measured in bits) for
             this PVC end-point in the egress direction (out of
             the frame relay network)."
     ::= { frPVCEndptEntry 8 }

 frPVCEndptOutCIR OBJECT-TYPE
     SYNTAX  Integer32
     MAX-ACCESS  read-create
     STATUS  current
     DESCRIPTION
             "The value of this object is equal to the
             committed information rate (CIR) parameter
             (measured in bits per second) for this PVC end-
             point in the egress direction (out of the frame
             relay network)."
     ::= { frPVCEndptEntry 9 }

 frPVCEndptConnectIdentifier OBJECT-TYPE
     SYNTAX  Integer32
     MAX-ACCESS  read-only
     STATUS  current
     DESCRIPTION
             "This object is used to associate PVC end-points
             as being part of one PVC segment connection.  This
             value of this object is equal to the value of
             frPVCConnectIndex, which is used as one of the
             indices into the frPVCConnectTable.  The value of
             this object is provided by the agent, after the
             associated entries in the frPVCConnectTable have
             been created."
     ::= { frPVCEndptEntry 10 }

 frPVCEndptRowStatus OBJECT-TYPE
     SYNTAX  RowStatus
     MAX-ACCESS  read-create
     STATUS  current
     DESCRIPTION
             "This object is used to create new rows in this
             table, modify existing rows, and to delete
             existing rows.  To create a new PVC, the entries
             for the PVC segment end-points in the
             frPVCEndptTable must first be created.  Next, the
             frPVCConnectTable is used to associate the Frame
             Relay PVC segment end-points.  In order for the
             manager to have the necessary error diagnostics,
             the frPVCEndptRowStatus object must initially be
             set to `createAndWait'.  While the
             frPVCEndptRowStatus object is in the
             `createAndWait' state, the manager can set each
             columnar object and get the necessary error
             diagnostics.  The frPVCEndptRowStatus object may
             not be set to `active' unless the following
             columnar objects exist in this row:
             frPVCEndptInMaxFrameSize, frPVCEndptInBc,
             frPVCEndptInBe, frPVCEndptInCIR,
             frPVCEndptOutMaxFrameSize, frPVCEndptOutBc,
             frPVCEndptOutBe, and frPVCEndptOutCIR."
     ::= { frPVCEndptEntry 11 }

 frPVCEndptRcvdSigStatus OBJECT-TYPE
     SYNTAX  INTEGER {
               deleted(1),
               active(2),
               inactive(3),
               none(4)
             }
     MAX-ACCESS  read-only
     STATUS  current
     DESCRIPTION
             "The value of this object identifies the PVC
             status received via the local in-channel signaling
             procedures for this PVC end-point.  This object is
             only pertinent for interfaces that perform the
             bidirectional procedures.  For user-to-network
             network side procedures, the value of this object
             should be none."
     ::= { frPVCEndptEntry 12 }

 frPVCEndptInFrames OBJECT-TYPE
     SYNTAX  Counter32
     MAX-ACCESS  read-only
     STATUS  current
     DESCRIPTION
             "The number of frames received by the network
             (ingress) for this PVC end-point. This includes
             any frames discarded by the network due to
             submitting more than Bc + Be data or due to any
             network congestion recovery procedures."
     ::= { frPVCEndptEntry 13 }

 frPVCEndptOutFrames OBJECT-TYPE
     SYNTAX  Counter32
     MAX-ACCESS  read-only
     STATUS  current
     DESCRIPTION
             "The number of frames sent by the network (egress)
             regardless of whether they are Bc or Be frames for
             this PVC end-point."
     ::= { frPVCEndptEntry 14 }

 frPVCEndptInDEFrames OBJECT-TYPE
     SYNTAX  Counter32
     MAX-ACCESS  read-only
     STATUS  current
     DESCRIPTION
             "The number of frames received by the network
             (ingress) with the DE bit set to (1) for this PVC
             end-point."
     ::= { frPVCEndptEntry 15 }

 frPVCEndptInExcessFrames OBJECT-TYPE
     SYNTAX  Counter32
     MAX-ACCESS  read-only
     STATUS  current
     DESCRIPTION
             "The number of frames received by the network
             (ingress) for this PVC end-point which were
             treated as excess traffic.  Frames which are sent
             to the network with DE set to zero are treated as
             excess when more than Bc bits are submitted to the
             network during the Committed Information Rate
             Measurement Interval (Tc).  Excess traffic may or
             may not be discarded at the ingress if more than
             Bc + Be bits are submitted to the network during
             Tc.  Traffic discarded at the ingress is not
             recorded in frPVCEndptInExcessFrames.  Frames
             which are sent to the network with DE set to one
             are also treated as excess traffic."
     ::= { frPVCEndptEntry 16 }

 frPVCEndptOutExcessFrames OBJECT-TYPE
     SYNTAX  Counter32
     MAX-ACCESS  read-only
     STATUS  current
     DESCRIPTION
             "The number of frames sent by the network (egress)
             for this PVC end-point which were treated as
             excess traffic.  (The DE bit may be set to one.)"
     ::= { frPVCEndptEntry 17 }

 frPVCEndptInDiscards OBJECT-TYPE
     SYNTAX  Counter32
     MAX-ACCESS  read-only
     STATUS  current
     DESCRIPTION
             "The number of frames received by the the network
             (ingress) that were discarded due to traffic
             enforcement for this PVC end-point."
     ::= { frPVCEndptEntry 18 }

 frPVCEndptInOctets OBJECT-TYPE
     SYNTAX  Counter32
     MAX-ACCESS  read-only
     STATUS  current
     DESCRIPTION
             "The number of octets received by the network
             (ingress) for this PVC end-point.  This counter
             should only count octets from the beginning of the
             frame relay header field to the end of user data.
             If the network supporting Frame Relay can not
             count octets, then this count should be an
             approximation."
     ::= { frPVCEndptEntry 19 }

 frPVCEndptOutOctets OBJECT-TYPE
     SYNTAX  Counter32
     MAX-ACCESS  read-only
     STATUS  current
     DESCRIPTION
             "The number of octets sent by the network (egress)
             for this PVC end-point.  This counter should only
             count octets from the beginning of the frame relay
             header field to the end of user data.  If the
             network supporting Frame Relay can not count
             octets, then this count should be an
             approximation."
     ::= { frPVCEndptEntry 20 }


 -- The Frame Relay PVC Connection Group

 -- The Frame Relay PVC Connection Group
 -- is used to model the bi-directional
 -- PVC segment flows;
 -- point-to-point PVCs, point-to-multipoint
 -- PVCs, and multipoint-to-multipoint
 -- PVCs.

 -- This table has read-create access and
 -- is used to associate PVC end-points
 -- together as belonging to one connection.
 -- The frPVCConnectIndex is used to associate
 -- all the bi-directional flows.
 -- Not all implementations will support the
 -- capability of creating/modifying/deleting
 -- PVCs using SNMP as a feature of Frame Relay
 -- CNM service.

 -- Once the entries in the frPVCEndptTable
 -- are created, the following step are used
 -- to associate the PVC end-points as belonging
 -- to one PVC connection:
 -- 1). Obtain a unique frPVCConnectIndex
 --     using the frPVCConnectIndexValue object.
 -- 2). Connect the PVC segment endpoints together
 --     with the applicable frPVCConnectIndex value
 --     obtained via
 --     frPVCConnectIndexValue.
 --     The entries in this table are created by using
 --     the frPVCConnectRowStatus object.
 -- 3). The agent will provide the value of the
 --     corresponding instances of
 --     frPVCEndptConnectIdentifier with the
 --     the frPVCConnectIndex value.
 -- 4). Set frPVCConnectAdminStatus to `active' in all
 --     rows for this PVC segment to
 --     turn the PVC on.
 -- For example, the Frame Relay PVC Connection Group
 -- models a bi-directional, point-to-point PVC segment
 -- as one entry in this table.

 -- Frame Relay Network                  Frame Relay Network
 --  Low Port ____________________________________ High Port
 --          |                                   |
 --    ______| >> from low to high PVC flow   >> |____________
 --          | << from high to low PVC flow   << |
 --          |___________________________________|
 --

 -- The terms low and high are chosen to represent numerical
 -- ordering of a PVC segment's endpoints for representation
 -- in this table.  That is, the endpoint with the lower value
 -- of ifIndex is termed 'low', while the opposite endpoint
 -- of the segment is termed 'high'.
 -- This terminology is to provide directional information;
 -- for example the frPVCConnectL2hOperStatus and
 -- frPVCConnectH2lOperStatus as illustrated above.

 -- If the Frame Relay Connection table is used to model
 -- a unidirectional PVC, then one direction (either from low to high
 -- or from high to low) has its Operational Status equal to down.

 -- A PVC segment is a portion of a PVC
 -- that traverses one Frame Relay Network, and
 -- a PVC segment is identified
 -- by its two end-points (UNI/NNI logical port index
 -- value and DLCI index value)
 -- through one Frame Relay Network.


 frPVCConnectIndexValue OBJECT-TYPE
     SYNTAX  INTEGER (0..2147483647)
     MAX-ACCESS  read-only
     STATUS  current
     DESCRIPTION
             "This object contains an appropriate value to be
             used for frPVCConnectIndex when creating entries
             in the frPVCConnectTable.  The value 0 indicates
             that no unassigned entries are available.  To
             obtain the frPVCConnectIndex value for a new
             entry, the manager issues a management protocol
             retrieval operation to obtain the current value of
             this object.  After each retrieval, the agent
             should modify the value to the next unassigned
             index."
     ::= { frnetservObjects 4 }

 --  The Frame Relay PVC Connection Table

 frPVCConnectTable OBJECT-TYPE
     SYNTAX  SEQUENCE OF FrPVCConnectEntry
     MAX-ACCESS  not-accessible
     STATUS  current
     DESCRIPTION
             "The Frame Relay PVC Connect table.  A bi-
             directional PVC segment is modeled as one entry in
             this table."
     ::= { frnetservObjects 5 }

 frPVCConnectEntry OBJECT-TYPE
     SYNTAX  FrPVCConnectEntry
     MAX-ACCESS  not-accessible
     STATUS  current
     DESCRIPTION
             "An entry in the Frame Relay PVC Connect table.
             This entry is used to model a PVC segment in two
             directions."
     INDEX { frPVCConnectIndex,
             frPVCConnectLowIfIndex, frPVCConnectLowDLCIIndex,
             frPVCConnectHighIfIndex, frPVCConnectHighDLCIIndex }
     ::= { frPVCConnectTable 1 }

 FrPVCConnectEntry ::=
     SEQUENCE {
         frPVCConnectIndex
             Integer32,
         frPVCConnectLowIfIndex
             IfIndex,
         frPVCConnectLowDLCIIndex
             Integer32,
         frPVCConnectHighIfIndex
             IfIndex,
         frPVCConnectHighDLCIIndex
             Integer32,
         frPVCConnectAdminStatus
             INTEGER,
         frPVCConnectL2hOperStatus
             INTEGER,
         frPVCConnectH2lOperStatus
             INTEGER,
         frPVCConnectL2hLastChange
             TimeStamp,
         frPVCConnectH2lLastChange
             TimeStamp,
         frPVCConnectRowStatus
             RowStatus
 }

 frPVCConnectIndex OBJECT-TYPE
     SYNTAX  Integer32
     MAX-ACCESS  not-accessible
     STATUS  current
     DESCRIPTION
             "The value of this object is equal to the
             frPVCConnectIndexValue obtained to uniquely
             identify this PVC segment connection."
     ::= { frPVCConnectEntry 1 }

 frPVCConnectLowIfIndex OBJECT-TYPE
     SYNTAX  IfIndex
     MAX-ACCESS  not-accessible
     STATUS  current
     DESCRIPTION
             "The value of this object is equal to MIB II's
             ifIndex value of the UNI/NNI logical port for this
             PVC segment.  The term low implies that this PVC
             segment end-point has the numerically lower
             ifIndex value than the connected/associated PVC
             segment end-point.  If the value is equal to zero,
             then this logical port is not a Frame Relay
             UNI/NNI logical port."
     ::= { frPVCConnectEntry 2 }

 frPVCConnectLowDLCIIndex OBJECT-TYPE
     SYNTAX  Integer32
     MAX-ACCESS  not-accessible
     STATUS  current
     DESCRIPTION
             "The value of this object is equal to the DLCI
             value for this end-point of the PVC segment.  If
             the value is equal to zero, then this endpoint of
             the PVC segment is not a Frame Relay connection."
     ::= { frPVCConnectEntry 3 }

 frPVCConnectHighIfIndex OBJECT-TYPE
     SYNTAX  IfIndex
     MAX-ACCESS  not-accessible
     STATUS  current
     DESCRIPTION
             "The value of this object is equal to MIB II's
             ifIndex value for the UNI/NNI logical port for
             this PVC segment.  The term high implies that this
             PVC segment end-point has the numerically higher
             ifIndex value than the connected/associated PVC
             segment end-point."
     ::= { frPVCConnectEntry 4 }

 frPVCConnectHighDLCIIndex OBJECT-TYPE
     SYNTAX  Integer32
     MAX-ACCESS  not-accessible
     STATUS  current
     DESCRIPTION
             "The value of this object is equal to the egress
             DLCI value for this end-point of the PVC segment."
     ::= { frPVCConnectEntry 5 }

 frPVCConnectAdminStatus OBJECT-TYPE
     SYNTAX  INTEGER {
               active(1),
               inactive(2),
               testing(3)
             }
     MAX-ACCESS  read-create
     STATUS  current
     DESCRIPTION
             "The value of this object identifies the desired
             administrative status of this bi-directional PVC
             segment.  The active state means the PVC segment
             is currently operational; the inactive state means
             the PVC segment is currently not operational; the
             testing state means the PVC segment is currently
             undergoing a test.  This state is set by an
             administrative entity.  This value affects the PVC
             status indicated across the ingress NNI/UNI of
             both end-points of the bi-directional PVC segment.
             When a PVC segment connection is created using
             this table, this object is initially set to
             `inactive'.  After the frPVCConnectRowStatus
             object is set to `active' (and the
             corresponding/associated entries in the
             frPVCEndptTable have their frPVCEndptRowStatus
             object set to `active'), the
             frPVCConnectAdminStatus object may be set to
             `active' to turn on the PVC segment connection."
     ::= { frPVCConnectEntry 6 }

 frPVCConnectL2hOperStatus OBJECT-TYPE
     SYNTAX  INTEGER {
               active(1),
               inactive(2),
               testing(3),
               unknown(4)
             }
     MAX-ACCESS  read-only
     STATUS  current
     DESCRIPTION
             "The value of this object identifies the current
             operational status of the PVC segment connection
             in one direction; (i.e., in the low to high
             direction).  The active state means it is
             currently operational; the inactive state means it
             is currently not operational; the testing state
             means it is currently undergoing a test; the
             unknown state means the status of it currently can
             not be determined.  This value affects the PVC
             status indicated across the ingress NNI/UNI (low
             side) of the PVC segment."
     ::= { frPVCConnectEntry 7 }

 frPVCConnectH2lOperStatus OBJECT-TYPE
     SYNTAX  INTEGER {
               active(1),
               inactive(2),
               testing(3),
               unknown(4)
             }
     MAX-ACCESS  read-only
     STATUS  current
     DESCRIPTION
             "The value of this object identifies the current
             operational status of the PVC segment connection
             in one direction; (i.e., in the high to low
             direction).  The active state means it is
             currently operational; the inactive state means it
             is currently not operational; the testing state
             means it is currently undergoing a test; the
             unknown state means the status of it currently can
             not be determined.  This value affects the PVC
             status indicated across the ingress NNI/UNI (high
             side) of the PVC segment."
     ::= { frPVCConnectEntry 8 }

 frPVCConnectL2hLastChange OBJECT-TYPE
     SYNTAX  TimeStamp
     MAX-ACCESS  read-only
     STATUS  current
     DESCRIPTION
             "The value of MIB II's sysUpTime object at the
             time this PVC segment entered its current
             operational state in the low to high direction.
             If the current state was entered prior to the last
             re-initialization of the proxy-agent, then this
             object contains a zero value."
     ::= { frPVCConnectEntry 9 }

 frPVCConnectH2lLastChange OBJECT-TYPE
     SYNTAX  TimeStamp
     MAX-ACCESS  read-only
     STATUS  current
     DESCRIPTION
             "The value of MIB II's sysUpTime object at the
             time this PVC segment entered its current
             operational state in the high to low direction.
             If the current state was entered prior to the last
             re-initialization of the proxy-agent, then this
             object contains a zero value."
     ::= { frPVCConnectEntry 10 }

 frPVCConnectRowStatus OBJECT-TYPE
     SYNTAX  RowStatus
     MAX-ACCESS  read-create
     STATUS  current
     DESCRIPTION
             "The status of this entry in the
             frPVCConnectTable.  This variable is used to
             create new connections for the PVC end-points and
             to change existing connections of the PVC end-
             points.  This object must be initially set to
             `createAndWait'.  In this state, the agent checks
             the parameters in the associated entries in the
             frPVCEndptTable to verify that the PVC end-points
             can be connected (i.e., the In parameters for one
             PVC end-point are equal to the Out parameters for
             the other PVC end-point).  This object can not be
             set to `active' unless the following columnar
             object exist in this row: frPVCConnectAdminStatus.
             The agent also supplies the associated value of
             frPVCConnectIndex for the frPVCEndptConnectIdentifier
             instances.  To turn on a PVC segment connection, the
             frPVCConnectAdminStatus is set to `active'."
     ::= { frPVCConnectEntry 11 }




 -- The Frame Relay Accounting Groups

 -- The groups are the following:
 --  Accounting on a PVC basis
 --  Accounting on an Interface/Logical Port basis

 -- The Accounting on a Frame Relay PVC basis Group

 -- The accounting information is collected for a PVC
 -- segment end-point.

 frAccountPVCTable OBJECT-TYPE
     SYNTAX  SEQUENCE OF FrAccountPVCEntry
     MAX-ACCESS  not-accessible
     STATUS  current
     DESCRIPTION
             "The Frame Relay Accounting PVC table.  This table
             is used to perform accounting on a PVC segment
             end-point basis."
     ::= { frnetservObjects 6 }

 frAccountPVCEntry OBJECT-TYPE
     SYNTAX  FrAccountPVCEntry
     MAX-ACCESS  not-accessible
     STATUS  current
     DESCRIPTION
             "An entry in the Frame Relay Accounting PVC
             table."
     INDEX   { ifIndex, frAccountPVCDLCIIndex }
     ::= { frAccountPVCTable 1 }

 FrAccountPVCEntry ::=
     SEQUENCE {
         frAccountPVCDLCIIndex
             Integer32,
         frAccountPVCSegmentSize
             Integer32,
         frAccountPVCInSegments
             Counter32,
         frAccountPVCOutSegments
             Counter32
     }


 frAccountPVCDLCIIndex OBJECT-TYPE
     SYNTAX  Integer32
     MAX-ACCESS  not-accessible
     STATUS  current
     DESCRIPTION
             "The value of this object is equal to the DLCI
             value for this PVC segment end-point."
     ::= { frAccountPVCEntry 1 }

 frAccountPVCSegmentSize OBJECT-TYPE
     SYNTAX  Integer32
     MAX-ACCESS  read-only
     STATUS  current
     DESCRIPTION
             "The value of this object is equal to the Segment
             Size for this PVC segment end-point."
     ::= { frAccountPVCEntry 2 }

 frAccountPVCInSegments OBJECT-TYPE
     SYNTAX  Counter32
     MAX-ACCESS  read-only
     STATUS  current
     DESCRIPTION
             "The value of this object is equal to the number
             of segments received by this PVC segment end-
             point."
     ::= { frAccountPVCEntry 3 }

  frAccountPVCOutSegments OBJECT-TYPE
     SYNTAX  Counter32
     MAX-ACCESS  read-only
     STATUS  current
     DESCRIPTION
             "The value of this object is equal to the number
             of segments sent by this PVC segment end-point."
     ::= { frAccountPVCEntry 4 }


 -- The Accounting on a Frame Relay Logical Port basis Group


 frAccountLportTable OBJECT-TYPE
     SYNTAX  SEQUENCE OF FrAccountLportEntry
     MAX-ACCESS  not-accessible
     STATUS  current
     DESCRIPTION
             "The Frame Relay Accounting Logical Port table.
             This table is used to perform accounting on a
             UNI/NNI Logical Port basis."
     ::= { frnetservObjects 7 }

 frAccountLportEntry OBJECT-TYPE
     SYNTAX  FrAccountLportEntry
     MAX-ACCESS  not-accessible
     STATUS  current
     DESCRIPTION
             "An entry in the Frame Relay Accounting Logical
             Port table."
     INDEX   { ifIndex }
     ::= { frAccountLportTable 1 }

 FrAccountLportEntry ::=
     SEQUENCE {
         frAccountLportSegmentSize
             Integer32,
         frAccountLportInSegments
             Counter32,
         frAccountLportOutSegments
             Counter32
     }


 frAccountLportSegmentSize OBJECT-TYPE
     SYNTAX  Integer32
     MAX-ACCESS  read-only
     STATUS  current
     DESCRIPTION
             "The value of this object is equal to the Segment
             Size for this UNI/NNI logical port."
     ::= { frAccountLportEntry 1 }

 frAccountLportInSegments OBJECT-TYPE
     SYNTAX  Counter32
     MAX-ACCESS  read-only
     STATUS  current
     DESCRIPTION
             "The value of this object is equal to the number
             of segments received by this UNI/NNI logical
             port."
     ::= { frAccountLportEntry 2 }

 frAccountLportOutSegments OBJECT-TYPE
     SYNTAX  Counter32
     MAX-ACCESS  read-only
     STATUS  current
     DESCRIPTION
             "The value of this object is equal to the number
             of segments sent by this UNI/NNI logical port."
     ::= { frAccountLportEntry 3 }

 -- Frame Relay Network Service TRAPS

 frPVCConnectStatusChange  NOTIFICATION-TYPE
     OBJECTS { frPVCConnectIndex,
               frPVCConnectLowIfIndex, frPVCConnectLowDLCIIndex,
               frPVCConnectHighIfIndex, frPVCConnectHighDLCIIndex,
               frPVCConnectL2hOperStatus, frPVCConnectH2lOperStatus,
               frPVCEndptRcvdSigStatus }
     STATUS  current
     DESCRIPTION
             "This trap indicates that the indicated PVC has
             changed state.  This trap is not sent if an FR-UNI
             changes state; a linkDown or linkUp trap should be
             sent instead."
     ::= { frnetservTraps 1 }


 -- Conformance Information

 frnetservConformance  OBJECT IDENTIFIER ::= { frnetservMIB 3 }

 frnetservGroups       OBJECT IDENTIFIER ::= { frnetservConformance 1 }
 frnetservCompliances  OBJECT IDENTIFIER ::= { frnetservConformance 2 }

 -- Compliance Statements

 frnetservCompliance MODULE-COMPLIANCE
       STATUS  current
       DESCRIPTION
         "The compliance statement for SNMPv2 entities
         which have Frame Relay Network Service Interfaces."

       MODULE -- this module
           MANDATORY-GROUPS { frnetservLportGroup,
                              frnetservMgtVCSigGroup,
                              frnetservPVCEndptGroup,
                              frnetservPVCConnectGroup }

           GROUP       frnetservAccountPVCGroup
           DESCRIPTION
                 "This group is optional for Frame Relay interfaces.
                 It is
                 mandatory if and only if accounting is performed
                 on a PVC
                 basis this
                 Frame Relay interface."

           GROUP       frnetservAccountLportGroup
           DESCRIPTION
                 "This group is optional for Frame Relay interfaces.
                 It is
                 mandatory if and only if accounting is
                 performed on a
                 logical port basis this
                 Frame Relay interface."

           OBJECT      frPVCEndptInMaxFrameSize
           SYNTAX      Integer32
           MIN-ACCESS  read-only
           DESCRIPTION
                 "Write access is not required."

           OBJECT      frPVCEndptInBc
           SYNTAX      Integer32
           MIN-ACCESS  read-only
           DESCRIPTION
                 "Write access is not required."

           OBJECT      frPVCEndptInBe
           SYNTAX      Integer32
           MIN-ACCESS  read-only
           DESCRIPTION
                 "Write access is not required."

           OBJECT      frPVCEndptInCIR
           SYNTAX      Integer32
           MIN-ACCESS  read-only
           DESCRIPTION
                 "Write access is not required."

           OBJECT      frPVCEndptOutMaxFrameSize
           SYNTAX      Integer32
           MIN-ACCESS  read-only
           DESCRIPTION
                 "Write access is not required."

           OBJECT      frPVCEndptOutBc
           SYNTAX      Integer32
           MIN-ACCESS  read-only
           DESCRIPTION
                 "Write access is not required."

           OBJECT      frPVCEndptOutBe
           SYNTAX      Integer32
           MIN-ACCESS  read-only
           DESCRIPTION
                 "Write access is not required."

           OBJECT      frPVCEndptOutCIR
           SYNTAX      Integer32
           MIN-ACCESS  read-only
           DESCRIPTION
                 "Write access is not required."

           OBJECT      frPVCEndptConnectIdentifier
           SYNTAX      Integer32
           MIN-ACCESS  read-only
           DESCRIPTION
                 "Write access is not required."

           OBJECT      frPVCEndptRowStatus
           SYNTAX      INTEGER { active(1) }  -- subset of RowStatus
           MIN-ACCESS  read-only
           DESCRIPTION
                 "Write access is not required, and only one of the
                 six enumerated values for the RowStatus textual
                 convention need be supported, specifically:
                 active(1)."

           OBJECT      frPVCConnectAdminStatus
           SYNTAX      INTEGER {
                         active(1),
                         inactive(2),
                         testing(3)
                        }
           MIN-ACCESS  read-only
           DESCRIPTION
                 "Write access is not required."

           OBJECT      frPVCConnectRowStatus
           SYNTAX      INTEGER { active(1) }  -- subset of RowStatus
           MIN-ACCESS  read-only
           DESCRIPTION
                 "Write access is not required."

           OBJECT      frPVCConnectRowStatus
           SYNTAX      INTEGER { active(1) }  -- subset of RowStatus
           MIN-ACCESS  read-only
           DESCRIPTION
                 "Write access is not required, and only one of the
                 six enumerated values for the RowStatus textual
                 convention need be supported, specifically:
                 active(1)."
       ::= { frnetservCompliances 1 }





 -- Units of Conformance

 frnetservLportGroup  OBJECT-GROUP
       OBJECTS { frLportNumPlan, frLportContact, frLportLocation,
                 frLportType,
                 frLportAddrDLCILen, frLportVCSigProtocol,
                 frLportVCSigPointer }
       STATUS  current
       DESCRIPTION
             "A collection of objects providing information applicable
             to a Frame Relay Logical Port."
       ::= { frnetservGroups 1 }

 frnetservMgtVCSigGroup  OBJECT-GROUP
       OBJECTS { frMgtVCSigProced,
                 frMgtVCSigUserN391,
                 frMgtVCSigUserN392,
                 frMgtVCSigUserN393,
                 frMgtVCSigUserT391,
                 frMgtVCSigNetN392,
                 frMgtVCSigNetN393,
                 frMgtVCSigNetT392,
                 frMgtVCSigNetnN4,
                 frMgtVCSigNetnT3,
                 frMgtVCSigUserLinkRelErrors,
                 frMgtVCSigUserProtErrors,
                 frMgtVCSigUserChanInactive,
                 frMgtVCSigNetLinkRelErrors,
                 frMgtVCSigNetProtErrors,
                 frMgtVCSigNetChanInactive }
       STATUS  current
       DESCRIPTION
             "A collection of objects providing information
             applicable to the
             Local In-Channel Signaling Procedures used for a
             UNI/NNI logical port."
       ::= { frnetservGroups 2 }

 frnetservPVCEndptGroup  OBJECT-GROUP
       OBJECTS { frPVCConnectIndexValue,
                 frPVCEndptInMaxFrameSize, frPVCEndptInBc,
                 frPVCEndptInBe, frPVCEndptInCIR,
                 frPVCEndptOutMaxFrameSize, frPVCEndptOutBc,
                 frPVCEndptOutBe, frPVCEndptOutCIR,
                 frPVCEndptConnectIdentifier, frPVCEndptRowStatus,
                 frPVCEndptRcvdSigStatus, frPVCEndptInFrames,
                 frPVCEndptOutFrames, frPVCEndptInDEFrames,
                 frPVCEndptInExcessFrames, frPVCEndptOutExcessFrames,
                 frPVCEndptInDiscards,
                 frPVCEndptInOctets, frPVCEndptOutOctets }
       STATUS  current
       DESCRIPTION
             "A collection of objects providing information application
             to a Frame Relay PVC end-point."
       ::= { frnetservGroups 3 }

 frnetservPVCConnectGroup  OBJECT-GROUP
       OBJECTS { frPVCConnectAdminStatus, frPVCConnectL2hOperStatus,
                 frPVCConnectH2lOperStatus, frPVCConnectL2hLastChange,
                 frPVCConnectH2lLastChange,
                 frPVCConnectRowStatus }
       STATUS  current
       DESCRIPTION
             "A collection of objects providing information applicable
             to a Frame Relay PVC connection."
       ::= { frnetservGroups 4 }

 frnetservAccountPVCGroup  OBJECT-GROUP
       OBJECTS { frAccountPVCSegmentSize, frAccountPVCInSegments,
                 frAccountPVCOutSegments }
       STATUS  current
       DESCRIPTION
             "A collection of objects providing accounting
             information application
             to a Frame Relay PVC end-point."
       ::= { frnetservGroups 5 }

 frnetservAccountLportGroup  OBJECT-GROUP
       OBJECTS { frAccountLportSegmentSize, frAccountLportInSegments,
                 frAccountLportOutSegments }
       STATUS  current
       DESCRIPTION
             "A collection of objects providing accounting
             information application
             to a Frame Relay logical port."
       ::= { frnetservGroups 6 }






-- *************************************************


               atmMIB  OBJECT IDENTIFIER ::= { leanMIB 2 }


               atmMIBObjects  OBJECT IDENTIFIER ::= { atmMIB 1 }

               -- This ATM MIB Module consists of the following groups:






               -- (1) ATM Interface configuration group
               -- (2) ATM Interface DS3 PLCP group
               -- (3) ATM Interface TC Sublayer group
               -- (4) ATM Interface VPL configuration group
               -- (5) ATM Interface VCL configuration group
               -- (6) ATM VP Cross Connect group
               -- (7) ATM VC Cross Connect group
               -- (8) ATM Interface AAL5 VCC performance statistics
               --     group




               AtmTrafficDescrParamIndex ::= TEXTUAL-CONVENTION
                    STATUS     current
                    DESCRIPTION
                      "The value of this object identifies the row
                       in the atmTrafficDescrParamTable."
                    SYNTAX     Integer32

               atmTrafficDescriptorTypes  OBJECT IDENTIFIER ::=
                                                    {atmMIBObjects 1}

               -- The following values are defined for use as
               -- possible values of the ATM traffic descriptor type.
               -- ATM Forum specified seven types of ATM traffic
               -- descriptors.

               atmNoTrafficDescriptor  OBJECT-IDENTITY
                    STATUS     current
                    DESCRIPTION
                      "This identifies the no ATM traffic descriptor
                       type. Parameters 1, 2, 3, 4, and 5 are not used.
                       This traffic descriptor type can be used for
                       best effort traffic."
                    ::= { atmTrafficDescriptorTypes 1}

               atmNoClpNoScr  OBJECT-IDENTITY






                    STATUS     current
                    DESCRIPTION
                     "This traffic descriptor is for no CLP and
                      no Sustained Cell Rate.  The use of the
                      parameter vector for this type:
                      Parameter 1: CLP=0+1 peak cell rate in
                                   cells per second
                      Parameter 2: not used
                      Parameter 3: not used
                      Parameter 4: not used
                      Parameter 5: not used.
                      This traffic descriptor type can be used
                      for best effort traffic."
                  ::= { atmTrafficDescriptorTypes 2}

               atmClpNoTaggingNoScr OBJECT-IDENTITY
                    STATUS     current
                    DESCRIPTION
                     "This traffic descriptor is for no CLP without
                      tagging and no Sustained Cell Rate.  The use
                      of the parameter vector for this type:
                      Parameter 1: CLP=0+1 peak cell rate in
                                   cells per second
                      Parameter 2: CLP=0 peak cell rate in
                                   cells per second
                      Parameter 3: not used
                      Parameter 4: not used
                      Parameter 5: not used."
                    ::= { atmTrafficDescriptorTypes 3}

               atmClpTaggingNoScr OBJECT-IDENTITY
                   STATUS     current
                   DESCRIPTION
                     "This traffic descriptor is for CLP with
                      tagging and no Sustained Cell Rate.  The
                      use of the parameter vector for this type:
                      Parameter 1: CLP=0+1 peak cell rate in
                                   cells per second
                      Parameter 2: CLP=0 peak cell rate in
                                   cells per second with excess
                                   traffic tagged as CLP=1
                      Parameter 3: not used
                      Parameter 4: not used
                      Parameter 5: not used."
                   ::= { atmTrafficDescriptorTypes 4}

               atmNoClpScr OBJECT-IDENTITY
                    STATUS     current






                    DESCRIPTION
                     "This traffic descriptor is for no CLP
                      with Sustained Cell Rate.  The
                      use of the parameter vector for this type:
                      Parameter 1: CLP=0+1 peak cell rate in
                                   cells per second
                      Parameter 2: CLP=0+1 sustained cell rate in
                                   cells per second
                      Parameter 3: CLP=0+1 maximum burst size
                                   in cells
                      Parameter 4: not used
                      Parameter 5: not used."
                   ::= { atmTrafficDescriptorTypes 5}

               atmClpNoTaggingScr OBJECT-IDENTITY
                    STATUS     current
                    DESCRIPTION
                     "This traffic descriptor is for CLP
                      with Sustained Cell Rate and no tagging.
                      The use of the parameter vector for this type:
                      Parameter 1: CLP=0+1 peak cell rate in
                                   cells per second
                      Parameter 2: CLP=0 sustained cell rate in
                                   cells per second
                      Parameter 3: CLP=0 maximum burst size in cells
                      Parameter 4: not used
                      Parameter 5: not used."
                   ::= { atmTrafficDescriptorTypes 6}

               atmClpTaggingScr OBJECT-IDENTITY
                    STATUS     current
                    DESCRIPTION
                     "This traffic descriptor is for CLP
                      with tagging and Sustained Cell Rate.
                      The use of the parameter vector for this type:
                      Parameter 1: CLP=0+1 peak cell rate in
                                   cells per second
                      Parameter 2: CLP=0 sustained cell rate in
                                   cells per second with excess
                                   traffic tagged as CLP=1
                      Parameter 3: CLP=0 maximum burst size in cells
                      Parameter 4: not used
                      Parameter 5: not used."
                    ::= { atmTrafficDescriptorTypes 7}


               --    ATM Interface Configuration Parameters Group







               -- This group contains ATM specific
               -- configuration information associated with
               -- an ATM interface beyond those
               -- supported using the ifTable.


               atmInterfaceConfTable    OBJECT-TYPE
                    SYNTAX      SEQUENCE OF AtmInterfaceConfEntry
                    MAX-ACCESS   not-accessible
                    STATUS       current
                    DESCRIPTION
                     "This table contains ATM local interface
                      configuration parameters, one entry per ATM
                      interface port."
                    ::= { atmMIBObjects 2 }

               atmInterfaceConfEntry    OBJECT-TYPE
                    SYNTAX         AtmInterfaceConfEntry
                    MAX-ACCESS     not-accessible
                    STATUS         current
                    DESCRIPTION
                     "This list contains ATM interface configuration
                      parameters and state variables."
                    INDEX { ifIndex }
                    ::= { atmInterfaceConfTable  1}

               AtmInterfaceConfEntry    ::= SEQUENCE  {
                    atmInterfaceMaxVpcs             INTEGER,
                    atmInterfaceMaxVccs             INTEGER,
                    atmInterfaceConfVpcs            INTEGER,
                    atmInterfaceConfVccs            INTEGER,
                    atmInterfaceMaxActiveVpiBits    INTEGER,
                    atmInterfaceMaxActiveVciBits    INTEGER,
                    atmInterfaceIlmiVpi             INTEGER,
                    atmInterfaceIlmiVci             INTEGER,
                    atmInterfaceAddressType         INTEGER,
                    atmInterfaceAdminAddress        OCTET STRING,
                    atmInterfaceMyNeighborIpAddress IpAddress,
                    atmInterfaceMyNeighborIfName    DisplayString
                         }

               atmInterfaceMaxVpcs    OBJECT-TYPE
                    SYNTAX       INTEGER  (0..4096)
                    MAX-ACCESS    read-write
                    STATUS         current
                    DESCRIPTION
                     "The maximum number of VPCs (PVCs and SVCs)
                      supported at this ATM interface.  At the ATM UNI,






                      the maximum number of VPCs (PVCs and SVCs)
                      ranges from 0 to 256 only."
                    ::= { atmInterfaceConfEntry 1}

               atmInterfaceMaxVccs    OBJECT-TYPE
                    SYNTAX       INTEGER  (0..65536)
                    MAX-ACCESS     read-write
                    STATUS         current
                    DESCRIPTION
                     "The maximum number of VCCs (PVCs and SVCs)
                      supported at this ATM interface."
                    ::= { atmInterfaceConfEntry 2}

               atmInterfaceConfVpcs    OBJECT-TYPE
                    SYNTAX       INTEGER  (0..4096)
                    MAX-ACCESS     read-only
                    STATUS         current
                    DESCRIPTION
                     "The number of VPCs (PVCs and SVCs)
                      configured for use at this ATM interface.
                      At the ATM UNI, the configured number of
                      VPCs (PVCs and SVCs) can range from
                      0 to 256 only."
                    ::= { atmInterfaceConfEntry 3}

               atmInterfaceConfVccs    OBJECT-TYPE
                    SYNTAX       INTEGER  (0..65536)
                    MAX-ACCESS    read-only
                    STATUS        current
                    DESCRIPTION
                     "The number of VCCs (PVCs and SVCs)
                      configured for use at the ATM interface."
                    ::= { atmInterfaceConfEntry 4}

               atmInterfaceMaxActiveVpiBits    OBJECT-TYPE
                    SYNTAX           INTEGER  (0..12)
                    MAX-ACCESS         read-write
                    STATUS             current
                    DESCRIPTION
                     "The  maximum number of active VPI bits
                      configured for use at the ATM interface.
                      At the ATM UNI, the maximum number of active
                      VPI bits configured for use ranges from
                      0 to 8 only."
                    ::= { atmInterfaceConfEntry 5}

               atmInterfaceMaxActiveVciBits    OBJECT-TYPE
                    SYNTAX             INTEGER  (0..16)






                    MAX-ACCESS         read-write
                    STATUS             current
                    DESCRIPTION
                     "The maximum number of active VCI bits
                      configured for use at this ATM interface."
                    ::= { atmInterfaceConfEntry 6}

               atmInterfaceIlmiVpi         OBJECT-TYPE
                    SYNTAX          INTEGER (0..255)
                    MAX-ACCESS       read-write
                    STATUS           current
                    DESCRIPTION
                     "The VPI value of the VCC supporting
                      the ILMI at this ATM interface.  If the values of
                      atmInterfaceIlmiVpi and atmInterfaceIlmiVci are
                      both equal to zero then the ILMI is not
                      supported at this ATM interface."
                    DEFVAL { 0 }
                    ::= { atmInterfaceConfEntry 7}

               atmInterfaceIlmiVci         OBJECT-TYPE
                    SYNTAX          INTEGER (0..65535)
                    MAX-ACCESS       read-write
                    STATUS           current
                    DESCRIPTION
                     "The VCI value of the VCC supporting
                      the ILMI at this ATM interface.  If the values of
                      atmInterfaceIlmiVpi and atmInterfaceIlmiVci are
                      both equal to zero then the ILMI is not
                      supported at this ATM interface."
                    DEFVAL { 16 }
                    ::= { atmInterfaceConfEntry 8}

               atmInterfaceAddressType    OBJECT-TYPE
                    SYNTAX      INTEGER {
                                         private(1),
                                         nsapE164(2),
                                         nativeE164(3),
                                         other(4)
                                        }
                    MAX-ACCESS    read-only
                    STATUS        current
                    DESCRIPTION
                     "The type of primary ATM address configured
                      for use at this ATM interface."
                    ::= { atmInterfaceConfEntry 9 }

               atmInterfaceAdminAddress    OBJECT-TYPE





                    SYNTAX      OCTET STRING (SIZE(0..255))
                    MAX-ACCESS    read-only
                    STATUS        current
                    DESCRIPTION
                     "An address assigned for administrative purposes,
                      for example, an address associated with the
                      service provider side of a public network UNI.
                      If this interface has no assigned administrative
                      address, or when the address used for
                      administrative  purposes is the same as that used
                      for ifPhysAddress, then this is an octet string of
                      zero length."
                    ::= { atmInterfaceConfEntry 10 }

               atmInterfaceMyNeighborIpAddress OBJECT-TYPE
                    SYNTAX       IpAddress
                    MAX-ACCESS   read-write
                    STATUS       current
                    DESCRIPTION
                     "The IP address of the neighbor system connected to
                      the  far end of this interface, to which a Network
                      Management Station can send SNMP messages, as IP
                      datagrams sent to UDP port 161, in order to access
                      network management information concerning the
                      operation of that system.  Note that the value
                      of this object may be obtained in different ways,
                      e.g., by manual configuration, or through ILMI
                      interaction with the neighbor system."
                    ::= { atmInterfaceConfEntry 11 }

               atmInterfaceMyNeighborIfName    OBJECT-TYPE
                    SYNTAX       DisplayString
                    MAX-ACCESS   read-write
                    STATUS       current
                    DESCRIPTION
                     "The textual name of the interface on the neighbor
                      system on the far end of this interface, and to
                      which this interface connects.  If the neighbor
                      system is manageable through SNMP and supports
                      the object ifName, the value of this object must
                      be identical with that of ifName for the ifEntry
                      of the lowest level physical interface
                      for this port.  If this interface does not have a
                      textual name, the value of this object is a zero
                      length string.  Note that the value of this object
                      may be obtained in different ways, e.g., by manual
                      configuration, or through ILMI interaction with
                      the neighbor system."






                    ::= { atmInterfaceConfEntry 12 }


               -- The ATM Interface DS3 PLCP Group

               -- This group contains the DS3 PLCP configuration and
               -- state parameters of those ATM interfaces
               -- which use DS3 PLCP for carrying ATM cells over DS3.

               atmInterfaceDs3PlcpTable    OBJECT-TYPE
                    SYNTAX      SEQUENCE OF AtmInterfaceDs3PlcpEntry
                    MAX-ACCESS   not-accessible
                    STATUS       current
                    DESCRIPTION
                     "This table contains ATM interface DS3 PLCP
                      parameters and state variables, one entry per
                      ATM interface port."
                    ::= { atmMIBObjects 3}

               atmInterfaceDs3PlcpEntry    OBJECT-TYPE
                    SYNTAX       AtmInterfaceDs3PlcpEntry
                    MAX-ACCESS   not-accessible
                    STATUS       current
                    DESCRIPTION
                     "This list contains DS3 PLCP parameters and
                      state variables at the ATM interface."
                    INDEX    {ifIndex }
                    ::= { atmInterfaceDs3PlcpTable 1}

               AtmInterfaceDs3PlcpEntry    ::= SEQUENCE  {
                    atmInterfaceDs3PlcpSEFSs         Counter32,
                    atmInterfaceDs3PlcpAlarmState    INTEGER,
                    atmInterfaceDs3PlcpUASs          Counter32
                      }


               atmInterfaceDs3PlcpSEFSs    OBJECT-TYPE
                    SYNTAX       Counter32
                    MAX-ACCESS   read-only
                    STATUS       current
                    DESCRIPTION
                     "The number of DS3 PLCP Severely Errored Framing
                      Second (SEFS).  Each SEFS represents a
                      one-second interval which contains
                      one or more SEF event."
                    ::= { atmInterfaceDs3PlcpEntry 1}

               atmInterfaceDs3PlcpAlarmState    OBJECT-TYPE






                    SYNTAX       INTEGER {
                                          noAlarm(1),
                                          receivedFarEndAlarm(2),
                                          incomingLOF(3)
                                                }
                    MAX-ACCESS     read-only
                    STATUS         current
                    DESCRIPTION
                     "This variable indicates if there is an
                      alarm present for the DS3 PLCP.  The value
                      receivedFarEndAlarm means that the DS3 PLCP
                      has received an incoming Yellow
                      Signal, the value incomingLOF means that
                      the DS3 PLCP has declared a loss of frame (LOF)
                      failure condition, and the value noAlarm
                      means that there are no alarms present.
                      Transition from the failure to the no alarm state
                      occurs when no defects (e.g., LOF) are received
                      for more than 10 seconds."
                    ::= { atmInterfaceDs3PlcpEntry 2}

               atmInterfaceDs3PlcpUASs    OBJECT-TYPE
                    SYNTAX       Counter32
                    MAX-ACCESS   read-only
                    STATUS       current
                    DESCRIPTION
                     "The counter associated with the number of
                      Unavailable Seconds encountered by the PLCP."
                    ::= { atmInterfaceDs3PlcpEntry 3}


               -- The ATM Interface TC Sublayer Group

               -- This group contains TC sublayer configuration and
               -- state parameters of those ATM interfaces
               -- which use TC sublayer for carrying ATM cells over
               -- SONET or DS3.


               atmInterfaceTCTable    OBJECT-TYPE
                    SYNTAX      SEQUENCE OF AtmInterfaceTCEntry
                    MAX-ACCESS   not-accessible
                    STATUS       current
                    DESCRIPTION
                     "This table contains ATM interface TC
                      Sublayer parameters and state variables,
                      one entry per ATM interface port."
                    ::= { atmMIBObjects 4}






               atmInterfaceTCEntry    OBJECT-TYPE
                    SYNTAX          AtmInterfaceTCEntry
                    MAX-ACCESS      not-accessible
                    STATUS          current
                    DESCRIPTION
                     "This list contains TC Sublayer parameters
                      and state variables at the ATM interface."
                    INDEX  {ifIndex }
                    ::= { atmInterfaceTCTable 1}

               AtmInterfaceTCEntry    ::= SEQUENCE  {
                    atmInterfaceOCDEvents      Counter32,
                    atmInterfaceTCAlarmState   INTEGER
                      }

               atmInterfaceOCDEvents    OBJECT-TYPE
                    SYNTAX        Counter32
                    MAX-ACCESS    read-only
                    STATUS        current
                    DESCRIPTION
                     "The number of times the Out of Cell
                      Delineation (OCD) events occur.  If seven
                      consecutive ATM cells have Header Error
                      Control (HEC) violations, an OCD event occurs.
                      A high number of OCD events may indicate a
                      problem with the TC Sublayer."
                    ::= { atmInterfaceTCEntry 1}

               atmInterfaceTCAlarmState    OBJECT-TYPE
                    SYNTAX        INTEGER {
                                           noAlarm(1),
                                           lcdFailure(2)
                                            }
                    MAX-ACCESS    read-only
                    STATUS        current
                    DESCRIPTION
                     "This variable indicates if there is an
                      alarm present for the TC Sublayer.  The value
                      lcdFailure indicates that a Loss of
                      Cell Delineation (LCD) failure state has been
                      declared for the TC Sublayer.  Transition from
                      failure to the no alarm state occurs
                      when 6 consecutive ATM cells
                      are received with valid HEC, followed by
                      about 10 seconds of acceptable working signal."
                     ::= { atmInterfaceTCEntry 2}








               --  ATM Traffic Descriptor Parameter Group

               -- This group contains a set of self-consistent
               -- ATM traffic parameters including the
               -- ATM traffic QoS Class.

               -- The ATM virtual link tables (i.e., VPL and VCL tables)
               -- will use this ATM Traffic Descriptor table
               -- to assign traffic parameters and QoS Class
               -- to the receive and transmit directions of
               -- the ATM virtual links (i.e., VPLs and VCLs).
               -- The ATM VPL or VCL table will indicate a row
               -- in the atmTrafficDescrParamTable
               -- using its atmTrafficDescrParamIndex value.
               -- The management application can then compare a set of
               -- ATM traffic parameters with a single value.

               -- If no suitable row(s) in the atmTrafficDescrParamTable
               -- exists, the manager must create a new row(s) in this
               -- table. If such a row is created, agent checks the
               -- sanity of that set of ATM traffic parameter values.

               -- When creating a new row, the parameter values
               -- will be checked for self-consistency.
               -- Predefined/template rows may be supported.

               -- A row in the atmTrafficDescrParamTable is deleted
               -- by setting the atmTrafficDescrRowStatus to destroy(6).
               -- The agent will check whether this row is still in use
               -- by any entry of the atmVplTable or atmVclTable.
               -- The agent denies the request if the row is still in
               -- use.

               --  The ATM Traffic Descriptor Parameter Table


               atmTrafficDescrParamTable    OBJECT-TYPE
                    SYNTAX      SEQUENCE OF AtmTrafficDescrParamEntry
                    MAX-ACCESS   not-accessible
                    STATUS       current
                    DESCRIPTION
                     "This table contains information on ATM traffic
                      descriptor type and the associated parameters."
                    ::= { atmMIBObjects 5}

               atmTrafficDescrParamEntry    OBJECT-TYPE
                    SYNTAX           AtmTrafficDescrParamEntry
                    MAX-ACCESS       not-accessible






                    STATUS           current
                    DESCRIPTION
                     "This list contains ATM traffic descriptor
                      type and the associated parameters."
                    INDEX  {atmTrafficDescrParamIndex}
                    ::= { atmTrafficDescrParamTable  1}

               AtmTrafficDescrParamEntry    ::= SEQUENCE  {
                 atmTrafficDescrParamIndex   AtmTrafficDescrParamIndex,
                 atmTrafficDescrType         OBJECT IDENTIFIER,
                 atmTrafficDescrParam1       Integer32,
                 atmTrafficDescrParam2       Integer32,
                 atmTrafficDescrParam3       Integer32,
                 atmTrafficDescrParam4       Integer32,
                 atmTrafficDescrParam5       Integer32,
                 atmTrafficQoSClass          INTEGER,
                 atmTrafficDescrRowStatus    RowStatus
                              }

               atmTrafficDescrParamIndex    OBJECT-TYPE
                    SYNTAX           AtmTrafficDescrParamIndex
                    MAX-ACCESS       not-accessible
                    STATUS        current
                    DESCRIPTION
                     "This object is used by the virtual link
                      table (i.e., VPL or VCL table)
                      to identify the row of this table."
                    ::= { atmTrafficDescrParamEntry  1}

               atmTrafficDescrType    OBJECT-TYPE
                    SYNTAX             OBJECT IDENTIFIER
                    MAX-ACCESS         read-create
                    STATUS             current
                    DESCRIPTION
                     "The value of this object identifies the type
                      of ATM traffic descriptor.
                      The type may indicate no traffic descriptor or
                      traffic descriptor with one or more parameters.
                      These parameters are specified as a parameter
                      vector, in the corresponding instances of the
                      objects:
                          atmTrafficDescrParam1
                          atmTrafficDescrParam2
                          atmTrafficDescrParam3
                          atmTrafficDescrParam4
                          atmTrafficDescrParam5."
                     DEFVAL  { atmNoTrafficDescriptor }
                     ::= { atmTrafficDescrParamEntry 2}






               atmTrafficDescrParam1    OBJECT-TYPE
                    SYNTAX             Integer32
                    MAX-ACCESS          read-create
                    STATUS              current
                    DESCRIPTION
                     "The first parameter of the ATM traffic descriptor
                      used according to the value of
                      atmTrafficDescrType."
                    DEFVAL  { 0 }
                    ::= { atmTrafficDescrParamEntry 3}

               atmTrafficDescrParam2    OBJECT-TYPE
                    SYNTAX             Integer32
                    MAX-ACCESS          read-create
                    STATUS              current
                    DESCRIPTION
                     "The second parameter of the ATM traffic descriptor
                      used according to the value of
                      atmTrafficDescrType."
                    DEFVAL  { 0 }
                    ::= { atmTrafficDescrParamEntry 4}

               atmTrafficDescrParam3    OBJECT-TYPE
                    SYNTAX             Integer32
                    MAX-ACCESS          read-create
                    STATUS              current
                    DESCRIPTION
                     "The third parameter of the ATM traffic descriptor
                      used according to the value of
                      atmTrafficDescrType."
                    DEFVAL  { 0 }
                    ::= { atmTrafficDescrParamEntry 5}

               atmTrafficDescrParam4    OBJECT-TYPE
                    SYNTAX             Integer32
                    MAX-ACCESS          read-create
                    STATUS              current
                    DESCRIPTION
                     "The fourth parameter of the ATM traffic descriptor
                      used according to the value of
                      atmTrafficDescrType."
                    DEFVAL  { 0 }
                    ::= { atmTrafficDescrParamEntry 6}

               atmTrafficDescrParam5    OBJECT-TYPE
                    SYNTAX             Integer32
                    MAX-ACCESS          read-create
                    STATUS              current






                    DESCRIPTION
                     "The fifth parameter of the ATM traffic descriptor
                      used according to the value of
                      atmTrafficDescrType."
                    DEFVAL  { 0 }
                    ::= { atmTrafficDescrParamEntry 7}

               atmTrafficQoSClass   OBJECT-TYPE
                    SYNTAX         INTEGER (0..255)
                    MAX-ACCESS      read-create
                    STATUS          current
                    DESCRIPTION
                     "The value of this object identifies the QoS Class.
                      Four Service classes have been
                      specified in the ATM Forum UNI Specification:
                      Service Class A: Constant bit rate video and
                                       Circuit emulation
                      Service Class B: Variable bit rate video/audio
                      Service Class C: Connection-oriented data
                      Service Class D: Connectionless data
                      Four QoS classes numbered 1, 2, 3, and 4 have
                      been specified with the aim to support service
                      classes A, B, C, and D respectively.
                      An unspecified QoS Class numbered `0' is used
                      for best effort traffic."
                    DEFVAL  { 0 }
                    ::= { atmTrafficDescrParamEntry 8}


               atmTrafficDescrRowStatus       OBJECT-TYPE
                    SYNTAX    RowStatus
                    MAX-ACCESS   read-create
                    STATUS          current
                    DESCRIPTION
                     "This object is used to create
                      a new row or modify or delete an
                      existing row in this table."
                    DEFVAL  { active }
                    ::= {atmTrafficDescrParamEntry 9}


               --  ATM Interface Virtual Path Link (VPL) Group

               -- This group contains configuration and state
               -- information of a bi-directional Virtual Path Link
               -- (VPL)

               -- This table can be used to create, delete or modify






               -- a VPL that is terminated in an ATM host or switch.
               -- This table can also be used to create, delete or
               -- modify a VPL which is cross-connected to another
               -- VPL.

               -- In the example below, the traffic flows on the receive
               -- and transmit directions of the VPLs are characterized
               -- by atmVplReceiveTrafficDescrIndex and
               -- atmVplTransmitTrafficDescrIndex respectively.
               -- The cross-connected VPLs are identified by
               -- atmVplCrossConnectIdentifier.



               --           ________________________________
               --           |                              |
               --  VPL      | ATM Host, Switch, or Network |   VPL
               -- receive   |                              |  receive
               -- ========> X                              X <=======
               -- <======== X                              X ========>
               -- transmit  |                              |  transmit
               --           |______________________________|



               --  The ATM Interface VPL Table


               atmVplTable    OBJECT-TYPE
                    SYNTAX      SEQUENCE OF AtmVplEntry
                    MAX-ACCESS   not-accessible
                    STATUS       current
                    DESCRIPTION
                     "The Virtual Path Link (VPL) table.  A
                      bi-directional VPL is modeled as one entry
                      in this table."
                    ::= { atmMIBObjects 6}

               atmVplEntry    OBJECT-TYPE
                    SYNTAX           AtmVplEntry
                    MAX-ACCESS       not-accessible
                    STATUS           current
                    DESCRIPTION
                     "An entry in the VPL table.  This entry is
                      used to model a bi-directional VPL.
                      To create a VPL at an ATM interface,
                      either of the following procedures are used:







                      Negotiated VPL establishment

                    (1) The management application creates
                        a VPL entry in the atmVplTable
                        by setting atmVplRowStatus to createAndWait(5).
                        This may fail for the following reasons:
                        - The selected VPI value is unavailable,
                        - The selected VPI value is in use.
                        Otherwise, the agent creates a row and
                        reserves the VPI value on that port.

                    (2) The manager selects an existing row(s) in the
                        atmTrafficDescrParamTable,
                        thereby, selecting a set of self-consistent
                        ATM traffic parameters and the QoS Class
                        for receive and transmit directions of the VPL.

                   (2a) If no suitable row(s) in the
                        atmTrafficDescrParamTable exists,
                        the manager must create a new row(s)
                        in that table.

                   (2b) The manager characterizes the VPL's traffic
                        parameters through setting the
                        atmVplReceiveTrafficDescrIndex and the
                        atmVplTransmitTrafficDescrIndex values
                        in the VPL table, which point to the rows
                        containing desired ATM traffic parameter values
                        in the atmTrafficDescrParamTable.  The agent
                        will check the availability of resources and
                        may refuse the request.

                    (3) The manager activates the VPL by setting the
                        the atmVplRowStatus to active(1).
                        If this set is successful, the agent has
                        reserved the resources to satisfy the requested
                        traffic parameter values and the QoS Class
                        for that VPL.
                    (4) If the VPL terminates a VPC in the ATM host
                        or switch, the manager turns on the
                        atmVplAdminStatus to up(1) to turn the VPL
                        traffic flow on.  Otherwise, the
                        atmVpCrossConnectTable  must be used
                        to cross-connect the VPL to another VPL(s)
                        in an ATM switch or network.

                      One-Shot VPL Establishment







                      A VPL may also be established in one step by a
                      set-request with all necessary VPL parameter
                      values and atmVplRowStatus set to createAndGo(4).

                      In contrast to the negotiated VPL establishment
                      which allows for detailed error checking
                      (i.e., set errors are explicitly linked to
                      particular resource acquisition failures),
                      the one-shot VPL establishment
                      performs the setup on one operation but
                      does not have the advantage of step-wise
                      error checking.

                      VPL Retirement

                      A VPL is released by setting atmVplRowStatus to
                      destroy(6), and the agent may release all
                      associated resources."
                    INDEX  {ifIndex, atmVplVpi }
                    ::= { atmVplTable  1}

               AtmVplEntry    ::= SEQUENCE  {
                    atmVplVpi                       INTEGER,
                    atmVplAdminStatus               INTEGER,
                    atmVplOperStatus                INTEGER,
                    atmVplLastChange                TimeStamp,
                    atmVplReceiveTrafficDescrIndex
                                    AtmTrafficDescrParamIndex,
                    atmVplTransmitTrafficDescrIndex
                                    AtmTrafficDescrParamIndex,
                    atmVplCrossConnectIdentifier    INTEGER,
                    atmVplRowStatus                 RowStatus
                       }


               atmVplVpi    OBJECT-TYPE
                    SYNTAX    INTEGER  (1..4095)
                    MAX-ACCESS     not-accessible
                    STATUS         current
                    DESCRIPTION
                     "The VPI value of the VPL.
                      Note that the VPI=0 is not used
                      for a VPL not associated with a VCL.
                      The maximum VPI value cannot
                      exceed the value allowable by the
                      atmInterfaceMaxVpiBits."
                    ::= { atmVplEntry 1}







               atmVplAdminStatus   OBJECT-TYPE
                    SYNTAX   INTEGER  {
                                       up(1),
                                       down(2)
                                           }
                    MAX-ACCESS   read-create
                    STATUS       current
                    DESCRIPTION
                     "This object is implemented only for a VPL which
                      terminates a VPC (i.e.,
                      one which is NOT cross-connected to other VPLs).
                      Its value specifies the desired administrative
                      state of the VPL.  The up and down states indicate
                      that the traffic flow is enabled and disabled
                      respectively for this VPL."
                    DEFVAL { down }                    ::= { atmVplEntry 2}


               atmVplOperStatus   OBJECT-TYPE
                    SYNTAX   INTEGER  {
                                       up(1),
                                       down(2),
                                       unknown(3)
                                           }
                    MAX-ACCESS   read-only
                    STATUS       current
                    DESCRIPTION
                     "This object indicates the current operational
                      status of the VPL.  The up and down states
                      indicate that the VPL is currently
                      operational, or not operational, respectively.
                      The unknown state indicates that the status of
                      this VPL cannot be determined."
                    ::= { atmVplEntry 3}

               atmVplLastChange     OBJECT-TYPE
                    SYNTAX  TimeStamp
                    MAX-ACCESS  read-only
                    STATUS  current
                    DESCRIPTION
                     "The value of MIB II's sysUpTime object
                      at the time this VPL entered its current
                      operational state.  If the current state was
                      entered prior to the last re-initialization of the
                      agent, then this object contains a zero value."
                    ::= { atmVplEntry 4 }







               atmVplReceiveTrafficDescrIndex    OBJECT-TYPE
                    SYNTAX             AtmTrafficDescrParamIndex
                    MAX-ACCESS         read-create
                    STATUS             current
                    DESCRIPTION
                     "The value of this object identifies the row
                      in the atmTrafficDescrParamTable which
                      applies to the receive direction of the VPL."
                     ::= { atmVplEntry 5}

               atmVplTransmitTrafficDescrIndex    OBJECT-TYPE
                    SYNTAX             AtmTrafficDescrParamIndex
                    MAX-ACCESS         read-create
                    STATUS             current
                    DESCRIPTION
                     "The value of this object identifies the row
                      in the atmTrafficDescrParamTable which
                      applies to the transmit direction of the VPL."
                     ::= { atmVplEntry 6}

               atmVplCrossConnectIdentifier   OBJECT-TYPE
                    SYNTAX         INTEGER (0..2147483647)
                    MAX-ACCESS      read-only
                    STATUS          current
                    DESCRIPTION
                     "This object is implemented only for a VPL
                      which is cross-connected to other VPLs
                      that belong to the same VPC.  All such
                      associated VPLs have the same value of this
                      object, and all their cross-connections are
                      identified by entries in the
                      atmVpCrossConnectTable for which
                      atmVpCrossConnectIndex has the same value.
                      The value of this object is initialized by the
                      agent after the associated entries in the
                      atmVpCrossConnectTable have been created."
                    ::= {atmVplEntry 7}

               atmVplRowStatus       OBJECT-TYPE
                    SYNTAX    RowStatus
                    MAX-ACCESS   read-create
                    STATUS          current
                    DESCRIPTION
                     "This object is used to create, delete
                      or modify a row in this table.
                      To create a new VCL, this object is
                      initially set to 'createAndWait' or
                      'createAndGo'.  This object must not be






                      set to 'active' unless the following columnar
                      objects exist in this row:
                      atmVplReceiveTrafficDescrIndex and
                      atmVplTransmitTrafficDescrIndex."
                    DEFVAL { active }
                    ::= {atmVplEntry 8}


               --  ATM Interface Virtual Channel Link (VCL) Group

               -- This group contains configuration and state
               -- information of a bi-directional Virtual Channel
               -- Link (VCL) at an ATM interface.

               -- This table can be used to create, delete or modify
               -- a VCL that is terminated in an ATM host or switch.
               -- This table can also be
               -- used to create, delete or modify a VCL that is
               -- cross-connected to another VCL.


               --  The ATM Interface VCL Table


               atmVclTable    OBJECT-TYPE
                    SYNTAX      SEQUENCE OF AtmVclEntry
                    MAX-ACCESS   not-accessible
                    STATUS       current
                    DESCRIPTION
                     "The Virtual Channel Link (VCL) table.  A
                      bi-directional VCL is modeled as one entry
                      in this table."
                    ::= { atmMIBObjects 7}

               atmVclEntry    OBJECT-TYPE
                    SYNTAX           AtmVclEntry
                    MAX-ACCESS       not-accessible
                    STATUS           current
                    DESCRIPTION
                     "An entry in the VCL table.  This entry is
                      used to model a bi-directional VCL.
                      To create a VCL at an ATM interface,
                      either of the following procedures are used:

                      Negotiated VCL establishment

                    (1) The management application creates
                        a VCL entry in the atmVclTable






                        by setting atmVclRowStatus to createAndWait(5).
                        This may fail for the following reasons:
                        - The selected VPI/VCI values are unavailable,
                        - The selected VPI/VCI values are in use.
                        Otherwise, the agent creates a row and
                        reserves the VPI/VCI values on that port.

                    (2) The manager selects an existing row(s) in the
                        atmTrafficDescrParamTable,
                        thereby, selecting a set of self-consistent
                        ATM traffic parameters and the QoS Class
                        for receive and transmit directions of the VCL.

                   (2a) If no suitable row(s) in the
                        atmTrafficDescrParamTable exists,
                        the manager must create a new row(s)
                        in that table.

                   (2b) The manager characterizes the VCL's traffic
                        parameters through setting the
                        atmVclReceiveTrafficDescrIndex and the
                        atmVclTransmitTrafficDescrIndex values
                        in the VCL table, which point to the rows
                        containing desired ATM traffic parameter values
                        in the atmTrafficDescrParamTable.  The agent
                        will check the availability of resources and
                        may refuse the request.

                    (3) The manager activates the VCL by setting the
                        the atmVclRowStatus to active(1).
                        If this set is successful, the agent has
                        reserved the resources to satisfy the requested
                        traffic parameter values and the QoS Class
                        for that VCL.
                    (4) If the VCL terminates a VCC in the ATM host
                        or switch, the manager turns on the
                        atmVclAdminStatus to up(1) to turn the VCL
                        traffic flow on.  Otherwise, the
                        atmVcCrossConnectTable  must be used
                        to cross-connect the VCL to another VCL(s)
                        in an ATM switch or network.

                     One-Shot VCL Establishment

                     A VCL may also be established in one step by a
                     set-request with all necessary VCL parameter
                     values and atmVclRowStatus set to createAndGo(4).







                     In contrast to the negotiated VCL establishment
                     which allows for detailed error checking
                     (i.e., set errors are explicitly linked to
                     particular resource acquisition failures),
                     the one-shot VCL establishment
                     performs the setup on one operation but
                     does not have the advantage of step-wise
                     error checking.

                     VCL Retirement

                     A VCL is released by setting atmVclRowStatus to
                     destroy(6), and the agent may release all
                     associated resources."
                    INDEX  {ifIndex, atmVclVpi, atmVclVci }
                    ::= { atmVclTable  1}

               AtmVclEntry    ::= SEQUENCE  {
                    atmVclVpi                       INTEGER,
                    atmVclVci                       INTEGER,
                    atmVclAdminStatus               INTEGER,
                    atmVclOperStatus                INTEGER,
                    atmVclLastChange                TimeStamp,
                    atmVclReceiveTrafficDescrIndex
                                    AtmTrafficDescrParamIndex,
                    atmVclTransmitTrafficDescrIndex
                                    AtmTrafficDescrParamIndex,
                    atmVccAalType                   INTEGER,
                    atmVccAal5CpcsTransmitSduSize   INTEGER,
                    atmVccAal5CpcsReceiveSduSize    INTEGER,
                    atmVccAal5EncapsType            INTEGER,
                    atmVclCrossConnectIdentifier    INTEGER,
                    atmVclRowStatus                 RowStatus
                           }

               atmVclVpi    OBJECT-TYPE
                    SYNTAX    INTEGER  (0..4095)
                    MAX-ACCESS     not-accessible
                    STATUS         current
                    DESCRIPTION
                     "The VPI value of the VCL.
                      The maximum VPI value cannot
                      exceed the value allowable by the
                      atmInterfaceMaxVpiBits."
                    ::= { atmVclEntry 1}

               atmVclVci    OBJECT-TYPE
                    SYNTAX    INTEGER  (0..65535)






                    MAX-ACCESS     not-accessible
                    STATUS         current
                    DESCRIPTION
                     "The VCI value of the VCL.
                      The maximum VCI value cannot
                      exceed the value allowable by the
                      atmInterfaceMaxVciBits."
                    ::= { atmVclEntry 2}

               atmVclAdminStatus   OBJECT-TYPE
                    SYNTAX   INTEGER  {
                                       up(1),
                                       down(2)
                                           }
                    MAX-ACCESS   read-create
                    STATUS       current
                    DESCRIPTION
                     "This object is implemented only for a VCL which
                      terminates a VCC (i.e.,
                      one which is NOT cross-connected to other VCLs).
                      Its value specifies the desired administrative
                      state of the VCL.  The up and down states indicate
                      that the traffic flow is enabled and disabled
                      respectively for this VCL."
                    ::= { atmVclEntry 3}

               atmVclOperStatus   OBJECT-TYPE
                    SYNTAX   INTEGER  {
                                       up(1),
                                       down(2),
                                       unknown(3)
                                           }
                    MAX-ACCESS   read-only
                    STATUS       current
                    DESCRIPTION
                     "This object indicates the current operational
                      status of the VCL.  The up and down states
                      indicate that the VCL is currently
                      operational, or not operational, respectively.
                      The unknown state indicates that the status of
                      this VCL cannot be determined."
                    ::= { atmVclEntry 4}

               atmVclLastChange     OBJECT-TYPE
                    SYNTAX  TimeStamp
                    MAX-ACCESS  read-only
                    STATUS  current
                    DESCRIPTION






                     "The value of MIB II's sysUpTime object
                      at the time this VCL entered its current
                      operational state.  If the current state was
                      entered prior to the last re-initialization of the
                      agent, then this object contains a zero value."
                    ::= { atmVclEntry 5 }

               atmVclReceiveTrafficDescrIndex    OBJECT-TYPE
                    SYNTAX             AtmTrafficDescrParamIndex
                    MAX-ACCESS         read-create
                    STATUS             current
                    DESCRIPTION
                     "The value of this object identifies the row
                      in the ATM Traffic Descriptor Table which
                      applies to the receive direction of this VCL."
                     ::= { atmVclEntry 6}

               atmVclTransmitTrafficDescrIndex    OBJECT-TYPE
                    SYNTAX             AtmTrafficDescrParamIndex
                    MAX-ACCESS         read-create
                    STATUS             current
                    DESCRIPTION
                     "The value of this object identifies the row
                      of the ATM Traffic Descriptor Table which applies
                      to the transmit direction of this VCL."
                     ::= { atmVclEntry 7}

               atmVccAalType    OBJECT-TYPE
                    SYNTAX      INTEGER {
                                         aal1(1),
                                         aal34(2),
                                         aal5(3),
                                         other(4),
                                         unknown(5)
                                        }
                    MAX-ACCESS    read-create
                    STATUS        current
                    DESCRIPTION
                     "An instance of this object only exists when the
                      local VCL end-point is also the VCC end-point,
                      and AAL is in use.
                      The type of AAL used on this VCC.
                      The AAL type includes AAL1, AAL3/4,
                      and AAL5. The other(4) may be user-defined
                      AAL type.  The unknown type indicates that
                      the AAL type cannot be determined."
                    ::= { atmVclEntry 8 }







               atmVccAal5CpcsTransmitSduSize OBJECT-TYPE
                    SYNTAX      INTEGER (1..65535)
                    MAX-ACCESS   read-create
                    STATUS       current
                    DESCRIPTION
                     "An instance of this object only exists when the
                      local VCL end-point is also the VCC end-point,
                      and AAL5 is in use.
                      The maximum AAL5 CPCS SDU size in octets that is
                      supported on the transmit direction of this VCC."
                    DEFVAL { 9188 }
                          ::= { atmVclEntry 9 }

               atmVccAal5CpcsReceiveSduSize OBJECT-TYPE
                    SYNTAX      INTEGER (1..65535)
                    MAX-ACCESS   read-create
                    STATUS       current
                    DESCRIPTION
                     "An instance of this object only exists when the
                      local VCL end-point is also the VCC end-point,
                      and AAL5 is in use.
                      The maximum AAL5 CPCS SDU size in octets that is
                      supported on the receive direction of this VCC."
                    DEFVAL { 9188 }
                          ::= { atmVclEntry 10 }

               atmVccAal5EncapsType  OBJECT-TYPE
                    SYNTAX   INTEGER {
                                   vcMultiplexRoutedProtocol(1),
                                   vcMultiplexBridgedProtocol8023(2),
                                   vcMultiplexBridgedProtocol8025(3),
                                   vcMultiplexBridgedProtocol8026(4),
                                   vcMultiplexLANemulation8023(5),
                                   vcMultiplexLANemulation8025(6),
                                   llcEncapsulation(7),
                                   multiprotocolFrameRelaySscs(8),
                                   other(9),
                                   unknown(10)
                                      }
                    MAX-ACCESS   read-create
                    STATUS        current
                    DESCRIPTION
                     "An instance of this object only exists when the
                      local VCL end-point is also the VCC end-point,
                      and AAL5 is in use.
                      The type of data encapsulation used over
                      the AAL5 SSCS layer. The definitions reference
                      RFC 1483 Multiprotocol Encapsulation






                      over ATM AAL5 and to the ATM Forum
                      LAN Emulation specification."
                    DEFVAL { llcEncapsulation }
                          ::= { atmVclEntry 11 }

               atmVclCrossConnectIdentifier   OBJECT-TYPE
                    SYNTAX         INTEGER (0..2147483647)
                    MAX-ACCESS      read-only
                    STATUS          current
                    DESCRIPTION
                     "This object is implemented only for a VCL
                      which is cross-connected to other VCLs
                      that belong to the same VCC.  All such
                      associated VCLs have the same value of this
                      object, and all their cross-connections are
                      identified by entries in the
                      atmVcCrossConnectTable for which
                      atmVcCrossConnectIndex has the same value.
                      The value of this object is initialized by the
                      agent after the associated entries in the
                      atmVcCrossConnectTable have been created."
                    ::= {atmVclEntry 12}

               atmVclRowStatus          OBJECT-TYPE
                    SYNTAX       RowStatus
                    MAX-ACCESS   read-create
                    STATUS       current
                    DESCRIPTION
                     "This object is used to create, delete or
                      modify a row in this table.  To create
                      a new VCL, this object is initially set
                      to 'createAndWait' or 'createAndGo'.
                      This object must not be set to 'active'
                      unless the following columnar objects exist
                      in this row:
                      atmVclReceiveTrafficDescrIndex,
                      atmVclTransmitTrafficDescrIndex.
                      In addition, if the local VCL end-point
                      is also the VCC end-point:
                      atmVccAalType.
                      In addition, for AAL5 connections only:
                      atmVccAal5CpcsTransmitSduSize,
                      atmVccAal5CpcsReceiveSduSize, and
                      atmVccAal5EncapsType."
                    DEFVAL { active }
                          ::= {atmVclEntry 13}








               --     ATM Virtual Path (VP) Cross Connect Group

               -- This group contains configuration and state
               -- information of all point-to-point,
               -- point-to-multipoint, or multipoint-to-multipoint
               -- VP cross-connects.

               -- This table has read-create access and can be used
               -- to cross-connect the VPLs together in an ATM switch
               -- or network. The atmVpCrossConnectIndex
               -- is used to associate the related
               -- VPLs that are cross-connected together.

               -- The ATM VP Cross Connect Group
               -- models each bi-directional VPC
               -- cross-connect as a set of entries in
               -- the atmVpCrossConnectTable. A
               -- point-to-point VPC cross-connect is modeled
               -- as one entry; a point-to-multipoint (N leafs) VPC
               -- cross-connect as N entries in this table; and
               -- a multipoint-to-multipoint (N parties) VPC cross-
               -- connect as N(N-1)/2 entries in this table.
               -- In the latter cases, all the N (or N(N-1)/2) entries
               -- are associated with a single VPC cross-connect by
               -- having the same value of atmVpCrossConnectIndex.


               --      _________________________________________
               --      |                                       |
               --  Low |         ATM Switch or Network         | High
               --  port|                                       | port
               -- _____|>> from low to high VPC traffic flow >>|______
               --      |<< from high to low VPC traffic flow <<|
               --      |                                       |
               --      |_______________________________________|
               --

               -- The terms low and high are chosen to represent
               -- numerical ordering of the two interfaces associated
               -- with a VPC cross-connect. That is, the ATM interface
               -- with the lower value of ifIndex is termed 'low',
               -- while the other ATM interface associated with the
               -- VPC cross-connect is termed 'high'. This terminology
               -- is used to provide directional information; for
               -- example, the atmVpCrossConnectL2HOperStatus applies
               -- to the low->high direction, and
               -- atmVpCrossConnectH2LOperStatus applies to the
               -- high->low  direction, as illustrated above.






               atmVpCrossConnectIndexNext    OBJECT-TYPE
                    SYNTAX  INTEGER (0..2147483647)
                    MAX-ACCESS  read-only
                    STATUS  current
                    DESCRIPTION
                     "This object contains an appropriate value to
                      be used for atmVpCrossConnectIndex when creating
                      entries in the atmVpCrossConnectTable.  The value
                      0 indicates that no unassigned entries are
                      available. To obtain the atmVpCrossConnectIndex
                      value for a new entry, the manager issues a
                      management protocol retrieval operation to obtain
                      the current value of this object.  After each
                      retrieval, the agent should modify the value to
                      the next unassigned index."
                    ::= { atmMIBObjects 8 }


               --  The ATM VP Cross Connect Table


               atmVpCrossConnectTable OBJECT-TYPE
                    SYNTAX  SEQUENCE OF AtmVpCrossConnectEntry
                    MAX-ACCESS  not-accessible
                    STATUS  current
                    DESCRIPTION
                     "The ATM VP Cross Connect table.  A bi-
                      directional VP cross-connect which
                      cross-connects two VPLs is modeled
                      as one entry in this table."
                    ::= { atmMIBObjects 9 }


               atmVpCrossConnectEntry OBJECT-TYPE
                    SYNTAX  AtmVpCrossConnectEntry
                    MAX-ACCESS  not-accessible
                    STATUS  current
                    DESCRIPTION
                     "An entry in the ATM VP Cross Connect table.
                      This entry is used to model a bi-directional
                      ATM VP cross-connect which cross-connects
                      two VPLs.

                      Step-wise Procedures to set up a VP Cross-connect

                      Once the entries in the atmVplTable are created,
                      the following procedures are used
                      to cross-connect the VPLs together.






                     (1) The manager obtains a unique
                         atmVpCrossConnectIndex by reading the
                         atmVpCrossConnectIndexNext object.

                     (2) Next, the manager creates a set of one
                         or more rows in the ATM VP Cross Connect
                         Table, one for each cross-connection between
                         two VPLs.  Each row is indexed by the ATM
                         interface port numbers and VPI values of the
                         two ends of that cross-connection.
                         This set of rows specifies the topology of the
                         VPC cross-connect and is identified by a single
                         value of atmVpCrossConnectIndex.

                      Negotiated VP Cross-Connect Establishment

                    (2a) The manager creates a row in this table by
                         setting atmVpCrossConnectRowStatus to
                         createAndWait(5).  The agent checks the
                         requested topology and the mutual sanity of
                         the ATM traffic parameters and
                         QoS Classes, i.e., the row creation fails if:
                         - the requested topology is not supported
                           by the agent,                         - the traffic/QoS parameter values
                           associated with the requested row are
                           incompatible with those of already existing
                           rows for this VP cross-connect.
                         [For example, for setting up
                         a point-to-point VP cross-connect, the
                         ATM traffic parameters in the receive direction
                         of a VPL at the low end of the cross-connect
                         must equal to the traffic parameters in the
                         transmit direction of the other VPL at the
                         high end of the cross-connect,
                         otherwise, the row creation fails.]
                         The agent also checks for internal errors
                         in building the cross-connect.

                         The atmVpCrossConnectIndex values in the
                         corresponding atmVplTable rows are filled
                         in by the agent at this point.

                    (2b) The manager promotes the row in the
                         atmVpCrossConnectTable by setting
                         atmVpCrossConnectRowStatus to active(1).  If
                         this set is successful, the agent has reserved
                         the resources specified by the ATM traffic






                         parameter and QoS Class values
                         for each direction of the VP cross-connect
                         in an ATM switch or network.

                     (3) The manager sets the
                         atmVpCrossConnectAdminStatus to up(1) in all
                         rows of this VP cross-connect to turn the
                         traffic flow on.


                      One-Shot VP Cross-Connect Establishment

                      A VP cross-connect may also be established in
                      one step by a set-request with all necessary
                      parameter values and atmVpCrossConnectRowStatus
                      set to createAndGo(4).

                      In contrast to the negotiated VP cross-connect
                      establishment which allows for detailed error
                      checking (i.e., set errors are explicitly linked
                      to particular resource acquisition failures),
                      the one-shot VP cross-connect establishment
                      performs the setup on one operation but does not
                      have the advantage of step-wise error checking.

                      VP Cross-Connect Retirement

                      A VP cross-connect identified by a particular
                      value of atmVpCrossConnectIndex is released by:

                     (1) Setting atmVpCrossConnectRowStatus of all
                         rows identified by this value of
                         atmVpCrossConnectIndex to destroy(6).
                         The agent may release all
                         associated resources, and the
                         atmVpCrossConnectIndex values in the
                         corresponding atmVplTable row are removed.
                         Note that a situation when only a subset of
                         the associated rows are deleted corresponds
                         to a VP topology change.

                     (2) After deletion of the appropriate
                         atmVpCrossConnectEntries, the manager may
                         set atmVplRowStatus to destroy(6) the
                         associated VPLs.  The agent releases
                         the resources and removes the associated
                         rows in the atmVplTable.







                      VP Cross-connect Reconfiguration

                      At the discretion of the agent, a VP
                      cross-connect may be reconfigured by
                      adding and/or deleting leafs to/from
                      the VP topology as per the VP cross-connect
                      establishment/retirement procedures.
                      Reconfiguration of traffic/QoS parameter
                      values requires release of the VP cross-connect
                      before those parameter values may by changed
                      for individual VPLs."
                    INDEX { atmVpCrossConnectIndex,
                          atmVpCrossConnectLowIfIndex,
                          atmVpCrossConnectLowVpi,
                          atmVpCrossConnectHighIfIndex,
                          atmVpCrossConnectHighVpi }
                    ::= { atmVpCrossConnectTable 1 }

               AtmVpCrossConnectEntry ::= SEQUENCE {
                    atmVpCrossConnectIndex          INTEGER,
                    atmVpCrossConnectLowIfIndex     IfIndex,
                    atmVpCrossConnectLowVpi         INTEGER,
                    atmVpCrossConnectHighIfIndex    IfIndex,
                    atmVpCrossConnectHighVpi        INTEGER,
                    atmVpCrossConnectAdminStatus    INTEGER,
                    atmVpCrossConnectL2HOperStatus  INTEGER,
                    atmVpCrossConnectH2LOperStatus  INTEGER,
                    atmVpCrossConnectL2HLastChange  TimeStamp,
                    atmVpCrossConnectH2LLastChange  TimeStamp,
                    atmVpCrossConnectRowStatus      RowStatus
                            }

               atmVpCrossConnectIndex OBJECT-TYPE
                    SYNTAX  INTEGER (1..2147483647)
                    MAX-ACCESS  not-accessible
                    STATUS  current
                    DESCRIPTION
                     "A unique value to identify this VP cross-connect."
                    ::= { atmVpCrossConnectEntry 1 }

               atmVpCrossConnectLowIfIndex OBJECT-TYPE
                    SYNTAX  IfIndex
                    MAX-ACCESS  not-accessible
                    STATUS  current
                    DESCRIPTION
                     "The value of this object is equal to MIB II's
                      ifIndex value of the ATM interface port for this
                      VP cross-connect.  The term low implies






                      that this ATM interface has the numerically lower
                      ifIndex value than the other ATM interface
                      identified in the same atmVpCrossConnectEntry."
                    ::= { atmVpCrossConnectEntry 2 }

               atmVpCrossConnectLowVpi OBJECT-TYPE
                    SYNTAX  INTEGER  (1..4095)
                    MAX-ACCESS  not-accessible
                    STATUS  current
                    DESCRIPTION
                     "The value of this object is equal to the VPI
                      value at the ATM interface
                      associated with the VP cross-connect that is
                      identified by atmVpCrossConnectLowIfIndex.
                      The VPI value cannot exceed the number
                      supported by the atmInterfaceMaxVpiBits
                      at the low ATM interface port."
                    ::= { atmVpCrossConnectEntry 3 }

               atmVpCrossConnectHighIfIndex OBJECT-TYPE
                    SYNTAX  IfIndex
                    MAX-ACCESS  not-accessible
                    STATUS  current
                    DESCRIPTION
                     "The value of this object is equal to MIB II's
                      ifIndex value of the ATM interface port for
                      this VP cross-connect.  The term high
                      implies that this ATM interface has the
                      numerically higher ifIndex value than the
                      other ATM interface identified in the same
                      atmVpCrossConnectEntry."
                    ::= { atmVpCrossConnectEntry 4 }

               atmVpCrossConnectHighVpi OBJECT-TYPE
                    SYNTAX  INTEGER   (1..4095)
                    MAX-ACCESS  not-accessible
                    STATUS  current
                    DESCRIPTION
                     "The value of this object is equal to the VPI
                      value at the ATM interface associated with
                      the VP cross-connect that is identified
                      by atmVpCrossConnectHighIfIndex.
                      The VPI value cannot exceed the number
                      supported by the atmInterfaceMaxVpiBits
                      at the high ATM interface port."
                    ::= { atmVpCrossConnectEntry 5 }

               atmVpCrossConnectAdminStatus OBJECT-TYPE






                    SYNTAX  INTEGER {
                                    up(1),
                                    down(2)
                            }
                    MAX-ACCESS  read-create
                    STATUS  current
                    DESCRIPTION
                     "The value of this object identifies the desired
                      administrative status of this bi-directional
                      VP cross-connect.  The up and down states
                      indicate that the traffic flow is enabled
                      and disabled respectively on this VP
                      cross-connect."
                    DEFVAL { down }
                    ::= { atmVpCrossConnectEntry 6 }

               atmVpCrossConnectL2HOperStatus OBJECT-TYPE
                    SYNTAX  INTEGER {
                              up(1),
                              down(2),
                              unknown(3)
                                }
                    MAX-ACCESS  read-only
                    STATUS  current
                    DESCRIPTION
                     "The value of this object identifies the current
                      operational status of the VP cross-connect
                      in one direction; (i.e., from the low to
                      high direction).  The up and down states indicate
                      that this ATM VP cross-connect from low
                      to high direction is operational or not
                      operational respectively.
                      The unknown state indicates that
                      the state of it cannot be determined."
                    ::= { atmVpCrossConnectEntry 7 }

               atmVpCrossConnectH2LOperStatus OBJECT-TYPE
                    SYNTAX  INTEGER {
                              up(1),
                              down(2),
                              unknown(3)
                                 }
                    MAX-ACCESS  read-only
                    STATUS  current
                    DESCRIPTION
                     "The value of this object identifies the current
                      operational status of the VP cross-connect
                      in one direction; (i.e., from the high to






                      low direction).  The up and down states indicate
                      that this ATM VP cross-connect from high
                      to low direction is operational or not
                      operational respectively.  The
                      unknown state indicates that the state
                      of it cannot be determined."
                    ::= { atmVpCrossConnectEntry 8 }

               atmVpCrossConnectL2HLastChange OBJECT-TYPE
                    SYNTAX  TimeStamp
                    MAX-ACCESS  read-only
                    STATUS  current
                    DESCRIPTION
                     "The value of MIB II's sysUpTime object
                      at the time this VP cross-connect entered
                      its current operational state in the low to
                      high direction.  If the current state was
                      entered prior to the last re-initialization of the
                      agent, then this object contains a zero value."
                    ::= { atmVpCrossConnectEntry 9 }

               atmVpCrossConnectH2LLastChange OBJECT-TYPE
                    SYNTAX  TimeStamp
                    MAX-ACCESS  read-only
                    STATUS  current
                    DESCRIPTION
                     "The value of MIB II's sysUpTime object at the
                      time this VP cross-connect entered its current
                      operational state in the high to low direction.
                      If the current state was entered prior to the
                      last re-initialization of the agent,
                      then this object contains a zero value."
                    ::= { atmVpCrossConnectEntry 10 }

               atmVpCrossConnectRowStatus OBJECT-TYPE
                    SYNTAX  RowStatus
                    MAX-ACCESS  read-create
                    STATUS  current
                    DESCRIPTION
                     "The status of this entry in the
                      atmVpCrossConnectTable.  This object is used to
                      create a cross-connect for cross-connecting
                      VPLs which are created using the atmVplTable
                      or to change or delete an existing cross-connect.
                      This object must be initially set
                      to `createAndWait' or 'createAndGo'.
                      This object cannot be set to `active'
                      unless the following columnar object exists






                      in this row: atmVpCrossConnectAdminStatus.
                      To turn on a VP cross-connect,
                      the atmVpCrossConnectAdminStatus
                      is set to `up'."
                    DEFVAL { active }
                    ::= { atmVpCrossConnectEntry 11 }


               --     ATM Virtual Channel (VC) Cross Connect Group

               -- This group contains configuration and state
               -- information of a bi-directional VC cross-connect.

               -- This group is used to model a bi-directional
               -- point-to-point, point-to-multipoint or
               -- multipoint-to-multipoint VC cross-connects.

               -- This table has read-create access and is used
               -- to cross-connect the VCLs together in an ATM switch
               -- or network that belong to a VC connection.
               -- The atmVcCrossConnectIndex is used to associate
               -- the related VCLs that are cross-connected together.


               -- The step-wise procedures described for setting
               -- up a VP cross-connect are also used for setting up
               -- a VC cross-connect.


               atmVcCrossConnectIndexNext    OBJECT-TYPE
                    SYNTAX  INTEGER (0..2147483647)
                    MAX-ACCESS  read-only
                    STATUS  current
                    DESCRIPTION
                     "This object contains an appropriate value to
                      be used for atmVcCrossConnectIndex when creating
                      entries in the atmVcCrossConnectTable.  The value
                      0 indicates that no unassigned entries are
                      available. To obtain the atmVpCrossConnectIndex
                      value for a new entry, the manager issues a
                      management protocol retrieval operation to obtain
                      the current value of this object.  After each
                      retrieval, the agent should modify the value to
                      the next unassigned index."
                    ::= { atmMIBObjects 10 }


               --  The ATM VC Cross Connect Table






               atmVcCrossConnectTable OBJECT-TYPE
                    SYNTAX  SEQUENCE OF AtmVcCrossConnectEntry
                    MAX-ACCESS  not-accessible
                    STATUS  current
                    DESCRIPTION
                     "The ATM VC Cross Connect table.  A bi-
                      directional VC cross-connect which
                      cross-connects two end points (i.e., VCLs)
                      is modeled as one entry in this table."
                    ::= { atmMIBObjects 11 }


               atmVcCrossConnectEntry OBJECT-TYPE
                    SYNTAX  AtmVcCrossConnectEntry
                    MAX-ACCESS  not-accessible
                    STATUS  current
                    DESCRIPTION
                     "An entry in the ATM VC Cross Connect table.
                      This entry is used to model a bi-directional ATM
                      VC cross-connect cross-connecting two end points.

                      Step-wise Procedures to set up a VC Cross-connect

                      Once the entries in the atmVclTable are created,
                      the following procedures are used
                      to cross-connect the VCLs together to
                      form a VCC segment.

                     (1) The manager obtains a unique
                         atmVcCrossConnectIndex by reading the
                         atmVcCrossConnectIndexNext object.

                     (2) Next, the manager creates a set of one
                         or more rows in the ATM VC Cross Connect
                         Table, one for each cross-connection between
                         two VCLs.  Each row is indexed by the ATM
                         interface port numbers and VPI/VCI values of
                         the two ends of that cross-connection.
                         This set of rows specifies the topology of the
                         VCC cross-connect and is identified by a single
                         value of atmVcCrossConnectIndex.

                      Negotiated VC Cross-Connect Establishment

                    (2a) The manager creates a row in this table by
                         setting atmVcCrossConnectRowStatus to
                         createAndWait(5).  The agent checks the
                         requested topology and the mutual sanity of






                         the ATM traffic parameters and
                         QoS Classes, i.e., the row creation fails if:
                         - the requested topology is not supported
                           by the agent,
                         - the traffic/QoS parameter values
                           associated with the requested row are
                           incompatible with those of already existing
                           rows for this VC cross-connect.
                         [For example, for setting up
                         a point-to-point VC cross-connect, the
                         ATM traffic parameters in the receive direction
                         of a VCL at the low end of the cross-connect
                         must equal to the traffic parameters in the
                         transmit direction of the other VCL at the
                         high end of the cross-connect,
                         otherwise, the row creation fails.]
                         The agent also checks for internal errors
                         in building the cross-connect.

                         The atmVcCrossConnectIndex values in the
                         corresponding atmVclTable rows are filled
                         in by the agent at this point.

                    (2b) The manager promotes the row in the
                         atmVcCrossConnectTable by setting
                         atmVcCrossConnectRowStatus to active(1).  If
                         this set is successful, the agent has reserved
                         the resources specified by the ATM traffic
                         parameter and QoS Class values
                         for each direction of the VC cross-connect
                         in an ATM switch or network.

                     (3) The manager sets the
                         atmVcCrossConnectAdminStatus to up(1)
                         in all rows of this VC cross-connect to
                         turn the traffic flow on.


                      One-Shot VC Cross-Connect Establishment

                      A VC cross-connect may also be established in
                      one step by a set-request with all necessary
                      parameter values and atmVcCrossConnectRowStatus
                      set to createAndGo(4).

                      In contrast to the negotiated VC cross-connect
                      establishment which allows for detailed error
                      checking i.e., set errors are explicitly linked to






                      particular resource acquisition failures), the
                      one-shot VC cross-connect establishment
                      performs the setup on one operation but does
                      not have the advantage of step-wise error
                      checking.

                      VC Cross-Connect Retirement

                      A VC cross-connect identified by a particular
                      value of atmVcCrossConnectIndex is released by:

                     (1) Setting atmVcCrossConnectRowStatus of all rows
                         identified by this value of
                         atmVcCrossConnectIndex to destroy(6).
                         The agent may release all
                         associated resources, and the
                         atmVcCrossConnectIndex values in the
                         corresponding atmVclTable row are removed.
                         Note that a situation when only a subset of
                         the associated rows are deleted corresponds
                         to a VC topology change.

                     (2) After deletion of the appropriate
                         atmVcCrossConnectEntries, the manager may
                         set atmVclRowStatus to destroy(6) the
                         associated VCLs.  The agent releases
                         the resources and removes the associated
                         rows in the atmVclTable.

                      VC Cross-Connect Reconfiguration

                      At the discretion of the agent, a VC
                      cross-connect may be reconfigured by
                      adding and/or deleting leafs to/from
                      the VC topology as per the VC cross-connect
                      establishment/retirement procedures.
                      Reconfiguration of traffic/QoS parameter
                      values requires release of the VC cross-connect
                      before those parameter values may by changed
                      for individual VCLs."
                    INDEX { atmVcCrossConnectIndex,
                          atmVcCrossConnectLowIfIndex,
                          atmVcCrossConnectLowVpi,
                          atmVcCrossConnectLowVci,
                          atmVcCrossConnectHighIfIndex,
                          atmVcCrossConnectHighVpi,
                          atmVcCrossConnectHighVci }
                    ::= { atmVcCrossConnectTable 1 }






               AtmVcCrossConnectEntry ::= SEQUENCE {
                    atmVcCrossConnectIndex          INTEGER,
                    atmVcCrossConnectLowIfIndex     IfIndex,
                    atmVcCrossConnectLowVpi         INTEGER,
                    atmVcCrossConnectLowVci         INTEGER,
                    atmVcCrossConnectHighIfIndex    IfIndex,
                    atmVcCrossConnectHighVpi        INTEGER,
                    atmVcCrossConnectHighVci        INTEGER,
                    atmVcCrossConnectAdminStatus    INTEGER,
                    atmVcCrossConnectL2HOperStatus  INTEGER,
                    atmVcCrossConnectH2LOperStatus  INTEGER,
                    atmVcCrossConnectL2HLastChange  TimeStamp,
                    atmVcCrossConnectH2LLastChange  TimeStamp,
                    atmVcCrossConnectRowStatus      RowStatus
                            }

               atmVcCrossConnectIndex OBJECT-TYPE
                    SYNTAX  INTEGER (1..2147483647)
                    MAX-ACCESS  not-accessible
                    STATUS  current
                    DESCRIPTION
                     "A unique value to identify this VC cross-connect."
                    ::= { atmVcCrossConnectEntry 1 }

               atmVcCrossConnectLowIfIndex OBJECT-TYPE
                    SYNTAX  IfIndex
                    MAX-ACCESS  not-accessible
                    STATUS  current
                    DESCRIPTION
                     "The value of this object is equal to MIB II's
                      ifIndex value of the ATM interface port for this
                      VC cross-connect.  The term low implies
                      that this ATM interface has the numerically lower
                      ifIndex value than the other ATM interface
                      identified in the same atmVcCrossConnectEntry."
                    ::= { atmVcCrossConnectEntry 2 }

               atmVcCrossConnectLowVpi OBJECT-TYPE
                    SYNTAX  INTEGER  (0..4095)
                    MAX-ACCESS  not-accessible
                    STATUS  current
                    DESCRIPTION
                     "The value of this object is equal to the VPI
                      value at the ATM interface
                      associated with the VC cross-connect that is
                      identified by atmVcCrossConnectLowIfIndex.
                      The VPI value cannot exceed the number
                      supported by the atmInterfaceMaxVpiBits






                      at the low ATM interface port."
                    ::= { atmVcCrossConnectEntry 3 }

               atmVcCrossConnectLowVci OBJECT-TYPE
                    SYNTAX  INTEGER  (0..65535)
                    MAX-ACCESS  not-accessible
                    STATUS  current
                    DESCRIPTION
                     "The value of this object is equal to the VCI
                      value at the ATM interface
                      associated with this VC cross-connect that is
                      identified by atmVcCrossConnectLowIfIndex.
                      The VCI value cannot exceed the number
                      supported by the atmInterfaceMaxVciBits
                      at the low ATM interface port."
                    ::= { atmVcCrossConnectEntry 4 }

               atmVcCrossConnectHighIfIndex OBJECT-TYPE
                    SYNTAX  IfIndex                    MAX-ACCESS  not-accessible
                    STATUS  current
                    DESCRIPTION
                     "The value of this object is equal to MIB II's
                      ifIndex value for the ATM interface port for
                      this VC cross-connect.  The term high
                      implies that this VC cross-connect
                      that this ATM interface has the numerically higher
                      ifIndex value than the other ATM interface
                      identified in the same atmVcCrossConnectEntry."
                    ::= { atmVcCrossConnectEntry 5 }

               atmVcCrossConnectHighVpi OBJECT-TYPE
                    SYNTAX  INTEGER   (0..4095)
                    MAX-ACCESS  not-accessible
                    STATUS  current
                    DESCRIPTION
                     "The value of this object is equal to the VPI
                      value at the ATM interface
                      associated with the VC cross-connect that is
                      identified by atmVcCrossConnectHighIfIndex.
                      The VPI value cannot exceed
                      the number supported by the atmInterfaceMaxVpiBits
                      at the high ATM interface port."
                    ::= { atmVcCrossConnectEntry 6 }

               atmVcCrossConnectHighVci OBJECT-TYPE
                    SYNTAX  INTEGER   (0..65535)
                    MAX-ACCESS  not-accessible






                    STATUS  current
                    DESCRIPTION
                     "The value of this object is equal to the VCI
                      value at the ATM interface
                      associated with the VC cross-connect that is
                      identified by atmVcCrossConnectHighIfIndex.
                      The VCI value cannot exceed
                      the number supported by the atmInterfaceMaxVciBits
                      at the high ATM interface port."
                    ::= { atmVcCrossConnectEntry 7 }

               atmVcCrossConnectAdminStatus OBJECT-TYPE
                    SYNTAX  INTEGER {
                              up(1),
                              down(2)
                              }
                    MAX-ACCESS  read-create
                    STATUS  current
                    DESCRIPTION
                     "The value of this object identifies the desired
                      administrative status of this bi-directional
                      VC cross-connect. The up and down states
                      indicate that the traffic flow is enabled or
                      disabled respectively on this VC cross-connect."
                    DEFVAL { down }
                    ::= { atmVcCrossConnectEntry 8 }

               atmVcCrossConnectL2HOperStatus OBJECT-TYPE
                    SYNTAX  INTEGER {
                              up(1),
                              down(2),
                              unknown(3)
                            }
                    MAX-ACCESS  read-only
                    STATUS  current
                    DESCRIPTION
                     "The value of this object identifies the current
                      operational status of the VC cross-connect
                      in one direction; (i.e., from the low to
                      high direction).  The up and down states indicate
                      that this ATM VC cross-connect from low
                      to high direction is operational or not
                      operational respectively.  The unknown state
                      indicates that the state of it cannot be
                      determined."
                    ::= { atmVcCrossConnectEntry 9 }








               atmVcCrossConnectH2LOperStatus OBJECT-TYPE
                    SYNTAX  INTEGER {
                              up(1),
                              down(2),
                              unknown(3)
                            }
                    MAX-ACCESS  read-only
                    STATUS  current
                    DESCRIPTION
                     "The value of this object identifies the current
                      operational status of the VC cross-connect
                      in one direction; (i.e., from the high to
                      low direction).  The up and down states indicate
                      that this ATM VC cross-connect from high
                      to low direction is operational or not
                      operational respectively.  The unknown state
                      indicates that the state of it cannot be
                      determined."
                    ::= { atmVcCrossConnectEntry 10 }

               atmVcCrossConnectL2HLastChange OBJECT-TYPE
                    SYNTAX  TimeStamp
                    MAX-ACCESS  read-only
                    STATUS  current
                    DESCRIPTION
                     "The value of MIB II's sysUpTime object
                      at the time this VC cross-connect entered
                      its current operational state in low to high
                      direction.  If the current state was
                      entered prior to the last re-initialization of the
                      agent, then this object contains a zero value."
                    ::= { atmVcCrossConnectEntry 11 }

               atmVcCrossConnectH2LLastChange OBJECT-TYPE
                    SYNTAX  TimeStamp
                    MAX-ACCESS  read-only
                    STATUS  current
                    DESCRIPTION
                     "The value of MIB II's sysUpTime object
                      at the time this VC cross-connect entered
                      its current operational state in high to low
                      direction.  If the current state was
                      entered prior to the last re-initialization of the
                      agent, then this object contains a zero value."
                    ::= { atmVcCrossConnectEntry 12 }

               atmVcCrossConnectRowStatus OBJECT-TYPE
                    SYNTAX  RowStatus






                    MAX-ACCESS  read-create
                    STATUS  current
                    DESCRIPTION
                     "The status of this entry in the
                      atmVcCrossConnectTable.  This object is used to
                      create a new cross-connect for cross-connecting
                      VCLs which are created using the atmVclTable
                      or to change or delete existing cross-connect.
                      This object must be initially set to
                      `createAndWait' or 'createAndGo'.  This object
                      cannot be set to `active' unless the following
                      columnar object exists in this row:
                      atmVcCrossConnectAdminStatus.
                      To turn on a VC cross-connect,
                      the atmVcCrossConnectAdminStatus
                      is set to `up'."
                    ::= { atmVcCrossConnectEntry 13 }


               -- AAL5 Virtual Channel Connection Performance Statistics
               -- Group

               -- This group contains the AAL5
               -- performance statistics of a VCC at the
               -- interface associated with an AAL5 entity in an ATM
               -- host or ATM switch.


               aal5VccTable    OBJECT-TYPE
                    SYNTAX      SEQUENCE OF Aal5VccEntry
                    MAX-ACCESS   not-accessible
                    STATUS       current
                    DESCRIPTION
                     "This table contains AAL5 VCC performance
                      parameters."
                    ::= { atmMIBObjects 12 }

               aal5VccEntry    OBJECT-TYPE
                    SYNTAX         Aal5VccEntry
                    MAX-ACCESS     not-accessible
                    STATUS         current
                    DESCRIPTION
                     "This list contains the AAL5 VCC
                      performance parameters."
                    INDEX { ifIndex, aal5VccVpi, aal5VccVci }
                    ::= { aal5VccTable 1 }

               Aal5VccEntry    ::= SEQUENCE  {






                    aal5VccVpi                        INTEGER,
                    aal5VccVci                        INTEGER,
                    aal5VccCrcErrors                  Counter32,
                    aal5VccSarTimeOuts                Counter32,
                    aal5VccOverSizedSDUs              Counter32
                         }


               aal5VccVpi               OBJECT-TYPE
                    SYNTAX       INTEGER  (0..4095)
                    MAX-ACCESS    not-accessible
                    STATUS         current
                    DESCRIPTION
                     "The VPI value of the AAL5 VCC at the
                      interface identified by the ifIndex."
                    ::= { aal5VccEntry 1 }

               aal5VccVci               OBJECT-TYPE
                    SYNTAX       INTEGER  (0..65535)
                    MAX-ACCESS    not-accessible
                    STATUS         current
                    DESCRIPTION
                     "The VCI value of the AAL5 VCC at the
                      interface identified by the ifIndex."
                    ::= { aal5VccEntry 2 }

               aal5VccCrcErrors    OBJECT-TYPE
                    SYNTAX  Counter32
                    MAX-ACCESS  read-only
                    STATUS           current
                    DESCRIPTION
                     "The number of AAL5 CPCS PDUs received with
                      CRC-32 errors on this AAL5 VCC at the
                      interface associated with an AAL5 entity."
                    ::= { aal5VccEntry 3 }

               aal5VccSarTimeOuts    OBJECT-TYPE
                    SYNTAX  Counter32
                    MAX-ACCESS  read-only
                    STATUS           current
                    DESCRIPTION
                     "The number of partially re-assembled AAL5
                      CPCS PDUs which were discarded
                      on this AAL5 VCC at the interface associated
                      with an AAL5 entity because they
                      were not fully re-assembled within the
                      required time period.  If the re-assembly
                      timer is not supported, then this object






                      contains a zero value."
                    ::= { aal5VccEntry 4 }

               aal5VccOverSizedSDUs    OBJECT-TYPE
                    SYNTAX  Counter32
                    MAX-ACCESS  read-only
                    STATUS           current
                    DESCRIPTION
                     "The number of AAL5 CPCS PDUs discarded
                      on this AAL5 VCC at the interface
                      associated with an AAL5 entity because the
                      AAL5 SDUs were too large."
                    ::= { aal5VccEntry 5 }


               -- Conformance Information

               atmMIBConformance   OBJECT IDENTIFIER ::= { atmMIB 2 }

               atmMIBGroups        OBJECT IDENTIFIER
                                          ::= { atmMIBConformance 1 }
               atmMIBCompliances   OBJECT IDENTIFIER
                                          ::= { atmMIBConformance 2 }


               -- Compliance Statements

               atmMIBCompliance       MODULE-COMPLIANCE
                    STATUS      current
                    DESCRIPTION
                      "The compliance statement for SNMP entities
                       including networks which have ATM and
                       AAL5 interfaces."

                    MODULE -- this module
                      MANDATORY-GROUPS  {atmInterfaceConfGroup,
                                         atmTrafficDescrGroup}

                      OBJECT   atmInterfaceMaxVpcs
                      MIN-ACCESS read-only
                      DESCRIPTION
                        "Write access is not required."

                      OBJECT   atmInterfaceMaxVccs
                      MIN-ACCESS read-only
                      DESCRIPTION
                        "Write access is not required."







                      OBJECT   atmInterfaceMaxActiveVpiBits
                      MIN-ACCESS read-only
                      DESCRIPTION
                        "Write access is not required."

                      OBJECT   atmInterfaceMaxActiveVciBits
                      MIN-ACCESS read-only
                      DESCRIPTION
                        "Write access is not required."

                      OBJECT   atmInterfaceIlmiVpi
                      MIN-ACCESS read-only
                      DESCRIPTION
                        "Write access is not required."

                      OBJECT   atmInterfaceIlmiVci
                      MIN-ACCESS read-only
                      DESCRIPTION
                        "Write access is not required."

                      OBJECT   atmInterfaceMyNeighborIpAddress
                      MIN-ACCESS read-only
                      DESCRIPTION
                        "Write access is not required."

                      OBJECT   atmInterfaceMyNeighborIfName
                      MIN-ACCESS read-only
                      DESCRIPTION
                        "Write access is not required."

                      OBJECT   atmTrafficDescrType
                      MIN-ACCESS read-only
                      DESCRIPTION
                        "Write access is not required."

                      OBJECT   atmTrafficDescrParam1
                      MIN-ACCESS read-only
                      DESCRIPTION
                        "Write access is not required."

                      OBJECT   atmTrafficDescrParam2
                      MIN-ACCESS read-only
                      DESCRIPTION
                        "Write access is not required."

                      OBJECT   atmTrafficDescrParam3
                      MIN-ACCESS read-only
                      DESCRIPTION






                        "Write access is not required."

                      OBJECT   atmTrafficDescrParam4
                      MIN-ACCESS read-only
                      DESCRIPTION
                        "Write access is not required."

                      OBJECT   atmTrafficDescrParam5
                      MIN-ACCESS read-only
                      DESCRIPTION
                        "Write access is not required."

                      OBJECT   atmTrafficQoSClass
                      MIN-ACCESS read-only
                      DESCRIPTION
                        "Write access is not required."

                      OBJECT   atmTrafficDescrRowStatus
                      SYNTAX   INTEGER {active(1)}
                                       -- subset of RowStatus
                      MIN-ACCESS read-only
                      DESCRIPTION
                        "Write access is not required, and only one
                         of the six enumerated values for the
                         RowStatus textual convention need be
                         supported, specifically: active(1)."

                      GROUP   atmInterfaceDs3PlcpGroup
                      DESCRIPTION
                        "This group is mandatory only for those
                         ATM interfaces which implement the
                         DS3 PLCP layer."

                      GROUP   atmInterfaceTCGroup
                      DESCRIPTION
                        "This group is mandatory only for those
                         ATM interfaces which implement the
                         TC Sublayer."

                      GROUP   atmVpcTerminationGroup
                      DESCRIPTION
                        "This group is mandatory only for those
                         ATM interfaces which implement ATM
                         VPLs that terminate VPCs (i.e., ones which
                         are NOT cross-connected to other VPLs)."

                      GROUP   atmVpCrossConnectGroup
                      DESCRIPTION






                        "This group is mandatory only for those
                         ATM interfaces which implement ATM
                         VPLs that are not associated with VCLs
                         and are cross-connected to other VPLs."

                      OBJECT   atmVplAdminStatus
                      MIN-ACCESS read-only
                      DESCRIPTION
                        "Write access is not required."

                      OBJECT   atmVplReceiveTrafficDescrIndex
                      MIN-ACCESS read-only
                      DESCRIPTION
                        "Write access is not required."

                      OBJECT   atmVplTransmitTrafficDescrIndex
                      MIN-ACCESS read-only
                      DESCRIPTION
                        "Write access is not required."

                      OBJECT   atmVplRowStatus
                      SYNTAX   INTEGER {active(1)}
                                       -- subset of RowStatus
                      MIN-ACCESS read-only
                      DESCRIPTION
                        "Write access is not required, and only one
                         of the six enumerated values for the
                         RowStatus textual convention need be
                         supported, specifically: active(1)."


                      OBJECT   atmVpCrossConnectAdminStatus
                      MIN-ACCESS read-only
                      DESCRIPTION
                        "Write access is not required."

                      OBJECT   atmVpCrossConnectRowStatus
                      SYNTAX   INTEGER {active(1)}
                                       -- subset of RowStatus
                      MIN-ACCESS read-only
                      DESCRIPTION
                        "Write access is not required, and only one
                         of the six enumerated values for the
                         RowStatus textual convention need be
                         supported, specifically: active(1)."

                      GROUP   atmVccTerminationGroup
                      DESCRIPTION
                        "This group is mandatory only for those
                         ATM interfaces which implement ATM
                         VCLs that terminate VCCs (i.e., ones which
                         are NOT cross-connected to other VCLs)."

                      GROUP   atmVcCrossConnectGroup
                      DESCRIPTION
                        "This group is mandatory only for those
                         ATM interfaces which implement ATM
                         VCLs that are cross-connected to
                         other VCLs."


                      OBJECT   atmVclAdminStatus
                      MIN-ACCESS read-only
                      DESCRIPTION
                        "Write access is not required."

                      OBJECT   atmVclReceiveTrafficDescrIndex
                      MIN-ACCESS read-only
                      DESCRIPTION
                        "Write access is not required."

                      OBJECT   atmVclTransmitTrafficDescrIndex






                      MIN-ACCESS read-only
                      DESCRIPTION
                        "Write access is not required."

                      OBJECT     atmVccAalType
                      MIN-ACCESS read-only
                      DESCRIPTION
                        "Write access is not required."

                      OBJECT   atmVclRowStatus
                      SYNTAX   INTEGER {active(1)}
                                       -- subset of RowStatus
                      MIN-ACCESS read-only
                      DESCRIPTION
                        "Write access is not required, and only one
                         of the six enumerated values for the
                         RowStatus textual convention need be
                         supported, specifically: active(1)."



                      OBJECT   atmVcCrossConnectAdminStatus
                      MIN-ACCESS read-only
                      DESCRIPTION
                        "Write access is not required."

                      OBJECT   atmVcCrossConnectRowStatus
                      SYNTAX   INTEGER { active(1)}
                                       -- subset of RowStatus
                      MIN-ACCESS read-only
                      DESCRIPTION
                        "Write access is not required, and only one
                         of the six enumerated values for the
                         RowStatus textual convention need be
                         supported, specifically: active(1)."







                      GROUP   aal5VccGroup
                      DESCRIPTION
                        "This group is mandatory for the
                         AAL5 virtual connections only."


                      OBJECT     atmVccAal5CpcsTransmitSduSize
                      MIN-ACCESS read-only
                      DESCRIPTION
                        "Write access is not required."

                      OBJECT     atmVccAal5CpcsReceiveSduSize
                      MIN-ACCESS read-only
                      DESCRIPTION
                        "Write access is not required."

                      OBJECT     atmVccAal5EncapsType
                      MIN-ACCESS read-only
                      DESCRIPTION
                        "Write access is not required."
                       ::= { atmMIBCompliances 1 }


               -- Units of Conformance

               atmInterfaceConfGroup    OBJECT-GROUP
                      OBJECTS {
                            atmInterfaceMaxVpcs, atmInterfaceMaxVccs,
                            atmInterfaceConfVpcs, atmInterfaceConfVccs,
                            atmInterfaceMaxActiveVpiBits,
                            atmInterfaceMaxActiveVciBits,
                            atmInterfaceIlmiVpi,
                            atmInterfaceIlmiVci,
                            atmInterfaceAddressType,
                            atmInterfaceAdminAddress,
                            atmInterfaceMyNeighborIpAddress,
                            atmInterfaceMyNeighborIfName}
                      STATUS     current
                      DESCRIPTION
                        "A collection of objects providing configuration
                         information about an ATM interface."
                      ::= { atmMIBGroups 1 }







               atmTrafficDescrGroup    OBJECT-GROUP
                      OBJECTS {
                          atmTrafficDescrType, atmTrafficDescrParam1,
                          atmTrafficDescrParam2, atmTrafficDescrParam3,
                          atmTrafficDescrParam4, atmTrafficDescrParam5,
                          atmTrafficQoSClass, atmTrafficDescrRowStatus}
                      STATUS     current
                      DESCRIPTION
                         "A collection of objects providing information
                          about ATM traffic descriptor type and
                          the associated parameters."
                      ::= { atmMIBGroups 2 }

               atmInterfaceDs3PlcpGroup    OBJECT-GROUP
                      OBJECTS {atmInterfaceDs3PlcpSEFSs,
                          atmInterfaceDs3PlcpAlarmState,
                          atmInterfaceDs3PlcpUASs}
                      STATUS     current
                      DESCRIPTION
                         "A collection of objects providing information
                          about DS3 PLCP layer at an ATM interface."
                      ::= { atmMIBGroups 3 }

               atmInterfaceTCGroup    OBJECT-GROUP
                      OBJECTS { atmInterfaceOCDEvents,
                          atmInterfaceTCAlarmState }
                      STATUS     current
                      DESCRIPTION
                         "A collection of objects providing information
                          about TC sublayer at an ATM interface."                      ::= { atmMIBGroups 4 }

               atmVpcTerminationGroup    OBJECT-GROUP
                      OBJECTS  {atmVplOperStatus, atmVplAdminStatus,
                          atmVplLastChange,
                          atmVplReceiveTrafficDescrIndex,
                          atmVplTransmitTrafficDescrIndex,
                          atmVplRowStatus }
                      STATUS     current
                      DESCRIPTION
                         "A collection of objects providing
                          information about a VPL at an ATM interface
                          which terminates a VPC
                          (i.e., one which is NOT cross-connected
                          to other VPLs)."
                      ::= { atmMIBGroups 5 }

               atmVccTerminationGroup    OBJECT-GROUP






                      OBJECTS {atmVclOperStatus, atmVclAdminStatus,
                          atmVclLastChange,
                           atmVclReceiveTrafficDescrIndex,
                           atmVclTransmitTrafficDescrIndex,
                           atmVccAalType, atmVclRowStatus }
                      STATUS     current
                      DESCRIPTION
                         "A collection of objects providing information
                          about a VCL at an ATM interface
                          which terminates a VCC (i.e., one which is
                          NOT cross-connected to other VCLs)."
                      ::= { atmMIBGroups 6 }

               atmVpCrossConnectGroup    OBJECT-GROUP
                      OBJECTS { atmVplReceiveTrafficDescrIndex,
                          atmVplTransmitTrafficDescrIndex,
                          atmVplOperStatus, atmVplRowStatus,
                          atmVpCrossConnectAdminStatus,
                          atmVpCrossConnectL2HOperStatus,
                          atmVpCrossConnectH2LOperStatus,
                          atmVpCrossConnectL2HLastChange,
                          atmVpCrossConnectH2LLastChange,
                          atmVpCrossConnectRowStatus,
                          atmVplCrossConnectIdentifier,
                          atmVpCrossConnectIndexNext }
                      STATUS     current
                      DESCRIPTION
                         "A collection of objects providing
                          information about a VP cross-connect
                          and the associated VPLs that are
                          cross-connected together."
                      ::= { atmMIBGroups 7 }

               atmVcCrossConnectGroup    OBJECT-GROUP
                      OBJECTS { atmVclReceiveTrafficDescrIndex,
                          atmVclTransmitTrafficDescrIndex,
                          atmVclOperStatus, atmVclRowStatus,
                          atmVcCrossConnectAdminStatus,
                          atmVcCrossConnectL2HOperStatus,
                          atmVcCrossConnectH2LOperStatus,
                          atmVcCrossConnectL2HLastChange,
                          atmVcCrossConnectH2LLastChange,
                          atmVcCrossConnectRowStatus,
                          atmVclCrossConnectIdentifier,
                           atmVcCrossConnectIndexNext }
                      STATUS     current
                      DESCRIPTION
                         "A collection of objects providing






                          information about a VC cross-connect
                          and the associated VCLs that are
                          cross-connected together."
                      ::= { atmMIBGroups 8 }

               aal5VccGroup    OBJECT-GROUP
                      OBJECTS {atmVccAal5CpcsTransmitSduSize,
                          atmVccAal5CpcsReceiveSduSize,
                          atmVccAal5EncapsType,
                          aal5VccCrcErrors, aal5VccSarTimeOuts,
                          aal5VccOverSizedSDUs }
                      STATUS     current
                      DESCRIPTION
                         "A collection of objects providing
                          AAL5 configuration and performance statistics
                          of a VCC."
                      ::= { atmMIBGroups 9 }


-- **************************************************





 END
