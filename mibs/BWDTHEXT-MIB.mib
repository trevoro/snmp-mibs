BWDTHEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32
			FROM SNMPv2-SMI
		DisplayString, RowStatus
			FROM SNMPv2-TC
		bwdthExt
			FROM APENT-MIB;

--BWDTHEXT MIB

    apBwdthExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  Web Host Bwdther information"
      ::= { bwdthExt 1}

apBwdthTable OBJECT-TYPE
	SYNTAX          SEQUENCE OF APBwdthEntry
	MAX-ACCESS      not-accessible
	STATUS          current
	DESCRIPTION
		"A list of Bandwidth records for the specified owners."
	::= { bwdthExt 2 }

apBwdthEntry OBJECT-TYPE
	SYNTAX          APBwdthEntry
	MAX-ACCESS      not-accessible
	STATUS          current
	DESCRIPTION
		"A group of information to identify a bandwidth requirements for the specified owner providing web hosting service."
	INDEX   { apBwdthOwnerName, apBwdthQOSClass }
	--DEFAULT apjam-group apBwdthInst, apBwdthQOSClass
	--DEFAULT apjam-popup-def apBwdthInst, Properties, local
	::= { apBwdthTable 1 }

APBwdthEntry ::= SEQUENCE {
		apBwdthOwnerName               DisplayString,
		apBwdthIndex                   Integer32,
		apBwdthQOSClass                Integer32,
		apBwdthOwnerId                 Integer32,
		apBwdthMaxBwdth                Integer32,
		apBwdthAvgBwdth                Integer32,
		apBwdthAllocStat               Integer32,
	 	apBwdthStatus 				 RowStatus
}

apBwdthOwnerName OBJECT-TYPE
	SYNTAX          DisplayString (SIZE(1..16))
	MAX-ACCESS      read-create
	STATUS          current
	DESCRIPTION     
			"The name of the web host owner providing service."
	--DEFAULT ap-display-name	Name
	--DEFAULT apjam-popup-ref apBwdthInst, Properties
	::= {apBwdthEntry 1}

apBwdthIndex OBJECT-TYPE
	SYNTAX          Integer32
	MAX-ACCESS      read-only
	STATUS  		current
	DESCRIPTION     
		"The unique index for each bandwidth record assigned to the specified owner."
	::= {apBwdthEntry 2}

apBwdthQOSClass OBJECT-TYPE
	SYNTAX          Integer32 (0..7)
	MAX-ACCESS      read-create
	STATUS  		current
	DESCRIPTION     
		"The QOS class for this bandwidth, the default is best effort."
	DEFVAL { 3 }
	--DEFAULT ap-display-name	QOS Class
	--DEFAULT apjam-popup-ref apBwdthInst, Properties
	::= {apBwdthEntry 3}

apBwdthOwnerId  OBJECT-TYPE
	SYNTAX          Integer32
	MAX-ACCESS      read-only
	STATUS  		current
	DESCRIPTION     
		"The unique index for each web host owner configured in this content-aware network.."
	::= {apBwdthEntry 4}


apBwdthMaxBwdth OBJECT-TYPE
	SYNTAX          Integer32 ( 0..100000 )
	MAX-ACCESS      read-create
	STATUS  		current
	DESCRIPTION     
		"The Max Bandwidth allowed for this owner in specified QoS class."
	DEFVAL { 0 }
	--DEFAULT ap-display-name	Max Bandwidth
	--DEFAULT apjam-popup-ref apBwdthInst, Properties
	::= {apBwdthEntry 5}

apBwdthAvgBwdth OBJECT-TYPE
	SYNTAX          Integer32  ( 0..100000 )
	MAX-ACCESS      read-create
	STATUS  		current
	DESCRIPTION     
		"The Average Bandwidth allowed for this owner in specified Qos class. "
	DEFVAL { 0 }
	--DEFAULT ap-display-name	Avg. Bandwidth
	--DEFAULT apjam-popup-ref apBwdthInst, Properties
	::= {apBwdthEntry 6}

apBwdthAllocStat OBJECT-TYPE
	SYNTAX          Integer32  ( 0..100000 )
	MAX-ACCESS      read-only
	STATUS  		current
	DESCRIPTION     
		"The Bandwidth allocated to this owner in specified QoS class. "
	DEFVAL { 0 }
	--DEFAULT ap-display-name	Alloc. Bandwidth
	--DEFAULT apjam-popup-ref apBwdthInst, Properties
	::= {apBwdthEntry 7}

apBwdthStatus OBJECT-TYPE
	SYNTAX          RowStatus
	MAX-ACCESS      read-create
	STATUS          current
	DESCRIPTION      
		"Status entry for this row "
	::= {apBwdthEntry 8}

END
