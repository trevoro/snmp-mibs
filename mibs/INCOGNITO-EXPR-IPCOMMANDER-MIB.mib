-- ****************************************************************************
-- Incognito Software IPC Services MIB
--
-- Copyright (c) 2008-2010 Incognito Software Inc.
-- ****************************************************************************

INCOGNITO-EXPR-IPCOMMANDER-MIB DEFINITIONS ::= BEGIN

IMPORTS
	incognitoExpr
		FROM INCOGNITO-MIB
	DateAndTime,
	DisplayString
		FROM SNMPv2-TC
	OBJECT-GROUP,
	NOTIFICATION-GROUP,
	MODULE-COMPLIANCE
		FROM SNMPv2-CONF
	enterprises,
	MODULE-IDENTITY,
	OBJECT-IDENTITY,
	OBJECT-TYPE,
	NOTIFICATION-TYPE,
	Counter32,
	IpAddress,
	Unsigned32
		FROM SNMPv2-SMI;

incognitoIPC MODULE-IDENTITY
	LAST-UPDATED "201001111600Z"	-- Jan 11, 2010 5:00:00 PM
	ORGANIZATION "Incognito Software Inc."
	CONTACT-INFO
		"Incognito Software Inc.
		Customer Service

		Postal:
		    #500 - 375 Water St.
		    Vancouver, BC, Canada
		    V6B 5C6

		Tel: +1 604-688-4332
		Fax: +1 604-688-4339

		E-Mail: support@incognito.com"
	DESCRIPTION
		""
	REVISION "200802131802Z"	-- Feb 13, 2008 6:02:00 PM
	DESCRIPTION
		"Adjusted ipcFailover to match what the service is using."
	REVISION "200805071834Z"	-- May  7, 2008 6:34:00 PM
	DESCRIPTION
		"Added license in use value."
	REVISION "200905081700Z"	-- May  8, 2009 5:00:00 PM
	DESCRIPTION
		"Added new service types for ipcmdNotifyServerType."
	REVISION "200907301100Z"	-- July 30, 2009 11:00:00 AM
	DESCRIPTION
		"Added a new branch, ipcDHCPPacketResponseStatistics, to keep track of packet response times."
	REVISION "200909150900Z"	-- Sep 15, 2009 09:00:00 AM
	DESCRIPTION
		"Added notifications for LDAP Set up and down."
	REVISION "200911060900Z"	-- Nov  6, 2009 09:00:00 AM
	DESCRIPTION
		"Added notifications for devices tripping the DoS detection."
	REVISION "200911060900Z"	-- Jan 11, 2010 4:00:00 PM
	DESCRIPTION
		"Relabeled ipcmdServiceInfo as ipcmdServiceStatus.  Added a new branch, ipcServiceInformation, to report information about the service."
	-- 1.3.6.1.4.1.3606.7.1
	::= { incognitoExpr 1 }


draftServerMIB OBJECT-IDENTITY
	STATUS current
	DESCRIPTION
		"The Draft DHCP Server MIB"
	-- 1.3.6.1.4.1.3606.7.1.1
	::= { incognitoIPC 1 }

ipcServerObjects OBJECT-IDENTITY
	STATUS current
	DESCRIPTION ""
	-- 1.3.6.1.4.1.3606.7.1.2
	::= { incognitoIPC 2 }

ipcNotificationPrefix OBJECT-IDENTITY
	STATUS current
	DESCRIPTION ""
	-- 1.3.6.1.4.1.3606.7.1.3
	::= { incognitoIPC 3 }

ipcTimeOfDayServer OBJECT-IDENTITY
	STATUS current
	DESCRIPTION ""
	-- 1.3.6.1.4.1.3606.7.1.5
	::= { incognitoIPC 5 }

ipcDeprecatedNotificationPrefix OBJECT-IDENTITY
	STATUS current
	DESCRIPTION ""
	-- 1.3.6.1.4.1.3606.7.1.99
	::= { incognitoIPC 99 }

-- Server Objects

ipcFailover OBJECT-IDENTITY
	STATUS current
	DESCRIPTION
		"Group of objects related to DHCP failover"
	-- 1.3.6.1.4.1.3606.7.1.2.100
	::= { ipcServerObjects 100 }

ipcDHCPStatistics OBJECT-IDENTITY
	STATUS current
	DESCRIPTION ""
	-- 1.3.6.1.4.1.3606.7.1.2.2
	::= { ipcServerObjects 2 }

ipcConfiguration OBJECT-IDENTITY
	STATUS current
	DESCRIPTION ""
	-- 1.3.6.1.4.1.3606.7.1.2.3
	::= { ipcServerObjects 3 }

ipcNotifyObjects OBJECT-IDENTITY
	STATUS current
	DESCRIPTION ""
	-- 1.3.6.1.4.1.3606.7.1.2.4
	::= { ipcServerObjects 4 }

ipcDeprecatedNotifyObjects OBJECT-IDENTITY
	STATUS current
	DESCRIPTION ""
	-- 1.3.6.1.4.1.3606.7.1.2.99
	::= { ipcServerObjects 99 }

ipcServiceStatistics OBJECT-IDENTITY
	STATUS current
	DESCRIPTION
		"Group of statistics related to IPC service"
	-- 1.3.6.1.4.1.3606.7.1.2.101
	::= { ipcServerObjects 101 }

ipcServiceInformation OBJECT-IDENTITY
	STATUS current
	DESCRIPTION
		"Group of information related to IPC service"
	-- 1.3.6.1.4.1.3606.7.1.2.102
	::= { ipcServerObjects 102 }

-- DHCP Failover Objects

ipcFailoverStatistics OBJECT-IDENTITY
	STATUS current
	DESCRIPTION
		"Group of objects related to DHCP failover statistics."
	-- 1.3.6.1.4.1.3606.7.1.2.100.1
	::= { ipcFailover 1 }

-- DHCP Failover Statistic Groups

ipcFailoverSummaryStatistics OBJECT-IDENTITY
	STATUS current
	DESCRIPTION
		"DHCP failover statistics summed for all
		types of DHCP database tables."
	-- 1.3.6.1.4.1.3606.7.1.2.100.1.1
	::= { ipcFailoverStatistics 1 }

ipcFailoverProtocolStatistics OBJECT-IDENTITY
	STATUS current
	DESCRIPTION
		"DHCP failover statistics for individual
		DHCP database tables."
	-- 1.3.6.1.4.1.3606.7.1.2.100.1.2
	::= { ipcFailoverStatistics 2 }

-- DHCP Failover Statistic Summary Sub-Groups

ipcFailoverTimerSummaryStatistics OBJECT-IDENTITY
	STATUS current
	DESCRIPTION
		"DHCP failover timer statistics summed
		for all types of DHCP configuration objects."
	-- 1.3.6.1.4.1.3606.7.1.2.100.1.1.1
	::= { ipcFailoverSummaryStatistics 1 }

ipcFailoverErrorSummaryStatistics OBJECT-IDENTITY
	STATUS current
	DESCRIPTION
		"DHCP failover error statistics summed
		for all types of DHCP configuration objects."
	-- 1.3.6.1.4.1.3606.7.1.2.100.1.1.2
	::= { ipcFailoverSummaryStatistics 2 }

ipcFailoverTimeDownSummaryStatistics OBJECT-IDENTITY
	STATUS current
	DESCRIPTION
		"DHCP failover time down statistics summed
		for all types of DHCP configuration objects."
	-- 1.3.6.1.4.1.3606.7.1.2.100.1.1.3
	::= { ipcFailoverSummaryStatistics 3 }

ipcFailoverResynchSummaryStatistics OBJECT-IDENTITY
	STATUS current
	DESCRIPTION
		"DHCP failover resynchronization statistics
		summed for all types of DHCP configuration
		objects."
	-- 1.3.6.1.4.1.3606.7.1.2.100.1.1.4
	::= { ipcFailoverSummaryStatistics 4 }

ipcFailoverTimeupSummaryStatistics OBJECT-IDENTITY
	STATUS current
	DESCRIPTION
		"DHCP failover time up statistics summed for
		all types of DHCP configuration objects."
	-- 1.3.6.1.4.1.3606.7.1.2.100.1.1.5
	::= { ipcFailoverSummaryStatistics 5 }

ipcFailoverRecdSummaryStatistics OBJECT-IDENTITY
	STATUS current
	DESCRIPTION
		"DHCP failover received message statistics
		summed for all types of DHCP configuration
		objects."
	-- 1.3.6.1.4.1.3606.7.1.2.100.1.1.6
	::= { ipcFailoverSummaryStatistics 6 }

ipcFailoverSentSummaryStatistics OBJECT-IDENTITY
	STATUS current
	DESCRIPTION
		"DHCP failover sent message statistics
		summed for all types of DHCP configuration
		objects."
	-- 1.3.6.1.4.1.3606.7.1.2.100.1.1.7
	::= { ipcFailoverSummaryStatistics 7 }

ipcFailoverTrafficSummaryStatistics OBJECT-IDENTITY
	STATUS current
	DESCRIPTION
		"DHCP failover traffic statistics summed for
		all types of DHCP configuration objects."
	-- 1.3.6.1.4.1.3606.7.1.2.100.1.1.8
	::= { ipcFailoverSummaryStatistics 8 }

ipcFailoverStatusSummaryStatistics OBJECT-IDENTITY
	STATUS current
	DESCRIPTION
		"DHCP failover status statistics summed for
		all types of DHCP configuration objects."
	-- 1.3.6.1.4.1.3606.7.1.2.100.1.1.9
	::= { ipcFailoverSummaryStatistics 9 }

-- ipcFailoverTimerSummaryStatistics group

ipcFailStatLastStartTime OBJECT-TYPE
	SYNTAX  DateAndTime
	MAX-ACCESS read-only
	STATUS current
	DESCRIPTION
		"The last time the failover relationship initiated."
	-- 1.3.6.1.4.1.3606.7.1.2.100.1.1.1.1
	::= { ipcFailoverTimerSummaryStatistics 1 }


ipcFailStatLastSyncTime OBJECT-TYPE
	SYNTAX  DateAndTime
	MAX-ACCESS read-only
	STATUS current
	DESCRIPTION
		"The last time database synchronization occurred
		between the primary and secondary DHCP failover
		services."
	-- 1.3.6.1.4.1.3606.7.1.2.100.1.1.1.2
	::= { ipcFailoverTimerSummaryStatistics 2 }


ipcFailStatLastTestTime OBJECT-TYPE
	SYNTAX  DateAndTime
	MAX-ACCESS read-only
	STATUS current
	DESCRIPTION
		"The last time failover communications were tested
		between the primary and secondary DHCP failover
		services."
	-- 1.3.6.1.4.1.3606.7.1.2.100.1.1.1.3
	::= { ipcFailoverTimerSummaryStatistics 3 }


ipcFailStatLastDownTime OBJECT-TYPE
	SYNTAX  DateAndTime
	MAX-ACCESS read-only
	STATUS current
	DESCRIPTION
		"The last time failover communications were failed
		between the primary and secondary DHCP failover
		services."
	-- 1.3.6.1.4.1.3606.7.1.2.100.1.1.1.4
	::= { ipcFailoverTimerSummaryStatistics 4 }


ipcFailStatLastUpTime OBJECT-TYPE
	SYNTAX  DateAndTime
	MAX-ACCESS read-only
	STATUS current
	DESCRIPTION
		"The last time failover communications were succeeded
		between the primary and secondary DHCP failover
		services."
	-- 1.3.6.1.4.1.3606.7.1.2.100.1.1.1.5
	::= { ipcFailoverTimerSummaryStatistics 5 }


-- ipcFailoverErrorSummaryStatistics group

ipcFailStatSendErrors OBJECT-TYPE
	SYNTAX  Counter32
	MAX-ACCESS read-only
	STATUS current
	DESCRIPTION
		"The number of errors that have occurred
		sending failover messages since the last
		time this counter was reset."
	-- 1.3.6.1.4.1.3606.7.1.2.100.1.1.2.1
	::= { ipcFailoverErrorSummaryStatistics 1 }


ipcFailStatRecvErrors OBJECT-TYPE
	SYNTAX  Counter32
	MAX-ACCESS read-only
	STATUS current
	DESCRIPTION
		"The number of errors that have occurred
		receiving failover messages since the last
		time this counter was reset."
	-- 1.3.6.1.4.1.3606.7.1.2.100.1.1.2.2
	::= { ipcFailoverErrorSummaryStatistics 2 }


ipcFailStatPlatformMismatchErrors OBJECT-TYPE
	SYNTAX  Counter32
	MAX-ACCESS read-only
	STATUS current
	DESCRIPTION
		"The number of times an attempt was made
		to initiate failover between this service
		and a partner failover service on a different
		platform, since the last time this counter
		was reset."
	-- 1.3.6.1.4.1.3606.7.1.2.100.1.1.2.3
	::= { ipcFailoverErrorSummaryStatistics 3 }


ipcFailStatVersionMismatchErrors OBJECT-TYPE
	SYNTAX  Counter32
	MAX-ACCESS read-only
	STATUS current
	DESCRIPTION
		"The number of times an attempt was made
		to initiate failover between this service
		and a partner failover service using a different
		failover protocol version, since the last time
		this counter was reset."
	-- 1.3.6.1.4.1.3606.7.1.2.100.1.1.2.4
	::= { ipcFailoverErrorSummaryStatistics 4 }


ipcFailStatRoleMismatchErrors OBJECT-TYPE
	SYNTAX  Counter32
	MAX-ACCESS read-only
	STATUS current
	DESCRIPTION
		"The number of times an attempt was made
		to initiate failover between this service
		and a partner failover service that was
		designated with the same failover role
		(both services were primary or both services
		were secondary), since the last time this
		counter was reset."
	-- 1.3.6.1.4.1.3606.7.1.2.100.1.1.2.5
	::= { ipcFailoverErrorSummaryStatistics 5 }


ipcFailStatCRC1Errors OBJECT-TYPE
	SYNTAX  Counter32
	MAX-ACCESS read-only
	STATUS current
	DESCRIPTION
		"The number of cyclic redundancy checksum
		errors that occurred for the first CRC
		encoding while decoding DHCP failover
		messages between the DHCP services ."
	-- 1.3.6.1.4.1.3606.7.1.2.100.1.1.2.6
	::= { ipcFailoverErrorSummaryStatistics 6 }


ipcFailStatCRC2Errors OBJECT-TYPE
	SYNTAX  Counter32
	MAX-ACCESS read-only
	STATUS current
	DESCRIPTION
		"The number of cyclic redundancy checksum
		errors that occurred for the second CRC
		encoding while decoding DHCP failover
		messages between the DHCP services ."
	-- 1.3.6.1.4.1.3606.7.1.2.100.1.1.2.7
	::= { ipcFailoverErrorSummaryStatistics 7 }


ipcFailStatDecryptErrors OBJECT-TYPE
	SYNTAX  Counter32
	MAX-ACCESS read-only
	STATUS current
	DESCRIPTION
		"The number of errors that occurred
		decrypting DHCP failover messages
		between the DHCP services."
	-- 1.3.6.1.4.1.3606.7.1.2.100.1.1.2.8
	::= { ipcFailoverErrorSummaryStatistics 8 }


ipcFailStatAccessDeniedErrors OBJECT-TYPE
	SYNTAX  Counter32
	MAX-ACCESS read-only
	STATUS current
	DESCRIPTION
		"The number of access denied errors
		that occurred while attempting to
		propagate DHCP configuration changes
		to the partner failover service."
	-- 1.3.6.1.4.1.3606.7.1.2.100.1.1.2.9
	::= { ipcFailoverErrorSummaryStatistics 9 }


-- ipcFailoverTimeDownSummaryStatistics group

ipcFailStatTotalTimeDown OBJECT-TYPE
	SYNTAX  Counter32
	MAX-ACCESS read-only
	STATUS current
	DESCRIPTION
		"The total number of seconds spend in
		the failover communications down state."
	-- 1.3.6.1.4.1.3606.7.1.2.100.1.1.3.1
	::= { ipcFailoverTimeDownSummaryStatistics 1 }


ipcFailStatLongestTimeDown OBJECT-TYPE
	SYNTAX  Counter32
	MAX-ACCESS read-only
	STATUS current
	DESCRIPTION
		"The longest period spend in the failover
		communications down state, in seconds."
	-- 1.3.6.1.4.1.3606.7.1.2.100.1.1.3.2
	::= { ipcFailoverTimeDownSummaryStatistics 2 }


ipcFailStatCountTimeDown OBJECT-TYPE
	SYNTAX  Counter32
	MAX-ACCESS read-only
	STATUS current
	DESCRIPTION
		"The total number of times the service
		has been in the failover communications
		down state."
	-- 1.3.6.1.4.1.3606.7.1.2.100.1.1.3.3
	::= { ipcFailoverTimeDownSummaryStatistics 3 }


-- ipcFailoverResynchSummaryStatistics group

ipcFailStatTotalResynch OBJECT-TYPE
	SYNTAX  Counter32
	MAX-ACCESS read-only
	STATUS current
	DESCRIPTION
		"The total number of seconds spend in
		the failover resynchronization state."
	-- 1.3.6.1.4.1.3606.7.1.2.100.1.1.4.1
	::= { ipcFailoverResynchSummaryStatistics 1 }


ipcFailStatLongestResynch OBJECT-TYPE
	SYNTAX  Counter32
	MAX-ACCESS read-only
	STATUS current
	DESCRIPTION
		"The longest period spend in the failover
		resynchronization state, in seconds."
	-- 1.3.6.1.4.1.3606.7.1.2.100.1.1.4.2
	::= { ipcFailoverResynchSummaryStatistics 2 }


ipcFailStatCountResynch OBJECT-TYPE
	SYNTAX  Counter32
	MAX-ACCESS read-only
	STATUS current
	DESCRIPTION
		"The total number of times the service
		has been in the failover resynchronization
		state."
	-- 1.3.6.1.4.1.3606.7.1.2.100.1.1.4.3
	::= { ipcFailoverResynchSummaryStatistics 3 }


-- ipcFailoverTimeupSummaryStatistics group

ipcFailStatTotalTimeUp OBJECT-TYPE
	SYNTAX  Counter32
	MAX-ACCESS read-only
	STATUS current
	DESCRIPTION
		"The total number of seconds spend in
		the failover communications up state."
	-- 1.3.6.1.4.1.3606.7.1.2.100.1.1.5.1
	::= { ipcFailoverTimeupSummaryStatistics 1 }


ipcFailStatLongestTimeUp OBJECT-TYPE
	SYNTAX  Counter32
	MAX-ACCESS read-only
	STATUS current
	DESCRIPTION
		"The longest period spend in the failover
		communications up state, in seconds."
	-- 1.3.6.1.4.1.3606.7.1.2.100.1.1.5.2
	::= { ipcFailoverTimeupSummaryStatistics 2 }


ipcFailStatCountTimeUp OBJECT-TYPE
	SYNTAX  Counter32
	MAX-ACCESS read-only
	STATUS current
	DESCRIPTION
		"The total number of times the service
		has been in the failover communications
		up state."
	-- 1.3.6.1.4.1.3606.7.1.2.100.1.1.5.3
	::= { ipcFailoverTimeupSummaryStatistics 3 }


-- ipcFailoverRecdSummaryStatistics group

ipcFailStatRecdHeartbeats OBJECT-TYPE
	SYNTAX  Counter32
	MAX-ACCESS read-only
	STATUS current
	DESCRIPTION
		"The total number of heartbeat messages
		received since the last time this statistic
		was reset."
	-- 1.3.6.1.4.1.3606.7.1.2.100.1.1.6.1
	::= { ipcFailoverRecdSummaryStatistics 1 }


ipcFailStatRecdTestRequests OBJECT-TYPE
	SYNTAX  Counter32
	MAX-ACCESS read-only
	STATUS current
	DESCRIPTION
		"The total number of test request messages
		received since the last time this statistic
		was reset."
	-- 1.3.6.1.4.1.3606.7.1.2.100.1.1.6.2
	::= { ipcFailoverRecdSummaryStatistics 2 }


ipcFailStatRecdTestReplies OBJECT-TYPE
	SYNTAX  Counter32
	MAX-ACCESS read-only
	STATUS current
	DESCRIPTION
		"The total number of test reply messages
		received since the last time this statistic
		was reset."
	-- 1.3.6.1.4.1.3606.7.1.2.100.1.1.6.3
	::= { ipcFailoverRecdSummaryStatistics 3 }


ipcFailStatRecdDataTxRequests OBJECT-TYPE
	SYNTAX  Counter32
	MAX-ACCESS read-only
	STATUS current
	DESCRIPTION
		"The total number of data transfer requests
		received since the last time this statistic
		was reset."
	-- 1.3.6.1.4.1.3606.7.1.2.100.1.1.6.4
	::= { ipcFailoverRecdSummaryStatistics 4 }


ipcFailStatRecdDataTxData OBJECT-TYPE
	SYNTAX  Counter32
	MAX-ACCESS read-only
	STATUS current
	DESCRIPTION
		"The total number of data transfer data packets
		received since the last time this statistic
		was reset."
	-- 1.3.6.1.4.1.3606.7.1.2.100.1.1.6.5
	::= { ipcFailoverRecdSummaryStatistics 5 }


ipcFailStatRecdDataTxAcks OBJECT-TYPE
	SYNTAX  Counter32
	MAX-ACCESS read-only
	STATUS current
	DESCRIPTION
		"The total number of data transfer acknowledgement
		packets received since the last time this
		statistic was reset."
	-- 1.3.6.1.4.1.3606.7.1.2.100.1.1.6.6
	::= { ipcFailoverRecdSummaryStatistics 6 }


ipcFailStatRecdDataTransactionData OBJECT-TYPE
	SYNTAX  Counter32
	MAX-ACCESS read-only
	STATUS current
	DESCRIPTION
		"The total number of data transaction data packets
		received since the last time this statistic
		was reset."
	-- 1.3.6.1.4.1.3606.7.1.2.100.1.1.6.7
	::= { ipcFailoverRecdSummaryStatistics 7 }


ipcFailStatRecdDataTransactionAcks OBJECT-TYPE
	SYNTAX  Counter32
	MAX-ACCESS read-only
	STATUS current
	DESCRIPTION
		"The total number of data transaction acknowledgement
		packets received since the last time this
		statistic was reset."
	-- 1.3.6.1.4.1.3606.7.1.2.100.1.1.6.8
	::= { ipcFailoverRecdSummaryStatistics 8 }


ipcFailStatRecdDataConflicts OBJECT-TYPE
	SYNTAX  Counter32
	MAX-ACCESS read-only
	STATUS current
	DESCRIPTION
		"The total number of data conflict messages
		received since the last time this statistic
		was reset."
	-- 1.3.6.1.4.1.3606.7.1.2.100.1.1.6.9
	::= { ipcFailoverRecdSummaryStatistics 9 }


ipcFailStatRecdDataConflictAcks OBJECT-TYPE
	SYNTAX  Counter32
	MAX-ACCESS read-only
	STATUS current
	DESCRIPTION
		"The total number of data conflict acknowledgement
		messages received since the last time this
		statistic was reset."
	-- 1.3.6.1.4.1.3606.7.1.2.100.1.1.6.10
	::= { ipcFailoverRecdSummaryStatistics 10 }


ipcFailStatRecdDataResynchRequests OBJECT-TYPE
	SYNTAX  Counter32
	MAX-ACCESS read-only
	STATUS current
	DESCRIPTION
		"The total number of data resynchronization
		request messages received since the last time
		this statistic was reset."
	-- 1.3.6.1.4.1.3606.7.1.2.100.1.1.6.11
	::= { ipcFailoverRecdSummaryStatistics 11 }


ipcFailStatRecdDataResynchAcks OBJECT-TYPE
	SYNTAX  Counter32
	MAX-ACCESS read-only
	STATUS current
	DESCRIPTION
		"The total number of data resynchronization
		acknowledgement messages received since the
		last time this statistic was reset."
	-- 1.3.6.1.4.1.3606.7.1.2.100.1.1.6.12
	::= { ipcFailoverRecdSummaryStatistics 12 }


ipcFailStatRecdShuttingDown OBJECT-TYPE
	SYNTAX  Counter32
	MAX-ACCESS read-only
	STATUS current
	DESCRIPTION
		"The total number of service stopping
		messages received from the partner failover
		DHCP service since the last time this statistic
		was reset."
	-- 1.3.6.1.4.1.3606.7.1.2.100.1.1.6.13
	::= { ipcFailoverRecdSummaryStatistics 13 }


-- ipcFailoverSentSummaryStatistics group

ipcFailStatSentHeartbeats OBJECT-TYPE
	SYNTAX  Counter32
	MAX-ACCESS read-only
	STATUS current
	DESCRIPTION
		"The total number of heartbeat messages
		sent since the last time this statistic
		was reset."
	-- 1.3.6.1.4.1.3606.7.1.2.100.1.1.7.1
	::= { ipcFailoverSentSummaryStatistics 1 }


ipcFailStatSentTestRequests OBJECT-TYPE
	SYNTAX  Counter32
	MAX-ACCESS read-only
	STATUS current
	DESCRIPTION
		"The total number of test request messages
		sent since the last time this statistic
		was reset."
	-- 1.3.6.1.4.1.3606.7.1.2.100.1.1.7.2
	::= { ipcFailoverSentSummaryStatistics 2 }


ipcFailStatSentTestReplies OBJECT-TYPE
	SYNTAX  Counter32
	MAX-ACCESS read-only
	STATUS current
	DESCRIPTION
		"The total number of test reply messages
		sent since the last time this statistic
		was reset."
	-- 1.3.6.1.4.1.3606.7.1.2.100.1.1.7.3
	::= { ipcFailoverSentSummaryStatistics 3 }


ipcFailStatSentDataTxRequests OBJECT-TYPE
	SYNTAX  Counter32
	MAX-ACCESS read-only
	STATUS current
	DESCRIPTION
		"The total number of data transfer requests
		sent since the last time this statistic
		was reset."
	-- 1.3.6.1.4.1.3606.7.1.2.100.1.1.7.4
	::= { ipcFailoverSentSummaryStatistics 4 }


ipcFailStatSentDataTxData OBJECT-TYPE
	SYNTAX  Counter32
	MAX-ACCESS read-only
	STATUS current
	DESCRIPTION
		"The total number of data transfer data packets
		sent since the last time this statistic
		was reset."
	-- 1.3.6.1.4.1.3606.7.1.2.100.1.1.7.5
	::= { ipcFailoverSentSummaryStatistics 5 }


ipcFailStatSentDataTxAcks OBJECT-TYPE
	SYNTAX  Counter32
	MAX-ACCESS read-only
	STATUS current
	DESCRIPTION
		"The total number of data transfer acknowledgement
		packets sent since the last time this
		statistic was reset."
	-- 1.3.6.1.4.1.3606.7.1.2.100.1.1.7.6
	::= { ipcFailoverSentSummaryStatistics 6 }


ipcFailStatSentDataTransactionData OBJECT-TYPE
	SYNTAX  Counter32
	MAX-ACCESS read-only
	STATUS current
	DESCRIPTION
		"The total number of data transaction data packets
		sent since the last time this statistic
		was reset."
	-- 1.3.6.1.4.1.3606.7.1.2.100.1.1.7.7
	::= { ipcFailoverSentSummaryStatistics 7 }


ipcFailStatSentDataTransactionAcks OBJECT-TYPE
	SYNTAX  Counter32
	MAX-ACCESS read-only
	STATUS current
	DESCRIPTION
		"The total number of data transaction acknowledgement
		packets sent since the last time this
		statistic was reset."
	-- 1.3.6.1.4.1.3606.7.1.2.100.1.1.7.8
	::= { ipcFailoverSentSummaryStatistics 8 }


ipcFailStatSentDataConflicts OBJECT-TYPE
	SYNTAX  Counter32
	MAX-ACCESS read-only
	STATUS current
	DESCRIPTION
		"The total number of data conflict messages
		sent since the last time this statistic
		was reset."
	-- 1.3.6.1.4.1.3606.7.1.2.100.1.1.7.9
	::= { ipcFailoverSentSummaryStatistics 9 }


ipcFailStatSentDataConflictAcks OBJECT-TYPE
	SYNTAX  Counter32
	MAX-ACCESS read-only
	STATUS current
	DESCRIPTION
		"The total number of data conflict acknowledgement
		messages sent since the last time this
		statistic was reset."
	-- 1.3.6.1.4.1.3606.7.1.2.100.1.1.7.10
	::= { ipcFailoverSentSummaryStatistics 10 }


ipcFailStatSentDataResynchRequests OBJECT-TYPE
	SYNTAX  Counter32
	MAX-ACCESS read-only
	STATUS current
	DESCRIPTION
		"The total number of data resynchronization
		request messages sent since the last time
		this statistic was reset."
	-- 1.3.6.1.4.1.3606.7.1.2.100.1.1.7.11
	::= { ipcFailoverSentSummaryStatistics 11 }


ipcFailStatSentDataResynchAcks OBJECT-TYPE
	SYNTAX  Counter32
	MAX-ACCESS read-only
	STATUS current
	DESCRIPTION
		"The total number of data resynchronization
		acknowledgement messages sent since the
		last time this statistic was reset."
	-- 1.3.6.1.4.1.3606.7.1.2.100.1.1.7.12
	::= { ipcFailoverSentSummaryStatistics 12 }


ipcFailStatSentShuttingDown OBJECT-TYPE
	SYNTAX  Counter32
	MAX-ACCESS read-only
	STATUS current
	DESCRIPTION
		"The total number of service stopping
		messages sent from the partner failover
		DHCP service since the last time this statistic
		was reset."
	-- 1.3.6.1.4.1.3606.7.1.2.100.1.1.7.13
	::= { ipcFailoverSentSummaryStatistics 13 }


-- ipcFailoverTrafficSummaryStatistics group

ipcFailStatBytesSent OBJECT-TYPE
	SYNTAX  Counter32
	MAX-ACCESS read-only
	STATUS current
	DESCRIPTION
		"The number of bytes sent in failover
		packets since the last time this statistic
		was reset"
	-- 1.3.6.1.4.1.3606.7.1.2.100.1.1.8.1
	::= { ipcFailoverTrafficSummaryStatistics 1 }


ipcFailStatBytesRecd OBJECT-TYPE
	SYNTAX  Counter32
	MAX-ACCESS read-only
	STATUS current
	DESCRIPTION
		"The number of bytes received in failover
		packets since the last time this statistic
		was reset"
	-- 1.3.6.1.4.1.3606.7.1.2.100.1.1.8.2
	::= { ipcFailoverTrafficSummaryStatistics 2 }


ipcFailStatTxSent OBJECT-TYPE
	SYNTAX  Counter32
	MAX-ACCESS read-only
	STATUS current
	DESCRIPTION
		"The number of failover transactions sent
		since the last time this statistic was reset"
	-- 1.3.6.1.4.1.3606.7.1.2.100.1.1.8.3
	::= { ipcFailoverTrafficSummaryStatistics 3 }


ipcFailStatTxRecd OBJECT-TYPE
	SYNTAX  Counter32
	MAX-ACCESS read-only
	STATUS current
	DESCRIPTION
		"The number of failover transactions received
		since the last time this statistic was reset"
	-- 1.3.6.1.4.1.3606.7.1.2.100.1.1.8.4
	::= { ipcFailoverTrafficSummaryStatistics 4 }


-- ipcFailoverStatusSummaryStatistics group

ipcFailStatStatus OBJECT-TYPE
	SYNTAX  DisplayString (SIZE (0..255))
	MAX-ACCESS read-only
	STATUS current
	DESCRIPTION
		"The current failover status of the service:
		up
		down
		disabled
		stand-alone
		n/a

		"
	-- 1.3.6.1.4.1.3606.7.1.2.100.1.1.9.1
	::= { ipcFailoverStatusSummaryStatistics 1 }


ipcFailStatOperation OBJECT-TYPE
	SYNTAX  DisplayString (SIZE (0..255))
	MAX-ACCESS read-only
	STATUS current
	DESCRIPTION
		"The current failover operation:
		terminating failover
		stopping
		stopped
		n/a

		"
	-- 1.3.6.1.4.1.3606.7.1.2.100.1.1.9.2
	::= { ipcFailoverStatusSummaryStatistics 2 }


ipcDHCPPacketStatistics OBJECT-IDENTITY
	STATUS current
	DESCRIPTION ""
	-- 1.3.6.1.4.1.3606.7.1.2.2.1
	::= { ipcDHCPStatistics 1 }

ipcDHCPPacketDiscardStatistics OBJECT-IDENTITY
	STATUS current
	DESCRIPTION ""
	-- 1.3.6.1.4.1.3606.7.1.2.2.1.1
	::= { ipcDHCPPacketStatistics 1 }

ipcDHCPDiscoverPacketDiscards OBJECT-TYPE
	SYNTAX  Counter32
	MAX-ACCESS read-only
	STATUS current
	DESCRIPTION ""
	-- 1.3.6.1.4.1.3606.7.1.2.2.1.1.1
	::= { ipcDHCPPacketDiscardStatistics 1 }


ipcDHCPRequestPacketDiscards OBJECT-TYPE
	SYNTAX  Counter32
	MAX-ACCESS read-only
	STATUS current
	DESCRIPTION ""
	-- 1.3.6.1.4.1.3606.7.1.2.2.1.1.2
	::= { ipcDHCPPacketDiscardStatistics 2 }


ipcDHCPInformPacketDiscards OBJECT-TYPE
	SYNTAX  Counter32
	MAX-ACCESS read-only
	STATUS current
	DESCRIPTION ""
	-- 1.3.6.1.4.1.3606.7.1.2.2.1.1.3
	::= { ipcDHCPPacketDiscardStatistics 3 }


ipcDHCPDeclinePacketDiscards OBJECT-TYPE
	SYNTAX  Counter32
	MAX-ACCESS read-only
	STATUS current
	DESCRIPTION ""
	-- 1.3.6.1.4.1.3606.7.1.2.2.1.1.4
	::= { ipcDHCPPacketDiscardStatistics 4 }


ipcDHCPOtherPacketDiscards OBJECT-TYPE
	SYNTAX  Counter32
	MAX-ACCESS read-only
	STATUS current
	DESCRIPTION ""
	-- 1.3.6.1.4.1.3606.7.1.2.2.1.1.5
	::= { ipcDHCPPacketDiscardStatistics 5 }


ipcDHCPPacketSupercedeStatistics OBJECT-IDENTITY
	STATUS current
	DESCRIPTION ""
	-- 1.3.6.1.4.1.3606.7.1.2.2.1.2
	::= { ipcDHCPPacketStatistics 2 }

ipcDHCPDiscoverPacketSupercedes OBJECT-TYPE
	SYNTAX  Counter32
	MAX-ACCESS read-only
	STATUS current
	DESCRIPTION ""
	-- 1.3.6.1.4.1.3606.7.1.2.2.1.2.1
	::= { ipcDHCPPacketSupercedeStatistics 1 }


ipcDHCPRequestPacketSupercedes OBJECT-TYPE
	SYNTAX  Counter32
	MAX-ACCESS read-only
	STATUS current
	DESCRIPTION ""
	-- 1.3.6.1.4.1.3606.7.1.2.2.1.2.2
	::= { ipcDHCPPacketSupercedeStatistics 2 }


ipcDHCPInformPacketSupercedes OBJECT-TYPE
	SYNTAX  Counter32
	MAX-ACCESS read-only
	STATUS current
	DESCRIPTION ""
	-- 1.3.6.1.4.1.3606.7.1.2.2.1.2.3
	::= { ipcDHCPPacketSupercedeStatistics 3 }


ipcDHCPDeclinePacketSupercedes OBJECT-TYPE
	SYNTAX  Counter32
	MAX-ACCESS read-only
	STATUS current
	DESCRIPTION ""
	-- 1.3.6.1.4.1.3606.7.1.2.2.1.2.4
	::= { ipcDHCPPacketSupercedeStatistics 4 }


ipcDHCPOtherPacketSupercedes OBJECT-TYPE
	SYNTAX  Counter32
	MAX-ACCESS read-only
	STATUS current
	DESCRIPTION ""
	-- 1.3.6.1.4.1.3606.7.1.2.2.1.2.5
	::= { ipcDHCPPacketSupercedeStatistics 5 }

ipcDHCPPacketResponseStatistics OBJECT-IDENTITY
	STATUS current
	DESCRIPTION "The average response time of the BOOTP/DHCP requests, in ms, in the last intervals"
	-- 1.3.6.1.4.1.3606.7.1.2.2.1.3
	::= { ipcDHCPPacketStatistics 3 }

ipcDHCPBOOTPPacketResponseAvg1minTime OBJECT-TYPE
	SYNTAX  Unsigned32
	MAX-ACCESS read-only
	STATUS current
	DESCRIPTION "The average response time of the BOOTP requests, in ms, in the last 1 min."
	-- 1.3.6.1.4.1.3606.7.1.2.2.1.3.1
	::= { ipcDHCPPacketResponseStatistics 1 }

ipcDHCPBOOTPPacketResponseAvg5minTime OBJECT-TYPE
	SYNTAX  Unsigned32
	MAX-ACCESS read-only
	STATUS current
	DESCRIPTION "The average response time of the BOOTP requests, in ms, in the last 5 min."
	-- 1.3.6.1.4.1.3606.7.1.2.2.1.3.2
	::= { ipcDHCPPacketResponseStatistics 2 }

ipcDHCPBOOTPPacketResponseAvg15minTime OBJECT-TYPE
	SYNTAX  Unsigned32
	MAX-ACCESS read-only
	STATUS current
	DESCRIPTION "The average response time of the BOOTP requests, in ms, in the last 15 min."
	-- 1.3.6.1.4.1.3606.7.1.2.2.1.3.3
	::= { ipcDHCPPacketResponseStatistics 3 }

ipcDHCPDHCPv4PacketResponseAvg1minTime OBJECT-TYPE
	SYNTAX  Unsigned32
	MAX-ACCESS read-only
	STATUS current
	DESCRIPTION "The average response time of the DHCPv4 requests, in ms, in the last 1 min."
	-- 1.3.6.1.4.1.3606.7.1.2.2.1.3.4
	::= { ipcDHCPPacketResponseStatistics 4 }

ipcDHCPDHCPv4PacketResponseAvg5minTime OBJECT-TYPE
	SYNTAX  Unsigned32
	MAX-ACCESS read-only
	STATUS current
	DESCRIPTION "The average response time of the DHCPv4 requests, in ms, in the last 5 min."
	-- 1.3.6.1.4.1.3606.7.1.2.2.1.3.5
	::= { ipcDHCPPacketResponseStatistics 5 }

ipcDHCPDHCPv4PacketResponseAvg15minTime OBJECT-TYPE
	SYNTAX  Unsigned32
	MAX-ACCESS read-only
	STATUS current
	DESCRIPTION "The average response time of the DHCPv4 requests, in ms, in the last 15 min."
	-- 1.3.6.1.4.1.3606.7.1.2.2.1.3.6
	::= { ipcDHCPPacketResponseStatistics 6 }

ipcConformance OBJECT-IDENTITY
	STATUS current
	DESCRIPTION ""
	-- 1.3.6.1.4.1.3606.7.1.4
	::= { incognitoIPC 4 }

-- ipcTimeOfDayServer

todServerObjects OBJECT-IDENTITY
	STATUS current
	DESCRIPTION ""
	-- 1.3.6.1.4.1.3606.7.1.5.1
	::= { ipcTimeOfDayServer 1 }

todClientObjects OBJECT-IDENTITY
	STATUS current
	DESCRIPTION ""
	-- 1.3.6.1.4.1.3606.7.1.5.1.2
	::= { todServerObjects 2 }

todCounters OBJECT-IDENTITY
	STATUS current
	DESCRIPTION ""
	-- 1.3.6.1.4.1.3606.7.1.5.1.1
	::= { todServerObjects 1 }

todCountTcpRequests OBJECT-TYPE
	SYNTAX  Counter32
	MAX-ACCESS read-only
	STATUS current
	DESCRIPTION
		"The number of time of day requests received over TCP."
	-- 1.3.6.1.4.1.3606.7.1.5.1.1.1
	::= { todCounters 1 }


todCountUdpRequests OBJECT-TYPE
	SYNTAX  Counter32
	MAX-ACCESS read-only
	STATUS current
	DESCRIPTION
		"The number of time of day requests received over Udp."
	-- 1.3.6.1.4.1.3606.7.1.5.1.1.2
	::= { todCounters 2 }


ipcServiceLeasesInUse OBJECT-TYPE
	SYNTAX  Counter32
	MAX-ACCESS read-only
	STATUS current
	DESCRIPTION "The number of leases in use."
	-- 1.3.6.1.4.1.3606.7.1.2.101.1
	::= { ipcServiceStatistics 1 }

ipcServiceServerName OBJECT-TYPE
	SYNTAX  DisplayString (SIZE (0..255))
	MAX-ACCESS read-only
	STATUS current
	DESCRIPTION "The name of the server."
	-- 1.3.6.1.4.1.3606.7.1.2.102.1
	::= { ipcServiceInformation 1 }

ipcServiceName OBJECT-TYPE
	SYNTAX  DisplayString (SIZE (0..255))
	MAX-ACCESS read-only
	STATUS current
	DESCRIPTION "The name of the service."
	-- 1.3.6.1.4.1.3606.7.1.2.102.2
	::= { ipcServiceInformation 2 }
	
ipcServiceVersion OBJECT-TYPE
	SYNTAX  DisplayString (SIZE (0..255))
	MAX-ACCESS read-only
	STATUS current
	DESCRIPTION "The version of the service."
	-- 1.3.6.1.4.1.3606.7.1.2.102.3
	::= { ipcServiceInformation 3 }

ipcServiceLicenseUsers OBJECT-TYPE
	SYNTAX  Unsigned32
	MAX-ACCESS read-only
	STATUS current
	DESCRIPTION "The number of users in license."
	-- 1.3.6.1.4.1.3606.7.1.2.102.4
	::= { ipcServiceInformation 4 }

ipcServiceSubscriptionExpiration OBJECT-TYPE
	SYNTAX  DateAndTime
	MAX-ACCESS read-only
	STATUS current
	DESCRIPTION "The date the subscription expires."
	-- 1.3.6.1.4.1.3606.7.1.2.102.5
	::= { ipcServiceInformation 5 }

ipcServiceLicenseType OBJECT-TYPE
	SYNTAX  Unsigned32
	MAX-ACCESS read-only
	STATUS current
	DESCRIPTION "The type of license (Licensed=0/Demo=1)."
	-- 1.3.6.1.4.1.3606.7.1.2.102.6
	::= { ipcServiceInformation 6 }

ipcServiceOperatingSystem OBJECT-TYPE
	SYNTAX  DisplayString (SIZE (0..255))
	MAX-ACCESS read-only
	STATUS current
	DESCRIPTION "The operating system of the server."
	-- 1.3.6.1.4.1.3606.7.1.2.102.7
	::= { ipcServiceInformation 7 }

ipcServiceStartTime OBJECT-TYPE
	SYNTAX  DateAndTime
	MAX-ACCESS read-only
	STATUS current
	DESCRIPTION "The time the service started."
	-- 1.3.6.1.4.1.3606.7.1.2.102.8
	::= { ipcServiceInformation 8 }

-- Tod Notifications

todServerNotificationPrefix OBJECT IDENTIFIER 
	-- 1.3.6.1.4.1.3606.7.1.5.2
	::= { ipcTimeOfDayServer 2 }

-- Tod Conformance

todServerConformance OBJECT-IDENTITY
	STATUS current
	DESCRIPTION ""
	-- 1.3.6.1.4.1.3606.7.1.5.3
	::= { ipcTimeOfDayServer 3 }

todServerCompliances OBJECT IDENTIFIER 
	-- 1.3.6.1.4.1.3606.7.1.5.3.1
	::= { todServerConformance 1 }

todServerGroups OBJECT IDENTIFIER 
	-- 1.3.6.1.4.1.3606.7.1.5.3.2
	::= { todServerConformance 2 }


todServerCompliance MODULE-COMPLIANCE
	STATUS current
	DESCRIPTION ""

	MODULE 
	MANDATORY-GROUPS {
			todServerCounterObjects }

	-- 1.3.6.1.4.1.3606.7.1.5.3.1.1
	::= { todServerCompliances 1 }

todServerCounterObjects OBJECT-GROUP
	OBJECTS {
		todCountTcpRequests,
		todCountUdpRequests }
	STATUS current
	DESCRIPTION ""
	-- 1.3.6.1.4.1.3606.7.1.5.3.2.1
	::= { todServerGroups 1 }

-- Service Statistics Conformance

ipcServiceStatisticsConformance OBJECT-IDENTITY
	STATUS current
	DESCRIPTION ""
	-- 1.3.6.1.4.1.3606.7.1.2.1
	::= { ipcServerObjects 1 }

ipcServiceStatisticsCompliances OBJECT IDENTIFIER 
	-- 1.3.6.1.4.1.3606.7.1.2.1.1
	::= { ipcServiceStatisticsConformance 1 }

ipcServiceSatisticsGroups OBJECT IDENTIFIER 
	-- 1.3.6.1.4.1.3606.7.1.2.1.2
	::= { ipcServiceStatisticsConformance 2 }

ipcServiceInformationGroups OBJECT IDENTIFIER 
	-- 1.3.6.1.4.1.3606.7.1.2.1.3
	::= { ipcServiceStatisticsConformance 3 }


ipcServiceStatisticsCompliance MODULE-COMPLIANCE
	STATUS current
	DESCRIPTION ""

	MODULE 
	MANDATORY-GROUPS {
			ipcServiceStatisticsObjects }

	-- 1.3.6.1.4.1.3606.7.1.2.1.1.1
	::= { ipcServiceStatisticsCompliances 1 }

ipcServiceStatisticsObjects OBJECT-GROUP
	OBJECTS {
		ipcServiceLeasesInUse }
	STATUS current
	DESCRIPTION ""
	-- 1.3.6.1.4.1.3606.7.1.2.1.2.1
	::= { ipcServiceSatisticsGroups 1 }

ipcServiceInformationObjects OBJECT-GROUP
	OBJECTS {
		ipcServiceServerName,
		ipcServiceName,
		ipcServiceVersion,
		ipcServiceLicenseUsers,
		ipcServiceSubscriptionExpiration,
		ipcServiceLicenseType,
		ipcServiceOperatingSystem,
		ipcServiceStartTime }
	STATUS current
	DESCRIPTION ""
	-- 1.3.6.1.4.1.3606.7.1.2.1.3.1
	::= { ipcServiceInformationGroups 1 }

-- Notify Objects

ipcPausedTime OBJECT-TYPE
	SYNTAX  DateAndTime
	MAX-ACCESS accessible-for-notify
	STATUS current
	DESCRIPTION
		"The date and time when the server paused
		operation."
	-- 1.3.6.1.4.1.3606.7.1.2.4.1
	::= { ipcNotifyObjects 1 }


ipcResumedTime OBJECT-TYPE
	SYNTAX  DateAndTime
	MAX-ACCESS accessible-for-notify
	STATUS current
	DESCRIPTION
		"The date and time when the server resumed
		operation."
	-- 1.3.6.1.4.1.3606.7.1.2.4.2
	::= { ipcNotifyObjects 2 }


-- Notifications

ipcNotifications OBJECT-IDENTITY
	STATUS current
	DESCRIPTION ""
	-- 1.3.6.1.4.1.3606.7.1.3.0
	::= { ipcNotificationPrefix 0 }


ipcNotifyServerPaused NOTIFICATION-TYPE
	OBJECTS {
		ipcPausedTime}
	STATUS current
	DESCRIPTION
		"This notification signifies that the server of the
		specified type has been paused on the host
		from which this notification has been sent."
	-- 1.3.6.1.4.1.3606.7.1.3.0.1
	::= { ipcNotifications 1 }


ipcNotifyServerResumed NOTIFICATION-TYPE
	OBJECTS {
		ipcResumedTime}
	STATUS current
	DESCRIPTION
		"This notification signifies that the server of the
		specified type has been paused on the host
		from which this notification has been sent."
	-- 1.3.6.1.4.1.3606.7.1.3.0.2
	::= { ipcNotifications 2 }

-- Deprecated DHCP Objects - objects that are used for DHCP

ipcDhcpNotifyObjects OBJECT-IDENTITY
	STATUS current
	DESCRIPTION
		"Deprecated DHCP Notify Objects"
	-- 1.3.6.1.4.1.3606.7.1.2.99.1
	::= { ipcDeprecatedNotifyObjects 1 }

ipcmdDHCPFreeAddressLowThreshold OBJECT-TYPE
	SYNTAX  Unsigned32
	MAX-ACCESS accessible-for-notify
	STATUS current
	DESCRIPTION
		"The low threshold for available free addresses in this rule scope.
		              If the value for available free addresses in this rule scope
		              becomes equal to or less than this value, a
		incognitoDHCPFreeAddressLowThreshold event is generated
		              for this shared network.  No more
		              incognitoDHCPFreeAddressLowThreshold events will be generated
		for this rule scope during this execution of the DHCP server until
		the value for available free addresses has exceeded the value
		of incognitoDHCPFreeAddressHighThreshold.

		              This value may be expressed as either an absolute value or a
		              percentage; the units are specified by the value of
		              incognitoDHCPFreeAddressUnits."
	-- 1.3.6.1.4.1.3606.7.1.2.99.1.1
	::= { ipcDhcpNotifyObjects 1 }


ipcmdDHCPFreeAddressHighThreshold OBJECT-TYPE
	SYNTAX  Unsigned32
	MAX-ACCESS accessible-for-notify
	STATUS current
	DESCRIPTION
		"The high threshold for available free addresses in this rule scope.
		              If a incognitoDHCPFreeAddressLowThreshold event has been generated
		for this rule scope, and the value for available free addresses has
		exceeded the value of incognitoDHCPFreeAddressHighThreshold, then a
		              incognitoNotifyFreeAddressessHigh event will be generated.  No more
		              incognitoNotifyFreeAddressessHigh events will be generated for this
		              rule scope during this execution of the DHCP server until the value for
		available free addresses becomes equal to or less than the value of
		incognitoDHCPFreeAddressHighThreshold.

		              This value may be expressed as either an absolute value or a
		              percentage; the units are specified by the value of
		              incognitoDHCPFreeAddressUnits."
	-- 1.3.6.1.4.1.3606.7.1.2.99.1.2
	::= { ipcDhcpNotifyObjects 2 }


ipcmdDHCPFreeAddressCriticalThreshold OBJECT-TYPE
	SYNTAX  Unsigned32
	MAX-ACCESS accessible-for-notify
	STATUS current
	DESCRIPTION
		"The ciritical threshold for available free addresses in this subnet.
		              If a incognitoDHCPFreeAddressHighThreshold event has been generated
		for this subnet, and the value for available free addresses has
		exceeded the value of incognitoDHCPFreeAddressCriticalThreshold, then a
		              incognitoNotifyCriticalAddressessLevel event will be generated.  No more
		              incognitoNotifyCriticalAddressessLevel events will be generated for this
		              subnet during this execution of the DHCP server until the value for
		available free addresses becomes equal to or less than the value of
		incognitoDHCPFreeAddressHighThreshold.

		              This value may be expressed as either an absolute value or a
		              percentage; the units are specified by the value of
		              incognitoDHCPFreeAddressUnits."
	-- 1.3.6.1.4.1.3606.7.1.2.99.1.3
	::= { ipcDhcpNotifyObjects 3 }


ipcmdDHCPFreeAddressValue OBJECT-TYPE
	SYNTAX  Unsigned32
	MAX-ACCESS accessible-for-notify
	STATUS current
	DESCRIPTION
		"The number of IP addresses on this rule scope that are not currently
		assigned to a client. May be expressed as either an absolute value
		or a percentage; the units are given by the value of
		incognitoDHCPFreeAddressUnits."
	-- 1.3.6.1.4.1.3606.7.1.2.99.1.4
	::= { ipcDhcpNotifyObjects 4 }


ipcmdDHCPFreeAddressUnits OBJECT-TYPE
	SYNTAX  INTEGER {
			value(1),
			percent(2) }
	MAX-ACCESS accessible-for-notify
	STATUS current
	DESCRIPTION
		"The units associated with the value of incognitoDHCPFreeAddressValue."
	-- 1.3.6.1.4.1.3606.7.1.2.99.1.5
	::= { ipcDhcpNotifyObjects 5 }


ipcmdDHCPRuleID OBJECT-TYPE
	SYNTAX  DisplayString (SIZE (0..255))
	MAX-ACCESS accessible-for-notify
	STATUS current
	DESCRIPTION
		"a 16 byte octet block lookup key of the rule in network order"
	-- 1.3.6.1.4.1.3606.7.1.2.99.1.6
	::= { ipcDhcpNotifyObjects 6 }


ipcmdDHCPRuleName OBJECT-TYPE
	SYNTAX  DisplayString (SIZE (0..255))
	MAX-ACCESS accessible-for-notify
	STATUS current
	DESCRIPTION
		"The rule name associated with ipcmdRuleID"
	-- 1.3.6.1.4.1.3606.7.1.2.99.1.7
	::= { ipcDhcpNotifyObjects 7 }


ipcmdDHCPRogueServerAddress OBJECT-TYPE
	SYNTAX  IpAddress
	MAX-ACCESS accessible-for-notify
	STATUS current
	DESCRIPTION
		"The IP Address of the rogue dhcp server that is detected."
	-- 1.3.6.1.4.1.3606.7.1.2.99.1.8
	::= { ipcDhcpNotifyObjects 8 }


ipcmdDHCPRogueServerNumRequest OBJECT-TYPE
	SYNTAX  Unsigned32
	MAX-ACCESS accessible-for-notify
	STATUS current
	DESCRIPTION
		"The number of request answered by the rogue dhcp server."
	-- 1.3.6.1.4.1.3606.7.1.2.99.1.9
	::= { ipcDhcpNotifyObjects 9 }


ipcmdDHCPRogueServerRequestTime OBJECT-TYPE
	SYNTAX  DisplayString (SIZE (0..255))
	MAX-ACCESS accessible-for-notify
	STATUS current
	DESCRIPTION
		"The time of the last request to rogue dhcp server."
	-- 1.3.6.1.4.1.3606.7.1.2.99.1.10
	::= { ipcDhcpNotifyObjects 10 }


ipcmdDHCPRogueServerInfo OBJECT-TYPE
	SYNTAX  DisplayString (SIZE (0..255))
	MAX-ACCESS accessible-for-notify
	STATUS current
	DESCRIPTION
		"Generic information about the rogue dhcp server."
	-- 1.3.6.1.4.1.3606.7.1.2.99.1.11
	::= { ipcDhcpNotifyObjects 11 }


ipcmdDHCPCurrentUserCount OBJECT-TYPE
	SYNTAX  Unsigned32
	MAX-ACCESS accessible-for-notify
	STATUS current
	DESCRIPTION
		"The current number of users using the DHCP service."
	-- 1.3.6.1.4.1.3606.7.1.2.99.1.12
	::= { ipcDhcpNotifyObjects 12 }


ipcmdDHCPLicenseCount OBJECT-TYPE
	SYNTAX  Unsigned32
	MAX-ACCESS accessible-for-notify
	STATUS current
	DESCRIPTION
		"The current license count registered for the DHCP service."
	-- 1.3.6.1.4.1.3606.7.1.2.99.1.13
	::= { ipcDhcpNotifyObjects 13 }


ipcmdDHCPExceedingLicenseLimit OBJECT-TYPE
	SYNTAX  Unsigned32
	MAX-ACCESS accessible-for-notify
	STATUS current
	DESCRIPTION
		"The max number of request above the license count the DHCP will answer."
	-- 1.3.6.1.4.1.3606.7.1.2.99.1.14
	::= { ipcDhcpNotifyObjects 14 }


ipcmdDHCPFailoverConflictAddress OBJECT-TYPE
	SYNTAX  IpAddress
	MAX-ACCESS accessible-for-notify
	STATUS current
	DESCRIPTION
		"The IP Address of conflicting failover partner."
	-- 1.3.6.1.4.1.3606.7.1.2.99.1.15
	::= { ipcDhcpNotifyObjects 15 }


ipcmdDHCPNetViewName OBJECT-TYPE
	SYNTAX  DisplayString (SIZE (0..255))
	MAX-ACCESS accessible-for-notify
	STATUS current
	DESCRIPTION
		"Network View name"
	-- 1.3.6.1.4.1.3606.7.1.2.99.1.16
	::= { ipcDhcpNotifyObjects 16 }


ipcmdDHCPCurrentHWM OBJECT-TYPE
	SYNTAX  Unsigned32
	MAX-ACCESS accessible-for-notify
	STATUS current
	DESCRIPTION
		"The current High Water Mark."
	-- 1.3.6.1.4.1.3606.7.1.2.99.1.17
	::= { ipcDhcpNotifyObjects 17 }


ipcmdDHCPFailoverResynchStartTime OBJECT-TYPE
	SYNTAX  DisplayString (SIZE (0..255))
	MAX-ACCESS accessible-for-notify
	STATUS current
	DESCRIPTION
		"The start time of the failover resynchronization operation."
	-- 1.3.6.1.4.1.3606.7.1.2.99.1.18
	::= { ipcDhcpNotifyObjects 18 }


ipcmdDHCPFailoverResynchEndTime OBJECT-TYPE
	SYNTAX  DisplayString (SIZE (0..255))
	MAX-ACCESS accessible-for-notify
	STATUS current
	DESCRIPTION
		"The stop time of the failover resynchronization operation."
	-- 1.3.6.1.4.1.3606.7.1.2.99.1.19
	::= { ipcDhcpNotifyObjects 19 }


ipcmdDHCPDuplicateDeviceHWAddress OBJECT-TYPE
	SYNTAX  DisplayString (SIZE (0..255))
	MAX-ACCESS accessible-for-notify
	STATUS current
	DESCRIPTION
		"The hardware address of a possible duplicate device."
	-- 1.3.6.1.4.1.3606.7.1.2.99.1.20
	::= { ipcDhcpNotifyObjects 20 }


ipcmdDHCPDuplicateDeviceIPAddress OBJECT-TYPE
	SYNTAX  IpAddress
	MAX-ACCESS accessible-for-notify
	STATUS current
	DESCRIPTION
		"The TCP/IP address of a possible duplicate device."
	-- 1.3.6.1.4.1.3606.7.1.2.99.1.21
	::= { ipcDhcpNotifyObjects 21 }


ipcmdDHCPDuplicateDeviceRemoteID OBJECT-TYPE
	SYNTAX  DisplayString (SIZE (0..255))
	MAX-ACCESS accessible-for-notify
	STATUS current
	DESCRIPTION
		"The remote ID of a possible duplicate device."
	-- 1.3.6.1.4.1.3606.7.1.2.99.1.22
	::= { ipcDhcpNotifyObjects 22 }


ipcmdDHCPDuplicateDeviceCircuitID OBJECT-TYPE
	SYNTAX  DisplayString (SIZE (0..255))
	MAX-ACCESS accessible-for-notify
	STATUS current
	DESCRIPTION
		"The circuit ID of a possible duplicate device."
	-- 1.3.6.1.4.1.3606.7.1.2.99.1.23
	::= { ipcDhcpNotifyObjects 23 }


ipcmdDHCPDuplicateDeviceGWAddress OBJECT-TYPE
	SYNTAX  IpAddress
	MAX-ACCESS accessible-for-notify
	STATUS current
	DESCRIPTION
		"The GW address of a possible duplicate device."
	-- 1.3.6.1.4.1.3606.7.1.2.99.1.24
	::= { ipcDhcpNotifyObjects 24 }


ipcmdTFTPServerAddress OBJECT-TYPE
	SYNTAX  IpAddress
	MAX-ACCESS accessible-for-notify
	STATUS current
	DESCRIPTION
		"The TCP/IP address of a TFTP Server."
	-- 1.3.6.1.4.1.3606.7.1.2.99.1.25
	::= { ipcDhcpNotifyObjects 25 }


ipcmdDHCPFailoverTerminatedReason OBJECT-TYPE
	SYNTAX  DisplayString (SIZE (0..255))
	MAX-ACCESS accessible-for-notify
	STATUS current
	DESCRIPTION
		"Additional information."
	-- 1.3.6.1.4.1.3606.7.1.2.99.1.26
	::= { ipcDhcpNotifyObjects 26 }


-- Deprecated Notify Objects - objects which are used only in notifications

ipcmdNotifyObjects OBJECT-IDENTITY
	STATUS current
	DESCRIPTION
		"Deprecated ipcmd Notify Objects"
	-- 1.3.6.1.4.1.3606.7.1.2.99.2
	::= { ipcDeprecatedNotifyObjects 2 }

ipcmdNotifyServer OBJECT-TYPE
	SYNTAX  IpAddress
	MAX-ACCESS accessible-for-notify
	STATUS current
	DESCRIPTION
		"The IP Address of a server with which IPcmd is attempting to communicate."
	-- 1.3.6.1.4.1.3606.7.1.2.99.2.1
	::= { ipcmdNotifyObjects 1 }


ipcmdNotifyServerType OBJECT-TYPE
	SYNTAX  INTEGER {
			dns(1),
			dhcp(2),
			ldap(3),
			mps(4),
			tftp(5),
			kdc(6),
			dhcpRelay(7),
			cfm(8),
			cfmproxy(9),
			unknown(10) }
	MAX-ACCESS accessible-for-notify
	STATUS current
	DESCRIPTION
		"The type of server"
	-- 1.3.6.1.4.1.3606.7.1.2.99.2.2
	::= { ipcmdNotifyObjects 2 }


ipcmdUnknownIPAddress OBJECT-TYPE
	SYNTAX  IpAddress
	MAX-ACCESS accessible-for-notify
	STATUS current
	DESCRIPTION
		"The IP Address of an unknown device discovered via PING (ICMP Echo)."
	-- 1.3.6.1.4.1.3606.7.1.2.99.2.3
	::= { ipcmdNotifyObjects 3 }


ipcmdServerDiskSpaceFreeTotal OBJECT-TYPE
	SYNTAX  Unsigned32
	MAX-ACCESS accessible-for-notify
	STATUS current
	DESCRIPTION
		"The amount of Disk Storage Available."
	-- 1.3.6.1.4.1.3606.7.1.2.99.2.4
	::= { ipcmdNotifyObjects 4 }


ipcmdServerDiskSpaceFreeCount OBJECT-TYPE
	SYNTAX  Unsigned32
	MAX-ACCESS accessible-for-notify
	STATUS current
	DESCRIPTION
		"The amount of Disk Storage Free. May be expressed as either an absolute value(in Kilobytes)
		or a percentage; the units are given by the value of
		incognitoServerDiskSpaceFreeUnits."
	-- 1.3.6.1.4.1.3606.7.1.2.99.2.5
	::= { ipcmdNotifyObjects 5 }


ipcmdServerDiskSpaceFreeUnits OBJECT-TYPE
	SYNTAX  INTEGER {
			value(1),
			percent(2) }
	MAX-ACCESS accessible-for-notify
	STATUS current
	DESCRIPTION
		"The units associated with the value of ipcmdServerDiskSpaceFreeCount.
		(1) value in KiloBytes
		(2) percentage"
	-- 1.3.6.1.4.1.3606.7.1.2.99.2.6
	::= { ipcmdNotifyObjects 6 }


ipcmdServiceStatus OBJECT-TYPE
	SYNTAX  DisplayString (SIZE (0..255))
	MAX-ACCESS accessible-for-notify
	STATUS current
	DESCRIPTION
		"Generic information about the service"
	-- 1.3.6.1.4.1.3606.7.1.2.99.2.7
	::= { ipcmdNotifyObjects 7 }


ipcmdNotifyHost OBJECT-TYPE
	SYNTAX  DisplayString (SIZE (0..255))
	MAX-ACCESS accessible-for-notify
	STATUS current
	DESCRIPTION
		"The hostname or IP Address of a server with which IPcmd is attempting to communicate."
	-- 1.3.6.1.4.1.3606.7.1.2.99.2.8
	::= { ipcmdNotifyObjects 8 }

ipcmdNotifyDevice OBJECT-TYPE
	SYNTAX DisplayString (SIZE (0..255))
	MAX-ACCESS accessible-for-notify
	STATUS current
	DESCRIPTION
		"The device identifier of a DHCP client."
	-- 1.3.6.1.4.1.3606.7.1.2.99.2.9
	::= { ipcmdNotifyObjects 9 }

-- Deprecated Notifications

incognitoNotifyNotifications OBJECT-IDENTITY
	STATUS current
	DESCRIPTION
		"Deprecated Notifications"
	-- 1.3.6.1.4.1.3606.7.1.99.0
	::= { ipcDeprecatedNotificationPrefix 0 }


incognitoIPCMDServerStart NOTIFICATION-TYPE
	OBJECTS {
		ipcmdNotifyServerType}
	STATUS current
	DESCRIPTION
		"This notification signifies that the server of the specified type has
		started on the host from which this notitication has been sent."
	-- 1.3.6.1.4.1.3606.7.1.99.0.1
	::= { incognitoNotifyNotifications 1 }


incognitoIPCMDServerStop NOTIFICATION-TYPE
	OBJECTS {
		ipcmdNotifyServerType}
	STATUS current
	DESCRIPTION
		"This notification signifies that the server of the specified type has
		stopped normally on the host from which this notitication has been sent."
	-- 1.3.6.1.4.1.3606.7.1.99.0.2
	::= { incognitoNotifyNotifications 2 }


incognitoIPCMDServicePaused NOTIFICATION-TYPE
	OBJECTS {
		ipcmdServiceStatus}
	STATUS current
	DESCRIPTION
		"This notification signifies that the dhcp service is paused."
	-- 1.3.6.1.4.1.3606.7.1.99.0.3
	::= { incognitoNotifyNotifications 3 }


incognitoIPCMDServiceResume NOTIFICATION-TYPE
	OBJECTS {
		ipcmdServiceStatus}
	STATUS current
	DESCRIPTION
		"This notification signiifes that the dhcp service resumes."
	-- 1.3.6.1.4.1.3606.7.1.99.0.4
	::= { incognitoNotifyNotifications 4 }


incognitoIPCMDExceededLicense NOTIFICATION-TYPE
	OBJECTS {
		ipcmdDHCPCurrentUserCount,
		ipcmdDHCPLicenseCount,
		ipcmdDHCPExceedingLicenseLimit}
	STATUS current
	DESCRIPTION
		"This notification signifies that the dhcp server's license has been exceeded."
	-- 1.3.6.1.4.1.3606.7.1.99.0.5
	::= { incognitoNotifyNotifications 5 }


incognitoIPCMDFreeAddressHigh NOTIFICATION-TYPE
	OBJECTS {
		ipcmdDHCPFreeAddressHighThreshold,
		ipcmdDHCPFreeAddressValue,
		ipcmdDHCPFreeAddressUnits,
		ipcmdDHCPRuleID,
		ipcmdDHCPRuleName}
	STATUS current
	DESCRIPTION
		"This notification signifies that the number of available IP addresses
		for a particular rule scope has risen above the value of
		incognitoDHCPFreeAddressHighThreshold for that rule scope."
	-- 1.3.6.1.4.1.3606.7.1.99.0.6
	::= { incognitoNotifyNotifications 6 }


incognitoIPCMDCriticalAddressLevel NOTIFICATION-TYPE
	OBJECTS {
		ipcmdDHCPFreeAddressCriticalThreshold,
		ipcmdDHCPFreeAddressValue,
		ipcmdDHCPFreeAddressUnits,
		ipcmdDHCPRuleID,
		ipcmdDHCPRuleName}
	STATUS current
	DESCRIPTION
		"This notification signifies that the number of available IP addresses
		for a particular subnet has reach a critical level for that subnet."
	-- 1.3.6.1.4.1.3606.7.1.99.0.7
	::= { incognitoNotifyNotifications 7 }


incognitoIPCMDOtherServerResponding NOTIFICATION-TYPE
	OBJECTS {
		ipcmdNotifyServer,
		ipcmdNotifyServerType}
	STATUS current
	DESCRIPTION
		"This notification signifies that a server which had formerly been unresponsive
		is now responding to updates from the IP Commander service. The identity of the
		server is given by the incognitoNotifyServer object. The type of the server is
		given by the incognitoNotifyServerType object."
	-- 1.3.6.1.4.1.3606.7.1.99.0.8
	::= { incognitoNotifyNotifications 8 }


incognitoIPCMDOtherServerNotResponding NOTIFICATION-TYPE
	OBJECTS {
		ipcmdNotifyServer,
		ipcmdNotifyServerType}
	STATUS current
	DESCRIPTION
		"This notification signifies that a server is not responding to updates
		from the DHCP server. The identity of the server is given by the
		incognitoNotifyServer object. The type of the server is given by the
		incognitoNotifyServerType object."
	-- 1.3.6.1.4.1.3606.7.1.99.0.9
	::= { incognitoNotifyNotifications 9 }


incognitoIPCMDFailoverConflict NOTIFICATION-TYPE
	OBJECTS {
		ipcmdDHCPFailoverConflictAddress}
	STATUS current
	DESCRIPTION
		"This notification signifes that the dhcp server' failvoer address conflicts."
	-- 1.3.6.1.4.1.3606.7.1.99.0.10
	::= { incognitoNotifyNotifications 10 }


incognitoIPCMDServiceOverloaded NOTIFICATION-TYPE
	OBJECTS {
		ipcmdServiceStatus}
	STATUS current
	DESCRIPTION
		"This notification signifes that the dhcp service is overloaded."
	-- 1.3.6.1.4.1.3606.7.1.99.0.11
	::= { incognitoNotifyNotifications 11 }


incognitoIPCMDServiceCaughtUp NOTIFICATION-TYPE
	OBJECTS {
		ipcmdServiceStatus}
	STATUS current
	DESCRIPTION
		"This notification signifes that the dhcp service caught up."
	-- 1.3.6.1.4.1.3606.7.1.99.0.12
	::= { incognitoNotifyNotifications 12 }


incognitoIPCMDDDNSFailure NOTIFICATION-TYPE
	OBJECTS {
		ipcmdNotifyServer,
		ipcmdNotifyServerType}
	STATUS current
	DESCRIPTION
		"This notification signifies the DNS server is not responding to dynamic
		DNS updates."
	-- 1.3.6.1.4.1.3606.7.1.99.0.13
	::= { incognitoNotifyNotifications 13 }


incognitoIPCMDUnknownDevice NOTIFICATION-TYPE
	OBJECTS {
		ipcmdUnknownIPAddress}
	STATUS current
	DESCRIPTION
		"This notification signifies the unknown device's IP address discovered
		via PING (ICMP Echo)."
	-- 1.3.6.1.4.1.3606.7.1.99.0.14
	::= { incognitoNotifyNotifications 14 }


incognitoIPCMDRogueServer NOTIFICATION-TYPE
	OBJECTS {
		ipcmdDHCPRogueServerAddress,
		ipcmdDHCPRogueServerNumRequest,
		ipcmdDHCPRogueServerRequestTime,
		ipcmdDHCPRogueServerInfo}
	STATUS current
	DESCRIPTION
		"This notification signifes that rogue dhcp server has been detected."
	-- 1.3.6.1.4.1.3606.7.1.99.0.15
	::= { incognitoNotifyNotifications 15 }


incognitoIPCMDDiskStorageLow NOTIFICATION-TYPE
	OBJECTS {
		ipcmdServerDiskSpaceFreeTotal,
		ipcmdServerDiskSpaceFreeCount,
		ipcmdServerDiskSpaceFreeUnits}
	STATUS current
	DESCRIPTION
		"This notification signifes that the dhcp server's disk storage is low."
	-- 1.3.6.1.4.1.3606.7.1.99.0.16
	::= { incognitoNotifyNotifications 16 }


incognitoIPCMDServiceBackupDone NOTIFICATION-TYPE
	OBJECTS {
		ipcmdServiceStatus}
	STATUS current
	DESCRIPTION
		"This notification signifies that the dhcp server backup is done."
	-- 1.3.6.1.4.1.3606.7.1.99.0.17
	::= { incognitoNotifyNotifications 17 }


incognitoIPCMDFreeAddressLow NOTIFICATION-TYPE
	OBJECTS {
		ipcmdDHCPFreeAddressLowThreshold,
		ipcmdDHCPFreeAddressValue,
		ipcmdDHCPFreeAddressUnits,
		ipcmdDHCPRuleID,
		ipcmdDHCPRuleName}
	STATUS current
	DESCRIPTION
		"This notification signifies that the number of available IP addresses
		for a particular rule scope has fallen below the value of
		incognitoDHCPFreeAddressLowThreshold for that rule scope."
	-- 1.3.6.1.4.1.3606.7.1.99.0.18
	::= { incognitoNotifyNotifications 18 }


incognitoIPCMDFailoverResynchOperationStarted NOTIFICATION-TYPE
	OBJECTS {
		ipcmdDHCPFailoverResynchStartTime,
		ipcmdNotifyServer}
	STATUS current
	DESCRIPTION
		"This notification signifies that the failover resynchronization operation
		have started."
	-- 1.3.6.1.4.1.3606.7.1.99.0.19
	::= { incognitoNotifyNotifications 19 }


incognitoIPCMDFailoverResynchOperationCompleted NOTIFICATION-TYPE
	OBJECTS {
		ipcmdDHCPFailoverResynchEndTime,
		ipcmdNotifyServer}
	STATUS current
	DESCRIPTION
		"This notification signifies that the failover resynchronization operation
		have completed."
	-- 1.3.6.1.4.1.3606.7.1.99.0.20
	::= { incognitoNotifyNotifications 20 }


incognitoIPCMDNetViewCriticalHWMExceeded NOTIFICATION-TYPE
	OBJECTS {
		ipcmdDHCPNetViewName,
		ipcmdDHCPCurrentHWM}
	STATUS current
	DESCRIPTION
		"This notification signifies that the Network View Critical HWM have been
		exceeded."
	-- 1.3.6.1.4.1.3606.7.1.99.0.21
	::= { incognitoNotifyNotifications 21 }


incognitoIPCMDNetViewWarningHWMExceeded NOTIFICATION-TYPE
	OBJECTS {
		ipcmdDHCPNetViewName,
		ipcmdDHCPCurrentHWM}
	STATUS current
	DESCRIPTION
		"This notification signifies that the Network View Warning HWM have been
		exceeded."
	-- 1.3.6.1.4.1.3606.7.1.99.0.22
	::= { incognitoNotifyNotifications 22 }


incognitoIPCMDPossibleDuplicateDevice NOTIFICATION-TYPE
	OBJECTS {
		ipcmdDHCPDuplicateDeviceHWAddress,
		ipcmdDHCPDuplicateDeviceIPAddress,
		ipcmdDHCPDuplicateDeviceRemoteID,
		ipcmdDHCPDuplicateDeviceCircuitID,
		ipcmdDHCPDuplicateDeviceGWAddress}
	STATUS current
	DESCRIPTION
		"This notification is sent whenever a possible duplicate device is found.
		This does not mean a duplicate IP address, but rather that the service considers
		the the incoming request comes from a device that appears to have a lease
		already."
	-- 1.3.6.1.4.1.3606.7.1.99.0.23
	::= { incognitoNotifyNotifications 23 }


incognitoIPCMDNoMoreAddressesAvailable NOTIFICATION-TYPE
	OBJECTS {
		ipcmdDHCPDuplicateDeviceHWAddress,
		ipcmdDHCPDuplicateDeviceRemoteID,
		ipcmdDHCPDuplicateDeviceCircuitID,
		ipcmdDHCPDuplicateDeviceGWAddress}
	STATUS current
	DESCRIPTION
		"This notification is sent whenever a device requests an addressbut
		no more addresses are available in the service. This usually signals
		address space exhaustion."
	-- 1.3.6.1.4.1.3606.7.1.99.0.24
	::= { incognitoNotifyNotifications 24 }


incognitoIPCMDTFTPServerJoining NOTIFICATION-TYPE
	OBJECTS {
		ipcmdTFTPServerAddress}
	STATUS current
	DESCRIPTION
		"This notification is sent whenever a new TFTP server joins a cluster."
	-- 1.3.6.1.4.1.3606.7.1.99.0.25
	::= { incognitoNotifyNotifications 25 }


incognitoIPCMDTFTPServerLeaving NOTIFICATION-TYPE
	OBJECTS {
		ipcmdTFTPServerAddress}
	STATUS current
	DESCRIPTION
		"This notification is sent whenever a new TFTP server leaves a cluster."
	-- 1.3.6.1.4.1.3606.7.1.99.0.26
	::= { incognitoNotifyNotifications 26 }


incognitoIPCMDServerJoinClusterIntegration NOTIFICATION-TYPE
	OBJECTS {
		ipcmdNotifyServer,
		ipcmdNotifyServerType}
	STATUS current
	DESCRIPTION
		"This notification signifies that a server has joined integration cluster.
		The identity of the server is given by the ipcmdNotifyServer object.
		The type of the server is given by the ipcmdNotifyServerType object."
	-- 1.3.6.1.4.1.3606.7.1.99.0.27
	::= { incognitoNotifyNotifications 27 }


incognitoIPCMDServerLeaveClusterIntegration NOTIFICATION-TYPE
	OBJECTS {
		ipcmdNotifyServer,
		ipcmdNotifyServerType}
	STATUS current
	DESCRIPTION
		"This notification signifies that a server has left integration cluster.
		The identity of the server is given by the ipcmdNotifyServer object.
		The type of the server is given by the ipcmdNotifyServerType object."
	-- 1.3.6.1.4.1.3606.7.1.99.0.28
	::= { incognitoNotifyNotifications 28 }


incognitoIPCMDFailoverTerminated NOTIFICATION-TYPE
	OBJECTS {
		ipcmdDHCPFailoverTerminatedReason,
		ipcmdNotifyServer}
	STATUS current
	DESCRIPTION
		"This notification signifies the the sender has terminated his relationship with
		the included partner. The reason will add additional information on the success or
		partial success of the operation."
	-- 1.3.6.1.4.1.3606.7.1.99.0.29
	::= { incognitoNotifyNotifications 29 }


incognitoIPCMDLDAPCommunicationsUp NOTIFICATION-TYPE
	OBJECTS {
		ipcmdNotifyHost}
	STATUS current
	DESCRIPTION
		"This notification signifies that communications have been successfully established
		with the LDAP service indicated in the ipcmdNotifyHost object."
	-- 1.3.6.1.4.1.3606.7.1.99.0.30
	::= { incognitoNotifyNotifications 30 }


incognitoIPCMDLDAPCommunicationsDown NOTIFICATION-TYPE
	OBJECTS {
		ipcmdNotifyHost}
	STATUS current
	DESCRIPTION
		"This notification signifies that communications have failed
		with the LDAP service indicated in the ipcmdNotifyHost object."
	-- 1.3.6.1.4.1.3606.7.1.99.0.31
	::= { incognitoNotifyNotifications 31 }


incognitoIPCMDLDAPTimedOut NOTIFICATION-TYPE
	OBJECTS {
		ipcmdNotifyHost}
	STATUS current
	DESCRIPTION
		"This notification signifies that an LDAP query timed out,
		indicating that the LDAP service may be overloaded."
	-- 1.3.6.1.4.1.3606.7.1.99.0.32
	::= { incognitoNotifyNotifications 32 }

incognitoIPCMDRADIUSAccountingHWMExceeded NOTIFICATION-TYPE
	OBJECTS {
		ipcmdNotifyHost,
		ipcmdDHCPCurrentHWM}
	STATUS current
	DESCRIPTION
		"This notification signifies that HWM for RADIUS Accounting was reached."
	-- 1.3.6.1.4.1.3606.7.1.99.0.33
	::= { incognitoNotifyNotifications 33 }

incognitoIPCMDLDAPSetCommunicationsUp NOTIFICATION-TYPE
	OBJECTS {
		ipcmdNotifyHost}
	STATUS current
	DESCRIPTION
		"This notification signifies that communications have been successfully established
		with the LDAP service set indicated in the ipcmdNotifyHost object."
	-- 1.3.6.1.4.1.3606.7.1.99.0.34
	::= { incognitoNotifyNotifications 34 }


incognitoIPCMDLDAPSetCommunicationsDown NOTIFICATION-TYPE
	OBJECTS {
		ipcmdNotifyHost}
	STATUS current
	DESCRIPTION
		"This notification signifies that communications have failed
		with the LDAP service set indicated in the ipcmdNotifyHost object."
	-- 1.3.6.1.4.1.3606.7.1.99.0.35
	::= { incognitoNotifyNotifications 35 }

incognitoIPCMDDHCPDoSExceededLimit NOTIFICATION-TYPE
	OBJECTS {
		ipcmdNotifyDevice}
	STATUS current
	DESCRIPTION
		"This notification signifies that the specified device has
		exceeded the defined DoS criteria."
	-- 1.3.6.1.4.1.3606.7.1.99.0.36
	::= { incognitoNotifyNotifications 36 }

incognitoIPCMDDHCPDoSBelowLimit NOTIFICATION-TYPE
	OBJECTS {
		ipcmdNotifyDevice}
	STATUS current
	DESCRIPTION
		"This notification signifies that the specified device no
		longer exceeds the defined DoS criteria."
	-- 1.3.6.1.4.1.3606.7.1.99.0.37
	::= { incognitoNotifyNotifications 37 }

-- Conformance

ipcCompliances OBJECT-IDENTITY
	STATUS current
	DESCRIPTION ""
	-- 1.3.6.1.4.1.3606.7.1.4.1
	::= { ipcConformance 1 }

ipcGroups OBJECT-IDENTITY
	STATUS current
	DESCRIPTION ""
	-- 1.3.6.1.4.1.3606.7.1.4.2
	::= { ipcConformance 2 }

ipcDeprecatedGroups OBJECT-IDENTITY
	STATUS current
	DESCRIPTION ""
	-- 1.3.6.1.4.1.3606.7.1.4.99
	::= { ipcConformance 99 }

ipcNotifyObjectsGroup OBJECT-GROUP
	OBJECTS {
		ipcResumedTime,
		ipcPausedTime }
	STATUS current
	DESCRIPTION ""
	-- 1.3.6.1.4.1.3606.7.1.4.2.1
	::= { ipcGroups 1 }

ipcFailoverSummaryStatisticsGroup OBJECT-GROUP
	OBJECTS {
		ipcFailStatLastStartTime,
		ipcFailStatLastSyncTime,
		ipcFailStatLastTestTime,
		ipcFailStatLastDownTime,
		ipcFailStatLastUpTime,
		ipcFailStatSendErrors,
		ipcFailStatRecvErrors,
		ipcFailStatPlatformMismatchErrors,
		ipcFailStatVersionMismatchErrors,
		ipcFailStatRoleMismatchErrors,
		ipcFailStatCRC1Errors,
		ipcFailStatCRC2Errors,
		ipcFailStatDecryptErrors,
		ipcFailStatAccessDeniedErrors,
		ipcFailStatTotalTimeDown,
		ipcFailStatLongestTimeDown,
		ipcFailStatCountTimeDown,
		ipcFailStatTotalResynch,
		ipcFailStatLongestResynch,
		ipcFailStatCountResynch,
		ipcFailStatTotalTimeUp,
		ipcFailStatLongestTimeUp,
		ipcFailStatCountTimeUp,
		ipcFailStatRecdHeartbeats,
		ipcFailStatRecdTestRequests,
		ipcFailStatRecdTestReplies,
		ipcFailStatRecdDataTxRequests,
		ipcFailStatRecdDataTxData,
		ipcFailStatRecdDataTxAcks,
		ipcFailStatRecdDataTransactionData,
		ipcFailStatRecdDataTransactionAcks,
		ipcFailStatRecdDataConflicts,
		ipcFailStatRecdDataConflictAcks,
		ipcFailStatRecdDataResynchRequests,
		ipcFailStatRecdDataResynchAcks,
		ipcFailStatRecdShuttingDown,
		ipcFailStatSentHeartbeats,
		ipcFailStatSentTestRequests,
		ipcFailStatSentTestReplies,
		ipcFailStatSentDataTxRequests,
		ipcFailStatSentDataTxData,
		ipcFailStatSentDataTxAcks,
		ipcFailStatSentDataTransactionData,
		ipcFailStatSentDataTransactionAcks,
		ipcFailStatSentDataConflicts,
		ipcFailStatSentDataConflictAcks,
		ipcFailStatSentDataResynchRequests,
		ipcFailStatSentDataResynchAcks,
		ipcFailStatSentShuttingDown,
		ipcFailStatBytesSent,
		ipcFailStatBytesRecd,
		ipcFailStatTxSent,
		ipcFailStatTxRecd,
		ipcFailStatStatus,
		ipcFailStatOperation }
	STATUS current
	DESCRIPTION
		"DHCP Failover Summary Statistics"
	-- 1.3.6.1.4.1.3606.7.1.4.2.3
	::= { ipcGroups 3 }

ipcDHCPPacketStatisticsGroup OBJECT-GROUP
	OBJECTS {
		ipcDHCPDiscoverPacketDiscards,
		ipcDHCPRequestPacketDiscards,
		ipcDHCPInformPacketDiscards,
		ipcDHCPDeclinePacketDiscards,
		ipcDHCPOtherPacketDiscards,
		ipcDHCPDiscoverPacketSupercedes,
		ipcDHCPRequestPacketSupercedes,
		ipcDHCPInformPacketSupercedes,
		ipcDHCPDeclinePacketSupercedes,
		ipcDHCPOtherPacketSupercedes,
		ipcDHCPBOOTPPacketResponseAvg1minTime,
		ipcDHCPBOOTPPacketResponseAvg5minTime,
		ipcDHCPBOOTPPacketResponseAvg15minTime,
		ipcDHCPDHCPv4PacketResponseAvg1minTime,
		ipcDHCPDHCPv4PacketResponseAvg5minTime,
		ipcDHCPDHCPv4PacketResponseAvg15minTime }
	STATUS current
	DESCRIPTION ""
	-- 1.3.6.1.4.1.3606.7.1.4.2.4
	::= { ipcGroups 4 }

ipcNotificationsGroup NOTIFICATION-GROUP
	NOTIFICATIONS {
		ipcNotifyServerResumed,
		ipcNotifyServerPaused }
	STATUS current
	DESCRIPTION ""
	-- 1.3.6.1.4.1.3606.7.1.4.2.2
	::= { ipcGroups 2 }

ipcDeprecatedNotificationsGroup NOTIFICATION-GROUP
	NOTIFICATIONS {
		incognitoIPCMDServerStart,
		incognitoIPCMDServerStop,
		incognitoIPCMDServicePaused,
		incognitoIPCMDServiceResume,
		incognitoIPCMDExceededLicense,
		incognitoIPCMDFreeAddressHigh,
		incognitoIPCMDCriticalAddressLevel,
		incognitoIPCMDOtherServerResponding,
		incognitoIPCMDOtherServerNotResponding,
		incognitoIPCMDFailoverConflict,
		incognitoIPCMDServiceOverloaded,
		incognitoIPCMDServiceCaughtUp,
		incognitoIPCMDDDNSFailure,
		incognitoIPCMDUnknownDevice,
		incognitoIPCMDRogueServer,
		incognitoIPCMDDiskStorageLow,
		incognitoIPCMDServiceBackupDone,
		incognitoIPCMDFreeAddressLow,
		incognitoIPCMDFailoverResynchOperationStarted,
		incognitoIPCMDFailoverResynchOperationCompleted,
		incognitoIPCMDNetViewCriticalHWMExceeded,
		incognitoIPCMDNetViewWarningHWMExceeded,
		incognitoIPCMDPossibleDuplicateDevice,
		incognitoIPCMDNoMoreAddressesAvailable,
		incognitoIPCMDTFTPServerLeaving,
		incognitoIPCMDTFTPServerJoining,
		incognitoIPCMDServerJoinClusterIntegration,
		incognitoIPCMDServerLeaveClusterIntegration,
		incognitoIPCMDFailoverTerminated,
		incognitoIPCMDLDAPCommunicationsUp,
		incognitoIPCMDLDAPCommunicationsDown,
		incognitoIPCMDLDAPTimedOut,
		incognitoIPCMDRADIUSAccountingHWMExceeded,
		incognitoIPCMDLDAPSetCommunicationsUp,
		incognitoIPCMDLDAPSetCommunicationsDown,
		incognitoIPCMDDHCPDoSExceededLimit,
		incognitoIPCMDDHCPDoSBelowLimit }
	STATUS current
	DESCRIPTION ""
	-- 1.3.6.1.4.1.3606.7.1.4.99.1
	::= { ipcDeprecatedGroups 1 }

ipcDeprecatedNotifyBaseObjectsGroup OBJECT-GROUP
	OBJECTS {
		ipcmdDHCPFreeAddressLowThreshold,
		ipcmdDHCPFreeAddressHighThreshold,
		ipcmdDHCPFreeAddressCriticalThreshold,
		ipcmdDHCPFreeAddressValue,
		ipcmdDHCPFreeAddressUnits,
		ipcmdDHCPRuleID,
		ipcmdDHCPRuleName,
		ipcmdDHCPRogueServerAddress,
		ipcmdDHCPRogueServerNumRequest,
		ipcmdDHCPRogueServerRequestTime,
		ipcmdDHCPRogueServerInfo,
		ipcmdDHCPCurrentUserCount,
		ipcmdDHCPLicenseCount,
		ipcmdDHCPExceedingLicenseLimit,
		ipcmdDHCPFailoverConflictAddress,
		ipcmdDHCPNetViewName,
		ipcmdDHCPCurrentHWM,
		ipcmdDHCPFailoverResynchStartTime,
		ipcmdDHCPFailoverResynchEndTime,
		ipcmdDHCPDuplicateDeviceHWAddress,
		ipcmdDHCPDuplicateDeviceIPAddress,
		ipcmdDHCPDuplicateDeviceRemoteID,
		ipcmdDHCPDuplicateDeviceCircuitID,
		ipcmdDHCPDuplicateDeviceGWAddress,
		ipcmdTFTPServerAddress,
		ipcmdDHCPFailoverTerminatedReason }
	STATUS current
	DESCRIPTION ""
	-- 1.3.6.1.4.1.3606.7.1.4.99.2
	::= { ipcDeprecatedGroups 2 }

ipcDeprecatedNotifyObjectsGroup OBJECT-GROUP
	OBJECTS {
		ipcmdNotifyServer,
		ipcmdNotifyServerType,
		ipcmdUnknownIPAddress,
		ipcmdServerDiskSpaceFreeTotal,
		ipcmdServerDiskSpaceFreeCount,
		ipcmdServerDiskSpaceFreeUnits,
		ipcmdServiceStatus,
		ipcmdNotifyHost,
		ipcmdNotifyDevice }
	STATUS current
	DESCRIPTION ""
	-- 1.3.6.1.4.1.3606.7.1.4.99.3
	::= { ipcDeprecatedGroups 3 }

END
