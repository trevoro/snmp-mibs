ARCserve-Alarm-MIB DEFINITIONS ::= BEGIN

	IMPORTS
		enterprises    FROM RFC1065-SMI
		OBJECT-TYPE    FROM RFC-1212
		TRAP-TYPE      FROM RFC-1215;
		
		cheyenne            OBJECT IDENTIFIER ::= { enterprises 46 }
		arcServe            OBJECT IDENTIFIER ::= { cheyenne 877 }
                arcServeRev         OBJECT IDENTIFIER ::= { arcServe 1 }

-- *************************************************************************
-- ARCserve (1.3.6.1.4.1.46.877)
-- **************************************************************************
arcServeevMajor OBJECT-TYPE
	SYNTAX INTEGER (0..65535)
	ACCESS read-only
	STATUS mandatory
	DESCRIPTION
		"The major revision level of ARCserve (left of the decimal).
		Used for presence checking."
	::= { arcServeRev 1 }

arcServeRevMinor OBJECT-TYPE
	SYNTAX INTEGER (0..65535)
	ACCESS read-only
	STATUS mandatory
	DESCRIPTION
		"The minor revision level of ARCserve (right of the decimal)."
	::= { arcServeRev 2 }

arcServeParmsTrapEnable OBJECT-TYPE
	SYNTAX INTEGER (0..1)
	ACCESS read-write
	STATUS mandatory
	DESCRIPTION
		"Indicates whether agent should or should not send traps."
	::= { arcServe 2 }

arcServeParmsPollTime OBJECT-TYPE
	SYNTAX INTEGER (60..2592000)
	ACCESS read-write
	STATUS mandatory
	DESCRIPTION
		"Seconds between checking for traps."
	::= { arcServe 3 }

arcServeServerName OBJECT-TYPE
                SYNTAX OCTET STRING
                ACCESS read-only
                STATUS mandatory
                DESCRIPTION
                        "ARCserve server which generated trap."
                ::= {arcServe 4}        
        
arcServetrapdesc   OBJECT-TYPE
                SYNTAX OCTET STRING
                ACCESS read-only
                STATUS optional
                DESCRIPTION
                        "A description of a specific Cheyenne trap"
                ::= {arcServe 5}        
        
-- *************************************************************************
-- traps
-- **************************************************************************
arcServetrapHigh                TRAP-TYPE       
	        		ENTERPRISE	arcServe
                                VARIABLES       {
                                                arcServeServerName,
                                                arcServetrapdesc
                                                }
        			DESCRIPTION
                                        "ARCserve Critical Trap
                                        
                                        A Critical trap has been generated by ARCserve.
                                        Refer to the trap summary information for a detailed
                                        description of this trap.  A critical trap normally
                                        indicates a serious error has occurred."
                                --#TYPE "ARCserve Critical"
                                --#SUMMARY "%s %s "
                                --#ARGUMENTS {0,1}
                                --#SEVERITY CRITICAL
                                --#STATE   DEGRADED     
	        	        ::= 1
arcServetrapMed                 TRAP-TYPE       
	        		ENTERPRISE	arcServe
                                VARIABLES       {
                                                arcServeServerName,
                                                arcServetrapdesc
                                                }
        			DESCRIPTION
                                        "ARCserve Minor Trap
                                        
                                        A minor trap has been generated by ARCserve.  Minor
                                        traps are used by ARCserve to warn the user of unusual,
                                        but not fatal incidents.  Review the message summary to
                                        determine if this trap should concern you."
                                --#TYPE "ARCserve Warning"
                                --#SUMMARY "%s %s "
                                --#ARGUMENTS {0,1}
                                --#SEVERITY MINOR
                                --#TIMEINDEX 1
                                --#STATE   OPERATIONAL     
	        	        ::= 2
arcServetrapLow                 TRAP-TYPE       
	        		ENTERPRISE	arcServe
                                VARIABLES       {
                                                arcServeServerName,
                                                arcServetrapdesc
                                                }
        			DESCRIPTION
                                        "ARCserve Informational Trap
                                        
                                        An ARCserve informational trap has been generated by
                                        ARCserve."
                                --#TYPE "ARCserve Informational"
                                --#SUMMARY "%s %s "
                                --#ARGUMENTS {0,1}
                                --#SEVERITY INFORMATIONAL
                                --#STATE   OPERATIONAL     
	        	        ::= 3
arcServetrap4                   TRAP-TYPE       
	        		ENTERPRISE	arcServe
                                VARIABLES       {
                                                arcServeServerName,
                                                arcServetrapdesc
                                                }
        			DESCRIPTION
                                        "Failed to locate job list service.
                                        
                                        This trap signifies that ARCserve was unable to locate
                                        it's NetWare queue or Windows NT/UNIX Job list.  This problem
                                        can be caused in NetWare by Bindery or Directory Services
                                        corruption or by the deletion of the ARCserve queue."
                                --#TYPE "Failed to locate job list service." 
                                --#SUMMARY "%s %s"
                                --#ARGUMENTS {0,1}
                                --#SEVERITY MINOR
                                --#TIMEINDEX 1
                                --#STATE   OPERATIONAL     
	        	        ::= 4
arcServetrap5                   TRAP-TYPE       
	        		ENTERPRISE	arcServe
                                VARIABLES       {
                                                arcServeServerName,
                                                arcServetrapdesc
                                                }
        			DESCRIPTION
                                        "Failed to retrieve job from Job List Service.
                                        
                                        This trap signifies that ARCserve cannot process jobs.
                                        Under NetWare, this is normally due to a Bindery or
                                        Directory Services corruption.  Please verify that ARCserve
                                        was completely installed and that your Bindery/Directory is
                                        not corrupted."
                                --#TYPE "Failed to retrieve job from Job List Service."
                                --#SUMMARY "%s %s"
                                --#ARGUMENTS {0,1}
                                --#SEVERITY MINOR
                                --#TIMEINDEX 1
                                --#STATE   OPERATIONAL     
	        	        ::= 5
arcServetrap6                   TRAP-TYPE       
	        		ENTERPRISE	arcServe
                                VARIABLES       {
                                                arcServeServerName,
                                                arcServetrapdesc
                                                }
        			DESCRIPTION
                                        "Failed to allocate memory.
                                        
                                        This trap signifies that ARCserve was unable to allocate
                                        memory.  More server memory may be required if this message
                                        occurs on a regular basis.  This message is not normally
                                        fatal, unless repeated attempts for memory fail."
                                --#TYPE "Failed to allocate memory."
                                --#SUMMARY "%s %s"
                                --#ARGUMENTS {0,1}
                                --#SEVERITY MINOR
                                --#TIMEINDEX 1
                                --#STATE   OPERATIONAL     
        	                ::= 7
arcServetrap7                   TRAP-TYPE       
	        		ENTERPRISE	arcServe
                                VARIABLES       {
                                                arcServeServerName,
                                                arcServetrapdesc
                                                }
        			DESCRIPTION
                                        "Server is low on memory, cannot start jobs.
	        	                                            
                                        This trap signifies that server is so low on memory
                                        that jobs cannot be processed.   Shutdown any unnecessary
                                        modules to obtain additional memory so that jobs can be
                                        processed.  Jobs will be processed when sufficeint memory
                                        has been restored on the server."

                                --#TYPE "Server is low on memory, cannot start jobs."
                                --#SUMMARY "%s %s"
                                --#ARGUMENTS {0,1}
                                --#SEVERITY MINOR
                                --#TIMEINDEX 1
                                --#STATE   OPERATIONAL     
        	                ::= 8	       	    
arcServetrap8                   TRAP-TYPE       
	        		ENTERPRISE	arcServe
                                VARIABLES       {
                                                arcServeServerName,
                                                arcServetrapdesc
                                                }
        			DESCRIPTION
                                        "Same license found on another server.
                                        
                                        This trap signifies that another server has the same
                                        license as the server which generated the server.  You
                                        must install different licenses on each ARCserve server."
                                --#TYPE "Same license found on another server."
                                --#SUMMARY "%s %s"
                                --#ARGUMENTS {0,1}
                                --#SEVERITY MINOR
                                --#TIMEINDEX 1
                                --#STATE   OPERATIONAL     
        	                ::= 9	
arcServetrap9                   TRAP-TYPE       
	        		ENTERPRISE	arcServe
                                VARIABLES       {
                                                arcServeServerName,
                                                arcServetrapdesc
                                                }
        			DESCRIPTION
                                        "Failed to format tape.
                                        
                                        This trap signifies that ARCserve was unable to format
                                        a tape.  This could be caused by hardware or media failure.
                                        Verify tape drive has been cleaned and all cable connections.
                                        This message can also occur when an invalid board driver has
                                        been loaded."
                                --#TYPE "Failed to format tape."
                                --#SUMMARY "%s %s"
                                --#ARGUMENTS {0,1}
                                --#SEVERITY MINOR
                                --#TIMEINDEX 1
                                --#STATE   OPERATIONAL     
        	                ::= 9
arcServetrap10                  TRAP-TYPE       
	        		ENTERPRISE	arcServe
                                VARIABLES       {
                                                arcServeServerName,
                                                arcServetrapdesc
                                                }
        			DESCRIPTION
                                        "Failed to read tape header.
                                        
                                        This trap signifies a hardware or device failure when trying
                                        to read the tape header.  Verify that the tape is an ARCserve
                                        formatted tape.  Also verify that the tape drive has been
                                        cleaned and all cables are properly connected.  This message
                                        can also be displayed when an invalid board driver has been
                                        loaded."
                                --#TYPE "Failed to read tape header."
                                --#SUMMARY "%s %s"
                                --#ARGUMENTS {0,1}
                                --#SEVERITY MINOR
                                --#TIMEINDEX 1
                                --#STATE   OPERATIONAL     
        	                ::= 10
arcServetrap11                  TRAP-TYPE       
	        		ENTERPRISE	arcServe
                                VARIABLES       {
                                                arcServeServerName,
                                                arcServetrapdesc
                                                }
        			DESCRIPTION
                                        "Failed to access tape.
                                        
                                        This trap signifies that ARCserve was unable to access the
                                        the tape.  Also verify that the tape drive has been
                                        cleaned and all cables are properly connected.  This message
                                        can also be displayed when an invalid board driver has been
                                        loaded."
                                --#TYPE "Failed to access tape."
                                --#SUMMARY "%s %s"
                                --#ARGUMENTS {0,1}
                                --#SEVERITY MINOR
                                --#TIMEINDEX 1
                                --#STATE   OPERATIONAL     
        	                ::= 11   
arcServetrap12                  TRAP-TYPE       
	        		ENTERPRISE	arcServe
                                VARIABLES       {
                                                arcServeServerName,
                                                arcServetrapdesc
                                                }
        			DESCRIPTION
                                        "Backup Operation Cancelled.
                                        
                                        This trap indicates that the backup job has been cancelled.
                                        This is normally due to an operator cancelling/deleting a job
                                        from the ARCserve job list."
                                --#TYPE "Backup Operation Cancelled"
                                --#SUMMARY "%s %s"
                                --#ARGUMENTS {0,1}
                                --#SEVERITY MINOR
                                --#TIMEINDEX 1
                                --#STATE   OPERATIONAL     
        	                ::= 12
arcServetrap13                  TRAP-TYPE       
	        		ENTERPRISE	arcServe
                                VARIABLES       {
                                                arcServeServerName,
                                                arcServetrapdesc
                                                }
        			DESCRIPTION
                                        "Backup Operation Successful
                                        
                                        This trap signifies that the backup operation completed
                                        successfully."
                                --#TYPE "Backup Operation Successful"
                                --#SUMMARY "%s %s"
                                --#ARGUMENTS {0,1}
                                --#SEVERITY INFORMATIONAL
                                --#TIMEINDEX 1
                                --#STATE   OPERATIONAL     
        	                ::= 13
arcServetrap14                  TRAP-TYPE       
	        		ENTERPRISE	arcServe
                                VARIABLES       {
                                                arcServeServerName,
                                                arcServetrapdesc
                                                }
        			DESCRIPTION
                                        "Backup Operation Incomplete
                                        
                                        This trap signifies that the backup operation completed with
                                        warnings.  Refer to the activity log to determine if important
                                        nodes selected for backup have been missed."
                                --#TYPE "Backup Operation Incomplete"
                                --#SUMMARY "%s %s"
                                --#ARGUMENTS {0,1}
                                --#SEVERITY MINOR
                                --#TIMEINDEX 1
                                --#STATE   OPERATIONAL 
        	                ::= 14
arcServetrap15                  TRAP-TYPE       
	        		ENTERPRISE	arcServe
                                VARIABLES       {
                                                arcServeServerName,
                                                arcServetrapdesc
                                                }
        			DESCRIPTION
                                        "Backup Operation Failed
                                        
                                        This trap signifies that backup operation failed.  This message
                                        indicates that the backup encountered serious processing errors.
                                        Refer to the activity log for a description of the problems en-
                                        countered which caused the backup failed."
                                --#TYPE "Backup Operation Failed"
                                --#SUMMARY "%s %s"
                                --#ARGUMENTS {0,1}
                                --#SEVERITY CRITICAL
                                --#TIMEINDEX 1
                                --#STATE   DEGRADED     
        	                ::= 15
END
