-- File Name : rdn-subscribertraps.mib
-- Date      : 02 Nov  10:50:35 EDT 2000
-- Author    : Rajan Bhalla

-- Change Summary
-- Initial Version      	11/02/2000 	 Rajan Bhalla



RDN-SMSTraps-MIB	DEFINITIONS ::= BEGIN

	IMPORTS
		NOTIFICATION-TYPE, MODULE-IDENTITY, OBJECT-TYPE, 
		TimeTicks, IpAddress, Counter64, Gauge32, enterprises
			FROM SNMPv2-SMI
		TRAP-TYPE
		        FROM RFC-1215
		docsIfCmtsCmStatusMacAddress, docsIfCmtsCmStatusValue
			FROM DOCS-IF-MIB
		riverdelta      FROM RDN-MIB;



-- module definitions

	rdnSubscriberTraps	OBJECT IDENTIFIER
		::=  {  riverdelta  5  }

-- All future traps can be appended in this mib
-- Both v1 and v2c traps have been defined for the same event.


       rdnCableModemV1Traps OBJECT IDENTIFIER
	--     DESCRIPTION
	--        "This module defines all the SNMPv1 RiverGuide Traps " 
        --        
    		::= { rdnSubscriberTraps  1  }

       
       rdnCableModemStatusV1 TRAP-TYPE
	   ENTERPRISE	riverdelta
	   VARIABLES	{ docsIfCmtsCmStatusMacAddress,
		 	  docsIfCmtsCmStatusValue } 
	   DESCRIPTION
	       "The event is generated when the SRM receives a valid DHCP PACK
	        packet. "

	   ::=  1  


      rdnCableModemV2Traps OBJECT IDENTIFIER
	--     DESCRIPTION
	--        "This module defines all the SNMPv2 CM Traps " 
        --        
    		::= {rdnSubscriberTraps  2}


     	rdnCableModemStatusV2 NOTIFICATION-TYPE
	   OBJECTS	{ docsIfCmtsCmStatusMacAddress,
		 	  docsIfCmtsCmStatusValue } 
	   STATUS 	current
	   DESCRIPTION
	       "The CM trap signifies that the SNMPv2 entity in the device
		acting in an agent role has detected a cable modem 
		registration event based on a valid DHCP PACK packet being 
		sent to the CM."

	   ::= {rdnCableModemV2Traps   1} 



END
