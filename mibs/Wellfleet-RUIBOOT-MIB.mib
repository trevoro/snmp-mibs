Wellfleet-RUIBOOT-MIB DEFINITIONS ::= BEGIN

-- Created by mdl2asn version 3.1
-- Creation date: Wed Aug 30 16:47:15 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfRuiBootGroup
        FROM Wellfleet-COMMON-MIB;


    wfRuiBoot	OBJECT IDENTIFIER ::= { wfRuiBootGroup 1 }

    wfRuiBootBaseDelete OBJECT-TYPE
        SYNTAX	INTEGER {
    		    created(1),
    		    deleted(2)
    		}
        ACCESS	read-write
        STATUS	mandatory
        DESCRIPTION
                "Create/Delete parameter. Default is created.
                Users perform a set operation on this
                object in order to create/delete RUI BOOT Gate."
        DEFVAL	{ created }
        ::= { wfRuiBoot 1 }

    wfRuiBootBaseDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable RUI BOOT Gate."
        DEFVAL	{ enabled }
        ::= { wfRuiBoot 2 }

    wfRuiBootBaseState OBJECT-TYPE
        SYNTAX	INTEGER {
    		    up(1),
    		    down(2),
    		    init(3),
    		    notpres(4)
    		}
        ACCESS	read-only
        STATUS	mandatory
        DESCRIPTION
                "The current state of the entire Boot Mib Gate."
        DEFVAL	{ notpres }
        ::= { wfRuiBoot 3 }

    wfRuiBootTable OBJECT-TYPE
        SYNTAX	SEQUENCE OF WfRuiBootEntry
        ACCESS	not-accessible
        STATUS	mandatory
        DESCRIPTION
                "Remote User Interface Boot Object Table "
        ::= { wfRuiBootGroup 2 }

    wfRuiBootEntry OBJECT-TYPE
        SYNTAX	WfRuiBootEntry
        ACCESS	not-accessible
        STATUS	mandatory
        DESCRIPTION
                "A description of a Boot Entry"
        INDEX	{ wfRuiBootDateAndTime }
        ::= { wfRuiBootTable 1 }

    WfRuiBootEntry ::= SEQUENCE {
    	    wfRuiBootDelete
    		INTEGER,
    	    wfRuiBootDisable
    		INTEGER,
    	    wfRuiBootState
    		INTEGER,
    	    wfRuiBootDateAndTime
    		OCTET STRING,
    	    wfRuiBootImageName
    		DisplayString,
    	    wfRuiBootConfigName
    		DisplayString,
    	    wfRuiBootErrorCode
    		INTEGER,
    	    wfRuiBootSystemErrorCode
    		INTEGER
        }

    wfRuiBootDelete OBJECT-TYPE
        SYNTAX	INTEGER {
    		    created(1),
    		    deleted(2)
    		}
        ACCESS	read-write
        STATUS	mandatory
        DESCRIPTION
                "Create/Delete parameter for determining whether
                or not BOOT is configured on this slot."
        DEFVAL	{ created }
        ::= { wfRuiBootEntry 1 }

    wfRuiBootDisable OBJECT-TYPE
        SYNTAX	INTEGER {
    		    enabled(1),
    		    disabled(2)
    		}
        ACCESS	read-write
        STATUS	mandatory
        DESCRIPTION
                "Enable/Disable parameter. Users perform an SNMP SET
                operation on this object to enable/disable a  BOOT
                Entry.  Default is enabled."
        DEFVAL	{ enabled }
        ::= { wfRuiBootEntry 2 }

    wfRuiBootState OBJECT-TYPE
        SYNTAX	INTEGER {
    		    scheduled(1),
    		    aged(2),
    		    time(3),
    		    error(4),
    		    initializing(5)
    		}
        ACCESS	read-only
        STATUS	mandatory
        DESCRIPTION
                "The current state of this Boot Entry"
        DEFVAL	{ initializing }
        ::= { wfRuiBootEntry 3 }

    wfRuiBootDateAndTime OBJECT-TYPE
        SYNTAX	OCTET STRING (SIZE (11))
        ACCESS	read-only
        STATUS	mandatory
        DESCRIPTION
                "The 11 octet date and time that a BOOT is
                to execute.
                Octet map:
                1-2 Year, 3 Month,   4 Day,
                5 Hour,   6 Minutes, 7 Seconds,  8 Deci-seconds,

                               'A date-time specification.

                               field  octets  contents                  range
                               -----  ------  --------                  -----
                                 1      1-2   year                      0..65536
                                 2       3    month                     1..12
                                 3       4    day                       1..31
                                 4       5    hour                      0..23
                                 5       6    minutes                   0..59
                                 6       7    seconds                   0..60
                                              (use 60 for leap-second)
                                 7       8    deci-seconds              0..9
                                 8       9    direction from UTC        '+' / '-'
                                 9      10    hours from UTC            0..11
                                10      11    minutes from UTC          0..59

                               For example, Tuesday May 26, 1992 at 1:30:15 PM
                               EDT would be displayed as:

                                           1992-5-26,13:30:15.0,-4:0

                               Note that if only local time is known, then
                               timezone information (fields 8-10) is not
                               present.'
                       SYNTAX       OCTET STRING (SIZE (8 | 11))"
        ::= { wfRuiBootEntry 4 }

    wfRuiBootImageName OBJECT-TYPE
        SYNTAX	DisplayString
        ACCESS	read-write
        STATUS	mandatory
        DESCRIPTION
                "Name of boot Image"
        ::= { wfRuiBootEntry 5 }

    wfRuiBootConfigName OBJECT-TYPE
        SYNTAX	DisplayString
        ACCESS	read-write
        STATUS	mandatory
        DESCRIPTION
                "Parameter for the specified command"
        ::= { wfRuiBootEntry 6 }

    wfRuiBootErrorCode OBJECT-TYPE
        SYNTAX	INTEGER {
    		    none(1),
    		    imagename(2),
    		    configname(3),
    		    imagefilenotfound(4),
    		    configfilenotfound(5),
    		    imagefilecorrupt(6),
    		    filesystem(7),
    		    invalidtime(8)
    		}
        ACCESS	read-only
        STATUS	mandatory
        DESCRIPTION
                "Error code from last execution."
        DEFVAL	{ none }
        ::= { wfRuiBootEntry 7 }

    wfRuiBootSystemErrorCode OBJECT-TYPE
        SYNTAX	INTEGER
        ACCESS	read-only
        STATUS	mandatory
        DESCRIPTION
                "Error code from specified subsystem indicated in wfRuiBootErrorCode
                File System Errors:
                NONE               1
                ACCESS_VIOLATION   2
                CORRUPT_FILE       3
                DEVICE_BUSY        4
                DEVICE_CLIENT      5
                DEVICE_FULL        6
                DEVICE_SERVER      7
                DEVICE_WP          8     DEVICE WRITE PROTECTED
                DIRECTORY_FULL     9
                FCN_NOT_WRITTEN   10
                FILE_EXISTS       11
                FILE_LOCKED       12
                ILLEGAL_SEEK      13
                INVALID_ARGUMENT  14
                INVALID_NAME      15
                INVALID_VOLUME    16
                IO_ERROR          17
                IS_A_DIRECTORY    18
                MODE_NOT_ALLOWED  19
                MOUNT_NOMATCH     20
                NAME_TOO_LONG     21
                NOT_A_DIRECTORY   22
                NO_ENTRY          23
                NO_READ_ACCESS    24
                NO_WRITE_ACCESS   25
                NOT_EMPTY_DIR     26
                DIR_IN_USE        27
                REQUEST_TIME_OUT  28
                REPLY_TIME_OUT    29
                CORRUPTED_VOLUME  30
                INSUFF_RESOURCES  31
                PARTITION_EXISTS  32
                NO_PARTITION      33
                CANT_PART_MEDIA   34
                VOL1_TOO_BIG      35
                COMPACT_VOL1      36"
        ::= { wfRuiBootEntry 8 }

    END  -- Wellfleet-RUIBOOT-MIB
