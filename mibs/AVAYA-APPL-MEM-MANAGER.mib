AVAYA-APPL-MEM-MANAGER DEFINITIONS ::= BEGIN
   IMPORTS 
   	avGatewayMibs			
	   	 FROM AVAYAGEN-MIB	
     OBJECT-GROUP, NOTIFICATION-GROUP, MODULE-COMPLIANCE
         FROM SNMPv2-CONF
     Integer32, Unsigned32, enterprises, Gauge32, Counter32, OBJECT-TYPE, 
      MODULE-IDENTITY, NOTIFICATION-TYPE
         FROM SNMPv2-SMI
      RowStatus, TEXTUAL-CONVENTION, TruthValue, DateAndTime, TimeInterval, DisplayString
         FROM SNMPv2-TC      
      IpAddress
         FROM RFC1155-SMI;
      


     avApplMemManager MODULE-IDENTITY
       LAST-UPDATED "200410201534Z"   
     ORGANIZATION
                       "Avaya"
     CONTACT-INFO
     "
       Avaya Customer Services
       Postal: Avaya, Inc.
       211 Mt Airy Rd.
       Basking Ridge, NJ 07920
       USA
       Tel:	+1 908 953 6000
       WWW: 	http://www.avaya.com
     "
     DESCRIPTION
     "              
     This module define the application memory manager. I.e. definition of the size in memory
     for specific applications as TFTP, SNIFFER, etc. For each application the user can 
     configure the size it takes in RAM, NVRAM, etc.

     Copyright notice:
     
     This AVAYA SNMP Management Information Base Specification (Specification) embodies
     AVAYA confidential and Proprietary intellectual property.  AVAYA retains all Title
     and ownership in the Specification, including any revisionsIt is AVAYA's intent to
     encourage the widespread use of this Specification in connection with the management
     of AVAYA products. AVAYA grants vendors, end-users, and other interested parties a
     non-exclusive license to use this Specification in connection with the management 
     of AVAYA products.This Specification is supplied 'as is', and AVAYA makes no warranty,
     either express or implied, as to the use, operation, condition, or performance of the
      Specification.     
     "

           ::= { avGatewayMibs 3  } 
           
--
-- Version 200420101536Z
--   Initial Version

		avApplMemManagerGenConfig OBJECT IDENTIFIER ::= { avApplMemManager 1 }

		avApplMemManagerTotalRamSize OBJECT-TYPE
			SYNTAX INTEGER 
			MAX-ACCESS read-write
			STATUS current
			DESCRIPTION
				"The total max size allowable of the Memory in KBytes."
			::= { avApplMemManagerGenConfig 1 }    
			
		avApplMemManagerTotalNvRamSize OBJECT-TYPE
			SYNTAX INTEGER 
			MAX-ACCESS read-write
			STATUS current
			DESCRIPTION
				"The total max size allowable of the Memory in KBytes."
			::= { avApplMemManagerGenConfig 2 }    			

 
		avApplMemManagerTable OBJECT-TYPE
			SYNTAX SEQUENCE OF AvApplMemManagerEntry
			MAX-ACCESS not-accessible
			STATUS current
			DESCRIPTION
				"Table of different application and their memory allocation in the RAM and NvRAM."
			::= { avApplMemManager 2 }
	
		avApplMemManagerEntry OBJECT-TYPE
			SYNTAX AvApplMemManagerEntry
			MAX-ACCESS not-accessible
			STATUS current
			DESCRIPTION
				"An entry in the table, containing data about application and its memory type."
			INDEX { avApplMemManagerId, avApplMemManagerType }
			::= { avApplMemManagerTable 1 }
		
		AvApplMemManagerEntry ::=
			SEQUENCE { 
				avApplMemManagerId
					INTEGER,
				avApplMemManagerType
					INTEGER,
				avApplMemManagerName
					DisplayString,  
				avApplMemManagerSize
					INTEGER,
				avApplMemManagerMinSize
					INTEGER,
				avApplMemManagerMaxSize
					INTEGER
				 }

		avApplMemManagerId OBJECT-TYPE
			SYNTAX INTEGER 
			MAX-ACCESS read-only
			STATUS current
			DESCRIPTION
				"Index of the application. SNIFFER application index is 1. 
				TFTP server application index is 2."
			::= { avApplMemManagerEntry 1 }
		
        avApplMemManagerType OBJECT-TYPE
			SYNTAX INTEGER 
			MAX-ACCESS read-only
			STATUS current
			DESCRIPTION
				"The Type of the memory that the application use.
				1 - NvRAM, 2 - RAM."
			::= { avApplMemManagerEntry 2 }
        
		avApplMemManagerName OBJECT-TYPE
			SYNTAX DisplayString
			MAX-ACCESS read-only
			STATUS current
			DESCRIPTION
				"The name of the application.
				For Sniffer application 'SNIFFER'. 
				For TFTP Server Application 'TFTP Server'.
				"
			::= { avApplMemManagerEntry 3 }

         	avApplMemManagerSize OBJECT-TYPE
			SYNTAX INTEGER 
			MAX-ACCESS read-write
			STATUS current
			DESCRIPTION
				"The size of the Memory in KBytes  for specific application and memory type."
			::= { avApplMemManagerEntry 4 }
			
			
			avApplMemManagerMinSize OBJECT-TYPE
			SYNTAX INTEGER 
			MAX-ACCESS read-only
			STATUS current
			DESCRIPTION
				"The Min size allowable of the Memory in KBytes for specific application 
				and memory type."
			::= { avApplMemManagerEntry 5 }
			
			
			avApplMemManagerMaxSize OBJECT-TYPE
			SYNTAX INTEGER 
			MAX-ACCESS read-only
			STATUS current
			DESCRIPTION
				"The max size allowable of the Memory in KBytes for specific application 
				 and memory type."
			::= { avApplMemManagerEntry 6 }    
    
 
  
  END
