ACC-ATMSLV DEFINITIONS ::= BEGIN

    IMPORTS
			OBJECT-TYPE, Gauge, Counter, TimeTicks FROM RFC1155-SMI
			accTrapLogSeqNum FROM ACC-SYSTEM
	accBRG, DisplayString, RowStatus, IfIndex, SmdsAddress
             FROM ACC-MIB
        accSysInfo FROM ACC-SYSTEM;

-- ATM Slave (VxWorks) Group
--
-- VxWorks specific Slave objects
-- Derived from existing MPPE slave objects
-- All descriptions are applicable only to Slave ICPs running
-- VxWorks even if not explicitly mentioned.
--
-- The VxWorks specific Slave group
accVWSlvGrp	OBJECT IDENTIFIER	::= { accSysInfo  31 }
-- The slave CPU configuration table
accVWSlvConfTable      	OBJECT-TYPE         
SYNTAX              	SEQUENCE OF AccVWSlvConfEntry             
ACCESS          	not-accessible           
STATUS              	mandatory           
DESCRIPTION         
	" Table of slave CPU configuration parameters. "
::= { accVWSlvGrp 1 }
accVWSlvConfEntry      	OBJECT-TYPE         
SYNTAX              	AccVWSlvConfEntry               
ACCESS          	not-accessible                
STATUS              	mandatory           
DESCRIPTION         
	" An entry in the Slave CPU configuration table. "
INDEX               	{ accVWSlvConfCPUID }
::= { accVWSlvConfTable 1 }
AccVWSlvConfEntry ::=
      SEQUENCE {
	 accVWSlvConfCPUID       	DisplayString,
	 accVWSlvConfSysDesc     	DisplayString,
	 accVWSlvConfSWVers      	DisplayString,
	 accVWSlvConfProcType    	INTEGER,
	 accVWSlvConfLocalRam    	INTEGER,
	 accVWSlvConfGlobalRam   	INTEGER,
	 accVWSlvConfHWVers      	DisplayString
}
accVWSlvConfCPUID		OBJECT-TYPE
SYNTAX				DisplayString 
ACCESS				read-only
STATUS				mandatory
DESCRIPTION
	" The CPU ID used as an instance. "
::= { accVWSlvConfEntry 1 }
accVWSlvConfSysDesc		OBJECT-TYPE
SYNTAX				DisplayString 
ACCESS				read-only
STATUS				mandatory
DESCRIPTION
	" The value of sysDescr for the Slave ICP. "
::= { accVWSlvConfEntry 2 }
accVWSlvConfSWVers		OBJECT-TYPE
SYNTAX				DisplayString 
ACCESS				read-only
STATUS				mandatory
DESCRIPTION
	" The software version running on the Slave ICP. "
::= { accVWSlvConfEntry 3 }
accVWSlvConfProcType		OBJECT-TYPE
SYNTAX				INTEGER { idtMips4700(1) }
ACCESS				read-only
STATUS				mandatory
DESCRIPTION
	" The Processor type on the slave ICP. "
::= { accVWSlvConfEntry 4 }
accVWSlvConfLocalRam		OBJECT-TYPE
SYNTAX				INTEGER 
ACCESS				read-only
STATUS				mandatory
DESCRIPTION
	" The amount of Local RAM in kilo bytes on the slave ICP. "
::= { accVWSlvConfEntry 5 }
accVWSlvConfGlobalRam		OBJECT-TYPE
SYNTAX				INTEGER 
ACCESS				read-only
STATUS				mandatory
DESCRIPTION
	" The amount of global RAM in kilo bytes on the slave ICP. "
::= { accVWSlvConfEntry 6 }
accVWSlvConfHWVers		OBJECT-TYPE
SYNTAX				DisplayString 
ACCESS				read-only
STATUS				mandatory
DESCRIPTION
	" The hardware versions on the slave ICP. "
::= { accVWSlvConfEntry 7 }
-- Slave Memory statistics table
accVWSlvMemStatTable   	OBJECT-TYPE         
SYNTAX              	SEQUENCE OF AccVWSlvMemStatEntry             
ACCESS          	not-accessible           
STATUS              	mandatory           
DESCRIPTION         
	" The Slave memory statistics table. "
::= { accVWSlvGrp 2 }
accVWSlvMemStatEntry   	OBJECT-TYPE         
SYNTAX              	AccVWSlvMemStatEntry               
ACCESS          	not-accessible                
STATUS              	mandatory           
DESCRIPTION         
	" An entry in the Slave memory statistics table. "
INDEX               	{ accVWSlvMemCPUID, accVWSlvMemBlkPoolId }
::= { accVWSlvMemStatTable 1 }
AccVWSlvMemStatEntry ::=
      SEQUENCE {
	 accVWSlvMemCPUID        	DisplayString,
	 accVWSlvMemBlkPoolId    	INTEGER,
	 accVWSlvMemBlkEntSize   	INTEGER,
	 accVWSlvMemBlkEntTotal  	INTEGER,
	 accVWSlvMemBlkEntInUse  	Gauge,
	 accVWSlvMemBlkEntFails  	Counter,
	 accVWSlvMemBlkEntAllocs 	Counter
}
accVWSlvMemCPUID		OBJECT-TYPE
SYNTAX				DisplayString 
ACCESS				read-only
STATUS				mandatory
DESCRIPTION
	" The slave ICP CPU id used as an instance. "
::= { accVWSlvMemStatEntry 1 }
accVWSlvMemBlkPoolId		OBJECT-TYPE
SYNTAX				INTEGER (0..6)
ACCESS				read-only
STATUS				mandatory
DESCRIPTION
	" The Memory Pool ID. Currently there are 7 memory pools. "
::= { accVWSlvMemStatEntry 2 }
accVWSlvMemBlkEntSize		OBJECT-TYPE
SYNTAX				INTEGER 
ACCESS				read-only
STATUS				mandatory
DESCRIPTION
	" Size in bytes of a memory block in a given pool. "
::= { accVWSlvMemStatEntry 3 }
accVWSlvMemBlkEntTotal		OBJECT-TYPE
SYNTAX				INTEGER 
ACCESS				read-only
STATUS				mandatory
DESCRIPTION
	" The total number of memory blocks in a pool. "
::= { accVWSlvMemStatEntry 4 }
accVWSlvMemBlkEntInUse		OBJECT-TYPE
SYNTAX				Gauge 
ACCESS				read-only
STATUS				mandatory
DESCRIPTION
	" The current number of memory blocks in use. "
::= { accVWSlvMemStatEntry 5 }
accVWSlvMemBlkEntFails		OBJECT-TYPE
SYNTAX				Counter 
ACCESS				read-only
STATUS				mandatory
DESCRIPTION
	" The number of failed allocation requests for a given pool. "
::= { accVWSlvMemStatEntry 6 }
accVWSlvMemBlkEntAllocs		OBJECT-TYPE
SYNTAX				Counter 
ACCESS				read-only
STATUS				mandatory
DESCRIPTION
	" The total number of requested allocations for a given pool. "
::= { accVWSlvMemStatEntry 7 }
-- Slave CPU time table
accVWSlvTimeTable      	OBJECT-TYPE         
SYNTAX              	SEQUENCE OF AccVWSlvTimeEntry             
ACCESS          	not-accessible           
STATUS              	mandatory           
DESCRIPTION         
	" The slave CPU time table. "
::= { accVWSlvGrp 3 }
accVWSlvTimeEntry      	OBJECT-TYPE         
SYNTAX              	AccVWSlvTimeEntry               
ACCESS          	not-accessible                
STATUS              	mandatory           
DESCRIPTION         
	" An entry in the slave CPU time table. "
INDEX               	{ accVWSlvSysCPUID }
::= { accVWSlvTimeTable 1 }
AccVWSlvTimeEntry ::=
      SEQUENCE {
	 accVWSlvSysCPUID        	DisplayString,
	 accVWSlvSysUpTime       	TimeTicks,
	 accVWSlvSysCpuAvgShort  	INTEGER,
	 accVWSlvSysCpuAvgLong   	INTEGER
}
accVWSlvSysCPUID		OBJECT-TYPE
SYNTAX				DisplayString 
ACCESS				read-only
STATUS				mandatory
DESCRIPTION
	" The slave CPU id used as an instance. "
::= { accVWSlvTimeEntry 1 }
accVWSlvSysUpTime		OBJECT-TYPE
SYNTAX				TimeTicks 
ACCESS				read-only
STATUS				mandatory
DESCRIPTION
	" The value of SysUpTime for the slave ICP. "
::= { accVWSlvTimeEntry 2 }
accVWSlvSysCpuAvgShort		OBJECT-TYPE
SYNTAX				INTEGER 
ACCESS				read-only
STATUS				mandatory
DESCRIPTION
	" The slave system current CPU usage. "
::= { accVWSlvTimeEntry 3 }
accVWSlvSysCpuAvgLong		OBJECT-TYPE
SYNTAX				INTEGER 
ACCESS				read-only
STATUS				mandatory
DESCRIPTION
	" The slave system average CPU usage. "
::= { accVWSlvTimeEntry 4 }

END
