--
-- OPCD-USSDB-MIB-V2
-- Last Modified: Oct 10, 2007
--


OPCD-USSDB-MIB-V2 DEFINITIONS ::= BEGIN


--  OPCD-USSDB-MIB:
--    A private enterprise mib for Opencode USSDBrowser application.


IMPORTS
	MODULE-IDENTITY, OBJECT-TYPE, NOTIFICATION-TYPE, enterprises	FROM SNMPv2-SMI
	DisplayString							FROM SNMPv2-TC
	opencode-systems 					      	FROM OPCD-SUPPORT-MIB-V2;





--  opencode ussdbrowser  branch: 30374.1
--  opencode ussdbrowser traps branch: 30374.1.1


ocussdbrowser		OBJECT IDENTIFIER ::= { opencode-systems 1 }
ocussdbrowser-traps	OBJECT IDENTIFIER ::= { ocussdbrowser 1 }

definitions 		OBJECT IDENTIFIER ::= { ocussdbrowser-traps 0 }
vars	 		OBJECT IDENTIFIER ::= { ocussdbrowser-traps 1 }




--
-- Node definitions
--




mcr-Host OBJECT-TYPE
	SYNTAX DisplayString (SIZE (0..255))
	MAX-ACCESS accessible-for-notify
	STATUS current
	DESCRIPTION
		"String containing hostname of fault node."
	::= { vars 1 }


mcr-Severity OBJECT-TYPE
	SYNTAX INTEGER{
		critical(1),
		major(2),
		minor(3),
		normal(4),
		warning(5)
	}
	MAX-ACCESS accessible-for-notify
	STATUS mandatory
	DESCRIPTION
		"Alarm severity."
	::= { vars 2 }


mcr-Text OBJECT-TYPE
	SYNTAX DisplayString (SIZE (0..255))
	MAX-ACCESS accessible-for-notify
	STATUS current
	DESCRIPTION
		"String containing text of the alarm."
	::= { vars 3 }


--
-- Traps
--
------------------------------------------------------------------------------------------

------------------------------------------------------------------------------------------


-- 1.3.6......0.2
ocussdbrowser-Restart NOTIFICATION-TYPE
	OBJECTS	{ mcr-Host, mcr-Severity, mcr-Text}	
	STATUS	current
	DESCRIPTION	"Ussdbrowser was restarted!"
	--#SUMMARY   "Alarm on host: $1 (ussdbrowser application) :  $3"
	--#CATEGORY  "Error Alarms"
        --#ARGUMENTS {}
        --#SEVERITY  WARNING
	::= { definitions 2 }


-- 1.3.6......0.3
ocussdbrowser-Restart-Canceled NOTIFICATION-TYPE
	OBJECTS	{ mcr-Host, mcr-Severity, mcr-Text}	
	STATUS	current
	DESCRIPTION	"Ussdbrowser was restarted-Canceled"
	--#SUMMARY   "Alarm on host: $1 (ussdbrowser application) :  $3"
	--#CATEGORY  "Error Alarms"
        --#ARGUMENTS {}
        --#SEVERITY  NORMAL
	::= { definitions 3 }


-- 1.3.6......0.4
ocussdbrowser-Crash NOTIFICATION-TYPE
	OBJECTS	{ mcr-Host, mcr-Severity, mcr-Text}	
	STATUS		current
	DESCRIPTION	"Ussdbrowser crash "
	--#SUMMARY   "Alarm on host: $1 (ussdbrowser application) :  $3"
	--#CATEGORY  "Error Alarms"
        --#ARGUMENTS {}
        --#SEVERITY  CRITICAL
	::= { definitions 4 }


-- 1.3.6......0.5
ocussdbrowser-Crash-Canceled NOTIFICATION-TYPE
	OBJECTS	{ mcr-Host, mcr-Severity, mcr-Text}	
	STATUS		current
	DESCRIPTION	"Ussdbrowser crash -Canceled"
	--#SUMMARY   "Alarm on host: $1 (ussdbrowser application) :  $3"
	--#CATEGORY  "Error Alarms"
        --#ARGUMENTS {}
        --#SEVERITY  NORMAL
	::= { definitions 5 }


-- 1.3.6......0.6
ocussdbrowser-Smsc-Conn NOTIFICATION-TYPE
	OBJECTS	{ mcr-Host, mcr-Severity, mcr-Text}	
	STATUS		current
	DESCRIPTION	"SMSC connection is down"
	--#SUMMARY   "Alarm on host: $1 (ussdbrowser application) :  $3"
	--#CATEGORY  "Error Alarms"
        --#ARGUMENTS {}
        --#SEVERITY  CRITICAL
	::= { definitions 6 }

-- 1.3.6......0.7
ocussdbrowser-Smsc-Conn-Canceled NOTIFICATION-TYPE
	OBJECTS	{ mcr-Host, mcr-Severity, mcr-Text}	
	STATUS		current
	DESCRIPTION	"SMSC connection is down-Canceled"
	--#SUMMARY   "Alarm on host: $1 (ussdbrowser application) :  $3"
	--#CATEGORY  "Error Alarms"
        --#ARGUMENTS {}
        --#SEVERITY  NORMAL
	::= { definitions 7 }


-- 1.3.6......0.8
ocussdbrowser-UssdgwConn NOTIFICATION-TYPE
	OBJECTS	{ mcr-Host, mcr-Severity, mcr-Text}	
	STATUS	current
	DESCRIPTION	"Connection to USSDGW is down!!"
	--#SUMMARY   "Alarm on host: $1 (ussdbrowser application) :  $3"
	--#CATEGORY  "Error Alarms"
        --#ARGUMENTS {}
        --#SEVERITY  CRITICAL
	::= { definitions 8 }


-- 1.3.6......0.9
ocussdbrowser-UssdgwConn-Canceled NOTIFICATION-TYPE
	OBJECTS	{ mcr-Host, mcr-Severity, mcr-Text}	
	STATUS	current
	DESCRIPTION	"Connection to USSDGW is down-Canceled"
	--#SUMMARY   "Alarm on host: $1 (ussdbrowser application) :  $3"
	--#CATEGORY  "Error Alarms"
        --#ARGUMENTS {}
        --#SEVERITY  NORMAL
	::= { definitions 9 }


-- 1.3.6......0.10
ocussdbrowser-SmppListener NOTIFICATION-TYPE
	OBJECTS	{ mcr-Host, mcr-Severity, mcr-Text}	
	STATUS	current
	DESCRIPTION	"SMPP Listener is down"
	--#SUMMARY   "Alarm on host: $1 (ussdbrowser application) :  $3"
	--#CATEGORY  "Error Alarms"
        --#ARGUMENTS {}
        --#SEVERITY  WARNING
	::= { definitions 10 }

-- 1.3.6......0.11
ocussdbrowser-SmppListener-Canceled NOTIFICATION-TYPE
	OBJECTS	{ mcr-Host, mcr-Severity, mcr-Text}	
	STATUS	current
	DESCRIPTION	"SMPP Listener is down-Canceled"
	--#SUMMARY   "Alarm on host: $1 (ussdbrowser application) :  $3"
	--#CATEGORY  "Error Alarms"
        --#ARGUMENTS {}
        --#SEVERITY  NORMAL
	::= { definitions 11 }


-- 1.3.6......0.12
ocussdbrowser-SmppClientConnectorDown NOTIFICATION-TYPE
	OBJECTS	{ mcr-Host, mcr-Severity, mcr-Text}	
	STATUS	current
	DESCRIPTION	"SMPP Client Connector is down!"
	--#SUMMARY   "Alarm on host: $1 (ussdbrowser application) :  $3"
	--#CATEGORY  "Error Alarms"
        --#ARGUMENTS {}
        --#SEVERITY  CRITICAL
	::= { definitions 12 }


-- 1.3.6......0.13
ocussdbrowser-SmppClientConnectorDown-Canceled NOTIFICATION-TYPE
	OBJECTS	{ mcr-Host, mcr-Severity, mcr-Text}	
	STATUS	current
	DESCRIPTION	"SMPP Client Connector is down-Canceled"
	--#SUMMARY   "Alarm on host: $1 (ussdbrowser application) :  $3"
	--#CATEGORY  "Error Alarms"
        --#ARGUMENTS {}
        --#SEVERITY  NORMAL
	::= { definitions 13 }


-- 1.3.6......0.14
ocussdbrowser-SmppClients NOTIFICATION-TYPE
	OBJECTS	{ mcr-Host, mcr-Severity, mcr-Text}	
	STATUS	current
	DESCRIPTION	"There are disconnected SMPP Clients!"
	--#SUMMARY   "Alarm on host: $1 (ussdbrowser application) :  $3"
	--#CATEGORY  "Error Alarms"
        --#ARGUMENTS {}
        --#SEVERITY  WARNING
	::= { definitions 14 }


-- 1.3.6......0.15
ocussdbrowser-SmppClients-Canceled NOTIFICATION-TYPE
	OBJECTS	{ mcr-Host, mcr-Severity, mcr-Text}	
	STATUS	current
	DESCRIPTION	"There are disconnected SMPP Clients-Canceled"
	--#SUMMARY   "Alarm on host: $1 (ussdbrowser application) :  $3"
	--#CATEGORY  "Error Alarms"
        --#ARGUMENTS {}
        --#SEVERITY  NORMAL
	::= { definitions 15 }


-- 1.3.6......0.16
ocussdbrowser-SmppClientsCritical NOTIFICATION-TYPE
	OBJECTS	{ mcr-Host, mcr-Severity, mcr-Text}	
	STATUS	current
	DESCRIPTION	"No SMPP Client Connections!"
	--#SUMMARY   "Alarm on host: $1 (ussdbrowser application) :  $3"
	--#CATEGORY  "Error Alarms"
        --#ARGUMENTS {}
        --#SEVERITY  CRITICAL
	::= { definitions 16 }


-- 1.3.6......0.17
ocussdbrowser-SmppClientsCritical-Canceled NOTIFICATION-TYPE
	OBJECTS	{ mcr-Host, mcr-Severity, mcr-Text}	
	STATUS	current
	DESCRIPTION	"No SMPP Client Connections-Canceled"
	--#SUMMARY   "Alarm on host: $1 (ussdbrowser application) :  $3"
	--#CATEGORY  "Error Alarms"
        --#ARGUMENTS {}
        --#SEVERITY  NORMAL
	::= { definitions 17 }


-- 1.3.6......0.18
ocussdbrowser-SmppClientsErrors NOTIFICATION-TYPE
	OBJECTS	{ mcr-Host, mcr-Severity, mcr-Text}	
	STATUS	current
	DESCRIPTION	"Error in SMPP Clients Part - Error Code!"
	--#SUMMARY   "Alarm on host: $1 (ussdbrowser application) :  $3"
	--#CATEGORY  "Error Alarms"
        --#ARGUMENTS {}
        --#SEVERITY  WARNING
	::= { definitions 18 }


-- 1.3.6......0.19
ocussdbrowser-SmppClientsErrors-Canceled NOTIFICATION-TYPE
	OBJECTS	{ mcr-Host, mcr-Severity, mcr-Text}	
	STATUS	current
	DESCRIPTION	"Error in SMPP Clients Part -Canceled"
	--#SUMMARY   "Alarm on host: $1 (ussdbrowser application) :  $3"
	--#CATEGORY  "Error Alarms"
        --#ARGUMENTS {}
        --#SEVERITY  NORMAL
	::= { definitions 19 }


-- 1.3.6......0.20
ocussdbrowser-HttpConnector NOTIFICATION-TYPE
	OBJECTS	{ mcr-Host, mcr-Severity, mcr-Text}	
	STATUS	current
	DESCRIPTION	"HTTP connector is down!"
	--#SUMMARY   "Alarm on host: $1 (ussdbrowser application) :  $3"
	--#CATEGORY  "Error Alarms"
        --#ARGUMENTS {}
        --#SEVERITY  CRITICAL
	::= { definitions 20 }


-- 1.3.6......0.21
ocussdbrowser-HttpConnector-Canceled NOTIFICATION-TYPE
	OBJECTS	{ mcr-Host, mcr-Severity, mcr-Text}	
	STATUS	current
	DESCRIPTION	"HTTP connector is down-Canceled"
	--#SUMMARY   "Alarm on host: $1 (ussdbrowser application) :  $3"
	--#CATEGORY  "Error Alarms"
        --#ARGUMENTS {}
        --#SEVERITY  NORMAL
	::= { definitions 21 }


-- 1.3.6......0.22
ocussdbrowser-HttpDedicatedUrl NOTIFICATION-TYPE
	OBJECTS	{ mcr-Host, mcr-Severity, mcr-Text}	
	STATUS	current
	DESCRIPTION	"HTTP dedicated connector problem!"
	--#SUMMARY   "Alarm on host: $1 (ussdbrowser application) :  $3"
	--#CATEGORY  "Error Alarms"
        --#ARGUMENTS {}
        --#SEVERITY  WARNING
	::= { definitions 22 }

-- 1.3.6......0.23
ocussdbrowser-HttpDedicatedUrl-Canceled NOTIFICATION-TYPE
	OBJECTS	{ mcr-Host, mcr-Severity, mcr-Text}	
	STATUS	current
	DESCRIPTION	"HTTP dedicated connector problem-Canceled"
	--#SUMMARY   "Alarm on host: $1 (ussdbrowser application) :  $3"
	--#CATEGORY  "Error Alarms"
        --#ARGUMENTS {}
        --#SEVERITY  NORMAL
	::= { definitions 23 }


-- 1.3.6......0.24
ocussdbrowser-HttpListener NOTIFICATION-TYPE
	OBJECTS	{ mcr-Host, mcr-Severity, mcr-Text}	
	STATUS	current
	DESCRIPTION	"HTTP Listener is down!"
	--#SUMMARY   "Alarm on host: $1 (ussdbrowser application) :  $3"
	--#CATEGORY  "Error Alarms"
        --#ARGUMENTS {}
        --#SEVERITY  CRITICAL
	::= { definitions 24 }


-- 1.3.6......0.25
ocussdbrowser-HttpListener-Canceled NOTIFICATION-TYPE
	OBJECTS	{ mcr-Host, mcr-Severity, mcr-Text}	
	STATUS	current
	DESCRIPTION	"HTTP Listener is down-Canceled"
	--#SUMMARY   "Alarm on host: $1 (ussdbrowser application) :  $3"
	--#CATEGORY  "Error Alarms"
        --#ARGUMENTS {}
        --#SEVERITY  NORMAL
	::= { definitions 25 }

-- 1.3.6......0.26
ocussdbrowser-IpcListener NOTIFICATION-TYPE
	OBJECTS	{ mcr-Host, mcr-Severity, mcr-Text}	
	STATUS	current
	DESCRIPTION	"IPC Listener is down!"
	--#SUMMARY   "Alarm on host: $1 (ussdbrowser application) :  $3"
	--#CATEGORY  "Error Alarms"
        --#ARGUMENTS {}
        --#SEVERITY  CRITICAL
	::= { definitions 26 }


-- 1.3.6......0.27
ocussdbrowser-IpcListener-Canceled NOTIFICATION-TYPE
	OBJECTS	{ mcr-Host, mcr-Severity, mcr-Text}	
	STATUS	current
	DESCRIPTION	"IPC Listener is down-Canceled"
	--#SUMMARY   "Alarm on host: $1 (ussdbrowser application) :  $3"
	--#CATEGORY  "Error Alarms"
        --#ARGUMENTS {}
        --#SEVERITY  NORMAL
	::= { definitions 27 }

-- 1.3.6......0.28
ocussdbrowser-SoapListener NOTIFICATION-TYPE
	OBJECTS	{ mcr-Host, mcr-Severity, mcr-Text}	
	STATUS	current
	DESCRIPTION	"SOAP Listener is down!"
	--#SUMMARY   "Alarm on host: $1 (ussdbrowser application) :  $3"
	--#CATEGORY  "Error Alarms"
        --#ARGUMENTS {}
        --#SEVERITY  CRITICAL
	::= { definitions 28 }


-- 1.3.6......0.29
ocussdbrowser-SoapListener-Canceled NOTIFICATION-TYPE
	OBJECTS	{ mcr-Host, mcr-Severity, mcr-Text}	
	STATUS	current
	DESCRIPTION	"SOAP Listener is down-Canceled"
	--#SUMMARY   "Alarm on host: $1 (ussdbrowser application) :  $3"
	--#CATEGORY  "Error Alarms"
        --#ARGUMENTS {}
        --#SEVERITY  NORMAL
	::= { definitions 29 }

-- 1.3.6......0.30
ocussdbrowser-InvalidService NOTIFICATION-TYPE
	OBJECTS	{ mcr-Host, mcr-Severity, mcr-Text}	
	STATUS  current
	DESCRIPTION  "Invalid USSD Browser Service!"
	--#SUMMARY   "Alarm on host: $1 (ussdbrowser application) :  $3"
	--#CATEGORY  "Error Alarms"
        --#ARGUMENTS {}
        --#SEVERITY  WARNING
	::= { definitions 30 }


-- 1.3.6......0.31
ocussdbrowser-InvalidService-Canceled NOTIFICATION-TYPE
	OBJECTS	{ mcr-Host, mcr-Severity, mcr-Text}	
	STATUS  current
	DESCRIPTION  "Invalid USSD Browser Service-Canceled"
	--#SUMMARY   "Alarm on host: $1 (ussdbrowser application) :  $3"
	--#CATEGORY  "Error Alarms"
        --#ARGUMENTS {}
        --#SEVERITY  NORMAL
	::= { definitions 31 }


-- 1.3.6......0.32
ocussdbrowser-MissingConnector NOTIFICATION-TYPE
        OBJECTS	{ mcr-Host, mcr-Severity, mcr-Text}	
		STATUS  current
        DESCRIPTION  "If there is no connection to a connector for a several
subsequent attempts an alarm is raised."
        --#SUMMARY   "Alarm on host: $1 (ussdbrowser application) :  $3"
        --#CATEGORY  "Error Alarms"
        --#ARGUMENTS {}
        --#SEVERITY  WARNING
        ::= { definitions 32 }


-- 1.3.6......0.33
ocussdbrowser-MissingConnector-Canceled NOTIFICATION-TYPE
        OBJECTS	{ mcr-Host, mcr-Severity, mcr-Text}	
		STATUS  current
        DESCRIPTION  "If there is no connection to a connector for a several
subsequent attempts an alarm is raised-Canceled"
        --#SUMMARY   "Alarm on host: $1 (ussdbrowser application) :  $3"
        --#CATEGORY  "Error Alarms"
        --#ARGUMENTS {}
        --#SEVERITY  NORMAL
        ::= { definitions 33 }


-- 1.3.6......0.34
ocussdbrowser-MissingService NOTIFICATION-TYPE
        OBJECTS	{ mcr-Host, mcr-Severity, mcr-Text}	
		STATUS  current
        DESCRIPTION  "This alarm is raised when a request with non-configured service code comes to USSDB, i.e. request to *123# if there is no such service."
        --#SUMMARY   "Alarm on host: $1 (ussdbrowser application) :  $3"
        --#CATEGORY  "Error Alarms"
        --#ARGUMENTS {}
        --#SEVERITY  WARNING
        ::= { definitions 34 }


-- 1.3.6......0.35
ocussdbrowser-MissingService-Canceled NOTIFICATION-TYPE
        OBJECTS	{ mcr-Host, mcr-Severity, mcr-Text}	
		STATUS  current
        DESCRIPTION  "The alarm ocussdbrowser-MissingService is canceled after alarm timeout by default 2 hours."
        --#SUMMARY   "Alarm on host: $1 (ussdbrowser application) :  $3"
        --#CATEGORY  "Error Alarms"
        --#ARGUMENTS {}
        --#SEVERITY  NORMAL
        ::= { definitions 35 }





END


--
-- OPCD-USSDB-MIB-V2
--
