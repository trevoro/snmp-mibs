-- $Id: it-link-mib.mib,v 1.1 2000/07/25 14:34:31 sse Exp $
        ITOUCH-LINK-MIB DEFINITIONS ::= BEGIN

               IMPORTS
                       Counter, TimeTicks, Gauge
                               FROM RFC1155-SMI
                       ifIndex
                               FROM RFC1213-MIB
                       OBJECT-TYPE
                               FROM RFC-1212
                       iTouch
                               FROM ITOUCH-MIB;

       xLink           OBJECT IDENTIFIER ::= { iTouch 24 }

       -- ITouch Link subgroups

       xLinkBasic      OBJECT IDENTIFIER ::= { xLink 1 }
       --                                    2 reserved for LAN
       xWan            OBJECT IDENTIFIER ::= { xLink 3 }




            -- This is a MIB module for all iTouch Communications systems
            -- that implement iTouch enhanced network communication links.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.



       -- link group

       linkTable OBJECT-TYPE
           SYNTAX SEQUENCE OF LinkEntry
           ACCESS not-accessible
           STATUS mandatory
           DESCRIPTION
               "A list of links."
           ::= { xLinkBasic 1 }

       linkEntry OBJECT-TYPE
           SYNTAX LinkEntry
           ACCESS not-accessible
           STATUS mandatory
           DESCRIPTION
               "Link entry."
           INDEX { ifIndex }
           ::= { linkTable 1 }

       LinkEntry ::=
           SEQUENCE {
               linkNoBuffers
                   Counter,
               linkDelayExceeded
                   Counter,
               linkOutputQFull
                   Counter,
               linkDownTime
                   Counter,
               linkDownCount
                   Counter,
               linkDownLastStart
                   TimeTicks,
               linkStatus
                   INTEGER,
               linkLostBuffers
                   Counter
           }

       linkNoBuffers OBJECT-TYPE
           SYNTAX Counter
           ACCESS read-only
           STATUS mandatory
           DESCRIPTION
               "The number of packets discarded because of lack of 
               buffers."
           ::= { linkEntry 1 }

       linkDelayExceeded OBJECT-TYPE
           SYNTAX Counter
           ACCESS read-only
           STATUS mandatory
           DESCRIPTION
               "The number of packets discarded because they were 
               held to long."
           ::= { linkEntry 2 }

       linkOutputQFull OBJECT-TYPE
           SYNTAX Counter
           ACCESS read-only
           STATUS mandatory
           DESCRIPTION
               "The number of packets discarded because the output 
               queue was full."
           ::= { linkEntry 3 }

       linkDownTime OBJECT-TYPE
           SYNTAX Counter
           ACCESS read-only
           STATUS mandatory
           DESCRIPTION
               "Total number of seconds that the link has been 
               down."
           ::= { linkEntry 4 }

       linkDownCount OBJECT-TYPE
           SYNTAX Counter
           ACCESS read-only
           STATUS mandatory
           DESCRIPTION
               "Number of times that the link has been down."
           ::= { linkEntry 5 }

       linkDownLastStart OBJECT-TYPE
           SYNTAX TimeTicks
           ACCESS read-only
           STATUS mandatory
           DESCRIPTION
               "Value of sysUpTime when the link last went down.  
               If the link is up the value is 0."
           ::= { linkEntry 6 }

       linkStatus OBJECT-TYPE
           SYNTAX INTEGER { running1(7), initWaitDsr(128),
                            initWait(129), running2(130),
                            purgeWait(131), down(132),
                            purging(133), loop(138), 
                            testSend(139), testReceive(140),
                            testLoop(141), speedChange(143),
                            disabled(145), badQuality(146) }
           ACCESS read-only
           STATUS mandatory
           DESCRIPTION
               "The status of the link"
           ::= { linkEntry 7 }

       linkLostBuffers OBJECT-TYPE
           SYNTAX Counter
           ACCESS read-only
           STATUS mandatory
           DESCRIPTION
               "Number of packets discarded because of lost 
               buffers"
           ::= { linkEntry 8 }

       -- the Link Resource table

       linkResourceTable OBJECT-TYPE
           SYNTAX SEQUENCE OF LinkResourceEntry
           ACCESS not-accessible
           STATUS mandatory
           DESCRIPTION
               "A list of link resources."
           ::= { xLinkBasic 2 }

       linkResourceEntry OBJECT-TYPE
           SYNTAX LinkResourceEntry
           ACCESS not-accessible
           STATUS mandatory
           DESCRIPTION
               "link entry."
           INDEX { linkResourceType, ifIndex }
           ::= { linkResourceTable 1 }

       LinkResourceEntry ::=
           SEQUENCE {
               linkResourceType
                   INTEGER,
               linkResourceCurrent
                   Gauge,
               linkResourceHigh
                   Gauge,
               linkResourceAverage
                   Gauge
           }

       linkResourceType OBJECT-TYPE
           SYNTAX INTEGER { utilization(1), outputQueue(2) }
           ACCESS read-only
           STATUS mandatory
           DESCRIPTION
               "The resource type."
           ::= { linkResourceEntry 1 }

       linkResourceCurrent OBJECT-TYPE
           SYNTAX Gauge
           ACCESS read-only
           STATUS mandatory
           DESCRIPTION
               "The current percent of the resource used."
           ::= { linkResourceEntry 2 }

       linkResourceHigh OBJECT-TYPE
           SYNTAX Gauge
           ACCESS read-only
           STATUS mandatory
           DESCRIPTION
               "The highest percent of the resource used."
           ::= { linkResourceEntry 3 }

       linkResourceAverage OBJECT-TYPE
           SYNTAX Gauge
           ACCESS read-only
           STATUS mandatory
           DESCRIPTION
               "The average percent of the resource used."
           ::= { linkResourceEntry 4 }


       -- WAN group

       wanTable OBJECT-TYPE
           SYNTAX SEQUENCE OF WanEntry
           ACCESS not-accessible
           STATUS mandatory
           DESCRIPTION
               "A list of WANs."
           ::= { xWan 1 }

       wanEntry OBJECT-TYPE
           SYNTAX WanEntry
           ACCESS not-accessible
           STATUS mandatory
           DESCRIPTION
               "WAN entry."
           INDEX { ifIndex }
           ::= { wanTable 1 }

       WanEntry ::=
           SEQUENCE {
               wanProtocol
                   INTEGER,
               wanCompressionAdminStatus
                   INTEGER,
               wanMaxForwardDelay
                   INTEGER,
               wanMaxMultiForwardDelay
                   INTEGER,
               wanAdminSpeed
                   INTEGER,
               wanCompressionOperStatus
                   INTEGER
           }

       wanProtocol OBJECT-TYPE
           SYNTAX INTEGER { xcp(2), fr(3), ppp(4), frlmi(5),
                            fransi(6), frdcelmi(7), frdceansi(8),
                            x25(9) }
           ACCESS read-write
           STATUS mandatory
           DESCRIPTION
               "Controls the protocol run on the link, changes 
               ifType, typically to 'other'."
           DEFVAL { xcp }
           ::= { wanEntry 1 }

       wanCompressionAdminStatus OBJECT-TYPE
           SYNTAX INTEGER { noCompression(1), compress(2),
                            auto(256) }
           ACCESS read-write
           STATUS mandatory
           DESCRIPTION
               "Controls whether link compression will be run if 
               the link is running the xyplex protocol.  Auto will 
               enable compression for links slower than 67000."
           DEFVAL { auto }
           ::= { wanEntry 2 }

       wanMaxForwardDelay OBJECT-TYPE
       --  SYNTAX INTEGER ( 0 | 500..32000 )  (Preferred)
           SYNTAX INTEGER ( 0..32000 )
           ACCESS read-write
           STATUS mandatory
           DESCRIPTION
               "The number of milliseconds that a packet may be 
               held on the Wan link before it will be discarded.  
               The value 0 indicates no limit."
           DEFVAL { 1000 }
           ::= { wanEntry 3 }

       wanMaxMultiForwardDelay OBJECT-TYPE
       --  SYNTAX INTEGER ( 0 | 350..32000 )  (Preferred)
           SYNTAX INTEGER ( 0..32000 )
           ACCESS read-write
           STATUS mandatory
           DESCRIPTION
               "The number of milliseconds that a multicast packet 
               may  be held on the Wan link before it will be 
               discarded.  The value 0 indicates no delay."
           DEFVAL { 700 }
           ::= { wanEntry 4 }

       wanAdminSpeed OBJECT-TYPE
           SYNTAX INTEGER
           ACCESS read-write
           STATUS mandatory
           DESCRIPTION
               "The speed that the software should use for the wan 
               link. The value 0 indicates that the measured speed 
               should be used."
           DEFVAL { 0 }
           ::= { wanEntry 5 }

       wanCompressionOperStatus OBJECT-TYPE
           SYNTAX INTEGER { notCompressing(1), compressing(2) }
           ACCESS read-only
           STATUS mandatory
           DESCRIPTION
               "If the link is running the Xyplex protocol, 
               indicates whether link compression is running."
           ::= { wanEntry 6 }

END
