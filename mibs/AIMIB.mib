AIMIB DEFINITIONS ::=  BEGIN

-- Applied Innovation Incorporated MIB definitions

IMPORTS
		DisplayString FROM SNMPv2-TC
    MODULE-IDENTITY, OBJECT-TYPE, NOTIFICATION-TYPE,
    Counter32, Integer32,
    enterprises
	FROM SNMPv2-SMI
--    InterfaceIndex
--        FROM IF-MIB
    MODULE-COMPLIANCE, OBJECT-GROUP
	FROM SNMPv2-CONF;


-- group object IDs

aii		OBJECT IDENTIFIER ::= { enterprises 539 }
aiProxy		OBJECT IDENTIFIER ::= { aii 1 }
aiSystemOID	OBJECT IDENTIFIER ::= { aii 2 }
aiGroup		OBJECT IDENTIFIER ::= { aii 4 }
aiISISGre	OBJECT IDENTIFIER ::= { aii 5 }
aiManager	OBJECT IDENTIFIER ::= { aii 6 }
aiSoftware	OBJECT IDENTIFIER ::= { aii 7 }

-- System Group for AI.

aiSystem	OBJECT IDENTIFIER ::= { aii 8 }

aiHub   MODULE-IDENTITY
    LAST-UPDATED "9505081700Z"
    ORGANIZATION "Applied Innovation Incorporated"
    CONTACT-INFO
        "        Engineering MIB Administrator

        Postal:  Applied Innovation Inc.
                 5800 Innovation Drive
                 Dublin, OH 43016-3271

           Tel:  614/798-2000
           Fax:  614/798-1770
        E-mail:  snmp@aiinet.com"
    DESCRIPTION
        "The MIB Module for Ethernet hubs"
    ::= { aii 3 }

aiCLC	MODULE-IDENTITY
    LAST-UPDATED "9505081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for the Common Logic Controller (CLC)"
    ::= { aii 9 }

aiSLC	MODULE-IDENTITY
    LAST-UPDATED "9505081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for Smart Line Cards (SLC)"
    ::= { aii 10 }

aiSLC1	MODULE-IDENTITY
    LAST-UPDATED "9505081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for Series One Smart Line Cards (SLC)"
    ::= { aii 11 }

aiX1	MODULE-IDENTITY
    LAST-UPDATED "9505081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for Series One X.25 Smart Line Cards (SLC)"
    ::= { aii 12 }

-- -- -- -- -- -- -- -- -- -- -- -- -- -- -- -- -- -- -- -- --
-- The { aii 13 } branch represents an obsolete subtree.    --
-- This branch will not be re-used.                         --
-- -- -- -- -- -- -- -- -- -- -- -- -- -- -- -- -- -- -- -- --

aiTX1	MODULE-IDENTITY
    LAST-UPDATED "9505081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for Series One TCP/IP Smart Line Cards (SLC)"
    ::= { aii 14 }

aiTTL1	MODULE-IDENTITY
    LAST-UPDATED "9505081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for TTL1-196"
    ::= { aii 15 }

aiSLC2	MODULE-IDENTITY
    LAST-UPDATED "9702211700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for Series Two Smart Line Cards (SLC)"
    ::= { aii 16 }

aiEts	MODULE-IDENTITY
    LAST-UPDATED "9702211700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for E2A cards"
    ::= { aii 17 }

aiLpt	MODULE-IDENTITY
    LAST-UPDATED "9804081700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for ILEG cards"
    ::= { aii 18 }

aiSpy	MODULE-IDENTITY
    LAST-UPDATED "9905101700Z"
    ORGANIZATION "Applied Innovation Incorporated"
    CONTACT-INFO
	"        Engineering MIB Administrator

	Postal:  Applied Innovation Inc.
		 5800 Innovation Drive
		 Dublin, OH 43016-3271

	   Tel:	 614/798-2000
	   Fax:	 614/798-1770
	E-mail:  snmp@aiinet.com"
    DESCRIPTION
	"The MIB Module for the AISpy"
    ::= { aii 20 }

-- System group for all SLCs

aiSLCSystem	OBJECT IDENTIFIER ::= { aiSLC 1 }

-- System group for Series One Smart Line Cards

aiSLC1System	OBJECT IDENTIFIER ::= { aiSLC1 1 }

-- Group for all Series One X.25 Smart Line Cards (SLC)

aiX1System	OBJECT IDENTIFIER ::= { aiX1 1 }
aiX1Appl	OBJECT IDENTIFIER ::= { aiX1 2 }
aiX1Pkt		OBJECT IDENTIFIER ::= { aiX1 3 }
aiX1Frm		OBJECT IDENTIFIER ::= { aiX1 4 }
aiX1Phys	OBJECT IDENTIFIER ::= { aiX1 5 }
aiX1VC		OBJECT IDENTIFIER ::= { aiX1 6 }

-- Group for all Series Two X.25 Smart Line Cards (SLC)

aiPVC		OBJECT IDENTIFIER ::= { aiSLC2 1 }
aiLink		OBJECT IDENTIFIER ::= { aiSLC2 2 }
aiiSubnet	OBJECT IDENTIFIER ::= { aiSLC2 3 }
streams		OBJECT IDENTIFIER ::= { aiSLC2 4 }

-- Groups for all Series One TCP/IP Smart Line Cards (SLC)

aiTX1System	OBJECT IDENTIFIER ::= { aiTX1 1 }
aiTX1Calls	OBJECT IDENTIFIER ::= { aiTX1 2 }

-- sysObjectIDs

ai194		OBJECT IDENTIFIER ::= { aiSystemOID 194 }
ai194Ver7	OBJECT IDENTIFIER ::= { ai194 7 }
ai194Ver71	OBJECT IDENTIFIER ::= { ai194Ver7 1 }
ai194Ver72	OBJECT IDENTIFIER ::= { ai194Ver7 2 }
ai194Ver73	OBJECT IDENTIFIER ::= { ai194Ver7 3 }
ai194Ver74	OBJECT IDENTIFIER ::= { ai194Ver7 4 }

ai193		OBJECT IDENTIFIER ::= { aiSystemOID 193 }
ai193Ver7	OBJECT IDENTIFIER ::= { ai193 7 }
ai193Ver71	OBJECT IDENTIFIER ::= { ai193Ver7 1 }
ai193Ver72	OBJECT IDENTIFIER ::= { ai193Ver7 2 }
ai193Ver73	OBJECT IDENTIFIER ::= { ai193Ver7 3 }
ai193Ver74	OBJECT IDENTIFIER ::= { ai193Ver7 4 }
ai193Ver75	OBJECT IDENTIFIER ::= { ai193Ver7 5 }
ai193Ver76	OBJECT IDENTIFIER ::= { ai193Ver7 6 }
ai193Ver77	OBJECT IDENTIFIER ::= { ai193Ver7 7 }

ai193ES         OBJECT IDENTIFIER ::= { ai193 2 }
ai193ESVer7     OBJECT IDENTIFIER ::= { ai193ES 7 }
ai193ESVer70    OBJECT IDENTIFIER ::= { ai193ESVer7 0 }
ai193ESVer702   OBJECT IDENTIFIER ::= { ai193ESVer70 2 }
ai193ESVer703   OBJECT IDENTIFIER ::= { ai193ESVer70 3 }

aiMgrSysOID	OBJECT IDENTIFIER ::= { aiSystemOID 1 }
aiMgrSysOIDVer1	OBJECT IDENTIFIER ::= { aiMgrSysOID 1 }
aiMgrSysOIDVer2	OBJECT IDENTIFIER ::= { aiMgrSysOID 2 }

aiUProxy	OBJECT IDENTIFIER ::= { aiSystemOID 2 }
aiUProxyVer1	OBJECT IDENTIFIER ::= { aiUProxy 1 }

ai192		OBJECT IDENTIFIER ::= { aiSystemOID 192 }
ai192Ver7	OBJECT IDENTIFIER ::= { ai192 7 }
ai192Ver77	OBJECT IDENTIFIER ::= { ai192Ver7 7 }
ai192Ver70	OBJECT IDENTIFIER ::= { ai192Ver7 0 }
ai192Ver708	OBJECT IDENTIFIER ::= { ai192Ver70 8 }
ai192Ver709	OBJECT IDENTIFIER ::= { ai192Ver70 9 }
ai192Ver71	OBJECT IDENTIFIER ::= { ai192Ver7 1 }
ai192Ver710	OBJECT IDENTIFIER ::= { ai192Ver71 0 }
ai192Ver72	OBJECT IDENTIFIER ::= { ai192Ver7 2 }
ai192Ver720	OBJECT IDENTIFIER ::= { ai192Ver72 0 }

ai196		OBJECT IDENTIFIER ::= { aiSystemOID 196 }
ai196Ver7	OBJECT IDENTIFIER ::= { ai196 7 }
ai196Ver77	OBJECT IDENTIFIER ::= { ai196Ver7 7 }
ai196Ver70	OBJECT IDENTIFIER ::= { ai196Ver7 0 }
ai196Ver708	OBJECT IDENTIFIER ::= { ai196Ver70 8 }
ai196Ver709	OBJECT IDENTIFIER ::= { ai196Ver70 9 }
ai196Ver71	OBJECT IDENTIFIER ::= { ai196Ver7 1 }
ai196Ver710	OBJECT IDENTIFIER ::= { ai196Ver71 0 }
ai196Ver72	OBJECT IDENTIFIER ::= { ai196Ver7 2 }
ai196Ver720	OBJECT IDENTIFIER ::= { ai196Ver72 0 }

-- In the block below, ai198Ver101 and ai198Ver11 both refer to the v1.01 
-- release of AI198 firmware.  ai198Ver101 fits the pattern established for 
-- other releases, but the v1.01 SNMP agent returns ai198Ver11.
ai198		OBJECT IDENTIFIER ::= { aiSystemOID 198 }
ai198Ver1	OBJECT IDENTIFIER ::= { ai198 1 }
ai198Ver10	OBJECT IDENTIFIER ::= { ai198Ver1 0 }
ai198Ver101	OBJECT IDENTIFIER ::= { ai198Ver10 1 }
ai198Ver11	OBJECT IDENTIFIER ::= { ai198Ver1 1 }
ai198Ver102	OBJECT IDENTIFIER ::= { ai198Ver10 2 }
ai198Ver103	OBJECT IDENTIFIER ::= { ai198Ver10 3 }
ai198Ver104	OBJECT IDENTIFIER ::= { ai198Ver10 4 }
ai198Ver12	OBJECT IDENTIFIER ::= { ai198Ver1 2 }
ai198Ver120	OBJECT IDENTIFIER ::= { ai198Ver12 0 }
ai198Ver122	OBJECT IDENTIFIER ::= { ai198Ver12 2 }

ai195		OBJECT IDENTIFIER ::= { aiSystemOID 195 }
aiRTR		OBJECT IDENTIFIER ::= { ai195 1 }

aiMPR		OBJECT IDENTIFIER ::= { ai195 2 }
aiMPRVer1	OBJECT IDENTIFIER ::= { aiMPR 1 }

ai196IVer8	OBJECT IDENTIFIER ::= { ai196 8 }
ai196IVer80	OBJECT IDENTIFIER ::= { ai196IVer8 0 }
ai196IVer800	OBJECT IDENTIFIER ::= { ai196IVer80 0 }
ai196IVer801	OBJECT IDENTIFIER ::= { ai196IVer80 1 }
ai196IVer802	OBJECT IDENTIFIER ::= { ai196IVer80 2 }
ai196IVer81	OBJECT IDENTIFIER ::= { ai196IVer8 1 }
ai196IVer810	OBJECT IDENTIFIER ::= { ai196IVer81 0 }
ai196IVer82	OBJECT IDENTIFIER ::= { ai196IVer8 2 }
ai196IVer820	OBJECT IDENTIFIER ::= { ai196IVer82 0 }
ai196IVer83	OBJECT IDENTIFIER ::= { ai196IVer8 3 }
ai196IVer830	OBJECT IDENTIFIER ::= { ai196IVer83 0 }
ai196IVer831	OBJECT IDENTIFIER ::= { ai196IVer83 1 }

-- TBOS to TL1 product

ai196IEGB	OBJECT IDENTIFIER ::= { aiSystemOID 3 }
ai196IEGBVer1	OBJECT IDENTIFIER ::= { ai196IEGB 1 }
ai196IEGBVer10	OBJECT IDENTIFIER ::= { ai196IEGBVer1 0 }
ai196IEGBVer100	OBJECT IDENTIFIER ::= { ai196IEGBVer10 0 }
ai196IEGBVer101	OBJECT IDENTIFIER ::= { ai196IEGBVer10 1 }
ai196IEGBVer102	OBJECT IDENTIFIER ::= { ai196IEGBVer10 2 }

-- E2A product

ai196E2A	OBJECT IDENTIFIER ::= { aiSystemOID 4 }
ai196E2AVer1	OBJECT IDENTIFIER ::= { ai196E2A 1 }
ai196E2AVer10	OBJECT IDENTIFIER ::= { ai196E2AVer1 0 }
ai196E2AVer100	OBJECT IDENTIFIER ::= { ai196E2AVer10 0 }
ai196E2AVer101	OBJECT IDENTIFIER ::= { ai196E2AVer10 1 }

-- ILEG product

ai196ILEG	OBJECT IDENTIFIER ::= { aiSystemOID 5 }

-- AI193-FT product

ai193FT		OBJECT IDENTIFIER ::= { aiSystemOID 6 }

-- AI296 product

ai296	  	OBJECT IDENTIFIER ::= { aiSystemOID 7 }

-- AI285 product

ai285	  	OBJECT IDENTIFIER ::= { aiSystemOID 9 }

-- AIScout product

aiScout	  	OBJECT IDENTIFIER ::= { aiSystemOID 10 }

-- AISpy product

aiSpyOid  	OBJECT IDENTIFIER ::= { aiSystemOID 11 }

-- group object ID's 

aiGroup194	OBJECT IDENTIFIER ::= { aiGroup 194 }
aiGroup194Ver7	OBJECT IDENTIFIER ::= { aiGroup194 7 }
aiGroup194Ver71	OBJECT IDENTIFIER ::= { aiGroup194Ver7 1 }
aiGroup194Ver72	OBJECT IDENTIFIER ::= { aiGroup194Ver7 2 }
aiGroup194Ver73	OBJECT IDENTIFIER ::= { aiGroup194Ver7 3 }
aiGroup194Ver74	OBJECT IDENTIFIER ::= { aiGroup194Ver7 4 }

-- the AIManager group

aiManagerTrapString OBJECT-TYPE
    SYNTAX DisplayString
    ACCESS read-only
    STATUS mandatory
    DESCRIPTION
	"The string that is sent to xnmevents by aidaemon"
::= { aiManager 1 }

aiManagerEnterprise OBJECT-TYPE
    SYNTAX OBJECT IDENTIFIER
    ACCESS read-only
    STATUS mandatory
    DESCRIPTION
	"The agent's system object ID."
::= { aiManager 2 }

aiManagerCommunity OBJECT-TYPE
    SYNTAX DisplayString
    ACCESS read-only
    STATUS mandatory
    DESCRIPTION
	"The agent's community string."
::= { aiManager 3 }

END
