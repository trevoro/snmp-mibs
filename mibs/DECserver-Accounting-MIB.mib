--
-- DECserver Accounting MIB v1.0
--

DECserver-Accounting-MIB DEFINITIONS ::= BEGIN

    IMPORTS
	TRAP-TYPE FROM RFC-1215
        OBJECT-TYPE FROM RFC-1212
        DisplayString, sysUpTime FROM RFC1213-MIB
        Counter, TimeTicks, enterprises FROM RFC1155-SMI; 

    private  OBJECT IDENTIFIER ::= { enterprises 1 }
    dec          OBJECT IDENTIFIER ::= { private 36 }
    ema          OBJECT IDENTIFIER ::= { dec 2 }
    mib-extensions-1    OBJECT IDENTIFIER ::= { ema 18 }
    decServeraccounting OBJECT IDENTIFIER ::= { mib-extensions-1 12 }

    -- the acctSys group provides system wide accounting
    -- parameters

    acctSystem OBJECT IDENTIFIER ::= { decServeraccounting 1 }

    acctConsole OBJECT-TYPE
        SYNTAX INTEGER {
            disable(1),
            enable(2)
            }
        ACCESS read-write
        STATUS mandatory
        DESCRIPTION
           "This object controls whether the managed
            system displays the accounting events to the
	    server's console port as they occur. The value
            disable(1) means that it does not. The
            value enable(2) means that it does. 

            The value of this object persists across
            power cycles and reboots. Setting takes
            effect immediately."
        DEFVAL { disable }
        ::= { acctSystem 1 }

    acctAdminLogSize OBJECT-TYPE
        SYNTAX INTEGER {
            none(1),
            size4K(2),
            size8K(3),
            size16K(4),
            size32K(5),
            size64K(6),
            size128K(7),
            size256K(8),
            size512K(9)
            }
        ACCESS read-write
        STATUS mandatory
        DESCRIPTION
           "This object controls the total number of
            bytes the managed system allocates for all
            accounting records. The value size4K(1)
            means the managed system allocates 4K bytes
            for the accounting table, etc. 

            The value of this object persists across
            power cycles and reboots of the managed
            system. Setting it via SNMP has no effect
            until the managed system again reboots."
        DEFVAL { size16K }
        ::= { acctSystem 2 }

    acctOperLogSize OBJECT-TYPE
        SYNTAX INTEGER {
            none(1),
            size4K(2),
            size8K(3),
            size16K(4),
            size32K(5),
            size64K(6),
            size128K(7),
            size256K(8),
            size512K(9)
            }
        ACCESS read-only
        STATUS mandatory
        DESCRIPTION
           "This object specifies the total number of
            bytes the managed system has allocated for all
            accounting records. The value size4K(1) means
            the managed system allocated 4K bytes for
            the accounting table, etc."
        ::= { acctSystem 3 }

    acctThreshold OBJECT-TYPE
        SYNTAX INTEGER {
            none(1),
            end(2),
            half(3),
            quarter(4),
            eighth(5)
            }
        ACCESS read-write
        STATUS mandatory
        DESCRIPTION
           "This object controls when the managed
            system generates an accounting trap. A trap 
            will be generated by the managed system whenever 
            logging another record will take it beyond the
            specified physical points in the log. For example,
            the value quarter(4) causes the managed system to 
            generate a trap when logging an entry takes it beyond
            the 1/4, 1/2, 3/4, or end of the log.

            The managed system maintains the value
            of this object across power-cycles and
            reboots, although setting it changes the
            behavior of the managed system
            immediately."
        DEFVAL { none }
        ::= { acctSystem 4 }

    -- The acctTable group represents an accounting log.

    acctTable OBJECT-TYPE
        SYNTAX SEQUENCE OF AcctEntry
        ACCESS not-accessible
        STATUS mandatory
        DESCRIPTION
           "The list of all accounting records at this
            managed system."
        ::= { decServeraccounting 2 }

    acctEntry OBJECT-TYPE
        SYNTAX AcctEntry
        ACCESS not-accessible
        STATUS mandatory
        DESCRIPTION
           "An accounting record for this managed
            system. The system automatically creates
            this record in response to an action
            which accounting requires to be logged."
        INDEX { acctEntryNonce1, acctEntryNonce2 }
        ::= { acctTable 1 }

    AcctEntry ::= SEQUENCE {
        acctEntryNonce1 INTEGER,
        acctEntryNonce2 INTEGER,
        acctEntryTime TimeTicks,
        acceEntryEvent INTEGER,
        acctEntryPort INTEGER,
        acctEntryUser DisplayString,
        acctEntrySessionId INTEGER,
        acctEntryProtocol INTEGER,
        acctEntryAccess INTEGER,
        acctEntryPeer DisplayString,
        acctEntryReason INTEGER,
        acctEntrySentBytes Counter,
        acctEntryReceivedBytes Counter
        }

    acctEntryNonce1 OBJECT-TYPE
        SYNTAX INTEGER (1..65535)
        ACCESS read-only
        STATUS mandatory
        DESCRIPTION
           "A number which, in combination with acctNonce2,
            distinguishes this object's entry from all
            others."
        ::= { acctEntry 1 }

    acctEntryNonce2 OBJECT-TYPE
        SYNTAX INTEGER (1..65535)
        ACCESS read-only
        STATUS mandatory
        DESCRIPTION
           "A number which, in combination with acctNonce1,
            distinguishes this object's entry from all
            others."
        ::= { acctEntry 2 }

    acctEntryTime OBJECT-TYPE
        SYNTAX TimeTicks
        ACCESS read-only
        STATUS mandatory
        DESCRIPTION
           "The value of the MIB-II sysUpTime object at
            which the managed system created this accounting
            log entry."
        ::= { acctEntry 3 }

    acctEntryEvent OBJECT-TYPE
        SYNTAX INTEGER {
            other(1),
            logIn(2),
            logOut(3),
            sessionConnect(4),
            sessionDisconnect(5),
            kerberosPasswordFail(6),
            privilegedPasswordFail(7),
            maintenancePasswordFail(8),
            loginPasswordFail(9),
	    remotePasswordFail(10),
            communityFail(11),
            privilegedPasswordModified(12),
            maintenacePasswordModified(13),
            loginPasswordModified(14),
	    remotePasswordModified(15),
            privilegeLevelModified(16),
            communityModified(17)
            }
        ACCESS read-only
        STATUS mandatory
        DESCRIPTION
           "This object identifies the record type
            associated with its entry. The value logIn(2)
            identifies the entry as a log-in record. The
            value logOut(3) identifies the entry as a
            log-out record. The value sessionConnect(4) means
            the entry is a connect attempt record. The
            value sessionDisconnect(5) means the record is a
            disconnect record. For all password fail events (6-10),
            the value identifies the entry as a record flagging a 
            failure to correctly provide the associated password.
            The value communityFail(11) identifies the record as 
            flagging a failure to provide a valid community in an 
            SNMP request. For all password modify events (12-16),
            the value identifies the entry as a record flagging a 
            modification to an associated password. The value 
            communityModified(17) indicates that the SNMP community 
            data base at the managed system has been modified. The value 
            other(1) indicates that some other event has occured."
        ::= { acctEntry 4 }

    acctEntryPort OBJECT-TYPE
        SYNTAX INTEGER
        ACCESS read-only
        STATUS mandatory
        DESCRIPTION
           "The port to which this entry applies. Its
            value is -1 when the managed system can
            associate the record with no port."
        ::= { acctEntry 5 }

    acctEntryUser OBJECT-TYPE
        SYNTAX DisplayString
        ACCESS read-only
        STATUS mandatory
        DESCRIPTION
           "The username associated with the logged-in port. 
            If the managed system can attribute no name to 
            the entry, the value of this object is the NULL string."
        ::= { acctEntry 6 }

    acctEntrySessionId OBJECT-TYPE
        SYNTAX INTEGER
        ACCESS read-only
        STATUS mandatory
        DESCRIPTION
           "The id of the session associated with this
            record. If the managed system associates no
            session with this accounting record, this
            object's value is -1."
        ::= { acctEntry 7 }

    acctEntryProtocol OBJECT-TYPE
        SYNTAX INTEGER {
            none(1),
            lat(2),
            telnet(3),
            slip(4),
            ping(5),
            mop(6),
            ppp(7),
            tn3270(8),
            autolink(9),
            snmp-ip(10),
            other(11)
            }
        ACCESS read-only
        STATUS mandatory
        DESCRIPTION
           "This object indicates the protocol associated
            with its entry. Its value is none(1) when the entry
            is not a connect or disconnect record.  The
            value other(11) applies to other session types than
            the ones specified above."
        ::= { acctEntry 8 }

    acctEntryAccess OBJECT-TYPE
        SYNTAX INTEGER {
            notApplicable(1),
            local(2),
            remote(3)
            }
        ACCESS read-only
        STATUS mandatory
        DESCRIPTION
           "This object indicates its entry's access. The
            value local(2) means the record is associated
            with a local access log-in or session connect. 
            The value remote(3) indicates the record is 
            associated with a remote access log-in or session
            connect. The value notApplicable(1) means the 
            entry is not a log-in or session connection record."
        ::= { acctEntry 9 }

    acctEntryPeer OBJECT-TYPE
        SYNTAX DisplayString
        ACCESS read-only
        STATUS mandatory
        DESCRIPTION
           "This object identifies the peer associated
            with the session connect, maintenance password
            fail or community fail events. The value is the NULL
            string for entries corresponding to other record
            types."
        ::= { acctEntry 10 }

    acctEntryReason OBJECT-TYPE
        SYNTAX INTEGER {
             notApplicable(1),
             normal(2),
             error(3),
             other(4)
             } 
        ACCESS read-only
        STATUS mandatory
        DESCRIPTION
           "This object indicates the session disconnect 
            reason for its entry. The value notApplicable(1)
            means that it is not a session disconnect event.
            The value normal(2) means that the session
            disconnect occured under normal circumstances.
            The value error(3) means that an error or some
            abnormal event occured to  disconnect the
            session. The value other(4) applies to  other
            disconnect reasons."
        ::= { acctEntry 11 }

    acctEntrySentBytes OBJECT-TYPE
        SYNTAX Counter
        ACCESS read-only
        STATUS mandatory
        DESCRIPTION
           "The number of bytes sent when this object's entry
            represents a session disconnect or logout, and 0 otherwise."
        ::= { acctEntry 12 }

    acctEntryReceivedBytes OBJECT-TYPE
        SYNTAX Counter
        ACCESS read-only
        STATUS mandatory
        DESCRIPTION
           "The number of bytes received when this object's
            entry represents a session disconnect or logout, and 0
            otherwise."
        ::= { acctEntry 13 }

    -- the acctTraps group specifies traps the
    -- accounting subsystem can generate

    acctTraps OBJECT IDENTIFIER ::= { decServeraccounting 3 }

    acctThresholdExceeded TRAP-TYPE
        ENTERPRISE acctTraps
        VARIABLES {
            sysUpTime,
            acctThreshold
            }
        DESCRIPTION
           "This trap reports that the managed system
            has crossed the configured threshold."
        ::= 1

END
