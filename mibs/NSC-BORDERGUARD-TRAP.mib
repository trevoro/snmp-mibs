-- *****************************************
-- Network System Corporation Enterprise MIB
-- *****************************************
--
-- Title:           NSC-BORDERGUARD-TRAP
-- Purpose:         This MIB defines SNMP traps which are specific to 
--                  BorderGuard Access Router.
-- Required MIBs:   nsc.mib
--
-- Version:         1.0
-- 1st revision:    Feb. 10, 1995     Raymond Lu


NSC-BORDERGUARD-TRAP DEFINITIONS ::= BEGIN

IMPORTS
	nscBorderGuard		FROM NSC-MIB
        OBJECT-TYPE             FROM RFC-1212
	DisplayString		FROM RFC1213-MIB
        TRAP-TYPE               FROM RFC-1215;



nscBorderGuardTraps 	OBJECT IDENTIFIER ::= { nscBorderGuard 1 }

nscBorderGuardTrapsBadImage	OBJECT-TYPE
       	SYNTAX	INTEGER   
	ACCESS	not-accessible
	STATUS	mandatory
	DESCRIPTION
          "This represents the image with bad CRC."

	::= { nscBorderGuardTraps 1 }

nscBorderGuardTrapsCurrentImage	OBJECT-TYPE
       	SYNTAX	INTEGER   
	ACCESS	not-accessible
	STATUS	mandatory
	DESCRIPTION
          "This represents the image currently running in the system."

	::= { nscBorderGuardTraps 2 }

nscBorderGuardTrapsBadFileSystem	OBJECT-TYPE
       	SYNTAX	INTEGER   
	ACCESS	not-accessible
	STATUS	mandatory
	DESCRIPTION
          "This represents the file system with an erased condition."

	::= { nscBorderGuardTraps 3 }

nscBorderGuardTrapsSoftFault	OBJECT-TYPE
       	SYNTAX	INTEGER   
	ACCESS	not-accessible
	STATUS	mandatory
	DESCRIPTION
          "This represents the code for a Soft Fault."

	::= { nscBorderGuardTraps 4 }

nscBorderGuardTrapsEventReason	OBJECT-TYPE
       	SYNTAX	DisplayString (SIZE (1..255))   
	ACCESS	not-accessible
	STATUS	mandatory
	DESCRIPTION
          "This represents the reason (in ASCII text) of a 
           BorderGuarder Access Router event."

	::= { nscBorderGuardTraps 5 }


--
-- Traps for Border Guard Access Router
--



nscBorderGuardBadCRC  TRAP-TYPE
	ENTERPRISE  nscBorderGuardTraps
        VARIABLES   { nscBorderGuardTrapsBadImage,
                      nscBorderGuardTrapsCurrentImage,
                      nscBorderGuardTrapsEventReason }
	DESCRIPTION
	"This trap indicates that a corrupted image occured."
	::= 1

nscBorderGuardBadFileSystem  TRAP-TYPE
	ENTERPRISE  nscBorderGuardTraps
        VARIABLES   { nscBorderGuardTrapsBadFileSystem,
                      nscBorderGuardTrapsEventReason }
	DESCRIPTION
	"This trap indicates that a file system was erased."
	::= 2

nscBorderGuardSoftFault  TRAP-TYPE
	ENTERPRISE  nscBorderGuardTraps
        VARIABLES   { nscBorderGuardTrapsSoftFault,
                      nscBorderGuardTrapsEventReason }
	DESCRIPTION
	"This trap indicates that a soft fault occured."
	::= 3


END
