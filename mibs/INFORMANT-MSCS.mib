INFORMANT-MSCS DEFINITIONS ::= BEGIN

IMPORTS
    MODULE-IDENTITY, OBJECT-IDENTITY, OBJECT-TYPE, Gauge32, Integer32
        FROM SNMPv2-SMI
    TruthValue, DisplayString
        FROM SNMPv2-TC
    informant, InstanceName
        FROM WTCS;

mscs MODULE-IDENTITY
    LAST-UPDATED "200504291751Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant standard entities."
    REVISION      "200504291751Z"
    DESCRIPTION
            "The initial revision of this MIB module."
    ::= { informant 31 }

mscsCluster OBJECT-IDENTITY
    STATUS     current
    DESCRIPTION
        "The Cluster object enables operations on the cluster and provides
        access to all of the objects in the cluster."
    ::= { mscs 1 }

mscsClusterBuildNumber OBJECT-TYPE
    SYNTAX     Integer32
    MAX-ACCESS read-only
    STATUS     current
    DESCRIPTION
        "The BuildNumber property returns the build number of the operating
        system installed on the local node."
    ::= { mscsCluster 1 }

mscsClusterHighestVersion OBJECT-TYPE
    SYNTAX     Integer32
    MAX-ACCESS read-only
    STATUS     current
    DESCRIPTION
        "The ClusterHighestVersion property returns a value containing the
        highest version of the Cluster service with which the current
        cluster is compatible.
        
        Long that receives the version value. The upper 16 bits of the
        value indicate the release number of the Cluster service. The lower
        16 bits specify the build number of the Cluster service."
    ::= { mscsCluster 2 }

mscsClusterLowestVersion OBJECT-TYPE
    SYNTAX     Integer32
    MAX-ACCESS read-only
    STATUS     current
    DESCRIPTION
        "The ClusterLowestVersion property returns a value containing the
        lowest version of the Cluster service with which the current
        cluster is compatible.
        
        Long that receives the version value. The upper 16 bits of the
        value indicate the release number of the Cluster service. The lower
        16 bits specify the build number of the Cluster service."
    ::= { mscsCluster 3 }

mscsClusterCSDVersion OBJECT-TYPE
    SYNTAX     DisplayString
    MAX-ACCESS read-only
    STATUS     current
    DESCRIPTION
        "The CSDVersion property returns the number of the latest service
        pack installed on the local node."
    ::= { mscsCluster 4 }

mscsClusterFlags OBJECT-TYPE
    SYNTAX     Integer32
    MAX-ACCESS read-only
    STATUS     current
    DESCRIPTION
        "The Flags property returns flags associated with the cluster
        version."
    ::= { mscsCluster 5 }

mscsClusterMajorVersion OBJECT-TYPE
    SYNTAX     Integer32
    MAX-ACCESS read-only
    STATUS     current
    DESCRIPTION
        "The MajorVersion property returns the integer portion of the
        version number for the operating system installed on the local
        node."
    ::= { mscsCluster 6 }

mscsClusterMinorVersion OBJECT-TYPE
    SYNTAX     Integer32
    MAX-ACCESS read-only
    STATUS     current
    DESCRIPTION
        "The MinorVersion property returns the decimal portion of the
        version of the operating system installed on the local node."
    ::= { mscsCluster 7 }

mscsClusterMixedVersion OBJECT-TYPE
    SYNTAX     TruthValue
    MAX-ACCESS read-only
    STATUS     current
    DESCRIPTION
        "The MixedVersion property indicates whether more than one version
        of the Cluster service is present in the cluster, a state described
        as mixed mode."
    ::= { mscsCluster 8 }

mscsClusterName OBJECT-TYPE
    SYNTAX     DisplayString
    MAX-ACCESS read-only
    STATUS     current
    DESCRIPTION
        "The Name property returns the name of the cluster."
    ::= { mscsCluster 9 }

mscsClusterQuorumLogSize OBJECT-TYPE
    SYNTAX     Integer32
    MAX-ACCESS read-only
    STATUS     current
    DESCRIPTION
        "The QuorumLogSize property returns or sets the maximum size of the
        log file maintained by the quorum resource."
    ::= { mscsCluster 10 }

mscsClusterQuorumPath OBJECT-TYPE
    SYNTAX     DisplayString
    MAX-ACCESS read-only
    STATUS     current
    DESCRIPTION
        "The QuorumPath property retrieves or sets the path to the log file
        maintained by the quorum resource."
    ::= { mscsCluster 11 }

mscsClusterVendorId OBJECT-TYPE
    SYNTAX     DisplayString
    MAX-ACCESS read-only
    STATUS     current
    DESCRIPTION
        "The VendorId property returns vendor information about the Cluster
        service installed on the local node."
    ::= { mscsCluster 12 }

mscsClusterDefaultNetworkRole OBJECT-TYPE
    SYNTAX     INTEGER {
        none(0),
        internalUse(1),
        clientAccess(2),
        internalAndClient(3)
    }
    MAX-ACCESS read-only
    STATUS     current
    DESCRIPTION
        "The DefaultNetworkRole property specifies the Role
        that the cluster automatically assigns to any newly
        discovered or created network."
    ::= { mscsCluster 13 }

mscsClusterDescription OBJECT-TYPE
    SYNTAX     DisplayString
    MAX-ACCESS read-only
    STATUS     current
    DESCRIPTION
        "The Description property stores administrative
        comments about the cluster. The following table
        summarizes the attributes of the Description
        property."
    ::= { mscsCluster 14 }

mscsClusterPropertiesTable OBJECT-TYPE
    SYNTAX     SEQUENCE OF ClusPropertiesEntry
    MAX-ACCESS not-accessible
    STATUS     current
    DESCRIPTION
        "A list of properties associated with this
        cluster."
    ::= { mscs 2 }

mscsClusterPropertiesEntry OBJECT-TYPE
    SYNTAX     ClusPropertiesEntry
    MAX-ACCESS not-accessible
    STATUS     current
    DESCRIPTION
        "Information on one particular property."
    INDEX      { mscsClusterPropertiesIndex }
    ::= { mscsClusterPropertiesTable 1 }

ClusPropertiesEntry ::= SEQUENCE {
    mscsClusterPropertiesIndex Integer32,
    mscsClusterPropertiesName DisplayString,
    mscsClusterPropertiesValue DisplayString
}

mscsClusterPropertiesIndex OBJECT-TYPE
    SYNTAX     Integer32 (1..2147483647)
    MAX-ACCESS read-only
    STATUS     current
    DESCRIPTION
        "A unique value for each property."
    ::= { mscsClusterPropertiesEntry 1 }

mscsClusterPropertiesName OBJECT-TYPE
    SYNTAX     DisplayString
    MAX-ACCESS read-only
    STATUS     current
    DESCRIPTION
        "Returns the property name."
    ::= { mscsClusterPropertiesEntry 2 }

mscsClusterPropertiesValue OBJECT-TYPE
    SYNTAX     DisplayString
    MAX-ACCESS read-only
    STATUS     current
    DESCRIPTION
        "Returns the property value as a string."
    ::= { mscsClusterPropertiesEntry 3 }

mscsNetInterfaceTable OBJECT-TYPE
    SYNTAX     SEQUENCE OF ClusNetInterfaceEntry
    MAX-ACCESS not-accessible
    STATUS     current
    DESCRIPTION
        "This collection provides access to the network
        interfaces in a cluster."
    ::= { mscs 3 }

mscsNetInterfaceEntry OBJECT-TYPE
    SYNTAX     ClusNetInterfaceEntry
    MAX-ACCESS not-accessible
    STATUS     current
    DESCRIPTION
        "Information about one particular
        'ClusNetInterfaces'"
    INDEX      { mscsNetInterfaceNameIndex }
    ::= { mscsNetInterfaceTable 1 }

ClusNetInterfaceEntry ::= SEQUENCE {
    mscsNetInterfaceNameIndex InstanceName,
    mscsNetInterfaceNameFull DisplayString,
    mscsNetInterfaceState INTEGER,
    mscsNetInterfaceAdapter DisplayString,
    mscsNetInterfaceAddress DisplayString,
    mscsNetInterfaceDescription DisplayString,
    mscsNetInterfaceNetwork DisplayString,
    mscsNetInterfaceNode DisplayString
}

mscsNetInterfaceNameIndex OBJECT-TYPE
    SYNTAX     InstanceName
    MAX-ACCESS read-only
    STATUS     current
    DESCRIPTION
        "The index name is the same as the full name but
        truncated to 64 characters and made unique."
    ::= { mscsNetInterfaceEntry 1 }

mscsNetInterfaceNameFull OBJECT-TYPE
    SYNTAX     DisplayString
    MAX-ACCESS read-only
    STATUS     current
    DESCRIPTION
        "The Name property provides the Clustering
        Service-generated name for the network interface."
    ::= { mscsNetInterfaceEntry 2 }

mscsNetInterfaceState OBJECT-TYPE
    SYNTAX     INTEGER {
        unknown(-1),
        unavailable(0),
        failed(1),
        unreachable(2),
        up(3)
    }
    MAX-ACCESS read-only
    STATUS     current
    DESCRIPTION
        "Indicates the current state of the network
        interface."
    ::= { mscsNetInterfaceEntry 3 }

mscsNetInterfaceAdapter OBJECT-TYPE
    SYNTAX     DisplayString
    MAX-ACCESS read-only
    STATUS     current
    DESCRIPTION
        "The Adapter property provides the name that is
        used to uniquely identify the network interface in
        the cluster."
    ::= { mscsNetInterfaceEntry 4 }

mscsNetInterfaceAddress OBJECT-TYPE
    SYNTAX     DisplayString
    MAX-ACCESS read-only
    STATUS     current
    DESCRIPTION
        "The Address property provides the primary network
        address that the node uses for the network
        interface."
    ::= { mscsNetInterfaceEntry 5 }

mscsNetInterfaceDescription OBJECT-TYPE
    SYNTAX     DisplayString
    MAX-ACCESS read-only
    STATUS     current
    DESCRIPTION
        "The Description property provides comments about
        the network interface."
    ::= { mscsNetInterfaceEntry 6 }

mscsNetInterfaceNetwork OBJECT-TYPE
    SYNTAX     DisplayString
    MAX-ACCESS read-only
    STATUS     current
    DESCRIPTION
        "The Network property provides the name of the
        network to which the network interface is
        connected."
    ::= { mscsNetInterfaceEntry 7 }

mscsNetInterfaceNode OBJECT-TYPE
    SYNTAX     DisplayString
    MAX-ACCESS read-only
    STATUS     current
    DESCRIPTION
        "The Node property provides the name of the node in
        which the network interface is installed."
    ::= { mscsNetInterfaceEntry 8 }

mscsNetInterfacePropertiesTable OBJECT-TYPE
    SYNTAX     SEQUENCE OF ClusNetInterfacePropertiesEntry
    MAX-ACCESS not-accessible
    STATUS     current
    DESCRIPTION
        "A list of properties associated with a network
        interface."
    ::= { mscs 4 }

mscsNetInterfacePropertiesEntry OBJECT-TYPE
    SYNTAX     ClusNetInterfacePropertiesEntry
    MAX-ACCESS not-accessible
    STATUS     current
    DESCRIPTION
        "Information on one particular property."
    INDEX      { mscsNetInterfaceNameIndex, mscsNetInterfacePropertiesIndex }
    ::= { mscsNetInterfacePropertiesTable 1 }

ClusNetInterfacePropertiesEntry ::= SEQUENCE {
    mscsNetInterfacePropertiesIndex Integer32,
    mscsNetInterfacePropertiesName DisplayString,
    mscsNetInterfacePropertiesValue DisplayString
}

mscsNetInterfacePropertiesIndex OBJECT-TYPE
    SYNTAX     Integer32 (1..2147483647)
    MAX-ACCESS read-only
    STATUS     current
    DESCRIPTION
        "A unique value for each property."
    ::= { mscsNetInterfacePropertiesEntry 1 }

mscsNetInterfacePropertiesName OBJECT-TYPE
    SYNTAX     DisplayString
    MAX-ACCESS read-only
    STATUS     current
    DESCRIPTION
        "Returns the property name."
    ::= { mscsNetInterfacePropertiesEntry 2 }

mscsNetInterfacePropertiesValue OBJECT-TYPE
    SYNTAX     DisplayString
    MAX-ACCESS read-only
    STATUS     current
    DESCRIPTION
        "Returns the property value as a string."
    ::= { mscsNetInterfacePropertiesEntry 3 }

mscsNetworkTable OBJECT-TYPE
    SYNTAX     SEQUENCE OF ClusNetworkEntry
    MAX-ACCESS not-accessible
    STATUS     current
    DESCRIPTION
        "This collection provides access to the networks in
        a cluster."
    ::= { mscs 5 }

mscsNetworkEntry OBJECT-TYPE
    SYNTAX     ClusNetworkEntry
    MAX-ACCESS not-accessible
    STATUS     current
    DESCRIPTION
        "Information about one particular 'ClusNetworks'"
    INDEX      { mscsNetworkNameIndex }
    ::= { mscsNetworkTable 1 }

ClusNetworkEntry ::= SEQUENCE {
    mscsNetworkNameIndex InstanceName,
    mscsNetworkNameFull DisplayString,
    mscsNetworkNetInterfaces DisplayString,
    mscsNetworkNetworkID DisplayString,
    mscsNetworkState INTEGER,
    mscsNetworkAddress DisplayString,
    mscsNetworkAddressMask DisplayString,
    mscsNetworkDescription DisplayString,
    mscsNetworkRole INTEGER
}

mscsNetworkNameIndex OBJECT-TYPE
    SYNTAX     InstanceName
    MAX-ACCESS read-only
    STATUS     current
    DESCRIPTION
        "The index name is the same as the full name but
        truncated to 64 characters and made unique."
    ::= { mscsNetworkEntry 1 }

mscsNetworkNameFull OBJECT-TYPE
    SYNTAX     DisplayString
    MAX-ACCESS read-only
    STATUS     current
    DESCRIPTION
        "The Name property retrieves the name of a
        network."
    ::= { mscsNetworkEntry 2 }

mscsNetworkNetInterfaces OBJECT-TYPE
    SYNTAX     DisplayString
    MAX-ACCESS read-only
    STATUS     current
    DESCRIPTION
        "The NetInterfaces property returns the list of
        network interface names associated with this
        network."
    ::= { mscsNetworkEntry 3 }

mscsNetworkNetworkID OBJECT-TYPE
    SYNTAX     DisplayString
    MAX-ACCESS read-only
    STATUS     current
    DESCRIPTION
        "The NetworkID property returns the unique network
        identifier for a network."
    ::= { mscsNetworkEntry 4 }

mscsNetworkState OBJECT-TYPE
    SYNTAX     INTEGER {
        unknown(-1),
        unavailable(0),
        down(1),
        partitioned(2),
        up(3)
    }
    MAX-ACCESS read-only
    STATUS     current
    DESCRIPTION
        "Current state of the network."
    ::= { mscsNetworkEntry 5 }

mscsNetworkAddress OBJECT-TYPE
    SYNTAX     DisplayString
    MAX-ACCESS read-only
    STATUS     current
    DESCRIPTION
        "The Address property provides the address for the
        entire network or subnet. The Address property does
        not specify the address of an individual node. The
        data is formatted as xxx.xxx.xxx.xxx where xxx
        represents a decimal number between 0 and 255."
    ::= { mscsNetworkEntry 6 }

mscsNetworkAddressMask OBJECT-TYPE
    SYNTAX     DisplayString
    MAX-ACCESS read-only
    STATUS     current
    DESCRIPTION
        "The AddressMask property provides the mask that
        distinguishes the network and host portions of an
        address. The data in the AddressMask property is
        formatted as xxx.xxx.xxx.xxx where xxx represents a
        decimal number between 0 and 255."
    ::= { mscsNetworkEntry 7 }

mscsNetworkDescription OBJECT-TYPE
    SYNTAX     DisplayString
    MAX-ACCESS read-only
    STATUS     current
    DESCRIPTION
        "The Description property provides comments about
        the network."
    ::= { mscsNetworkEntry 8 }

mscsNetworkRole OBJECT-TYPE
    SYNTAX     INTEGER {
        none(0),
        unternalUse(1),
        clientAccess(2),
        internalAndClient(3)
    }
    MAX-ACCESS read-only
    STATUS     current
    DESCRIPTION
        "The Role property provides the role of the network
        in the cluster."
    ::= { mscsNetworkEntry 9 }

mscsNetworkPropertiesTable OBJECT-TYPE
    SYNTAX     SEQUENCE OF ClusNetworkPropertiesEntry
    MAX-ACCESS not-accessible
    STATUS     current
    DESCRIPTION
        "A list of properties associated with a network."
    ::= { mscs 6 }

mscsNetworkPropertiesEntry OBJECT-TYPE
    SYNTAX     ClusNetworkPropertiesEntry
    MAX-ACCESS not-accessible
    STATUS     current
    DESCRIPTION
        "Information on one particular property."
    INDEX      { mscsNetworkNameIndex, mscsNetworkPropertiesIndex }
    ::= { mscsNetworkPropertiesTable 1 }

ClusNetworkPropertiesEntry ::= SEQUENCE {
    mscsNetworkPropertiesIndex Integer32,
    mscsNetworkPropertiesName DisplayString,
    mscsNetworkPropertiesValue DisplayString
}

mscsNetworkPropertiesIndex OBJECT-TYPE
    SYNTAX     Integer32 (1..2147483647)
    MAX-ACCESS read-only
    STATUS     current
    DESCRIPTION
        "A unique value for each property."
    ::= { mscsNetworkPropertiesEntry 1 }

mscsNetworkPropertiesName OBJECT-TYPE
    SYNTAX     DisplayString
    MAX-ACCESS read-only
    STATUS     current
    DESCRIPTION
        "Returns the property name."
    ::= { mscsNetworkPropertiesEntry 2 }

mscsNetworkPropertiesValue OBJECT-TYPE
    SYNTAX     DisplayString
    MAX-ACCESS read-only
    STATUS     current
    DESCRIPTION
        "Returns the property value as a string."
    ::= { mscsNetworkPropertiesEntry 3 }

mscsNodeTable OBJECT-TYPE
    SYNTAX     SEQUENCE OF ClusNodeEntry
    MAX-ACCESS not-accessible
    STATUS     current
    DESCRIPTION
        "This collection provides access to the nodes in a
        cluster."
    ::= { mscs 7 }

mscsNodeEntry OBJECT-TYPE
    SYNTAX     ClusNodeEntry
    MAX-ACCESS not-accessible
    STATUS     current
    DESCRIPTION
        "Information about one particular 'ClusNodes'"
    INDEX      { mscsNodeNameIndex }
    ::= { mscsNodeTable 1 }

ClusNodeEntry ::= SEQUENCE {
    mscsNodeNameIndex InstanceName,
    mscsNodeNameFull DisplayString,
    mscsNodeNetInterfaces DisplayString,
    mscsNodeNodeID  DisplayString,
    mscsNodeState INTEGER,
    mscsNodeBuildNumber Gauge32,
    mscsNodeCSDVersion DisplayString,
    mscsNodeDescription DisplayString,
    mscsNodeEnableEventLogReplicate TruthValue,
    mscsNodeMajorVersion Gauge32,
    mscsNodeMinorVersion Gauge32,
    mscsNodeHighestVersion Gauge32,
    mscsNodeLowestVersion Gauge32
}

mscsNodeNameIndex OBJECT-TYPE
    SYNTAX     InstanceName
    MAX-ACCESS read-only
    STATUS     current
    DESCRIPTION
        "The index name is the same as the full name but
        truncated to 64 characters and made unique."
    ::= { mscsNodeEntry 1 }

mscsNodeNameFull OBJECT-TYPE
    SYNTAX     DisplayString
    MAX-ACCESS read-only
    STATUS     current
    DESCRIPTION
        "The Name property retrieves the name of a node."
    ::= { mscsNodeEntry 2 }

mscsNodeNetInterfaces OBJECT-TYPE
    SYNTAX     DisplayString
    MAX-ACCESS read-only
    STATUS     current
    DESCRIPTION
        "The NetInterfaces property returns a
        ClusNodeNetInterfaces collection providing access
        to the network interfaces installed on a node."
    ::= { mscsNodeEntry 3 }

mscsNodeNodeID  OBJECT-TYPE
    SYNTAX     DisplayString
    MAX-ACCESS read-only
    STATUS     current
    DESCRIPTION
        "The NodeID property returns the unique identifier
        of a cluster node."
    ::= { mscsNodeEntry 4 }

mscsNodeState OBJECT-TYPE
    SYNTAX     INTEGER {
        unknown(-1),
        up(0),
        down(1),
        paused(2),
        joining(3)
    }
    MAX-ACCESS read-only
    STATUS     current
    DESCRIPTION
        "The State property retrieves the state of a node."
    ::= { mscsNodeEntry 5 }

mscsNodeBuildNumber OBJECT-TYPE
    SYNTAX     Gauge32
    MAX-ACCESS read-only
    STATUS     current
    DESCRIPTION
        "The BuildNumber property specifies the build
        number of Windows NT or Windows 2000 installed on a
        node.
        
        The version of Windows installed on a node is fully
        described by the following properties:
        MajorVersion
        MinorVersion
        CSDVersion"
    ::= { mscsNodeEntry 6 }

mscsNodeCSDVersion OBJECT-TYPE
    SYNTAX     DisplayString
    MAX-ACCESS read-only
    STATUS     current
    DESCRIPTION
        "The CSDVersion property specifies the name of the
        most recent service pack installed on the node (if
        any).
        
        The version of Windows NT or Windows 2000 installed
        on a node is fully described by the following
        properties:
        MajorVersion
        MinorVersion
        BuildNumber"
    ::= { mscsNodeEntry 7 }

mscsNodeDescription OBJECT-TYPE
    SYNTAX     DisplayString
    MAX-ACCESS read-only
    STATUS     current
    DESCRIPTION
        "The Description property provides comments about
        the node."
    ::= { mscsNodeEntry 8 }

mscsNodeEnableEventLogReplicate OBJECT-TYPE
    SYNTAX     TruthValue
    MAX-ACCESS read-only
    STATUS     current
    DESCRIPTION
        "The EnableEventLogReplication property controls
        whether a node's system, application, and security
        event log entries are replicated in the event logs
        of all other cluster nodes.
        
        The EnableEventLogReplication property only affects
        events logged to a node's system, application, and
        security logs."
    ::= { mscsNodeEntry 9 }

mscsNodeMajorVersion OBJECT-TYPE
    SYNTAX     Gauge32
    MAX-ACCESS read-only
    STATUS     current
    DESCRIPTION
        "The MajorVersion property specifies the integer
        component of the Windows NT or Windows 2000 version
        installed on the node. For example, the major
        version of Windows NT 4.0 is 4.
        
        The MajorVersion and MinorVersion properties
        represent a Windows NT or Windows 2000 version
        number of the form MajorVersion. MinorVersion.
        Further version information is provided by the
        CSDVersion and BuildNumber properties.
        
        Note that the MajorVersion and MinorVersion
        properties refer to the Windows NT or Windows 2000
        version installed on the node, while the
        NodeHighestVersion property describes the version
        of the Cluster service installed on the node."
    ::= { mscsNodeEntry 10 }

mscsNodeMinorVersion OBJECT-TYPE
    SYNTAX     Gauge32
    MAX-ACCESS read-only
    STATUS     current
    DESCRIPTION
        "The MinorVersion property specifies the decimal
        component of the Windows NT or Windows 2000 version
        installed on the node. For example, the minor
        version of Windows NT 4.0 is 0.
        
        The MajorVersion and MinorVersion properties
        represent a Windows NT or Windows 2000 version
        number of the form MajorVersion. MinorVersion.
        Further version information is provided by the
        CSDVersion and BuildNumber properties.
        
        Note that the MajorVersion and MinorVersion
        properties refer to the Windows NT or Windows 2000
        version installed on the node, while the
        NodeHighestVersion property describes the version
        of the Cluster service installed on the node."
    ::= { mscsNodeEntry 11 }

mscsNodeHighestVersion OBJECT-TYPE
    SYNTAX     Gauge32
    MAX-ACCESS read-only
    STATUS     current
    DESCRIPTION
        "The NodeHighestVersion property specifies the
        highest possible version of the Cluster service
        with which the node can join or communicate. The
        following table summarizes the attributes of the
        NodeHighestVersion property.
        
        The value of NodeHighestVersion is set when the
        Cluster service is installed or upgraded on a node.
        The upper 16 bits of the value store the version
        number, while the lower 16 bits describe the build
        number. For more information on how the Cluster
        service creates and uses version numbers, see
        Version Compatibility."
    ::= { mscsNodeEntry 12 }

mscsNodeLowestVersion OBJECT-TYPE
    SYNTAX     Gauge32
    MAX-ACCESS read-only
    STATUS     current
    DESCRIPTION
        "The NodeLowestVersion property specifies the
        lowest possible version of the Cluster service with
        which the node can join or communicate. The
        following table summarizes the attributes of the
        NodeLowestVersion property.
        
        The value of NodeHighestVersion is set when the
        Cluster service is installed or upgraded on a node.
        The upper 16 bits of the value store the version
        number, while the lower 16 bits describe the build
        number. For more information on how the Cluster
        service creates and uses version numbers, see
        Version Compatibility."
    ::= { mscsNodeEntry 13 }

mscsNodePropertiesTable OBJECT-TYPE
    SYNTAX     SEQUENCE OF ClusNodePropertiesEntry
    MAX-ACCESS not-accessible
    STATUS     current
    DESCRIPTION
        "A list of properties associated with a node."
    ::= { mscs 8 }

mscsNodePropertiesEntry OBJECT-TYPE
    SYNTAX     ClusNodePropertiesEntry
    MAX-ACCESS not-accessible
    STATUS     current
    DESCRIPTION
        "Information on one particular property."
    INDEX      { mscsNodeNameIndex, mscsNodePropertiesIndex }
    ::= { mscsNodePropertiesTable 1 }

ClusNodePropertiesEntry ::= SEQUENCE {
    mscsNodePropertiesIndex Integer32,
    mscsNodePropertiesName DisplayString,
    mscsNodePropertiesValue DisplayString
}

mscsNodePropertiesIndex OBJECT-TYPE
    SYNTAX     Integer32 (1..2147483647)
    MAX-ACCESS read-only
    STATUS     current
    DESCRIPTION
        "A unique value for each property."
    ::= { mscsNodePropertiesEntry 1 }

mscsNodePropertiesName OBJECT-TYPE
    SYNTAX     DisplayString
    MAX-ACCESS read-only
    STATUS     current
    DESCRIPTION
        "Returns the property name."
    ::= { mscsNodePropertiesEntry 2 }

mscsNodePropertiesValue OBJECT-TYPE
    SYNTAX     DisplayString
    MAX-ACCESS read-only
    STATUS     current
    DESCRIPTION
        "Returns the property value as a string."
    ::= { mscsNodePropertiesEntry 3 }

mscsResGroupTable OBJECT-TYPE
    SYNTAX     SEQUENCE OF ClusResGroupEntry
    MAX-ACCESS not-accessible
    STATUS     current
    DESCRIPTION
        "This collection provides access to all cluster
        groups belonging either to a cluster or to a
        particular node in a cluster."
    ::= { mscs 9 }

mscsResGroupEntry OBJECT-TYPE
    SYNTAX     ClusResGroupEntry
    MAX-ACCESS not-accessible
    STATUS     current
    DESCRIPTION
        "Information about one particular 'ClusResGroups'"
    INDEX      { mscsResGroupNameIndex }
    ::= { mscsResGroupTable 1 }

ClusResGroupEntry ::= SEQUENCE {
    mscsResGroupNameIndex InstanceName,
    mscsResGroupNameFull DisplayString,
    mscsResGroupOwnerNode DisplayString,
    mscsResGroupResources DisplayString,
    mscsResGroupState INTEGER,
    mscsResGroupAntiAffinityClassNam DisplayString,
    mscsResGroupAutoFailbackType INTEGER,
    mscsResGroupDescription DisplayString,
    mscsResGroupFailbackWindowEnd Integer32,
    mscsResGroupFailbackWindowStart Integer32,
    mscsResGroupFailoverPeriod Integer32,
    mscsResGroupFailoverThreshold Gauge32,
    mscsResGroupPersistentState TruthValue
}

mscsResGroupNameIndex OBJECT-TYPE
    SYNTAX     InstanceName
    MAX-ACCESS read-only
    STATUS     current
    DESCRIPTION
        "The index name is the same as the full name but
        truncated to 64 characters and made unique."
    ::= { mscsResGroupEntry 1 }

mscsResGroupNameFull OBJECT-TYPE
    SYNTAX     DisplayString
    MAX-ACCESS read-only
    STATUS     current
    DESCRIPTION
        "The Name property retrieves or sets the name of a
        group."
    ::= { mscsResGroupEntry 2 }

mscsResGroupOwnerNode OBJECT-TYPE
    SYNTAX     DisplayString
    MAX-ACCESS read-only
    STATUS     current
    DESCRIPTION
        "The OwnerNode property returns the node currently
        hosting a group."
    ::= { mscsResGroupEntry 3 }

mscsResGroupResources OBJECT-TYPE
    SYNTAX     DisplayString
    MAX-ACCESS read-only
    STATUS     current
    DESCRIPTION
        "The Resources property provides access to the
        resources in a group."
    ::= { mscsResGroupEntry 4 }

mscsResGroupState OBJECT-TYPE
    SYNTAX     INTEGER {
        unknown(-1),
        online(0),
        offline(1),
        failed(2),
        partialOnline(3),
        pending(4)
    }
    MAX-ACCESS read-only
    STATUS     current
    DESCRIPTION
        "The State property returns the state of a group."
    ::= { mscsResGroupEntry 5 }

mscsResGroupAntiAffinityClassNam OBJECT-TYPE
    SYNTAX     DisplayString
    MAX-ACCESS read-only
    STATUS     current
    DESCRIPTION
        "The AntiAffinityClassNames property is used to
        identify groups that should not be hosted on the
        same cluster node.
        
        A group's AntiAffinityClassNames property consists
        of zero or more arbitrary user-defined strings. If
        the AntiAffinityClassNames properties of two or
        more groups contain at least one identical string,
        the groups are said to be anti-affined. By default,
        all groups are affined (because their
        AntiAffinityClassNames property is NULL).
        
        When a group is moved and the destination node is
        not specified (during failover, for example),
        anti-affinity affects the algorithm used to
        determine the destination node as follows:
        1. Using the preferred owner list of the group
        being moved, the Cluster service finds the next
        preferred node. 
        2. If the node is not hosting any group
        anti-affined with the group being moved, it is
        selected as the destination node. 
        3. If the next preferred available node is
        currently hosting a group anti-affined with the
        group being moved, the Cluster service moves to the
        next preferred available node in the preferred
        owner list. 
        4. If the only available nodes are hosting
        anti-affined groups, the Cluster service ignores
        anti-affinity and selects the next preferred
        available node as the destination node.
        
        Use this property to identify groups that should
        not be hosted on the same node. Generate a unique
        string value (such as a GUID) and add it to the
        AntiAffinityClassNames property of each group that
        should be anti-affined.
        
        Note that because of the behavior described in
        point 4 above, anti-affinity does not guarantee
        that groups will never be hosted by the same node.
        If you have an application that cannot support more
        than one instance per node under any circumstances,
        you need to create a resource DLL to enforce that
        limitation."
    ::= { mscsResGroupEntry 6 }

mscsResGroupAutoFailbackType OBJECT-TYPE
    SYNTAX     INTEGER {
        preventFailback(0),
        allowFailback(1),
        failbackTypeCount(2)
    }
    MAX-ACCESS read-only
    STATUS     current
    DESCRIPTION
        "The AutoFailbackType property specifies whether
        the group should automatically be failed back to
        the node identified as its preferred owner when
        that node comes back online following a failover."
    ::= { mscsResGroupEntry 7 }

mscsResGroupDescription OBJECT-TYPE
    SYNTAX     DisplayString
    MAX-ACCESS read-only
    STATUS     current
    DESCRIPTION
        "The Description property provides comments about
        the group."
    ::= { mscsResGroupEntry 8 }

mscsResGroupFailbackWindowEnd OBJECT-TYPE
    SYNTAX     Integer32(-1..23)
    UNITS "hours"
    MAX-ACCESS read-only
    STATUS     current
    DESCRIPTION
        "The FailbackWindowEnd property provides the latest
        time that the group can be failed back to the node
        identified as its preferred owner node. -1
        indicates that no failback window exists. "
    ::= { mscsResGroupEntry 9 }

mscsResGroupFailbackWindowStart OBJECT-TYPE
    SYNTAX     Integer32(-1..23)
    UNITS "hours"
    MAX-ACCESS read-only
    STATUS     current
    DESCRIPTION
        "The FailbackWindowStart property provides the
        earliest time (that is, local time as kept by the
        cluster) that the group can be failed back to the
        node identified as its preferred owner node. -1
        indicates that no failback window exists."
    ::= { mscsResGroupEntry 10 }

mscsResGroupFailoverPeriod OBJECT-TYPE
    SYNTAX     Integer32(-1..1193)
    UNITS "hours"
    MAX-ACCESS read-only
    STATUS     current
    DESCRIPTION
        "The FailoverPeriod property specifies a number of
        hours during which a maximum number of failover
        attempts, specified by FailoverThreshold, can
        occur.
        
        If the Cluster service exceeds the number of
        failover attempts specified by FailoverThreshold
        within the time interval specified by
        FailoverPeriod, it stops trying to fail over the
        group.
        
        For example, if FailoverThreshold is set to 2 and
        FailoverPeriod is set to 1, then a node can
        tolerate two failover attempts of the group within
        any 1-hour interval. More than three failover
        attempts can occur, as long as they occur over an
        interval that is greater than 1 hour.
        
        FailoverPeriod has a maximum value of 1193 hours.
        If a value for FailoverPeriod is not specified, the
        default value is 6 hours."
    ::= { mscsResGroupEntry 11 }

mscsResGroupFailoverThreshold OBJECT-TYPE
    SYNTAX     Gauge32
    MAX-ACCESS read-only
    STATUS     current
    DESCRIPTION
        "The FailoverThreshold property specifies the
        maximum number of failover attempts that can be
        made on a group within a time interval defined by
        FailoverPeriod.
        
        If the Cluster service exceeds the number of
        failover attempts specified by FailoverThreshold
        within the time interval specified by
        FailoverPeriod, it stops trying to fail over the
        group.
        
        For example, if FailoverThreshold is set to 2 and
        RestartPeriod is set to 1, a node can tolerate 2
        failover attempts of the group within any 1-hour
        interval. More than 3 failover attempts can occur,
        as long as they occur over an interval that is
        greater than 1 hour.
        
        If a value for FailoverThreshold is not specified,
        the default value is 10."
    ::= { mscsResGroupEntry 12 }

mscsResGroupPersistentState OBJECT-TYPE
    SYNTAX     TruthValue
    MAX-ACCESS read-only
    STATUS     current
    DESCRIPTION
        "The PersistentState property specifies whether a
        group should be automatically brought online when
        the cluster forms.
        
        Set PersistentState to TRUE (1) for any group that
        should be automatically brought online when the
        cluster forms (for information on the form/join
        process, see Nodes). The default value is FALSE (0)
        which means that the group is left offline when the
        cluster forms.
        
        Resources use their group's PersistentState
        property when they lack a value for their own
        PersistentState property."
    ::= { mscsResGroupEntry 13 }

mscsResGroupPropertiesTable OBJECT-TYPE
    SYNTAX     SEQUENCE OF ClusResGroupPropertiesEntry
    MAX-ACCESS not-accessible
    STATUS     current
    DESCRIPTION
        "A list of properties associated with a resource
        group."
    ::= { mscs 10 }

mscsResGroupPropertiesEntry OBJECT-TYPE
    SYNTAX     ClusResGroupPropertiesEntry
    MAX-ACCESS not-accessible
    STATUS     current
    DESCRIPTION
        "Information on one particular property."
    INDEX      { mscsResGroupNameIndex, mscsResGroupPropertiesIndex }
    ::= { mscsResGroupPropertiesTable 1 }

ClusResGroupPropertiesEntry ::= SEQUENCE {
    mscsResGroupPropertiesIndex Integer32,
    mscsResGroupPropertiesName DisplayString,
    mscsResGroupPropertiesValue DisplayString
}

mscsResGroupPropertiesIndex OBJECT-TYPE
    SYNTAX     Integer32 (1..2147483647)
    MAX-ACCESS read-only
    STATUS     current
    DESCRIPTION
        "A unique value for each property."
    ::= { mscsResGroupPropertiesEntry 1 }

mscsResGroupPropertiesName OBJECT-TYPE
    SYNTAX     DisplayString
    MAX-ACCESS read-only
    STATUS     current
    DESCRIPTION
        "Returns the property name."
    ::= { mscsResGroupPropertiesEntry 2 }

mscsResGroupPropertiesValue OBJECT-TYPE
    SYNTAX     DisplayString
    MAX-ACCESS read-only
    STATUS     current
    DESCRIPTION
        "Returns the property value as a string."
    ::= { mscsResGroupPropertiesEntry 3 }

mscsResourceTable OBJECT-TYPE
    SYNTAX     SEQUENCE OF ClusResourceEntry
    MAX-ACCESS not-accessible
    STATUS     current
    DESCRIPTION
        "This collection provides access to the resources
        that belong to a cluster."
    ::= { mscs 11 }

mscsResourceEntry OBJECT-TYPE
    SYNTAX     ClusResourceEntry
    MAX-ACCESS not-accessible
    STATUS     current
    DESCRIPTION
        "Information about one particular 'ClusResources'"
    INDEX      { mscsResourceNameIndex }
    ::= { mscsResourceTable 1 }

ClusResourceEntry ::= SEQUENCE {
    mscsResourceNameIndex InstanceName,
    mscsResourceNameFull DisplayString,
    mscsResourceDependencies DisplayString,
    mscsResourceDependents DisplayString,
    mscsResourceGroup DisplayString,
    mscsResourceOwnerNode DisplayString,
    mscsResourcePossibleOwnerNodes DisplayString,
    mscsResourceState INTEGER,
    mscsResourceTypeName DisplayString,
    mscsResourceDebugPrefix DisplayString,
    mscsResourceDescription DisplayString,
    mscsResourceIsAlivePollInterval Gauge32,
    mscsResourceLooksAlivePollIntrvl Gauge32,
    mscsResourcePendingTimeout Gauge32,
    mscsResourcePersistentState TruthValue,
    mscsResourceRestartAction INTEGER,
    mscsResourceRestartPeriod Gauge32,
    mscsResourceRestartThreshold Gauge32,
    mscsResourceRetryPeriodOnFailure Gauge32,
    mscsResourceSeparateMonitor TruthValue,
    mscsResourceType DisplayString
}

mscsResourceNameIndex OBJECT-TYPE
    SYNTAX     InstanceName
    MAX-ACCESS read-only
    STATUS     current
    DESCRIPTION
        "The index name is the same as the full name but
        truncated to 64 characters and made unique."
    ::= { mscsResourceEntry 1 }

mscsResourceNameFull OBJECT-TYPE
    SYNTAX     DisplayString
    MAX-ACCESS read-only
    STATUS     current
    DESCRIPTION
        "The Name property retrieves or sets the name of a
        resource."
    ::= { mscsResourceEntry 2 }

mscsResourceDependencies OBJECT-TYPE
    SYNTAX     DisplayString
    MAX-ACCESS read-only
    STATUS     current
    DESCRIPTION
        "The Dependencies property retrieves the
        dependencies of a resource."
    ::= { mscsResourceEntry 3 }

mscsResourceDependents OBJECT-TYPE
    SYNTAX     DisplayString
    MAX-ACCESS read-only
    STATUS     current
    DESCRIPTION
        "The Dependents collection provides access to the
        dependents of a resource."
    ::= { mscsResourceEntry 4 }

mscsResourceGroup OBJECT-TYPE
    SYNTAX     DisplayString
    MAX-ACCESS read-only
    STATUS     current
    DESCRIPTION
        "The Group property returns the group to which a
        resource belongs."
    ::= { mscsResourceEntry 5 }

mscsResourceOwnerNode OBJECT-TYPE
    SYNTAX     DisplayString
    MAX-ACCESS read-only
    STATUS     current
    DESCRIPTION
        "The OwnerNode property returns a resource's
        current owner node."
    ::= { mscsResourceEntry 6 }

mscsResourcePossibleOwnerNodes OBJECT-TYPE
    SYNTAX     DisplayString
    MAX-ACCESS read-only
    STATUS     current
    DESCRIPTION
        "The PossibleOwnerNodes property returns the nodes
        specified as possible owners of a resource."
    ::= { mscsResourceEntry 7 }

mscsResourceState OBJECT-TYPE
    SYNTAX     INTEGER {
        unknown(-1),
        inherited(0),
        initializing(1),
        online(2),
        offline(3),
        failed(4),
        pending(128),
        onlinePending(129),
        offlinePending(130)
    }
    MAX-ACCESS read-only
    STATUS     current
    DESCRIPTION
        "The State property returns a description of the
        operational condition of a resource."
    ::= { mscsResourceEntry 8 }

mscsResourceTypeName OBJECT-TYPE
    SYNTAX     DisplayString
    MAX-ACCESS read-only
    STATUS     current
    DESCRIPTION
        "The TypeName property returns the resource type
        name of the resource."
    ::= { mscsResourceEntry 9 }

mscsResourceDebugPrefix OBJECT-TYPE
    SYNTAX     DisplayString
    MAX-ACCESS read-only
    STATUS     current
    DESCRIPTION
        "The DebugPrefix property specifies the path to the
        debugger used to debug the resource.
        
        To use the DebugPrefix property, a resource must
        run in a separate Resource Monitor. The debugger
        specified by the DebugPrefix property is attached
        to the Resource Monitor. If the debugger is in a
        directory that is included in the path, DebugPrefix
        can be set to a relative path. Otherwise, a full
        path must be specified.
        
        Setting the DebugPrefix property causes -p <process
        id> to be appended to the end of the debug command,
        where <process id> represents the process
        identifier for the Resource Monitor handling the
        resource.
        
        For more information about debugging a resource,
        see Debugging a Resource DLL."
    ::= { mscsResourceEntry 10 }

mscsResourceDescription OBJECT-TYPE
    SYNTAX     DisplayString
    MAX-ACCESS read-only
    STATUS     current
    DESCRIPTION
        "The Description property provides comments about
        the resource."
    ::= { mscsResourceEntry 11 }

mscsResourceIsAlivePollInterval OBJECT-TYPE
    SYNTAX     Gauge32
    UNITS "Milliseconds"
    MAX-ACCESS read-only
    STATUS     current
    DESCRIPTION
        "The IsAlivePollInterval property provides the
        recommended interval in milliseconds at which the
        Cluster service should poll the resource to
        determine if it is operational. The polling occurs
        when the Resource Monitor calls the resource DLL's
        IsAlive entry point function.
        
        If a resource does not set the IsAlivePollInterval
        property or sets it to - 1, the Cluster service
        uses the IsAlivePollInterval property for the
        resource type associated with the resource.
        
        The data value for IsAlivePollInterval cannot be
        zero."
    ::= { mscsResourceEntry 12 }

mscsResourceLooksAlivePollIntrvl OBJECT-TYPE
    SYNTAX     Gauge32
    UNITS "Milliseconds"
    MAX-ACCESS read-only
    STATUS     current
    DESCRIPTION
        "The LooksAlivePollInterval property provides the
        recommended interval in milliseconds at which the
        Cluster service should poll the resource to
        determine if it appears operational. The polling
        occurs when the Resource Monitor calls the resource
        DLL's LooksAlive entry point function.
        
        If a resource does not set the
        LooksAlivePollInterval property or sets it to
        0xFFFFFFFF, the Cluster service uses the
        LooksAlivePollInterval property for the resource
        type associated with the resource.
        
        The resource DLL should return an event handle from
        the Online call that is signaled when a resource
        fails. For more information, see Implementing
        LooksAlive and Implementing Online."
    ::= { mscsResourceEntry 13 }

mscsResourcePendingTimeout OBJECT-TYPE
    SYNTAX     Gauge32
    MAX-ACCESS read-only
    STATUS     current
    DESCRIPTION
        "The PendingTimeout property sets the number of
        milliseconds that a Resource Monitor will wait for
        a resource DLL to update the status of a resource
        in an OnlinePending or OfflinePending state before
        terminating the resource.
        
        The PendingTimeout property does not necessarily
        limit the time that a resource can spend in a
        ClusterOnlinePending or ClusterOfflinePending
        state. This property determines only how long a
        Resource Monitor will wait for resource DLLs to
        report status updates with the SetResourceStatus
        function. As long as a resource DLL never exceeds
        the PendingTimeout interval between calls to
        SetResourceStatus, the resource DLL can keep a
        resource in a pending state indefinitely.
        
        If a resource DLL exceeds the PendingTimeout
        interval between calls to SetResourceStatus, the
        Resource Monitor calls the resource DLL's Terminate
        entry point function."
    ::= { mscsResourceEntry 14 }

mscsResourcePersistentState OBJECT-TYPE
    SYNTAX     TruthValue
    MAX-ACCESS read-only
    STATUS     current
    DESCRIPTION
        "The PersistentState property specifies whether the
        resource should be brought online or left offline
        when the Cluster service is started.
        
        The data value for the PersistentState property can
        be set to TRUE or FALSE. When PersistentState is
        set to TRUE, the resource is automatically brought
        online when the Cluster service starts. When set to
        FALSE, it is left offline.
        
        When a resource is brought online, its
        PersistentState property is deleted from the
        cluster database. Therefore, PersistentState should
        only be set when a resource is offline.
        
        To retrieve the current state of a resource, call
        the GetClusterResourceState function."
    ::= { mscsResourceEntry 15 }

mscsResourceRestartAction OBJECT-TYPE
    SYNTAX     INTEGER {
        dontRestart(0),
        restartNoNotify(1),
        restartNotify(2),
        restartActionCount(3)
    }
    MAX-ACCESS read-only
    STATUS     current
    DESCRIPTION
        "The RestartAction property describes the action to
        be taken by the Cluster service if the resource
        fails."
    ::= { mscsResourceEntry 16 }

mscsResourceRestartPeriod OBJECT-TYPE
    SYNTAX     Gauge32
    MAX-ACCESS read-only
    STATUS     current
    DESCRIPTION
        "The RestartPeriod property defines an interval of
        time, in milliseconds, during which a specified
        number of restart attempts can be made on a
        nonresponsive resource. The RestartThreshold
        property specifies the allowable number of restart
        attempts that can occur within the interval defined
        by RestartPeriod.
        
        When a resource fails, the Cluster service attempts
        to restart the resource (unless the RestartAction
        property is set to ClusterResourceDontRestart).
        
        The RestartPeriod and RestartThreshold properties
        work together to limit restart attempts. For
        example, if the RestartPeriod property is set to
        200 milliseconds, and the RestartThreshold property
        is set to two retry attempts, the Cluster service
        tolerates two restart failures within any 200
        millisecond interval. More than two failures can
        occur, as long as they occur over an interval that
        is greater than 200 milliseconds. On the third
        restart failure within the 200 millisecond
        interval, the Cluster service considers the
        resource to have failed and may, depending on the
        RestartAction property, attempt to fail over the
        resource's group to another node.
        
        After the interval defined by the RestartPeriod
        property is exceeded, the Cluster service resets
        the property to zero.
        
        If not specified, the default value for the
        RestartPeriod property is 90000 milliseconds."
    ::= { mscsResourceEntry 17 }

mscsResourceRestartThreshold OBJECT-TYPE
    SYNTAX     Gauge32
    MAX-ACCESS read-only
    STATUS     current
    DESCRIPTION
        "The RestartThreshold property specifies the
        maximum number of restart attempts that can be made
        on a resource within an interval defined by the
        RestartPeriod property before the Cluster service
        initiates the action specified by the RestartAction
        property.
        
        When a resource does fails, the Cluster service
        attempts to restart the resource (unless the
        RestartAction property is set to
        ClusterResourceDontRestart).
        
        The RestartPeriod and RestartThreshold properties
        work together to limit restart attempts. For
        example, if the RestartPeriod property is set to
        200 milliseconds, and the RestartThreshold property
        is set to two retry attempts, then the Cluster
        service tolerates two restart failures within any
        200 millisecond interval. More than two failures
        can occur, as long as they occur over an interval
        that is greater than 200 milliseconds. On the third
        restart failure within the 200 millisecond
        interval, the Cluster service considers the
        resource to have failed and may, depending on the
        RestartAction property, attempt to fail over the
        resource's group to another node."
    ::= { mscsResourceEntry 18 }

mscsResourceRetryPeriodOnFailure OBJECT-TYPE
    SYNTAX     Gauge32
    MAX-ACCESS read-only
    STATUS     current
    DESCRIPTION
        "The RetryPeriodOnFailure property specifies the
        interval of time (in milliseconds) that a resource
        should remain in a failed state before the Cluster
        service attempts to restart it.
        
        By default, if a resource fails, it remains in the
        failed state until an active effort is made to
        locate and restart the resource. The
        RetryPeriodOnFailure property provides a way for
        resources to recover from failures automatically.
        
        When adjusting the RetryPeriodOnFailure property:
        Note that the default value (0xFFFFFFFF) prevents
        the Cluster service from making a restart attempts;
        Intervals measured in minutes (multiples of 0xEA60)
        are recommended; Do not set the interval any lower
        than that specified by the RestartPeriod property. 
        
        The Cluster Service attempts to restart the
        resource by calling its resource DLL's Online entry
        point function."
    ::= { mscsResourceEntry 19 }

mscsResourceSeparateMonitor OBJECT-TYPE
    SYNTAX     TruthValue
    MAX-ACCESS read-only
    STATUS     current
    DESCRIPTION
        "The SeparateMonitor property indicates whether the
        resource requires its own Resource Monitor.
        
        The data value for the SeparateMonitor property can
        be set to TRUE or FALSE. To use a debugger with a
        resource DLL, the resource's SeparateMonitor
        property must be set to TRUE.
        
        A change to the SeparateMonitor property does not
        take effect immediately unless the resource is
        offline at the time of the change. If the resource
        is online, the change takes effect after the
        resource is taken offline and brought back online."
    ::= { mscsResourceEntry 20 }

mscsResourceType OBJECT-TYPE
    SYNTAX     DisplayString
    MAX-ACCESS read-only
    STATUS     current
    DESCRIPTION
        "The Type property specifies the display name of
        the resource.
        
        It is important to distinguish between the display
        name of the resource's type and the registered name
        of the resource's type. For more information, see
        Display Names.
        
        To access the type name of a resource type, call
        ClusterResourceControl and pass
        CLUSCTL_RESOURCE_GET_RESOURCE_TYPE for the
        dwControlCode parameter.
        
        The Name property for resource types also specifies
        a resource type display name."
    ::= { mscsResourceEntry 21 }

mscsResourcePropertiesTable OBJECT-TYPE
    SYNTAX     SEQUENCE OF ClusResourcePropertiesEntry
    MAX-ACCESS not-accessible
    STATUS     current
    DESCRIPTION
        "A list of properties associated with a resource."
    ::= { mscs 12 }

mscsResourcePropertiesEntry OBJECT-TYPE
    SYNTAX     ClusResourcePropertiesEntry
    MAX-ACCESS not-accessible
    STATUS     current
    DESCRIPTION
        "Information on one particular property."
    INDEX      { mscsResourceNameIndex, mscsResourcePropertiesIndex }
    ::= { mscsResourcePropertiesTable 1 }

ClusResourcePropertiesEntry ::= SEQUENCE {
    mscsResourcePropertiesIndex Integer32,
    mscsResourcePropertiesName DisplayString,
    mscsResourcePropertiesValue DisplayString
}

mscsResourcePropertiesIndex OBJECT-TYPE
    SYNTAX     Integer32 (1..2147483647)
    MAX-ACCESS read-only
    STATUS     current
    DESCRIPTION
        "A unique value for each property."
    ::= { mscsResourcePropertiesEntry 1 }

mscsResourcePropertiesName OBJECT-TYPE
    SYNTAX     DisplayString
    MAX-ACCESS read-only
    STATUS     current
    DESCRIPTION
        "Returns the property name."
    ::= { mscsResourcePropertiesEntry 2 }

mscsResourcePropertiesValue OBJECT-TYPE
    SYNTAX     DisplayString
    MAX-ACCESS read-only
    STATUS     current
    DESCRIPTION
        "Returns the property value as a string."
    ::= { mscsResourcePropertiesEntry 3 }

END
