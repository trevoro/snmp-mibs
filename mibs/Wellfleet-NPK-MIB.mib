Wellfleet-NPK-MIB DEFINITIONS ::= BEGIN



    IMPORTS

      OBJECT-TYPE
        FROM RFC-1212
      DisplayString
	FROM RFC1213-MIB    
      wfGameGroup
        FROM Wellfleet-COMMON-MIB;


    wfNpkBase  OBJECT IDENTIFIER ::= { wfGameGroup 8 }

    wfNpkBaseCreate OBJECT-TYPE
	 SYNTAX  INTEGER {
		     created(1),
		     deleted(2)
                 }
         ACCESS  read-write
	 STATUS  mandatory
	 DESCRIPTION
	       "Create/Delete parameter"
         DEFVAL { created }
	 ::= { wfNpkBase 1 }
       
    wfNpkBaseHash OBJECT-TYPE
        SYNTAX	OCTET STRING 
        ACCESS	read-write
        STATUS	mandatory
        DESCRIPTION
                "Hash value: MD5 of NPK used to protect this configuration"
        ::= { wfNpkBase 2 }

    wfNpkBaseLastMod OBJECT-TYPE
	SYNTAX  DisplayString
	ACCESS  read-write
        STATUS  mandatory
        DESCRIPTION
		"Stores Last modification time-stamp for NPK"
	::= { wfNpkBase 3 }

    END  -- Wellfleet-NPK-MIB
