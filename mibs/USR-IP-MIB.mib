USR-IP-MIB DEFINITIONS ::= BEGIN
	IMPORTS
	     Counter32, IpAddress, Integer32,
             OBJECT-TYPE, MODULE-IDENTITY
             FROM SNMPv2-SMI
             TruthValue, DisplayString
	     FROM SNMPv2-TC
             common, UsrConfigStatus, UsrNetLogicalId,
             DisplayString
             FROM USR-DEFINITIONS-MIB;
   usrIp MODULE-IDENTITY
		 LAST-UPDATED "200305241530Z"
         ORGANIZATION "CommWorks Corporation, a 3Com company"
         CONTACT-INFO "Customer Support"
         DESCRIPTION    "The enterprise specific defined objects for IP"
--       REVISION       "200303241530Z"
--       DESCRIPTION    "Added new MIB Object usrIpSrcSNMPAddress"
--       REVISION       "200208151645Z"
--       DESCRIPTION    "Added new MIB object for IP networks filename"
--       REVISION       "200208231400Z"
--       DESCRIPTION "Clarify usage and labels for usrIpIeaSendUnsolicitedArp,
--          usrIpIeaForceNexthopRoute, usrIpIeaNextHopRouting,
--          usrIpSrcRouteInterfaceEnabled."
--       REVISION       "200208231400Z"
--       DESCRIPTION "Clarify usage and labels for usrIpIeaSendUnsolicitedArp,
--          usrIpIeaForceNexthopRoute, usrIpIeaNextHopRouting,
--          usrIpSrcRouteInterfaceEnabled."
--       REVISION       "200208131445Z"
--       DESCRIPTION "Modify usrIpNetRip2AuthKey"
--       REVISION       "200207261500Z"
--       DESCRIPTION "Update the description field for the MIB objects related 
--                      "to the usrIpSrcRouteTable"
--       REVISION       "200202080430Z"
--       DESCRIPTION "Merge HA and HACN into PDSN version of USR-IP-MIB so
--		             "PDSN version of MIB can manage PDSN,HA and HACN"
         ::= { common 12 }
   -- Begin managed object definitions here...
usrIpVersion OBJECT-TYPE
	SYNTAX		DisplayString
	MAX-ACCESS	read-only
	STATUS		current
	DESCRIPTION
		"The current software version of the IP Forwarder."
::= { usrIp 1 }
usrIpCFMStatusFlag OBJECT-TYPE
	SYNTAX		UsrConfigStatus
	MAX-ACCESS	read-write
	STATUS		current
	DESCRIPTION
		"This variable controls saving and loading of configuration
           information for the IP Module. The value can be SET to either 
           save(2) or load(4) by a management station; a GET following
           should return normal(1). The other values indicate if any 
           configuration operation and what type is in progress."
::= { usrIp 2 }
usrIpCfgFileName OBJECT-TYPE
	SYNTAX      DisplayString
	MAX-ACCESS  read-only
	STATUS      current
	DESCRIPTION		
		"The name of a ConfigFile to read/write  permanent database records.
		 If the value of this object is an empty string, then the
		 IP module uses the default name `@file://IPModule.cfg'. "
::= { usrIp 3 }
usrIpNetworkTable OBJECT-TYPE
	SYNTAX SEQUENCE OF UsrIpNetworkEntry
	MAX-ACCESS not-accessible
	STATUS current
	DESCRIPTION
		"The (conceptual) table of IP Networks. The objects in this table
		 are essentially read/write versions of the ipAddrTable in MIB-2.
		 These objects are defined as read/write so that they can be configured
		 by a Network Manager at the time an IP Network is added to the Netserver
		 configuration. Any attempt to modify these parameters when the network
		 is in an active state will fail."
::= { usrIp 4 }
usrIpNetworkEntry OBJECT-TYPE
	SYNTAX UsrIpNetworkEntry
	MAX-ACCESS not-accessible
	STATUS current
	DESCRIPTION
		"A (conceptual) entry for one IP Network."
	INDEX { usrIpNetId }
::= { usrIpNetworkTable 1 }
UsrIpNetworkEntry ::= SEQUENCE {
	usrIpNetId				UsrNetLogicalId,
	usrIpNetAddr				IpAddress,
	usrIpNetMask				IpAddress,
	usrIpNetBcastAddr			Integer32,
	usrIpNetReasmMaxSize			Integer32,
	usrIpNetRoutingProtocol			INTEGER,
	usrIpNetSendDefaultRoutePolicy  	INTEGER,
	usrIpNetSendRoutesPolicy 		INTEGER,
	usrIpNetSendSubnetsOnlyPolicy 	        INTEGER,
	usrIpNetAcceptDefaultRoutePolicy 	INTEGER,
	usrIpNetSilentPolicy 			INTEGER,
	usrIpNetSplitHorizonPolicy 		INTEGER,
	usrIpNetPoisonReversePolicy 		INTEGER,
	usrIpNetFlashUpdatePolicy 		INTEGER,
	usrIpNetSimpleAuthenPolicy		INTEGER,
	usrIpNetSendRipV1CompatPolicy 	        INTEGER,
	usrIpNetRcvRipV1Policy	 		INTEGER,
	usrIpNetRcvRipV2Policy	 		INTEGER,
	usrIpNetRip2AuthKey  			DisplayString,
	usrIpNetReconfigNeeded                  TruthValue,
	usrIpNetRoutingMetric                   Integer32,
	usrIpNetExportMetric                    Integer32,
	usrIpNetRoutingNone                     INTEGER,
	usrIpNetRoutingRipV1			INTEGER,
	usrIpNetRoutingRipV2			INTEGER,
	usrIpNetRoutingOspf			INTEGER
	}
usrIpNetId OBJECT-TYPE
	SYNTAX		UsrNetLogicalId
	MAX-ACCESS		not-accessible
	STATUS		current
	DESCRIPTION
		"The logical identifier of the IP Network. This is the value
		 of the usrCfgNetLogicalId object in the usrCfgNetworkTable.
		 The IP forwarder returns this identifier to the Configuration
		 process in the FWD_ADD_NETWORK_RSP message. It allows management
		 applications to correlate Network Table entries with protocol
		 specific table entries."
::= { usrIpNetworkEntry 1 }
usrIpNetAddr OBJECT-TYPE
	SYNTAX  IpAddress
     MAX-ACCESS  read-only
     STATUS  current
     DESCRIPTION
		"The IP address this network has assigned to the
		 local interface."
::= { usrIpNetworkEntry 2 }
usrIpNetMask OBJECT-TYPE
     SYNTAX  IpAddress
     MAX-ACCESS  read-only
     STATUS  current
     DESCRIPTION
		"The subnet mask associated with the IP address of
           this entry.  The value of the mask is an IP
           address with all the network bits set to 1 and all
           the hosts bits set to 0."
::= { usrIpNetworkEntry 3 }
usrIpNetBcastAddr OBJECT-TYPE
     SYNTAX  Integer32 (0..1)
     MAX-ACCESS  read-write
	STATUS  current
     DESCRIPTION
          "The value of the least-significant bit in the IP
           broadcast address used for sending datagrams on
           the (logical) interface associated with the IP
           address of this entry.  For example, when the
           Internet standard all-ones broadcast address is
           used, the value will be 1.  This value applies to
           both the subnet and network broadcasts addresses
           used by the entity on this (logical) interface."
::= { usrIpNetworkEntry 4 }
usrIpNetReasmMaxSize OBJECT-TYPE
     SYNTAX  Integer32 (0..65535)
     MAX-ACCESS  read-write
     STATUS  current
     DESCRIPTION
		"The size of the largest IP datagram which this
           entity can re-assemble from incoming IP fragmented
           datagrams received on this interface."
::= { usrIpNetworkEntry 5 }
usrIpNetRoutingProtocol OBJECT-TYPE
	SYNTAX INTEGER {
			none(0),
			ripv1(1),
			ripv2(2)
		}
	MAX-ACCESS read-write
	STATUS obsolete
	DESCRIPTION
		"The routing protocol to be operated on this IP network."
::= { usrIpNetworkEntry 6 }
usrIpNetSendDefaultRoutePolicy OBJECT-TYPE
	SYNTAX	INTEGER {
		disable(0),
		enable(1)
	}
	MAX-ACCESS	read-write
	STATUS	current
	DESCRIPTION
		"Allows disabling or enabling of the send default route RIP policy.
		 This policy is enabled by default."
::= { usrIpNetworkEntry 7 }
usrIpNetSendRoutesPolicy OBJECT-TYPE
	SYNTAX	INTEGER {
		disable(0),
		enable(1)
	}
	MAX-ACCESS	read-write
	STATUS	current
	DESCRIPTION
		"Allows disabling or enabling of the send routes RIP policy.
		 This policy is enabled by default."
::= { usrIpNetworkEntry 8 }
usrIpNetSendSubnetsOnlyPolicy OBJECT-TYPE
	SYNTAX	INTEGER {
		disable(0),
		enable(1)
	}
	MAX-ACCESS	read-write
	STATUS	current
	DESCRIPTION
		"Allows disabling or enabling of the send subnets only RIP policy.
		 This policy is enabled by default."
::= { usrIpNetworkEntry 9 }
usrIpNetAcceptDefaultRoutePolicy OBJECT-TYPE
	SYNTAX	INTEGER {
		disable(0),
		enable(1)
	}
	MAX-ACCESS	read-write
	STATUS	current
	DESCRIPTION
		"Allows disabling or enabling of the accept default route RIP policy.
		 This policy is disabled by default."
::= { usrIpNetworkEntry 10 }
usrIpNetSilentPolicy OBJECT-TYPE
	SYNTAX	INTEGER {
		disable(0),
		enable(1)
	}
	MAX-ACCESS	read-write
	STATUS	current
	DESCRIPTION
		"Allows disabling or enabling of the silent policy.
		 This policy is disabled by default."
::= { usrIpNetworkEntry 11 }
usrIpNetSplitHorizonPolicy OBJECT-TYPE
	SYNTAX	INTEGER {
		disable(0),
		enable(1)
	}
	MAX-ACCESS	read-write
	STATUS	current
	DESCRIPTION
		"Allows disabling or enabling of the split horizon RIP policy.
		 This policy is enabled by default."
::= { usrIpNetworkEntry 12 }
usrIpNetPoisonReversePolicy OBJECT-TYPE
	SYNTAX	INTEGER {
		disable(0),
		enable(1)
	}
	MAX-ACCESS	read-write
	STATUS	current
	DESCRIPTION
		"Allows disabling or enabling of the poison reverse RIP policy.
	 	 This policy is enabled by default."
::= { usrIpNetworkEntry 13 }
usrIpNetFlashUpdatePolicy OBJECT-TYPE
	SYNTAX	INTEGER {
		disable(0),
		enable(1)
	}
	MAX-ACCESS	read-write
	STATUS	current
	DESCRIPTION
		"Allows disabling or enabling of the flash update RIP policy.
		 This policy is enabled by default."
::= { usrIpNetworkEntry 14 }
usrIpNetSimpleAuthenPolicy OBJECT-TYPE
	SYNTAX	INTEGER {
		disable(0),
		enable(1)
	}
	MAX-ACCESS	read-write
	STATUS	current
	DESCRIPTION
		"Allows disabling or enabling of the simple authentication RIP policy.
		 This policy is valid for RIPV2 only and is enabled by default when
		 RIPV2 is selected as the routing protocol."
::= { usrIpNetworkEntry 15 }
usrIpNetSendRipV1CompatPolicy OBJECT-TYPE
	SYNTAX	INTEGER {
		disable(0),
		enable(1)
	}
	MAX-ACCESS	read-write
	STATUS	current
	DESCRIPTION
		"Allows disabling or enabling of the send RipV1 compatible policy.
		 This policy is enabled by default."
::= { usrIpNetworkEntry 16 }
usrIpNetRcvRipV1Policy OBJECT-TYPE
	SYNTAX	INTEGER {
		disable(0),
		enable(1)
	}
	MAX-ACCESS	read-write
	STATUS	current
	DESCRIPTION
		"Allows disabling or enabling of the receive RipV1 policy.
		 This policy is enabled by default."
::= { usrIpNetworkEntry 17 }
usrIpNetRcvRipV2Policy OBJECT-TYPE
	SYNTAX	INTEGER {
		disable(0),
		enable(1)
	}
	MAX-ACCESS	read-write
	STATUS	current
	DESCRIPTION
		"Allows disabling or enabling of the receive RipV2 policy.
		 This policy is enabled by default."
::= { usrIpNetworkEntry 18 }
usrIpNetRip2AuthKey OBJECT-TYPE
	SYNTAX DisplayString (SIZE(0..16))
	MAX-ACCESS read-write
	STATUS current
	DESCRIPTION
		"this variable defines the authentication key for ip rip2.  when
		 this variable is set, by default, the authentication type is also
		 set to simple."
::= { usrIpNetworkEntry 19 }
usrIpNetReconfigNeeded  OBJECT-TYPE
       SYNTAX      TruthValue
       MAX-ACCESS  read-only
       STATUS      current
       DESCRIPTION
               "This object has a value of TRUE by default. If any other
			 object in the usrIpNetworkTable has been changed since the
			 network was enabled, the value of this object becomes TRUE.
			 All object values in this table only take effect when
			 the network is enabled. This object is meant to notify 
			 the system administrator that at least one network parameter
			 has been modified and the network should be reinitialized
			 in order for the new parameter values to take effect.
			 The network can be automatically reconfigured by setting
			 the network state to 'reconfigure' in the usrCfgNetStatus
			 object of the usrCfgNetworkTable."
::= { usrIpNetworkEntry 20 }
usrIpNetRoutingMetric OBJECT-TYPE
        SYNTAX Integer32 (1..16)
        MAX-ACCESS read-write
        STATUS current
        DESCRIPTION
                "The routing metric for using this IP network."
::= { usrIpNetworkEntry 21 }
usrIpNetExportMetric OBJECT-TYPE
        SYNTAX Integer32 (0..15)
        MAX-ACCESS read-write
        STATUS current
        DESCRIPTION
                "The metric for advertising route through this IP network."
::= { usrIpNetworkEntry 22 }
usrIpNetRoutingNone OBJECT-TYPE
	SYNTAX INTEGER {
			disable(0),
			enable(1)
		}
	MAX-ACCESS read-write
	STATUS current
	DESCRIPTION
		"Specifies that no routing protocol will be operating on this 
           IP network. Only valid SET option is enable(1) since disable is
           meaningless unless a specific routing protocol is set; 
           doing this will automatically set RoutingProtocolNone to disable(0)"
::= { usrIpNetworkEntry 27 }
usrIpNetRoutingRipV1 OBJECT-TYPE
	SYNTAX INTEGER {
			disable(0),
			enable(1)
		}
	MAX-ACCESS read-write
	STATUS current
	DESCRIPTION
		"Specifies if the RIPv1 routing protocol will be operating
           or not operating on this IP network."
::= { usrIpNetworkEntry 28 }
usrIpNetRoutingRipV2 OBJECT-TYPE
	SYNTAX INTEGER {
			disable(0),
			enable(1)
		}
	MAX-ACCESS read-write
	STATUS current
	DESCRIPTION
		"Specifies if the RIPv2 routing protocol will be operating
           or not operating on this IP network."
::= { usrIpNetworkEntry 29 }
usrIpNetRoutingOspf OBJECT-TYPE
	SYNTAX INTEGER {
			disable(0),
			enable(1)
		}
	MAX-ACCESS read-write
	STATUS current
	DESCRIPTION
		"Specifies if the OSPF routing protocol will be operating
           or not operating on this IP network."
::= { usrIpNetworkEntry 30 }
usrIpAddressPoolSize	OBJECT-TYPE
	SYNTAX	Integer32 (0..254)
	MAX-ACCESS	read-write
	STATUS	obsolete
	DESCRIPTION
		"this variable denotes the size of the dynamic address assignment
		 pool.  the default size is 8. no, not olympic.  to have a size other
		 than the default, one should set the pool size to the desired number
		 before setting usrIpAddressPoolBegin."
	-- CONFIGURABLE
::= { usrIp 5 }
usrIpAddressPoolBegin	OBJECT-TYPE
	SYNTAX	IpAddress
	MAX-ACCESS read-write
	STATUS	obsolete
	DESCRIPTION
		"the variable denotes the starting ip address of the dynamic 
		 address assignment pool.  one needs to restart the system to change 
		 it once it is set."
	-- CONFIGURABLE
::= { usrIp 6 }
usrIpHostAddress	OBJECT-TYPE
	SYNTAX	IpAddress
	MAX-ACCESS read-write
	STATUS	current
	DESCRIPTION
	   "this variable shows the host ip address of the system.  it is 
	    registered automatically by the ip forwarder and is not settable
            via SNMP. In general, the host address is also the ip address of 
            the first added lan interface's ip address."
	--CONFIGURABLE
::= { usrIp 7 }
usrIpRoutesFlag OBJECT-TYPE
	SYNTAX UsrConfigStatus
	MAX-ACCESS read-write
	STATUS current
	DESCRIPTION
		"this flag triggers cfm to save/load ip static routes, good luck."
::= { usrIp 8 }
usrIpForwarding OBJECT-TYPE
     SYNTAX  INTEGER {
             forwarding(1),    -- acting as a gateway
             not-forwarding(2) -- NOT acting as a gateway
             }
	MAX-ACCESS read-write
	STATUS current
	DESCRIPTION
		"this variable mirrors the ipForwarding flag in MIB-II"
	--CONFIGURABLE
::= { usrIp 9 }
usrIpIcmp OBJECT IDENTIFIER ::= { usrIp 10 }
usrIpIcmpOutRouterAdvertise OBJECT-TYPE
     SYNTAX  Counter32
     MAX-ACCESS  read-only
     STATUS  current
     DESCRIPTION
          "The total number of ICMP Router Advertisement messages 
           that has been sent by the router.  Note this counter 
           includes all those counted by icmpOutMsgs."
::= { usrIpIcmp 1 }
usrIpIcmpInRouterAdvertise OBJECT-TYPE
     SYNTAX  Counter32
     MAX-ACCESS  read-only
     STATUS  current
     DESCRIPTION
          "The total number of ICMP Router Advertisement messages 
           that the router has received.  Note this counter 
	      includes all those counted by icmpInMsgs."
::= { usrIpIcmp 2 }
usrIpIcmpInRouterSolicit OBJECT-TYPE
     SYNTAX  Counter32
     MAX-ACCESS  read-only
     STATUS  current
     DESCRIPTION
          "The total number of ICMP Router Solicitation messages
           that has been received by the router.  Note this counter
	      includes all those counted by icmpInMsgs."
::= { usrIpIcmp 3 }
usrIpIcmpLogFlag OBJECT-TYPE
     SYNTAX  INTEGER {
             logging(1),    -- syslogging is ENABLED
             not-logging(0) -- syslogging is DISABLED
             }
	MAX-ACCESS read-write
	STATUS current
	DESCRIPTION
		"Flag indicates whether ICMP syslogging is enabled or
           or not."
	--CONFIGURABLE
::= { usrIpIcmp 4 }
usrIpIcmpRouterAdvertiseFlag OBJECT-TYPE
     SYNTAX  INTEGER {
             enable(1),    -- router advertise is ENABLED
             disable(0) -- router advertise is DISABLED
             }
	MAX-ACCESS read-write
	STATUS current
	DESCRIPTION
		"Flag indicates whether ICMP router advertisement is enabled or
           or not."
	--CONFIGURABLE
::= { usrIpIcmp 5 }
usrIpDropAllFO1 OBJECT-TYPE
     SYNTAX  INTEGER {
             enable(1),    -- dropping ip packet with FO = 1
             disable(0)    -- NOT dropping.
             }
	MAX-ACCESS read-write
	STATUS current
	DESCRIPTION
		"indicating whether ip packet with FO = 1 is to be dropped"
	--CONFIGURABLE
::= { usrIp 11 }
usrIpDropTcpFO1 OBJECT-TYPE
     SYNTAX  INTEGER {
             enable(1),   -- dropping ip packet with FO==1 AND protocol==TCP
             disable(0)   -- NOT dropping.
             }
	MAX-ACCESS read-write
	STATUS current
	DESCRIPTION
		"indicating whether ip packet with FO == 1 AND protocol == TCP 
		 is to be dropped"
	--CONFIGURABLE
::= { usrIp 12 }
usrIpDropOptions OBJECT-TYPE
     SYNTAX  INTEGER {
             enable(1),   -- dropping ip packet with options
             disable(0)   -- NOT dropping.
             }
	MAX-ACCESS read-write
	STATUS current
	DESCRIPTION
		"indicating whether ip packet with options is to be dropped"
	--CONFIGURABLE
::= { usrIp 13 }
usrIpDropSRRoute OBJECT-TYPE
     SYNTAX  INTEGER {
             enable(1),   -- dropping ip packet with OPTION==Source Route
             disable(0)   -- NOT dropping.
             }
	MAX-ACCESS read-write
	STATUS current
	DESCRIPTION
		"indicating whether ip packet with  OPTION==Source Route
		 is to be dropped"
	--CONFIGURABLE
::= { usrIp 14 }
usrIpAddrPoolTable OBJECT-TYPE
	SYNTAX SEQUENCE OF UsrIpAddrPoolEntry
	MAX-ACCESS not-accessible
	STATUS current
	DESCRIPTION
		"The table of IP Address Pools. These objects are defined 
		 as read/write so that they can be configured by a Network
		 Manager at the time an IP Address Pool is added."
::= { usrIp 15}
usrIpAddrPoolEntry OBJECT-TYPE
	SYNTAX UsrIpAddrPoolEntry
	MAX-ACCESS not-accessible
	STATUS current
	DESCRIPTION
		"A (conceptual) entry for one IP Address Pool. To create 
		 a new row in this table the objects usrIpAddrPoolBegin
	         and usrIpAddrPoolNetMask must be provided."
	INDEX { usrIpAddrPoolName}
::= { usrIpAddrPoolTable 1 }
UsrIpAddrPoolEntry ::= SEQUENCE {
	usrIpAddrPoolName		DisplayString,
	usrIpAddrPoolBegin		IpAddress,
	usrIpAddrPoolNetMask    	IpAddress,
	usrIpAddrPoolSize		Integer32,
	usrIpAddrPoolState		INTEGER,
	usrIpAddrPoolRoute 		INTEGER,
	usrIpAddrPoolStatus		INTEGER,
        usrIpAddrPoolInUse              Integer32,
        usrIpAddrPoolMaxWasted          Integer32,
	usrIpAddrPoolPriority		Integer32
	}
usrIpAddrPoolName	OBJECT-TYPE
	SYNTAX	 DisplayString (SIZE (1..16))
	MAX-ACCESS	 not-accessible
	STATUS	 current
	DESCRIPTION
		"the name of this IP address pool."
::= { usrIpAddrPoolEntry 1 }
usrIpAddrPoolBegin	OBJECT-TYPE
	SYNTAX	 IpAddress
	MAX-ACCESS	 read-write
	STATUS	 current
	DESCRIPTION
		"the starting ip address of this IP address pool."
	--CONFIGURABLE
::= { usrIpAddrPoolEntry 2 }
usrIpAddrPoolNetMask	 OBJECT-TYPE
	SYNTAX	 IpAddress
	MAX-ACCESS	 read-write
	STATUS	 current
	DESCRIPTION
		"the network mask for this IP address pool. For classful
                 pools this will be one of A/B/C/D/H; if not specified
                 with usrIpAddrPoolBegin it will default to Class A.
                 For classless pools the value of this object is
                 calculated internally based on CIDR(RFC1519)"
	--CONFIGURABLE
::= { usrIpAddrPoolEntry 3 }
usrIpAddrPoolSize	 OBJECT-TYPE
	SYNTAX	 Integer32 (1..10000)
	MAX-ACCESS	 read-write
	STATUS	 current
	DESCRIPTION
		"the number of IP addresses in this pool. the default size is 1
		Note that on the PDSN, the range is (1..4096)
		Note that on the HACN, the range is (1..4096)
		Note that on the HA, the range is (1..10000)"
	--CONFIGURABLE
::= { usrIpAddrPoolEntry 4 }
usrIpAddrPoolState	 OBJECT-TYPE
	SYNTAX	 INTEGER	{
		public(1),
		private(2)
	}
	MAX-ACCESS	 read-write
	STATUS	 current
	DESCRIPTION
		"If this object is set to public(1) an IP address can be selected
		 from this pool for any user not assigned to a pool.  If set to
		 private(2) IP addresses can only be selected from this pool by 
		 users assigned to it. "
	--CONFIGURABLE
::= { usrIpAddrPoolEntry 5 }
usrIpAddrPoolRoute	 OBJECT-TYPE
	SYNTAX	 INTEGER	{
		aggregate(1),
		no-aggregate(2),
		aggr-multiple-route(3)
	}
	MAX-ACCESS	 read-write
	STATUS	 current
	DESCRIPTION
		"If this object is set to aggregate(1) a host routes
                 within RIP updates will be aggregated.  If set to 
                 no_aggregate(2) host routes will not be aggregated."
	--CONFIGURABLE
::= { usrIpAddrPoolEntry 6 }
usrIpAddrPoolStatus 	OBJECT-TYPE
	SYNTAX	 INTEGER {
		delete(1),
		active(2),
		remove(3),
		remove-pending(4),
		delete-pending(5)
	}
	MAX-ACCESS	 read-write
	STATUS	 current
	DESCRIPTION
		"This object can only be set to delete(1) or active(2).
           If set to active(2) IP addresses can be assigned from this pool. 
		 If set to delete(1) this pool is being deleted so no new users can 	
		 be assigned IP addresses from this pool.  If set to remove(3) IP 
		 addresses are being removed from this pool so no new users can
		 be assigned IP address from this pool.  If set to remove_pending(4) 
		 this pool is currently waiting for users to release IP addresses that
		 need to be deleted, new users can be assigned IP addresses from
		 this pool.  If set to delete_pending(5) this pool is waiting for users
		 to release IP addresses so this pool can be deleted.  No new users
		can be assigned from this pool "
::= { usrIpAddrPoolEntry 7 }
usrIpAddrPoolInUse       OBJECT-TYPE
        SYNTAX   Integer32
        MAX-ACCESS   read-only 
        STATUS   current
        DESCRIPTION
                "the number of pool addresses in use.  This is calculated using the size
                 and the number of entries available. "
::= { usrIpAddrPoolEntry 8 }
usrIpAddrPoolMaxWasted       OBJECT-TYPE   
        SYNTAX   Integer32
        MAX-ACCESS   read-write
        STATUS   current     
        DESCRIPTION
                "the Max number of pool addresses wasted in case of
                 multiple routes aggr pool
		For PDSN, Range is (0..4096)
		For HA,   Range is (0..10000)"
    --CONFIGURABLE
::= { usrIpAddrPoolEntry 9 } 
usrIpAddrPoolPriority	OBJECT-TYPE
	SYNTAX	Integer32
	MAX-ACCESS	read-write
	STATUS	current
	DESCRIPTION
		"Priority for a Pool. Address pool selection for NOT round-robin
		 method shall use this field. Lowest value (1) has highest priority."
    --CONFIGURABLE
::= { usrIpAddrPoolEntry 10 }
usrIpAddressPoolFilter OBJECT-TYPE
     SYNTAX  INTEGER {
             filtering(1),       -- enable ip address_pool_filtering 
             not-filtering(2)    -- disable ip address_pool_filtering
             }
	MAX-ACCESS read-write
	STATUS current
	DESCRIPTION
		"This object may only be set to enable(1) or disable
                 (2).  If set to enable(1) and if IP address found in
                 any pools, but for which a host route does not exits, 
                 will return null route to drop packet.  If set to 
                 disable(2) there will be no check for IP address in
                 pool table.  This is disabled by default."
	--CONFIGURABLE
::= { usrIp 16 }
usrIpSRCPPPAddress OBJECT-TYPE
	SYNTAX	IpAddress
	MAX-ACCESS	read-write
	STATUS	current
	DESCRIPTION
		" This variable sets the local address for WAN links (SLIP/PPP). If zero
		system will user internal or other ethernet address for it"
	--CONFIGURABLE
::= { usrIp 17 }
usrIpSRCRADIUSAddress OBJECT-TYPE
	SYNTAX	IpAddress
	MAX-ACCESS	read-write
	STATUS	current
	DESCRIPTION
		"For all radius packets send out this will the source address. If zero
		 internal ip address or interface IP address will be the source address
		 ."
	--CONFIGURABLE
::= { usrIp 18 }
usrIpSRCSyslogAddress OBJECT-TYPE
	SYNTAX	IpAddress
	MAX-ACCESS	read-write
	STATUS	current
	DESCRIPTION
		"For all Syslog packets send out this will the source address. If zero
		 internal ip address or interface IP address will be the source address
		 ."
	--CONFIGURABLE
::= { usrIp 19 }
usrIpClearArp OBJECT-TYPE
        SYNTAX  Integer32
	MAX-ACCESS read-write
	STATUS current
	DESCRIPTION
		"This object is used to clear the entire ARP cache"
::= { usrIp 20 }
usrIpSrcIGMPAddress OBJECT-TYPE
	SYNTAX	IpAddress
	MAX-ACCESS	read-write
	STATUS	current
	DESCRIPTION
		"For all IGMP packets send out this will the source address. If zero
		 internal ip address or interface IP address will be the source address
		 ."
	--CONFIGURABLE
::= { usrIp 21 }
usrIpAddressPoolRoundRobin OBJECT-TYPE
     SYNTAX  INTEGER {
             round-robin(1),     -- enable ip address_pool_round_robin 
             not-round-robin(2)  -- disable ip address_pool_round_robin 
             }
	MAX-ACCESS read-write
	STATUS current
	DESCRIPTION
		"This object may only be set to enable(1) or disable
           (2).  If set to enable(1), addresses will be allocated
		 from address pools in round-robin fashion.  If set to
		 disable(2), addresses will be allocated from the first
		 pool until all of its addresses are depleted.  Then
		 addresses will be allocated from the next pool, and so
		 forth.  This is enabled by default."
	--CONFIGURABLE
::= { usrIp 22 }
usrIpDefaultRouteTable OBJECT-TYPE
	SYNTAX SEQUENCE OF UsrIpDefaultRouteEntry
	MAX-ACCESS not-accessible
	STATUS current
	DESCRIPTION
		"Table of default route entries. Since all default
                routes have all 0's address and mask gateway address
                will be used as a index."
::= { usrIp 23 }
usrIpDefaultRouteEntry OBJECT-TYPE
	SYNTAX UsrIpDefaultRouteEntry
	MAX-ACCESS not-accessible
	STATUS current
	DESCRIPTION
		"All 0's for the network and all 0's mask."
	INDEX { usrIpDefaultRouteGateway }
::= { usrIpDefaultRouteTable 1 }
UsrIpDefaultRouteEntry ::= SEQUENCE {
	usrIpDefaultRouteGateway        IpAddress,
        usrIpDefaultRouteStatus         INTEGER,
	usrIpDefaultRouteMetric         Integer32
	}
usrIpDefaultRouteGateway OBJECT-TYPE
    SYNTAX  IpAddress
    MAX-ACCESS  read-only
    STATUS  current
    DESCRIPTION
		"Gateway for this default route."
::= { usrIpDefaultRouteEntry 1 }
usrIpDefaultRouteStatus OBJECT-TYPE
    SYNTAX INTEGER{
          create(1),
          delete(2),
          disable(3)
    }
    MAX-ACCESS  read-write
    STATUS  current
    DESCRIPTION
		"Create/delete parameter."
	--CONFIGURABLE
::= { usrIpDefaultRouteEntry 2 }
usrIpDefaultRouteMetric OBJECT-TYPE
    SYNTAX  Integer32
    MAX-ACCESS  read-write
    STATUS  current
    DESCRIPTION
        "Metric for this default route."
	--CONFIGURABLE
::= { usrIpDefaultRouteEntry 3 }
usrGlobalSourceIpFilterFlag OBJECT-TYPE 
    SYNTAX INTEGER
    {
       disabled(2),
       enabled(1)
    }
    MAX-ACCESS   read-write 
    STATUS   current
    DESCRIPTION
        "Indicates whether Global Source address assurance  
         feature is enabled."
             --CONFIGURABLE
::= { usrIp 24 }
usrIpIeaSendUnsolicitedArp OBJECT-TYPE
    SYNTAX     INTEGER {
                    enabled(1),
                    disabled(2)
                    }
    MAX-ACCESS read-write
    STATUS current
    DESCRIPTION
      "This flag is DISABLED by default. In order to send unsolicited ARP
       request when the user gets connected, the needs to be set to ENABLED."
    --CONFIGURABLE
::= { usrIp 25 }
usrIpIeaForceNexthopRoute OBJECT-TYPE
    SYNTAX     INTEGER {
                    enabled(1),
                    disabled(2)
                    }
    MAX-ACCESS read-write
    STATUS current
    DESCRIPTION
  	    "This flag is DISABLED by default. The state DISABLED states NOT
		 to drop the connection for the user if the next hop in INVALID 
         and also to use other routes to forward the packets when the next 
         hop router is unreachable. 
		 If the state is ENABLED, then the user will be disconnected 
         if nexthop route is INVALID and also drop the packets when nexthop 
         route becomes unreachable."
    --CONFIGURABLE
::= { usrIp 26 }
usrIpSRCPingAddress OBJECT-TYPE
    SYNTAX  IpAddress
    MAX-ACCESS  read-write
    STATUS  current
    DESCRIPTION
        "This variable sets the src address for ping"
    --CONFIGURABLE
::= { usrIp 27 }
usrIpSRCTraceRouteAddress OBJECT-TYPE
    SYNTAX  IpAddress
    MAX-ACCESS  read-write
    STATUS  current
    DESCRIPTION
        "This variable sets the src address for traceroute"
    --CONFIGURABLE
::= { usrIp 28 }
usrIpProxyArpAllDialinNet OBJECT-TYPE 
    SYNTAX INTEGER
    {
       disabled(2),
       enabled(1)
    }
    MAX-ACCESS   read-write 
    STATUS   current
    DESCRIPTION
        "Indicates whether Proxy ARPing all dialin networks 
         feature is enabled. Default is disabled"
             --CONFIGURABLE
::= { usrIp 29 }
usrIpSendHostUnreachForPool OBJECT-TYPE
    SYNTAX INTEGER
    {
       disabled(2),
       enabled(1)
    }
    MAX-ACCESS   read-write
    STATUS   current
    DESCRIPTION
        "Indicates whether to send icmp unreachable for pool addresses
         Default is disabled"
   --CONFIGURABLE
::= { usrIp 30 }
usrIpIeaNextHopRouting OBJECT-TYPE
    SYNTAX     INTEGER {
                    enabled(1),
                    disabled(2)
                    }
    MAX-ACCESS read-write
    STATUS current
    DESCRIPTION
      "Indicates whether next hop routing is enabled or not.
       The default value is ENABLED"
    --CONFIGURABLE
::= { usrIp 31 }
usrIpSrcVTPAddress OBJECT-TYPE
        SYNTAX  IpAddress
        MAX-ACCESS  read-write
        STATUS  current
        DESCRIPTION
                "For all VTP packets send out this will the source address.
                 If zero internal ip address or interface IP address
                 will be the source address."
        --CONFIGURABLE 
::= { usrIp 32 }
usrIpSrcPPTPAddress OBJECT-TYPE
        SYNTAX  IpAddress
        MAX-ACCESS  read-write
        STATUS  current
        DESCRIPTION
        "For all PPTP packets sent out by the PAC, this will the source address.
         If this is zero then the internal ip addr or interface IP addr will be
         the source address ."
        --CONFIGURABLE
::= { usrIp 33 }
usrIpSrcL2TPAddress OBJECT-TYPE
    SYNTAX  IpAddress
    MAX-ACCESS  read-write
    STATUS  current
    DESCRIPTION 
        "For all L2TP packets sent out by the LAC, this will the source address.
         If this is zero then the internal ip addr or interface IP addr will be
         the source address ."
    --CONFIGURABLE
::= { usrIp 34 }
          -- the IP source address based routing table
          -- The IP routing table contains an entry for each route
          -- presently known to this entity.
          usrIpSrcRouteTable OBJECT-TYPE
              SYNTAX  SEQUENCE OF UsrIpSrcRouteEntry
              MAX-ACCESS  not-accessible
              STATUS  current
              DESCRIPTION
                      "This entity's IP Source Routing table."
              ::= { usrIp 35 }
          usrIpSrcRouteEntry OBJECT-TYPE
              SYNTAX  UsrIpSrcRouteEntry
              MAX-ACCESS  not-accessible
              STATUS  current
              DESCRIPTION
                      "A route to a particular destination."
              INDEX   { usrIpSrcRouteDest }
              ::= { usrIpSrcRouteTable 1 }
          UsrIpSrcRouteEntry ::=
              SEQUENCE {
                  usrIpSrcRouteDest
                      IpAddress,
                  usrIpSrcRouteIfIndex
                      Integer32,
                  usrIpSrcRouteMetric1
                      Integer32,
                  usrIpSrcRouteNextHop
                      IpAddress,
                  usrIpSrcRouteType
                      INTEGER,
                  usrIpSrcRouteProto
                      INTEGER,
                  usrIpSrcRouteMask
                      IpAddress,
                  usrIpSrcRouteStatus
                      INTEGER
              }
          usrIpSrcRouteDest OBJECT-TYPE
              SYNTAX  IpAddress
              MAX-ACCESS  read-write
              STATUS  current
              DESCRIPTION
                      "The destination IP address of this route.  An
                      entry with a value of 0.0.0.0 is considered a
                      default route.  Multiple routes to a single
                      destination can appear in the table, but access to
                      such multiple entries is dependent on the table-
                      access mechanisms defined by the network
                      management protocol in use.  
                      This object is not applicable to the PDSN"
                 --CONFIGURABLE
              ::= { usrIpSrcRouteEntry 1 }
          usrIpSrcRouteIfIndex OBJECT-TYPE
              SYNTAX  Integer32
              MAX-ACCESS  read-write
              STATUS  current
              DESCRIPTION
                      "The index value which uniquely identifies the
                      local interface through which the next hop of this
                      route should be reached.  The interface identified
                      by a particular value of this index is the same
                      interface as identified by the same value of
                      ifIndex.
                      This object is not applicable to the PDSN"
              ::= { usrIpSrcRouteEntry 2 }
          usrIpSrcRouteMetric1 OBJECT-TYPE
              SYNTAX  Integer32 (0..15)
              MAX-ACCESS  read-write
              STATUS  current
              DESCRIPTION
                      "The primary routing metric for this route.  The
                      semantics of this metric are determined by the
                      routing-protocol specified in the route's
                      ipRouteProto value.  If this metric is not used,
                      its value should be set to -1.
                      This object is not applicable to the PDSN"
              --CONFIGURABLE
              ::= { usrIpSrcRouteEntry 3 }
          usrIpSrcRouteNextHop OBJECT-TYPE
              SYNTAX  IpAddress
              MAX-ACCESS  read-write
              STATUS  current
              DESCRIPTION
                      "The IP address of the next hop of this route.
                      (In the case of a route bound to an interface
                      which is realized via a broadcast media, the value
                      of this field is the agent's IP address on that
                      interface.)
                      This object is not applicable to the PDSN"
               --CONFIGURABLE
              ::= { usrIpSrcRouteEntry 4 }
          usrIpSrcRouteType OBJECT-TYPE
              SYNTAX  INTEGER {
                          other(1),        -- none of the following
                          invalid(2),      -- an invalidated route
                                           -- route to directly
                          direct(3),       -- connected (sub-)network
                                           -- route to a non-local
                          indirect(4)      -- host/network/sub-network
                      }
              MAX-ACCESS  read-write
              STATUS  current
              DESCRIPTION
                      "The type of route.  Note that the values
                      direct(3) and indirect(4) refer to the notion of
                      direct and indirect routing in the IP
                      architecture. The only value settable from SNMP
                      is invalid(2).
                      Setting this object to the value invalid(2) has
                      the effect of invalidating the corresponding entry
                      in the ipRouteTable object.  That is, it
                      effectively disassociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { usrIpSrcRouteEntry 5 }
          usrIpSrcRouteProto OBJECT-TYPE
              SYNTAX  INTEGER {
                          other(1),       -- none of the following
                                          -- non-protocol information,
                                          -- e.g., manually configured
                          local(2),       -- entries
                                          -- set via a network
                          netmgmt(3),     -- management protocol
                                          -- obtained via ICMP,
                          icmp(4),        -- e.g., Redirect
                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14),
                          source(15)
                      }
              MAX-ACCESS  read-only
              STATUS  current
              DESCRIPTION
                      "The routing mechanism via which this route was
                      learned.  Inclusion of values for gateway routing
                      protocols is not intended to imply that hosts
                      should support those protocols.
                      This object is not applicable to the PDSN"
              ::= { usrIpSrcRouteEntry 6 }
          usrIpSrcRouteMask OBJECT-TYPE
              SYNTAX  IpAddress
              MAX-ACCESS  read-write
              STATUS  current
              DESCRIPTION
                      "Indicate the mask to be logical-ANDed with the
                      destination address before being compared to the
                      value in the ipSrcRouteDest field.  For those systems
                      that do not support arbitrary subnet masks, an
                      agent constructs the value of the ipRouteMask by
                      determining whether the value of the correspondent
                      ipSrcRouteDest field belong to a class-A, B, or C
                      network, and then using one of:
                           mask           network
                           255.0.0.0      class-A
                           255.255.0.0    class-B
                           255.255.255.0  class-C
                      If the value of the ipRouteDest is 0.0.0.0 (a
                      default route), then the mask value is also
                      0.0.0.0.  It should be noted that all IP routing
                      subsystems implicitly use this mechanism.  
                      This object is not applicable to the PDSN"
              --CONFIGURABLE
              ::= { usrIpSrcRouteEntry 7 }
          usrIpSrcRouteStatus OBJECT-TYPE
              SYNTAX  INTEGER {
                                up(1),
                                down(2),
                                invalid(3)
                                }
              MAX-ACCESS  read-write
              STATUS  current
              DESCRIPTION
                      "Whether the route is UP or DOWN - updated 
                       internally depending upon whether the network 
                       goes up or down. Not settable via SNMP.
                       This object is not applicable to the PDSN"
              ::= { usrIpSrcRouteEntry 8 }
-- The following table is modeled after IGMP.
usrIpSrcRouteInterfaceTable OBJECT-TYPE
    SYNTAX     SEQUENCE OF UsrIpSrcRouteInterfaceEntry
    MAX-ACCESS not-accessible
    STATUS     current
    DESCRIPTION
    "The table listing the interfaces on which source based routing is enabled."
    ::= { usrIp 36 }
usrIpSrcRouteInterfaceEntry OBJECT-TYPE
    SYNTAX     UsrIpSrcRouteInterfaceEntry
    MAX-ACCESS not-accessible
    STATUS     current
    DESCRIPTION
    "An entry representing an interface on which source based routing is enabled."
    INDEX      { usrIpSrcRouteInterfaceIfName }
    ::= { usrIpSrcRouteInterfaceTable 1 }
UsrIpSrcRouteInterfaceEntry ::= SEQUENCE {
    usrIpSrcRouteInterfaceIfName       DisplayString,
    usrIpSrcRouteInterfaceEnabled      INTEGER
                                        }
usrIpSrcRouteInterfaceIfName OBJECT-TYPE
    SYNTAX     DisplayString (SIZE (1..32))
    MAX-ACCESS not-accessible
    STATUS     current
    DESCRIPTION
            "The interface name for which source rbased routing is enabled."
::= { usrIpSrcRouteInterfaceEntry 1 }
usrIpSrcRouteInterfaceEnabled OBJECT-TYPE
    SYNTAX     INTEGER {
                    enabled(1),
                    disabled(2)
                    }
    MAX-ACCESS read-write                                                 
    STATUS     current                                                   
    DESCRIPTION 
             "Indicates whether source routing is enabled or not." 
    DEFVAL    { disabled }
    --CONFIGURABLE                         
::= { usrIpSrcRouteInterfaceEntry 2 }                                        
usrIpRespondToDirectedBcst OBJECT-TYPE 
    SYNTAX INTEGER
    {
       disabled(2),
       enabled(1)
    }
    MAX-ACCESS   read-write 
    STATUS   current
    DESCRIPTION
        "Disable responding to directed bcast globally"
             --CONFIGURABLE
::= { usrIp 37 }
usrIpForwardDirectedBcst OBJECT-TYPE 
    SYNTAX INTEGER
    {
       disabled(2),
       enabled(1)
    }
    MAX-ACCESS   read-write 
    STATUS   current
    DESCRIPTION
        "Enable directed bcast forwarding in IP"
             --CONFIGURABLE
::= { usrIp 39 }
usrIpStaticArpTable OBJECT-TYPE
	SYNTAX SEQUENCE OF UsrIpStaticRouteEntry
	MAX-ACCESS not-accessible
	STATUS current
	DESCRIPTION
		"Table of Static Arp cache"
::= { usrIp 38 }
usrIpStaticArpEntry OBJECT-TYPE
	SYNTAX UsrIpStaticRouteEntry
	MAX-ACCESS not-accessible
	STATUS current
	DESCRIPTION
		""
	INDEX { usrIpStaticArpIpAddr,usrIpusrIpStaticArpInt}
::= { usrIpStaticArpTable 1 }
UsrIpStaticRouteEntry ::= SEQUENCE {
	usrIpStaticArpIpAddr        IpAddress,
	usrIpusrIpStaticArpInt      OCTET STRING,
	usrIpStaticArpStatus	    INTEGER,
        usrIpStaticArpMacAddr       OCTET STRING,
	usrIpStaticArpState	    INTEGER
	}
usrIpStaticArpIpAddr OBJECT-TYPE
    SYNTAX  IpAddress
    MAX-ACCESS  read-only
    STATUS  current
    DESCRIPTION
		"The ip address of the ARP entry"
::= { usrIpStaticArpEntry 1 }
usrIpusrIpStaticArpInt OBJECT-TYPE
    SYNTAX  OCTET STRING (SIZE(0..16))
    MAX-ACCESS  read-only
    STATUS  current
    DESCRIPTION
		"The interface of the static ARP entry"
::= { usrIpStaticArpEntry 2 }
usrIpStaticArpStatus OBJECT-TYPE
    SYNTAX  INTEGER {
                add(1), -- set when arp entry added
                delete(2) -- delete entry
                }
	MAX-ACCESS read-write
	STATUS current
	DESCRIPTION
		"This object is used to identify the ARP operation.
                 It is set to 1 when an entry is added; setting it
                 to 2 will delete the entry."
   --CONFIGURABLE
::= { usrIpStaticArpEntry 3 }
usrIpStaticArpMacAddr OBJECT-TYPE
    SYNTAX OCTET STRING (SIZE(6))
	MAX-ACCESS read-write
	STATUS current
	DESCRIPTION
		"This object is used to store the associated MAC address"
   --CONFIGURABLE
::= { usrIpStaticArpEntry 4 }
usrIpStaticArpState OBJECT-TYPE
	SYNTAX	INTEGER {
		public(1),
		private(2),
                invalid(3)
	}
	MAX-ACCESS	read-write
	STATUS	current
	DESCRIPTION
		"This is the type of static arp entry. Public/private "
   --CONFIGURABLE
::= { usrIpStaticArpEntry 5 }
usrIpAggregateRouteTable OBJECT-TYPE
    SYNTAX  SEQUENCE OF UsrIpAggregateRouteEntry
    MAX-ACCESS  not-accessible
    STATUS  current
    DESCRIPTION
        "This table is used to display multiple aggregate routes for an
         IP pool. An IP pool could be segregated into multiple sub pools.
         depending on the size."          
    ::= { usrIp 40 } 
usrIpAggregateRouteEntry OBJECT-TYPE 
    SYNTAX  UsrIpAggregateRouteEntry
    MAX-ACCESS  not-accessible
    STATUS  current
    DESCRIPTION    
        "A table of PoolName, Initial Address, Aggregate Route, Endpoint address,
         Type"      
    INDEX { usrIpAggInitPoolAddress }
    ::= { usrIpAggregateRouteTable 1 }
UsrIpAggregateRouteEntry ::= 
    SEQUENCE {
        usrIpAggInitPoolAddress  
            IpAddress,
        usrIpAggPoolName
            DisplayString,     
        usrIpAggPoolAggregateRoute
            IpAddress,
        usrIpAggPoolNetMask
            IpAddress,
        usrIpAggPoolSize
            Integer32,
        usrIpAggPoolType    
            Integer32    
    }   
usrIpAggInitPoolAddress OBJECT-TYPE
    SYNTAX  IpAddress
    MAX-ACCESS  read-only
    STATUS  current
    DESCRIPTION
        "Initial pool address for aggregate pool"
    ::= { usrIpAggregateRouteEntry 1 }
usrIpAggPoolName OBJECT-TYPE
    SYNTAX  DisplayString
    MAX-ACCESS  read-only
    STATUS  current
    DESCRIPTION
        "Aggregate Pool name"
    ::= { usrIpAggregateRouteEntry 2 }
usrIpAggPoolAggregateRoute OBJECT-TYPE
    SYNTAX  IpAddress
    MAX-ACCESS  read-only
    STATUS  current
    DESCRIPTION
        "Aggregate route that will be broadcasted"
    ::= { usrIpAggregateRouteEntry 3 }
usrIpAggPoolNetMask OBJECT-TYPE
    SYNTAX  IpAddress
    MAX-ACCESS  read-only
    STATUS  current
    DESCRIPTION
        "Mask for an aggregate route pool"
    ::= { usrIpAggregateRouteEntry 4 }
usrIpAggPoolSize OBJECT-TYPE
    SYNTAX  Integer32
    MAX-ACCESS  read-only
    STATUS  current
    DESCRIPTION
        "Indicates the last valid address in this aggregate pool"
    ::= { usrIpAggregateRouteEntry 5 }
usrIpAggPoolType OBJECT-TYPE
    SYNTAX  Integer32
    MAX-ACCESS  read-only
    STATUS  current
    DESCRIPTION
        "Indicates the type of the aggregate pool. It might be
         MULTI_AGGREGATE, NON_AGGREGATE, AGGREGATE"
    ::= { usrIpAggregateRouteEntry 6 }
usrIpSrcFAAddress OBJECT-TYPE
        SYNTAX  IpAddress
        MAX-ACCESS  read-write
        STATUS  current
        DESCRIPTION
                "For all FA packets send out this will the source address.
                 If zero internal ip address or interface IP address
                 will be the source address.
		This object is valid only for PDSN."
        --CONFIGURABLE 
::= { usrIp 41 }
usrIpSrcVHAAddress OBJECT-TYPE
        SYNTAX  IpAddress
        MAX-ACCESS  read-write
        STATUS  current
        DESCRIPTION
                "For all VHA packets send out this will the source address.
                 If zero internal ip address or interface IP address
                 will be the source address.
		 This object is valid only for PDSN."
        --CONFIGURABLE 
::= { usrIp 42 }
usrIpSrcHAAddress OBJECT-TYPE
   SYNTAX IpAddress
   MAX-ACCESS read-write
   STATUS current
   DESCRIPTION
       "This will be the HA source IP address. The user will specify using
        this object that which address HA will use as its Boot IP address.
        This object is valid only for HA. "
   --CONFIGURABLE
::= { usrIp 43}
usrIpSrcHACNAddress OBJECT-TYPE
   SYNTAX IpAddress
   MAX-ACCESS read-write
   STATUS current
   DESCRIPTION
       "This will be the HACN boot IP address.
	This object is valid only for HACN"
   --CONFIGURABLE
::= { usrIp 46}
usrIpNetworksCfgFileName OBJECT-TYPE
	SYNTAX      DisplayString
	MAX-ACCESS  read-only
	STATUS      current
	DESCRIPTION		
		"The name of a ConfigFile to read/write  permanent database records.
		 If the value of this object is an empty string, then the
		 IP module uses the default name `@file://IPModule.cfg'. "
::= { usrIp 52}
usrIpSrcSNMPAddress OBJECT-TYPE
        SYNTAX  IpAddress
        MAX-ACCESS  read-write
        STATUS  current
        DESCRIPTION
                "For all SNMP packets send out this will the source address.
                 If zero internal ip address or interface IP address
                 will be the source address.
		This object is valid only for PDSN, HA, HACN."
        --CONFIGURABLE 
::= { usrIp 55 }
END         -- End USR-IP-MIB DEFINITIONS
-- ************************************************************************
--
--	usr_invarp.mib - A proprietary MIB file for Inverse ARP cache 
--
-- Author:        P K Das 
--
