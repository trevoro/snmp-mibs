-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
--
-- 1.00      22-May-95  N. Marino	Initial Revision
-- 1.00A     26-Jun-96  N. Marino	Latching loopback detection
--
SNMP540-MGMT-MIB DEFINITIONS ::= BEGIN

IMPORTS

	OBJECT-TYPE			FROM RFC-1212
	DisplayString			FROM RFC1213-MIB
	dsu				FROM DDS-MIB;

snmp540 	OBJECT IDENTIFIER ::= { dsu 4 }

-- This MIB module uses the extended OBJECT-TYPE macro as
-- defined in RFC 1212.

-- The implementation of all groups is mandatory for all products in
-- the SNMP540 family.

-- Note:  All rows in all tables defined within this MIB module are
-- virtual.  They can neither be created or deleted by management
-- operations.

-- The Version Group. This group identifies the version information
-- for the MIB.
--
snmp540MIBversion OBJECT-TYPE
    SYNTAX DisplayString (SIZE (5))
    ACCESS read-only
    STATUS mandatory
    DESCRIPTION
    	"Identifies the version of the MIB. The format
	 of the version is x.yzT, where 'x' identifies
	 the major revision number, 'y'identifies the
	 minor revision number, 'z' identifies the
    	 typographical revision, and T identifies the
	 test revision.  Acceptable values for the 
	 individual revision components are
    	 as follows

    		x: 1 - 9
    		y: 0 - 9
    		z: 0 - 9
    		T: A - Z

    	Upon formal release, no designation for the test
	revision will be present."
    ::= { snmp540 1 }

-- The snmp540 Group.  This group contains objects that support the
-- specific management requirements of the snmp540 that are not
-- addressed through other standard MIB modules. 

snmp540Config OBJECT IDENTIFIER ::= { snmp540 2 }

snmp540ActivateCfg OBJECT-TYPE
    SYNTAX INTEGER {
    	noChange(1),
    	activateNewCfg(2)
    }
    ACCESS read-write
    STATUS mandatory
    DESCRIPTION
	"The Activate configuration object.
	 The value noChange(1), will maintain the
	 old dataset configuration without saving any
	 changes. The value activateNewCfg(2),
	 will activate the latest changes into
	 the dataset configuration. No configuration
	 changes will be activated until 
	 the activateNewCfg(2) is performed. Once
	 activateNewCfg(2) is sent and acknowledged,
	 the unit will modify its active configuration.
	 The unit may temporarily be out of service
         until the activate has been completed.
	 A set using noChange(1) value will cause 
	 the snmp540 to discard all unactivated changes."
    ::= { snmp540Config  1 }

snmp540DtePortType OBJECT-TYPE
    SYNTAX INTEGER {
    	rs232(1),
    	v35(2),
	auto(3)
    }
    ACCESS read-write
    STATUS mandatory
    DESCRIPTION
	"The value auto(3) indicates that the electrical
	 portion of the DTE interface is automatically
	 detected. The rs232(1) value forces the DTE port
         to EIA/TIA-232-E, and v35(2) will force the DTE
	 port to V.35."
    ::= { snmp540Config 2 }

snmp540EiaTestControl OBJECT IDENTIFIER ::= { snmp540Config 3 }

snmp540EiaRlcontrol OBJECT-TYPE
    SYNTAX INTEGER {
        allow(1),
        block(2)
        }
    ACCESS  read-write
    STATUS  mandatory
    DESCRIPTION
        "The RL Eia Test control lead option.
         This option either allows or blocks EIA
         initiated test inputs from the DTE
         interface."
    ::= { snmp540EiaTestControl 1 }

snmp540EiaLlcontrol OBJECT-TYPE
    SYNTAX INTEGER {
        allow(1),
        block(2)
        }
    ACCESS  read-write
    STATUS  mandatory
    DESCRIPTION
        "The LL Eia Test control lead option.
         This option either allows or blocks EIA
         initiated test inputs from the DTE
         interface."
    ::= { snmp540EiaTestControl 2 }

snmp540EiaTmcontrol OBJECT-TYPE
    SYNTAX INTEGER {
	allow(1),
	block(2)
	}
    ACCESS  read-write
    STATUS  mandatory
    DESCRIPTION
	" The Eia Test Mode lead option.
	This option controls the operation of
	the Test Mode output indication.  A
	value of (1) allows the Test Mode 
	output to indicate the snmp540 is
	in a test mode.  A value of (2)
	will block all Test Mode lead
	indications."
    ::= { snmp540EiaTestControl 3 }

snmp540LlbDetect OBJECT-TYPE
    SYNTAX INTEGER {
	allow(1),
	block(2)
	}
    ACCESS  read-write
    STATUS  mandatory
    DESCRIPTION
	" The Latching Loopback test detect option.
	This option controls the operation of
	the latching loopback detection.  A
	value of (1) allows, the latching loopback
	test pattern will be detected.  A value of (2)
	will block the detection of latching loopback
	pattern."
    ::= { snmp540EiaTestControl 4 }

snmp540Control OBJECT IDENTIFIER ::= { snmp540 3 }

snmp540UnitReset OBJECT-TYPE
    SYNTAX INTEGER {
	normal(1),
        reset(2)
    }
    ACCESS read-write
    STATUS mandatory
    DESCRIPTION
	"The value reset(2) will cause the snmp540
	 to perform a cold start.  As soon as the
	 object has been set to reset(2), the snmp540
	 will begin its reinitialization. A normal(1)
	 set request will have no effect."
    ::= { snmp540Control 1 }

--**************************************************************************
--                      Alarm Configuration
--**************************************************************************
snmp540AlarmData OBJECT IDENTIFIER ::= { snmp540 4 }

snmp540PowerUpAlm 		OBJECT IDENTIFIER ::= { snmp540AlarmData 1 }
snmp540CfgChkSumErrAlm 		OBJECT IDENTIFIER ::= { snmp540AlarmData 2 }
snmp540StcLoopbackAlm       	OBJECT IDENTIFIER ::= { snmp540AlarmData 3 } 
snmp540NoNtwkLoopCurrentAlm 	OBJECT IDENTIFIER ::= { snmp540AlarmData 4 } 
snmp540LinePairsReversedAlm 	OBJECT IDENTIFIER ::= { snmp540AlarmData 5 } 
snmp540NoSignalAlm	        OBJECT IDENTIFIER ::= { snmp540AlarmData 6 } 
snmp540FpTestAlm	        OBJECT IDENTIFIER ::= { snmp540AlarmData 7 } 
snmp540DSRLossAlm		OBJECT IDENTIFIER ::= { snmp540AlarmData 8 } 
snmp540DTRLossAlm 		OBJECT IDENTIFIER ::= { snmp540AlarmData 9 }
snmp540DTPLossAlm        	OBJECT IDENTIFIER ::= { snmp540AlarmData 10 }
snmp540DCDLossAlm        	OBJECT IDENTIFIER ::= { snmp540AlarmData 11 } 
snmp540RXDLossAlm        	OBJECT IDENTIFIER ::= { snmp540AlarmData 12 } 
snmp540TXDLossAlm        	OBJECT IDENTIFIER ::= { snmp540AlarmData 13 } 
snmp540JitterAlm         	OBJECT IDENTIFIER ::= { snmp540AlarmData 14 } 
snmp540BpvAlm            	OBJECT IDENTIFIER ::= { snmp540AlarmData 15 } 
snmp540FrameLossAlm      	OBJECT IDENTIFIER ::= { snmp540AlarmData 16 } 
snmp540SignalToNoiseAlm  	OBJECT IDENTIFIER ::= { snmp540AlarmData 17 } 
snmp540RxSignalLowAlm    	OBJECT IDENTIFIER ::= { snmp540AlarmData 18 } 

-- All alarms 'ARE MASKABLE'. Alarm entries snmp540JitterAlm{14}, snmp540BpvAlm{15}, 
-- snmp540FrameLossAlm{16}, snmp540SignalToNoiseAlm{17}, and snmp540RxSignalLowAlm{18} 
-- require threshold settings. See snmp540AlarmCfgTable for alarm threshold settings.

-- Alarm		Table Entry			Port Use
-- --------------	---------------------------	------------ 
-- Power Up Alarm 	snmp540PowerUpAlm		DTE and Line
-- EEPROM Corrupt	snmp540CfgChkSumErrAlm		DTE and Line
-- Network Loop		snmp540StcLoopbackAlm 		Line
-- No Loop Current	snmp540NoNtwkLoopCurrentAlm 	Line
-- Line Pair Reversed	snmp540LinePairsReversedAlm	Line
-- No Signal		snmp540NoSignalAlm		Line
-- Front Panel Test	snmp540FpTestAlm		Not reported on SNMP540-IFP
-- DSR Loss		snmp540DSRLossAlm		DTE
-- DTR Loss		snmp540DTRLossAlm		DTE
-- DTP Loss		snmp540DTPLossAlm		DTE
-- DCD Loss		snmp540DCDLossAlm		DTE
-- RXD Loss		snmp540RXDLossAlm		DTE
-- TXD Loss		snmp540TXDLossAlm		DTE
-- Jitter		snmp540JitterAlm		Line
-- Bipolar Violations	snmp540BpvAlm			Line
-- Frame Loss		snmp540FrameLossAlm		Line
-- Signal/Noise Ratio	snmp540SignalToNoiseAlm		Line
-- RX Level Low		snmp540RxSignalLowAlm		Line


snmp540AlarmCfgThr OBJECT IDENTIFIER ::= { snmp540 5 }

snmp540AlarmCfgCountWindow OBJECT-TYPE
    SYNTAX  INTEGER (1..15)
    ACCESS read-write
    STATUS mandatory
    DESCRIPTION
    	"This is the  DDS Alarm Threshold Interval. It
	 specifies the amount of time, 1 to 15 minutes,
	 in which the threshold setting is to be exceeded
	 for the alarm to occur."
    ::= { snmp540AlarmCfgThr 1 }


snmp540AlarmCfgTable OBJECT-TYPE
        SYNTAX  SEQUENCE OF Snmp540AlarmCfgEntry
        ACCESS  not-accessible
        STATUS  mandatory   
        DESCRIPTION 
                "The GDC snmp540 Alarm Configuration Table."
        ::= { snmp540AlarmCfgThr 2 }

snmp540AlarmCfgEntry OBJECT-TYPE
        SYNTAX  Snmp540AlarmCfgEntry
        ACCESS  not-accessible
        STATUS  mandatory
        DESCRIPTION
	    "An entry in the snmp540 alarm table."
        INDEX   { snmp540AlarmCfgIdentifier }   
        ::= { snmp540AlarmCfgTable 1 }

Snmp540AlarmCfgEntry ::=
        SEQUENCE {
                snmp540AlarmCfgIdentifier 	OBJECT IDENTIFIER,
		snmp540AlarmCfgThreshold	INTEGER
	}

snmp540AlarmCfgIdentifier OBJECT-TYPE
    SYNTAX OBJECT IDENTIFIER
    ACCESS read-only
    STATUS mandatory
    DESCRIPTION
        "The unique alarm identifier assigned to this
	 alarm type. The format of this identifier is
	 an OBJECT IDENTIFIER that has the following
	 format: {iso(1) org(3) dod(6) internet(1)
         private(4) enterprises(1) gdc(498) xxx(x)
	 alarm(z) yyy(y) where xxx(x) is the
	 administratively assigned family object
         identifier (z) is the object identifier for
	 alarms in the family defined MIB and yyy(y)
	 is the administratively assigned alarm
         type identifier for this alarm."
    ::= { snmp540AlarmCfgEntry 1 }

snmp540AlarmCfgThreshold OBJECT-TYPE
    SYNTAX  INTEGER (-50..99)
    ACCESS read-write
    STATUS mandatory
    DESCRIPTION
    	"This function sets/reads the alarm threshold
	 settings criteria.  This threshold is used
	 along with the alarm window to determine
	 the number of instances in a given time frame
	 for an alarm to occur before the alarm is
	 considered active. 

	Alarm       Table Entry	       Range     Default
	-------     ----------------  ---------  --------
	Jitter    snmp540JitterAlm     0 to 99%      10%
	BPV's	  snmp540BpvAlm        0 to 99Count  10
	Frm Loss  snmp540FrameLossAlm  0 to 99Count  10
	SNRatio   snmp540SignalToNoiseAlm  0 to 50    0
	Rx Low 	  snmp540RxSignalLowAlm  -50 to 6db -30dB"
    ::= { snmp540AlarmCfgEntry 2 }
--
-- DDS Line Statistics
--
snmp540LineStats OBJECT IDENTIFIER ::= { snmp540 6 }

snmp540LineStatsInterval OBJECT-TYPE
    SYNTAX  INTEGER (1..15)
    ACCESS read-write
    STATUS mandatory
    DESCRIPTION
    	"The DDS Line Statistics Interval specifies
         the amount of LineStats data to be reported.
         Measurements are stored every minute and
         accumulated.  The latest 15 minutes(samples)
         of information are always available.
         The LineStatsInterval specifies the number
         of one minute sample intervals that will
         be accumulated and reported." 
    ::= { snmp540LineStats 1 }
    
snmp540LineStatsTxLevel OBJECT-TYPE
    SYNTAX  INTEGER (0..6)
    ACCESS read-only
    STATUS mandatory
    DESCRIPTION
    	"Transmit level being generated into the
         private line circuit.  This value
	is typically 6db."
    ::= { snmp540LineStats 2 }

snmp540LineStatsRxInterpretation OBJECT-TYPE
    SYNTAX INTEGER {
    	noSignal(1),
    	notAvailable(2),
        signalToNoiseNotMeasured(3),
        allReadingsValid(4),
        sToNRatioGreaterThanMeasured(5)
    }
    ACCESS read-only
    STATUS mandatory
    DESCRIPTION
    	"This object the characterizes LineStats readings.

	Interpretation code		Meaning
       .....................   ...........................

 	noSignal(1)	 No line signal is being received.

	notAvailable(2)    Data is still being accumulated.

	signalToNoiseNotMeasured(3) S/N ratio not measured.

	allReadingsValid(4)   All data reported is in range.

        sToNRatioGreaterThanMeasured(5) S/N ratio (greater)
		                than the value reported in
                                        SignalToNoiseRatio."
    ::= { snmp540LineStats 3 }

snmp540LineStatsRxLevel OBJECT-TYPE
    SYNTAX INTEGER (-50..6)
    ACCESS read-only
    STATUS mandatory
    DESCRIPTION
    	"This object reports the receive level
        measurement for the selected interval.
         The range reported is from -50dB to +6dB."
    ::= { snmp540LineStats 4 }

snmp540LineStatsSignalToNoiseRatio OBJECT-TYPE
    SYNTAX INTEGER (0..50)
    ACCESS read-only
    STATUS mandatory
    DESCRIPTION
    	"This object will the report the signal to
         noise ratio ranging from 0db to 50db for
         the selected interval. The value is absolute.
         If RxInterpretation reports sToNRatioGreaterThanMeasured,
         then the actual signal to noise ratio is better than
         the value reported here.  If RxInterpretation reports
         signalToNoiseNotMeasured, the value reported here
	 is meaningless."
    ::= { snmp540LineStats 5 }

snmp540LineStatsSignalQuality OBJECT-TYPE
    SYNTAX INTEGER {
    	good(1),
    	fair(2),
    	bad(3)
    }
    ACCESS read-only
    STATUS mandatory
    DESCRIPTION
    	"This object reports the signal quality of 
	the line, for the selected interval."
    ::= { snmp540LineStats 6 }

snmp540LineStatsJitter OBJECT-TYPE
    SYNTAX INTEGER (0..99)
    ACCESS read-only
    STATUS mandatory
    DESCRIPTION
    	"This object will the report the percent jitter
	of the line, for the selected interval."
    ::= { snmp540LineStats 7 }

snmp540LineStatsBpvCount OBJECT-TYPE
    SYNTAX INTEGER (0..99)
    ACCESS read-only
    STATUS mandatory
    DESCRIPTION
    	"This object will the report the number of bipolar
         violation codes received during for the selected
         LineStatsInterval."
    ::= { snmp540LineStats 8 }

snmp540LineStatsFrameLossCount OBJECT-TYPE
    SYNTAX INTEGER (0..99)
    ACCESS read-only
    STATUS mandatory
    DESCRIPTION
    	"This object will the report the number frame
         losses received for the selected
         LineStatsInterval."
    ::= { snmp540LineStats 9 }

-- 
-- Diagnostic Test Group
--
-- The objects here are used to configure, initiate, and
-- read all test results, and halt all tests that might be 
-- running.  

snmp540DiagTest OBJECT IDENTIFIER ::= { snmp540 7 }

snmp540DiagTestPattern OBJECT-TYPE
    SYNTAX INTEGER {
    	snmp540Send511Pattern(1),
    	snmp540Send2047Pattern(2),
    	snmp540Send15BitPattern(3)
    }
    ACCESS read-write
    STATUS mandatory
    DESCRIPTION
	"The Self Test Pattern choices generated 
         internally by the snmp540 are 511 Pattern
         (snmp540Send511Pattern(2)), 2047 pattern,
	 (snmp540Send2047Pattern(3)) and 15 bit pattern,
	 snmp540Send15BitPattern(4)."
    ::= { snmp540DiagTest 1 }

snmp540DiagTestExceptions OBJECT-TYPE
    SYNTAX INTEGER {
	noExceptions(1),
	bitsOutOfRange(2)
    }
    ACCESS read-only
    STATUS mandatory
    DESCRIPTION
    	"Indicates exceptions that have occurred
         that may affect interpretation of the
         test results.

         The exception values are:

         value	exception:
         ....... .....................................

	  1   All test results are valid.
          2   snmp540DiagBitErrors has been exceeded."
		
    ::= { snmp540DiagTest 2 }

snmp540DiagBitErrors OBJECT-TYPE
    SYNTAX INTEGER
    ACCESS read-only
    STATUS mandatory
    DESCRIPTION
    	"The bit errors of the most recently run
         diagnostic test.  If TestExceptions reports
         bitsOutOfRange, this object should be ignored."
    ::= { snmp540DiagTest 3 }

snmp540DiagBlockErrors OBJECT-TYPE
    SYNTAX INTEGER
    ACCESS read-only
    STATUS mandatory
    DESCRIPTION
    	"The block errors of the most recently run
         diagnostic test."
    ::= { snmp540DiagTest 4 }

snmp540RlLoopType OBJECT-TYPE
    SYNTAX INTEGER {
    	pn127(1),		
    	v54(2)		
    }
    ACCESS read-write
    STATUS mandatory
    DESCRIPTION
	"The value Pn127(1), will use a PN127 loopback
         sequence to initiate a remote loopback test.
         The value v54(2) will use a V54 loopback
         sequence to initiate a remote loopback test." 
    ::= { snmp540DiagTest 5 }

snmp540DiagBlocksToSend OBJECT-TYPE
    SYNTAX INTEGER {
	blocks1(1),
	blocks10(2),
	blocks100(3),
	blocks500(4),
	blocks1000(5),
	blocks5000(6),
	blocks10000(7),
	blocks50000(8),
        external(9)
	}
    ACCESS read-write
    STATUS mandatory
    DESCRIPTION
    	"Specifies the number of test pattern blocks to
         generate during the test.  The requested number
         of blocks are sent and checked during the test
         as a means of verifying circuit and/or unit
         integrity.  Each block contains 1000 bits of test
         pattern.  The external selection specifies that
         the test be invoked without any test pattern
	 block generation.  The external(9) disables the
	 automatic test tear-down timer, and requires the
	 use of an external Bit Error Rate Tester(BERT).

	 !!!!!!!!!!! WARNING !!!!!!!!!!!!!!!!!!
	
	 THE SNMP540 EXTERNAL(9) TEST SELECTION REQUIRES 
	 A POWER-UP RESET TO END THE TEST !!" 

    ::= { snmp540DiagTest 6 }

snmp540DiagControl OBJECT-TYPE
    SYNTAX INTEGER {
	noTest(1),
        lineloop(2),
	remoteLoop(3),
	resetTestToNorm(4),
	telcoLoop(5)		-- Loopback Initiated by Telco
    }
    ACCESS read-write
    STATUS mandatory
    DESCRIPTION
	"The lineloop(2) selection places the
         snmp540 into line loopback mode. The
         noTest(1) and telcoLoop(5) are READ ONLY
         values.  NoTest(1) indicates that no 
	 diagnostic test is in progress. The
         value telcoLoop(5) will be reported
         when a DSU/CSU test is initiated by
         Telco. The value remoteLoop(3) is used
         initiate a remote loopback test. The
         value resetTestToNorm(4) will halt the
         execution of diagnostic test that may be running."
    ::= { snmp540DiagTest 7 }

snmp540Led OBJECT IDENTIFIER ::= { snmp540 8 }

snmp540LedStatus OBJECT-TYPE
        SYNTAX  OCTET STRING (SIZE(2))
        ACCESS  read-only
        STATUS  mandatory
	DESCRIPTION
                "Returns a bitwise snapshot of the front panel LED state.
                Octet 1 bit 7 - not used
                        bit 6 - NS	-- No Signal
                        bit 5 - SD	-- Send Data
                        bit 4 - RD	-- Receive Data
			bit 3 - RS	-- Request to Send
			bit 2 - CS	-- Clear to Send
                        bit 1 - CO	-- Carrier
			bit 0 - TR	-- Terminal Ready
									   
                Octet 2 bit 7 - not used
                        bit 6 - NORM	--
                        bit 5 - TEST OK	-- Test Ok
                        bit 4 - DBU	-- Dataset on DBU
                        bit 3 - CO	-- In-Band CO detected.
                        bit 2 - DATA	-- SNMP Diag Data
                        bit 1 - RESP	-- SNMP transmit Diag Data
			bit 0 - TEST	-- Dataset in Test"
    ::= { snmp540Led 1 }

snmp540DeviceSerialNumber OBJECT-TYPE
    SYNTAX  OCTET STRING (SIZE(8))
    ACCESS  read-only
    STATUS  mandatory
    DESCRIPTION
    	"Display's the unique serial number of this
         device.  The octet string starts with the
         two byte product code (0540) followed by a
         reserved byte value (rr) and the date code
         (mm,dd,yy).  The last two bytes is the manufactured
	 unit count for the aforementioned date code(####).
	    Example  0540rrMMddYY#### "

    ::= { snmp540 9 }

END
