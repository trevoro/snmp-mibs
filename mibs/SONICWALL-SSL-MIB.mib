SONICWALL-SSL-MIB DEFINITIONS ::= BEGIN

IMPORTS
    enterprises, IpAddress, Integer32,
	MODULE-IDENTITY 			FROM SNMPv2-SMI
	TRAP-TYPE				FROM RFC-1215
	OBJECT-TYPE				FROM RFC-1212;

-- Our enterprise

sonicWall	OBJECT IDENTIFIER ::= { enterprises 3884 }

sonicWallSSLMIB MODULE-IDENTITY
    LAST-UPDATED "200102081330Z"
    ORGANIZATION "SonicWALL Inc."
    CONTACT-INFO
	"Technical Support
	 SonicWALL Inc.
	 348 East 4500 South
	 Salt Lake City, UT 84107
	 USA

	 801-743-2200
	 support@sonicwall.com"
    DESCRIPTION
	"The MIB module to describe SSL objects and traps."
    REVISION      "200102081330Z"
    DESCRIPTION
	"Refine the cpu utilization objects/traps
	 and add ssl-tps, ssl-total-conn, and config-changed
	 traps"
    REVISION      "200102071030Z"
    DESCRIPTION
	"Initial revision, internal use only."
    ::= { sonicWall 2 }

-- The Information Group

-- All these objects really belong in a device-based module...

information     OBJECT IDENTIFIER ::= { sonicWallSSLMIB 1 }

--cpuUtilLoThresh OBJECT-TYPE
--    SYNTAX      Integer32
--    MAX-ACCESS  read-only
--    STATUS      current
--    DESCRIPTION
--	"When a system is in a hi cpu utilization state, this is the
--	 threshold value that cpu utilization must fall below to enter
--	 the low cpu utlization state.  The value is expressed as the
--	 percentage cpu utilization on a scale of 0-100."
--    ::= { information 1 }
--
--cpuUtilHiThresh OBJECT-TYPE
--    SYNTAX      Integer32
--    MAX-ACCESS  read-only
--    STATUS      current
--    DESCRIPTION
--	"When a system is in a low cpu utilization state, this is the
--	 threshold value that cpu utilization must rise above to enter
--	 the hi cpu utlization state.  The value is expressed as the
--	 percentage cpu utilization on a scale of 0-100."
--    ::= { information 2 }
--
--cpuUtilStatus OBJECT-TYPE
--    SYNTAX      Integer32 {
--			lo(1)
--			hi(2),
--			}
--    MAX-ACCESS  read-only
--    STATUS      current
--    DESCRIPTION
--	"The current state of the cpu utilization on the device.
--	 See the cpuUtilLoThresh and cpuUtilHiThresh values to
--	 see how the state is determined."
--    ::= { information 3 }

lastConfigChangeInitiator OBJECT-TYPE
    SYNTAX      IpAddress
    MAX-ACCESS  read-only
    STATUS      mandatory
    DESCRIPTION
	"The IP address of the initiator of the last configuration
	 change on this device."
    ::= { information 4 }

lastConfigChangeCmd OBJECT-TYPE
    SYNTAX      Integer32
    MAX-ACCESS  read-only
    STATUS      mandatory
    DESCRIPTION
	"The ioctl of the last configuration change on this device."
    ::= { information 5 }


-- Traps

sslTraps OBJECT IDENTIFIER ::= { sonicWallSSLMIB 0 }

-- These cpu based traps really belong in a device-based module...

cpuUtilChangeHi TRAP-TYPE
    ENTERPRISE sonicWall
    DESCRIPTION
	"The percentage of CPU utilization has transitioned above the upper
	 threshold limit."
    ::= 1

cpuUtilChangeLo TRAP-TYPE
    ENTERPRISE sonicWall
    DESCRIPTION
	"The percentage of CPU utilization has transitioned below the lower
	 threshold limit."
    ::= 2 

sslTpsChangeHi TRAP-TYPE
    ENTERPRISE sonicWall
    DESCRIPTION
	"The number of ssl negotiations per second has transitioned
	 above the upper threshold limit."
    ::= 3 

sslTpsChangeLo TRAP-TYPE
    ENTERPRISE sonicWall
    DESCRIPTION
	"The number of ssl transactions per second has transitioned
	 below the lower threshold limit."
    ::= 4

sslTotalConnectsChangeHi TRAP-TYPE
    ENTERPRISE sonicWall
    DESCRIPTION
	"The number of ssl connections has transitioned above the upper
	 threshold limit."
    ::= 5

sslTotalConnectsChangeLo TRAP-TYPE
    ENTERPRISE sonicWall
    DESCRIPTION
	"The number of ssl connections has transitioned below the
	 lower threshould limit."
    ::= 6

-- This config-change trap really belongs in a device-based module...

configChange TRAP-TYPE
    ENTERPRISE sonicWall
    VARIABLES { lastConfigChangeInitiator, lastConfigChangeCmd }
    DESCRIPTION
	"Configuration of the device has been modified."
    ::= 7

END
