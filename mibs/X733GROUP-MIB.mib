X733GROUP-MIB DEFINITIONS ::= BEGIN

   IMPORTS
       Integer32, MODULE-IDENTITY, OBJECT-TYPE, NOTIFICATION-TYPE, enterprises
           FROM SNMPv2-SMI
       DisplayString
           FROM SNMPv2-TC;

   sni                         OBJECT IDENTIFIER ::= { enterprises 231 }
   siemensUnits                OBJECT IDENTIFIER ::= { sni 7 }
   oenProductMibs              OBJECT IDENTIFIER ::= { siemensUnits 1 }
   nms                         OBJECT IDENTIFIER ::= { oenProductMibs 3 }
   ncProxy                     OBJECT IDENTIFIER ::= { nms 1 }


  ewsdAlarms MODULE-IDENTITY
       LAST-UPDATED "200110150000Z"
       ORGANIZATION "Siemens AG Osterreich"
       CONTACT-INFO
              "         Technical Support

                Postal: Siemens AG Oesterreich
                        Rampengasse 3-5
                        1190 Wien, Austria

                   Tel: + 43 5 1707 43623
                   Fax:

                E-mail: martin.zach@siemens.at"

       DESCRIPTION
               "This MIB module implements X733 Alarms 
          which are extracted from MML alarms (EWSD classic),
          from SNMP alarms (EWSD InterNode and other SNMP managed devices)
          and from Q3 alarms (EWSD PowerNode). According to this distinction,
          different traps for spontaneous alarms are defined.
          This MIB module is compatible to previous versions 
          which did not support SNMP and Q3 alarms,
          and countAlarms with the number of major, critical and minor
          alarms of the relevant Network Element."     -- description changed
       ::= { ncProxy 1 }



   commonGroup                 OBJECT IDENTIFIER ::= { ewsdAlarms 1 }
   controlGroup                OBJECT IDENTIFIER ::= { ewsdAlarms 2 }
   summaryGroup                OBJECT IDENTIFIER ::= { ewsdAlarms 3 }
   miscGroup                   OBJECT IDENTIFIER ::= { ewsdAlarms 4 }
   x733Group                   OBJECT IDENTIFIER ::= { ewsdAlarms 5 } 
   q3Group                     OBJECT IDENTIFIER ::= { ewsdAlarms 6 } 
   osGroup                     OBJECT IDENTIFIER ::= { ewsdAlarms 7 }




    --********************************************************************
    -- commonGroup: Objects that are used in different contexts
    --********************************************************************

    neName OBJECT-TYPE                              -- name changed
       SYNTAX  DisplayString
       MAX-ACCESS  not-accessible
       STATUS  current
       DESCRIPTION
               "name of the EWSD"
       ::= { commonGroup 1 }

    managedObjectClass OBJECT-TYPE                   -- name changed
       SYNTAX  DisplayString
       MAX-ACCESS  not-accessible
       STATUS  current
       DESCRIPTION
               "naming attribute of the class of alarm Object
                (only EWSD classic); possible values: 
                DLU, SAL, MAL, LTG, SN, MB ..."         
       ::= { commonGroup 2 }

    notificationId OBJECT-TYPE
       SYNTAX  DisplayString
       MAX-ACCESS  not-accessible
       STATUS  current
       DESCRIPTION
               "corresponds to X.721/X.733:NotificationIdentifier -
                an ascii string uniquely identifying an
                alarm within all EWSDs."
       ::= { commonGroup 3 }

    globalAlarmIds OBJECT-TYPE
       SYNTAX  OCTET STRING (SIZE (0..8192))
       MAX-ACCESS  not-accessible
       STATUS  current
       DESCRIPTION
               "an ascii string containing 0..64 commaseparated
                strings uniquely identifying an alarm within all
                EWSDs."
       ::= { commonGroup 4 }


    --********************************************************************
    -- controlGroup: Control Summaries and alarm repetitions
    --********************************************************************

    setPeriod OBJECT-TYPE
       SYNTAX  INTEGER  ( 0..60 )
       MAX-ACCESS  read-write       
       STATUS  current
       DESCRIPTION
               "defines the time period for the periodical alarm summaries
                unit of measurement: 8 minutes, initially set to 1 
                (i.e. 8 minutes)."
        DEFVAL  { 1 }
       ::= { controlGroup 1 }

    sendSummary OBJECT-TYPE
       SYNTAX  DisplayString
       MAX-ACCESS  read-write       
       STATUS  current
       DESCRIPTION
               "The value must be a neName. Setting a value causes an
               immediate alarm status summary with respect to the chosen
               EWSD( forced alarm status summary). Possible EWSD names can
               be learned from the periodical status summary alarms."
       ::= { controlGroup 2 }

    resendAlarm OBJECT-TYPE
       SYNTAX  DisplayString
       MAX-ACCESS  read-write       
       STATUS  current
       DESCRIPTION
               "The value must be a notificationID. Setting a value causes
               an immediate alarm notification. Possible notificationIDs can
               be learned from the status summary alarms."      
       ::= { controlGroup 3 }

    sendAllAlarms OBJECT-TYPE
       SYNTAX  INTEGER (0..4294967295)
       MAX-ACCESS  read-write       
       STATUS  current
       DESCRIPTION
               "Whenever this object is set to any (!) integer value
                all open Alarms will be sent."
       ::= { controlGroup 4 }
       
    alarmSpontan OBJECT-TYPE                    -- new 
       SYNTAX  INTEGER  { yes(1), no(2) }
       MAX-ACCESS  read-write       
       STATUS  current
       DESCRIPTION
               "Setting to no(2) disables sending of spontaneousAlarms,
                default: yes(1)."
        DEFVAL  { 1 }
       ::= { controlGroup 5 }
 
    countAlarmPeriod OBJECT-TYPE                  -- new 
       SYNTAX  INTEGER  ( 0..60 )
       MAX-ACCESS  read-write       
       STATUS  current
       DESCRIPTION
               "defines the time period for the periodic count alarms
                unit of measurement: 8 minutes; initially set to 0 (which 
                means no periodic count alarms."
        DEFVAL  { 0 }
       ::= { controlGroup 6 } 
                                                    
    countAlarmSpontan OBJECT-TYPE                -- new
       SYNTAX  INTEGER  { yes(1), no(2) }
       MAX-ACCESS  read-write       
       STATUS  current
       DESCRIPTION
               "Setting to yes(1) enables sending of spontaneous count alarms
                default: no(2)."
        DEFVAL  { 2 }
       ::= { controlGroup 7 }


    --********************************************************************
    -- summaryGroup: Objects that are used in different contexts
    --********************************************************************

    numberOfAlarms OBJECT-TYPE                   
       SYNTAX  Integer32
       MAX-ACCESS  not-accessible
       STATUS  current
       DESCRIPTION
               "Total number of open alarms of the relevant EWSD."
       ::= { summaryGroup 1 }

    connectionReliable OBJECT-TYPE              
       SYNTAX  INTEGER  { yes(1), no(2) }
       MAX-ACCESS  not-accessible
       STATUS  current
       DESCRIPTION
               "The connection to the relevant EWSD is reliable if the 
                last information exchange with ADS is not longer than 
                8 minutes ago (valid for MML alarms)."                     -- description changed
       ::= { summaryGroup 2 } 
       
    critical OBJECT-TYPE                         -- new
       SYNTAX  Integer32
       MAX-ACCESS  not-accessible
       STATUS  current
       DESCRIPTION
               "Total number of critical alarms of the relevant EWSD."
       ::= { summaryGroup 3 }
       
    major OBJECT-TYPE                            -- new
       SYNTAX  Integer32
       MAX-ACCESS  not-accessible
       STATUS  current
       DESCRIPTION
               "Total number of major alarms of the relevant EWSD."
       ::= { summaryGroup 4 }
       
     minor OBJECT-TYPE                           -- new
       SYNTAX  Integer32
       MAX-ACCESS  not-accessible
       STATUS  current
       DESCRIPTION
               "Total number of minor alarms of the relevant EWSD."
       ::= { summaryGroup 5 }



    --*********************************************************--
    -- miscGroup: Objects that are introduced only to          --
    --            identify variable bindings of traps          --
    --*********************************************************--
    
    timePeriod OBJECT-TYPE
       SYNTAX  INTEGER  ( 0..60 )
       MAX-ACCESS  not-accessible
       STATUS  current
       DESCRIPTION
               "actual value of time period for alarm summaries
                   - unit of measurement: 8 minutes
                   - initially set to 1 (i.e. 8 minutes)"
        DEFVAL  { 1 }
       ::= { miscGroup 3 }     
       
    q3AlarmNumber OBJECT-TYPE                    -- new 
       SYNTAX  INTEGER  ( 0..9999 )
       MAX-ACCESS  not-accessible
       STATUS  current
       DESCRIPTION
               "number of q3Alarm traps in which a Q3 alarm is divided
               (with CONTINUE_FLAG). Started from value 0, 
               if it's not the last trap for this alarm
               value is incremented with 9000.
               A complete Q3 alarm consists of one q3Alarm trap, plus
               'q3AlarmNumber' q3contAlarm traps."
       ::= { miscGroup 4 }


    --********************************************************************
    -- x733Group:
    --********************************************************************

    eventType OBJECT-TYPE         
       SYNTAX  INTEGER  { indeterminate(0), communicationsAlarm(2),
                      enviromentalAlarm(3), equipmentAlarm(4), 
                      integrityViolation(5), operationalViolation(8),
                      physicalViolation(9), processingErrorAlarm(10), 
                      qualityOfServiceAlarm(11),                       
                      securityServiceOrMechanismViolation(13),
                      timeDomainViolation(15)  }
       MAX-ACCESS  not-accessible
       STATUS  current
       DESCRIPTION
               "last component of the respective OID defined in X.721."
       ::= { x733Group 1 }

    severity OBJECT-TYPE
       SYNTAX  INTEGER  { indeterminate(0), critical(1), major(2),
                           minor(3), warning(4), cleared(5) }
       MAX-ACCESS  not-accessible
       STATUS  current
       DESCRIPTION
               " corresponds to X.721/X.733:PerceivedSeverity."
       ::= { x733Group 2 }

    probableCause OBJECT-TYPE
       SYNTAX  DisplayString
       MAX-ACCESS  not-accessible
       STATUS  current
       DESCRIPTION
               " corresponds to X.721/X.733:ProbableCause."
       ::= { x733Group 3 }

    originalAlarm OBJECT-TYPE                    -- name changed
       SYNTAX  OCTET STRING (SIZE (0..8192))
       MAX-ACCESS  not-accessible
       STATUS  current
       DESCRIPTION
               "corresponds to X.721/X.733:AdditionalText:
                The original EWSD alarm (max. 8 kByte) for EWSD classic,
                formatted output for SNMP traps and Q3 alarms"
                                            -- description changed
       ::= { x733Group 4 }

    processingStatus OBJECT-TYPE
       SYNTAX  INTEGER  { not-processed(0), in-process(1),
                          under-repair(2), deferred(3), cleared(4) }
       MAX-ACCESS  not-accessible
       STATUS  current
       DESCRIPTION
               "An element of X.721:SpecificProblem "
       ::= { x733Group 5 }

    alarmClass OBJECT-TYPE
       SYNTAX  DisplayString
       MAX-ACCESS  not-accessible
       STATUS  current
       DESCRIPTION
               "An element of X.721:AdditionalInformation; can be
                seen as a CMIS-ManagedObjectClass-field if an object
                model with a finer granularity would be defined;
                example: SLM (subscriber line module) identifies
                a line card"
       ::= { x733Group 6 }

    managedObjectInstance OBJECT-TYPE           -- name changed
       SYNTAX  DisplayString
       MAX-ACCESS  not-accessible
       STATUS  current
       DESCRIPTION
               "An element of X.721:AdditionalInformation; can be
                seen as a part of the CMIS-ManagedObjectInstance-field
                if an object model with a finer granularity would be
                defined "
       ::= { x733Group 7 }

   rack OBJECT-TYPE
       SYNTAX  INTEGER (0..9999)
       MAX-ACCESS  not-accessible
       STATUS  current
       DESCRIPTION
               "An element of X.721:AdditionalInformation "
       ::= { x733Group 8 }

   shelf OBJECT-TYPE
       SYNTAX  INTEGER (0..9999)
       MAX-ACCESS  not-accessible
       STATUS  current
       DESCRIPTION
               "An element of X.721:AdditionalInformation "
       ::= { x733Group 9 }

   fromCard OBJECT-TYPE
       SYNTAX  INTEGER (0..9999)
       MAX-ACCESS  not-accessible
       STATUS  current
       DESCRIPTION
               "An element of X.721:AdditionalInformation "
       ::= { x733Group 10 }

   toCard OBJECT-TYPE
       SYNTAX  INTEGER (0..9999)
       MAX-ACCESS  not-accessible
       STATUS  current
       DESCRIPTION
               "An element of X.721:AdditionalInformation;
                - same value as fromCard: a single card is
                  affected by the alarm
                - otherweise cards from fromCard to toCard are
                  affected "
       ::= { x733Group 11 }

   fromPort OBJECT-TYPE
       SYNTAX  INTEGER (0..9999)
       MAX-ACCESS  not-accessible
       STATUS  current
       DESCRIPTION
               "An element of X.721:AdditionalInformation "
       ::= { x733Group 12 }

   toPort OBJECT-TYPE
       SYNTAX  INTEGER (0..9999)
       MAX-ACCESS  not-accessible
       STATUS  current
       DESCRIPTION
               "An element of X.721:AdditionalInformation;
                - same value as fromPort: a single port is
                  affected by the alarm
                - otherweise ports from fromPort to toPort are
                  affected "
       ::= { x733Group 13 }

   eventTime OBJECT-TYPE
       SYNTAX  DisplayString
       MAX-ACCESS  not-accessible
       STATUS  current
       DESCRIPTION
               "An element of X.710: Parameter contains 
                the time of generation of the event, if event 
                time is sent from network element, otherwise 
                it is the time of reception of the alarm by NetM
                The EventTime is a GeneralizedTime (defined in X.208),
                format is YYYYMMDDhhmmss.f+hhmm where 
                Y year 
                M month in year
                D day in month
                h hour in day (0-23)
                m minute in hour
                s second in minute
                f tenth part of second
                +hhmm	local time offset(+-) to UTC time. 
                Time represents the local time (t1), and the time 
                differential (t2) enables UTC time to be determined as follows:
					UTC time = t1 - t2"
       ::= { x733Group 14 } 

   ipAddress OBJECT-TYPE                        
       SYNTAX  DisplayString
       MAX-ACCESS  not-accessible
       STATUS  current
       DESCRIPTION
               "An element of X.721:AdditionalInformation;
                indicates the source of the original SNMP trap."
       ::= { x733Group 15 }

   trapName OBJECT-TYPE                         
       SYNTAX  DisplayString
       MAX-ACCESS  not-accessible
       STATUS  current
       DESCRIPTION
               "An element of X.721:AdditionalInformation;
                the name/OID of the original SNMP trap."
       ::= { x733Group 16 }

   specificProblems OBJECT-TYPE                  -- new
       SYNTAX  DisplayString
       MAX-ACCESS  not-accessible
       STATUS  current
       DESCRIPTION
               "corresponds to X.733:SpecificProblems;
                further refinements to the ProbableCause;
                example: the value of 'slmiAlarmStateReason' 
                for an 'slmiAlarmStateTrap'."
       ::= { x733Group 17 } 
       
   additionalText OBJECT-TYPE                    -- new
       SYNTAX  OCTET STRING (SIZE (0..2048))
       MAX-ACCESS  not-accessible
       STATUS  current
       DESCRIPTION
               "This parameter allows the inclusion of a set
               of additional information in the event report."
       ::= { x733Group 18 }

       
   additionalInformation OBJECT-TYPE             -- new
       SYNTAX  OCTET STRING (SIZE (0..8192))
       MAX-ACCESS  not-accessible
       STATUS  current
       DESCRIPTION
               "This parameter allows the inclusion of a set
               of additional information in the event report."
       ::= { x733Group 19 }

                 
   --********************************************************************
    -- q3Group
    --********************************************************************

    backupStatus OBJECT-TYPE             -- new
       SYNTAX  INTEGER  { yes(1), no(2) }
       MAX-ACCESS  not-accessible
       STATUS  current
       DESCRIPTION
               "This parameter specifies whether or not the object 
               emitting the alarm has been backed-up."             
       ::= { q3Group 1 }  
       
   backupObject OBJECT-TYPE              -- new
       SYNTAX  DisplayString
       MAX-ACCESS  not-accessible
       STATUS  current
       DESCRIPTION
               "This parameter specifies the managed object instance that 
               is providing backup services for the managed object about 
               which the notification pertains."                
       ::= { q3Group 2 }   
       
   trendIndication OBJECT-TYPE          -- new
       SYNTAX  INTEGER  { moresevere(1), nochange(2), lesssevere(3) }
       MAX-ACCESS  not-accessible
       STATUS  current
       DESCRIPTION
               "This parameter, when present, specifies the current severity
                trend of the managed object."               
       ::= { q3Group 3 }   
       
   thresholdInformation OBJECT-TYPE       -- new
       SYNTAX  DisplayString
       MAX-ACCESS  not-accessible
       STATUS  current
       DESCRIPTION
               "This parameter shall be present when the alarm is a result 
               of crossing a threshold."                -- new
       ::= { q3Group 4 }   
                             
   correlatedEvents OBJECT-TYPE            -- new
       SYNTAX  OCTET STRING (SIZE (0..8192))
       MAX-ACCESS  not-accessible
       STATUS  current
       DESCRIPTION
               "an ascii string containing comma-separated notifications,
               considered to be correlated."             
       ::= { q3Group 5 }     
       
   stateChanges OBJECT-TYPE                -- new
       SYNTAX  DisplayString
       MAX-ACCESS  not-accessible
       STATUS  current
       DESCRIPTION
               "This parameter is used to indicate a state transition
                associated with the alarm."             
       ::= { q3Group 6 }      
       
   monitoredAttributes OBJECT-TYPE          -- new
       SYNTAX  OCTET STRING (SIZE (0..8192))
       MAX-ACCESS  not-accessible
       STATUS  current
       DESCRIPTION
               "an ascii string containing comma-separated List of 
               Monitored Attributes( attribute:value )."        
       ::= { q3Group 7 }  
                
   securityAlarmDetector OBJECT-TYPE     -- new
       SYNTAX  DisplayString
       MAX-ACCESS  not-accessible
       STATUS  current
       DESCRIPTION
               "This attribute identifies the entity that detected 
               the security alarm."           
       ::= { q3Group 8 }
      
   serviceUser OBJECT-TYPE                -- new
       SYNTAX  DisplayString
       MAX-ACCESS  not-accessible
       STATUS  current
       DESCRIPTION
               "This attribute contains information about the service
                user associated with the service request that caused 
                the security alarm."             
       ::= { q3Group 9 }
      
   serviceProvider OBJECT-TYPE             -- new
       SYNTAX  DisplayString
       MAX-ACCESS  not-accessible
       STATUS  current
       DESCRIPTION
               "This attribute contains information about the service
                provider associated with the service request that caused 
                the security alarm."                
       ::= { q3Group 10 } 
       
   listOfFaultyBoards OBJECT-TYPE           -- new 
       SYNTAX  OCTET STRING (SIZE (0..8192))
       MAX-ACCESS  not-accessible
       STATUS  current
       DESCRIPTION
               "PowerNode equipment alarms contain a list of faulty
                boards. This information exactly defines the boards, 
                which must be considered for repair/replacement.
                An ascii string containing comma-separated items. 
                Each item contains: 
                Module_name:LocationName:RackID:ShelfID:PitchID"   
       ::= { q3Group 11 }

	--********************************************************************
    -- osGroup
    --********************************************************************
        
	mmnKey OBJECT-TYPE             -- new
       SYNTAX  DisplayString
       MAX-ACCESS  not-accessible
       STATUS  current
       DESCRIPTION
               "This identifies the Help Topic for the OS Alarm in
                the OS Alarm Help file. The format of the MMN key for 
                the Basic Components: BASE_<Component Code>_<Alarm number>"                
       ::= { osGroup 1 }

   thresholdValue OBJECT-TYPE
       SYNTAX  INTEGER (0..4294967295)
       MAX-ACCESS  not-accessible
       STATUS  current
       DESCRIPTION
               "This attribute is relevant only for OS Threshold Alarms.
                - specifies the threshold value for any counter/monitored
                object, which is allowed and can be tolerated"
       ::= { osGroup 2 } 
       
    currentValue OBJECT-TYPE
       SYNTAX  INTEGER (0..4294967295)
       MAX-ACCESS  not-accessible
       STATUS  current
       DESCRIPTION
               "This attribute is relevant only for OS Threshold Alarms.
                - specifies the current value for the measurements, which
                has violated th threhold value of monitored measurements "
       ::= { osGroup 3 }




    --********************************************************************
    -- x733 Traps definition
    --********************************************************************

    summaryAlarms NOTIFICATION-TYPE
       OBJECTS { neName, numberOfAlarms, connectionReliable, globalAlarmIds }
       STATUS  current
       DESCRIPTION
               "This trap will be sent periodically or after an explicit 
                request via SNMP set. It is useful for these reasons:
                - to notice that the connection to NetM is reliable
                - to notice that the connection from NetM to an EWSD is reliable
                - to learn the names of EWSDs under control of NetM
                - to notice that traps got lost."
       ::= { x733Group 201 }

    spontaneousAlarms NOTIFICATION-TYPE
       OBJECTS { neName, managedObjectClass, notificationId, severity, eventType,
                 eventTime, probableCause, processingStatus, alarmClass,
                 managedObjectInstance, rack, shelf, fromCard, toCard, fromPort, 
                 toPort, originalAlarm }
       STATUS  current
       DESCRIPTION
               "Spontaneous Alarm from EWSD classic (MML).
                This trap will notify management systems after
                notifications from the EWSD classic. This trap type will be sent 
                also in case of a 'resend' request. Each spontaneous alarm
                contains the variable binding 'originalAlarm' representing
                the original EWSD alarm. This information can be very large
                ( about 8 Kbyte)."                  -- description changed
       ::= { x733Group 202 }

    snmpAlarm NOTIFICATION-TYPE                 
       OBJECTS { neName, notificationId, severity, eventType, eventTime,
                 probableCause, specificProblems, managedObjectClass,
                 managedObjectInstance, ipAddress, trapName, originalAlarm }
       STATUS  current
       DESCRIPTION
               "Spontaneous Alarm from EWSD InterNode or other SNMP managed devices.
                This trap will notify management systems
                after an SNMP alarm trap has been received by NetM. 
                This trap type will be sent also in case of a 'resend' request. 
                Each snmpAlarm trap contains the formatted output of the 
                original SNMP trap in 'originalAlarm'."       
       ::= { x733Group 203 }                                                    
       
     q3Alarm NOTIFICATION-TYPE                  -- new
       OBJECTS { neName, notificationId, q3AlarmNumber, severity, eventType, eventTime,
                 probableCause, specificProblems, managedObjectClass, 
                 managedObjectInstance, additionalText,additionalInformation,
                 backupStatus, backupObject, trendIndication, 
                 thresholdInformation, correlatedEvents, stateChanges,
                 monitoredAttributes, securityAlarmDetector, serviceUser, 
                 serviceProvider, listOfFaultyBoards, originalAlarm }
       STATUS  current
       DESCRIPTION
               "Spontaneous Alarm from EWSD PowerNode.
                This trap will notify management systems
                after a Q3 alarm has been received from EWSD PowerNode. 
                This trap type will be sent also in case of a 'resend' request. 
                Each q3Alarm trap contains the formatted output of the 
                original PowerNode trap in 'originalAlarm'.
                If the size of q3alarm exceeds 10KB, or one of the variables exceeds
                8KB, 'q3alarm' is followed by 'q3contAlarm'.
                'q3AlarmNumber' is 0 if the whole Q3 alarm is contained, or 9000 if it 
                is continued with a 'q3contAlarm' sequence."
       ::= { x733Group 204 }  
       
    q3contAlarm NOTIFICATION-TYPE                   -- new
       OBJECTS { neName, notificationId, q3AlarmNumber, correlatedEvents,
       			 monitoredAttributes, listOfFaultyBoards, originalAlarm }
       STATUS  current
       DESCRIPTION
               "Continuation of a Q3 Alarm. If the size of the trap exceeds 10KB,
                or one of the variables exceeds 8KB, the next 'q3contAlarm' is generated.
                In 'q3AlarmNumber' there is the sequence number and a flag (9000)
                if it continues with a new 'q3contAlarm'."      
       ::= { x733Group 205 }

    timeAckAlarms NOTIFICATION-TYPE
       OBJECTS { timePeriod }
       STATUS  current
       DESCRIPTION
               "A 'timeAckAlarms' trap is sent as acknowledgement for
                a 'setPeriod' set request."
       ::= { x733Group 206 }

    proxyStartUp NOTIFICATION-TYPE
       STATUS  current
       DESCRIPTION
               "A 'proxyStartUp' trap is sent if the proxy comes up."
       ::= { x733Group 207 } 
       
    countAlarm NOTIFICATION-TYPE                   -- new
       OBJECTS { neName, critical, major, minor }
       STATUS  current
       DESCRIPTION
               "Spontaneous or periodical trap, which contains the number 
               of critical, major and minor alarms for a Network Element.
               Spontaneous:  if the number of critical, major or minor alarms
               for a Network Element has changed.
               Periodical: depending on the setting of 'countAlarmPeriod'."      
       ::= { x733Group 208 }  
       
     osAlarm NOTIFICATION-TYPE                  -- new
       OBJECTS { neName, notificationId, severity, eventType, eventTime,
                 probableCause, managedObjectClass, managedObjectInstance,  
                 mmnKey, additionalText, thresholdValue, currentValue,
                 securityAlarmDetector, serviceUser, serviceProvider
               }
       STATUS  current
       DESCRIPTION
               "Spontaneous OS Alarm from NetManager.
                This trap will notify management systems after a OS alarm has 
                been  generated from the NetManager. 
                This trap type will be sent also in case of a 'resend' request. 
                NeName is filled up with OS Name.
                Notification ID has form: OS_<AlarmID>
                "
       ::= { x733Group 209 }  


END
