-- Start - JUNIPER-WX-GLOBAL-MIB Module

JUNIPER-WX-GLOBAL-MIB DEFINITIONS ::= BEGIN 

IMPORTS
	MODULE-IDENTITY, 
	OBJECT-IDENTITY, 
	OBJECT-TYPE, 
	Integer32 
		FROM SNMPv2-SMI
	DisplayString
		FROM SNMPv2-TC
	jnxWxMibRoot
		FROM JUNIPER-SMI;

jnxWxGrpModule MODULE-IDENTITY
    LAST-UPDATED    "200804081400Z"
    ORGANIZATION    "Juniper Networks, Inc"
    CONTACT-INFO    "
          Customer Support
          Juniper Networks, Inc.
          1194 North Mathilda Avenue
          Sunnyvale, CA  94089
          support@juniper.net"

    DESCRIPTION
      "Juniper Networks enterprise MIB module for WAN
       Acceleration (WX) product-line from software release
       version JWOS 6.0 onwards.
       "
    ::= { jnxWxMibRoot 1 }

jnxWxGrp OBJECT-IDENTITY
    STATUS  current
    DESCRIPTION
      "The MIB group containing all status, statistics, events
       and configuration information for WX product-line
       from software release version JWOS 6.0 onwards.
      "
    ::= { jnxWxGrpModule 1 }

jnxWxGrpStatus OBJECT-IDENTITY
  STATUS  current
  DESCRIPTION
      "The MIB group containing status related information.
      "
  ::= { jnxWxGrp 1 }

jnxWxGrpStats OBJECT-IDENTITY
    STATUS  current
    DESCRIPTION
      "This group contains statisitics related information.
       It contains system, acceleration, compression and
       wan performance data.
      "
    ::= { jnxWxGrp 2 }

jnxWxGrpEvents OBJECT-IDENTITY
    STATUS  current
    DESCRIPTION
      "This group contains events related information.
      "
    ::= { jnxWxGrp 3 }

jnxWxGrpConf OBJECT-IDENTITY
    STATUS  current
    DESCRIPTION
      "This group contains configuration related information.
      "
    ::= { jnxWxGrp 4 }

  -- OID registrations for WX product lines
  -- These OIDs are never queried by management stations.
  -- They can be returned as product identifiers in responses.

jnxWxGrpProduct OBJECT-IDENTITY
    STATUS  current
    DESCRIPTION
      "This group contains product related information.
      "
    ::= { jnxWxGrp 5 }

jnxWxGrpProductWxc250 OBJECT-IDENTITY
      STATUS          current
      DESCRIPTION       "
        Sequence Caching Model 250"
      ::= { jnxWxGrpProduct 1 }

jnxWxGrpProductWxc500 OBJECT-IDENTITY
      STATUS          current
      DESCRIPTION       "
        Sequence Caching Model 500"
      ::= { jnxWxGrpProduct 2 }

jnxWxGrpProductWxc590 OBJECT-IDENTITY
      STATUS          current
      DESCRIPTION       "
        Sequence Caching Model 590"
      ::= { jnxWxGrpProduct 3 }

jnxWxGrpProductWxc1800 OBJECT-IDENTITY
      STATUS          current
      DESCRIPTION       "
        WAN Acceleration Model 1800
        New in Phoenix"
      ::= { jnxWxGrpProduct 4 }

jnxWxGrpProductWxc2600 OBJECT-IDENTITY
      STATUS          current
      DESCRIPTION       "
        WAN Acceleration Model 2600
        New in Phoenix"
      ::= { jnxWxGrpProduct 5 }

jnxWxGrpProductWxc3400 OBJECT-IDENTITY
      STATUS          current
      DESCRIPTION       "
        WAN Acceleration Model 3400
        New in Phoenix"
      ::= { jnxWxGrpProduct 6 }

jnxWxGrpProductWxc7800 OBJECT-IDENTITY
      STATUS          current
      DESCRIPTION       "
        WAN Acceleration Model 7800
        New in Phoenix"
      ::= { jnxWxGrpProduct 7 }


END

-- End - JUNIPER-WX-GLOBAL-MIB Module
