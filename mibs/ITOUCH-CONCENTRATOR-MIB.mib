-- $Id: it-concentrator-mib.mib,v 1.1 2000/07/25 14:36:26 sse Exp $
            ITOUCH-CONCENTRATOR-MIB DEFINITIONS ::= BEGIN

                    IMPORTS
                            Counter, TimeTicks
                                    FROM RFC1155-SMI
                            DisplayString
                                    FROM RFC1213-MIB
                            OBJECT-TYPE
                                    FROM RFC-1212
                            Letter
                                    FROM ITOUCH-CHASSIS-MIB
                            IOType, iTouch
                                    FROM ITOUCH-MIB;

            xConcentrator      OBJECT IDENTIFIER ::= { iTouch 25 }


            -- This is a MIB module for all iTouch Ethernet repeaters.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.



            -- The basic information group contains information and
            -- status concerning the chassis:
    
            concentratorMode OBJECT-TYPE
                SYNTAX INTEGER { twoRing(1), fourRing(2) }
                ACCESS read-write
                STATUS mandatory
                DESCRIPTION
                    "This variable controls the ring mode of the
                    chassis."
                ::= { xConcentrator 1 }
    
            concentratorManagement OBJECT-TYPE
                SYNTAX INTEGER { disabled(1), enabled(2) }
                ACCESS read-write
                STATUS mandatory
                DESCRIPTION
                    "This variable controls the ability to manage token
                    ring concentrators."
                ::= { xConcentrator 2 }
    
            concentratorBuildTopology OBJECT-TYPE
                SYNTAX INTEGER { ready(1), execute(2) }
                ACCESS read-write
                STATUS mandatory
                DESCRIPTION
                    "This variable causes the chassis token ring
                    topology database to be constructed."
                ::= { xConcentrator 3 }
    
            concentratorTopologyLastBuild OBJECT-TYPE
                SYNTAX TimeTicks
                ACCESS read-only
                STATUS mandatory
                DESCRIPTION
                    "This variable contains the value of sysUpTime at
                    the time the chassis token ring topology database
                    was last constructed."
                ::= { xConcentrator 4 }
    
            concentratorChassisRingDefaults OBJECT-TYPE
                SYNTAX INTEGER { ready(1), execute(2) }
                ACCESS read-write
                STATUS mandatory
                DESCRIPTION
                    "This variable causes the chassis ring area of NVS
                    to be set to defaults."
                ::= { xConcentrator 5 }
    

            -- The slot group contains information and status concerning
            -- the individual slots of the chassis:
    
            concentratorSlotTable OBJECT-TYPE
                SYNTAX SEQUENCE OF ConcentratorSlotEntry
                ACCESS not-accessible
                STATUS mandatory
                DESCRIPTION
                    "Table of descriptive and status information about a
                    Token Ring Concentrator."
                ::= { xConcentrator 6 }
    
            concentratorSlotEntry OBJECT-TYPE
                SYNTAX ConcentratorSlotEntry
                ACCESS not-accessible
                STATUS mandatory
                DESCRIPTION
                    "An entry in the table containing information about
                    a specific concentrator."
                INDEX { concentratorSlotIndex }
                ::= { concentratorSlotTable 1 }
    
            ConcentratorSlotEntry ::=
                SEQUENCE {
                    concentratorSlotIndex
                         INTEGER,
                    concentratorSlotIOType
                         IOType,
                    concentratorSlotIOFirmwareVersion
                         INTEGER,
                    concentratorSlotIOOperStatus
                         INTEGER,
                    concentratorSlotUptime
                         TimeTicks,
                    concentratorSlotNumPorts
                         INTEGER
                }
    
            concentratorSlotIndex OBJECT-TYPE
                SYNTAX INTEGER
                ACCESS read-only
                STATUS mandatory
                DESCRIPTION
                    "This variable identifies the slot of the chassis."
                ::= { concentratorSlotEntry 1 }
    
            concentratorSlotIOType OBJECT-TYPE
                SYNTAX IOType
                ACCESS read-only
                STATUS mandatory
                DESCRIPTION
                    "This variable represents the type of the I/O card."
                ::= { concentratorSlotEntry 2 }
    
            concentratorSlotIOFirmwareVersion OBJECT-TYPE
                SYNTAX INTEGER
                ACCESS read-only
                STATUS mandatory
                DESCRIPTION
                    "This variable represents the revision level of the
                    firmware on the I/O card."
                ::= { concentratorSlotEntry 3 }
    
            concentratorSlotIOOperStatus OBJECT-TYPE
                SYNTAX INTEGER { loadRequested(1),
                  loading(2),
                  dumpRequested(3),
                  dumping(4),
                  paramRequested(5),
                  paramLoading(6),
                  running(7),
                  initializing(8),
                  attended(9),
                  internal10(10),
                  internal11(11),
                  inhibited(12),
                  maxserverCard(13),
                  invalidConfigStorage(14),
                  securityLockdown(15) }
                ACCESS read-only
                STATUS mandatory
                DESCRIPTION
                    "This variable represents the current operating
                    status of the I/O card."
                ::= { concentratorSlotEntry 4 }
    
            concentratorSlotUptime OBJECT-TYPE
                SYNTAX TimeTicks
                ACCESS read-only
                STATUS mandatory
                DESCRIPTION
                    "This variable contains the value of sysUpTime at
                    the time the concentrator was last reset."
                ::= { concentratorSlotEntry 5 }
    
            concentratorSlotNumPorts OBJECT-TYPE
                SYNTAX INTEGER
                ACCESS read-only
                STATUS mandatory
                DESCRIPTION
                    "This variable represents the number of Token Ring
                    ports supported by the concentrator."
                ::= { concentratorSlotEntry 6 }
    
            -- The slot ring group contains information and status
            -- concerning the individual rings of a slot:
    
            concentratorSlotRingTable OBJECT-TYPE
                SYNTAX SEQUENCE OF ConcentratorSlotRingEntry
                ACCESS not-accessible
                STATUS mandatory
                DESCRIPTION
                    "Table of descriptive and status information about
                    the rings of a controller."
                ::= { xConcentrator 7 }
    
            concentratorSlotRingEntry OBJECT-TYPE
                SYNTAX ConcentratorSlotRingEntry
                ACCESS not-accessible
                STATUS mandatory
                DESCRIPTION
                    "An entry in the table containing information about
                    a specific ring."
                INDEX { concentratorSlotIndex,
                 concentratorSlotRingIndex }
                ::= { concentratorSlotRingTable 1 }
    
            ConcentratorSlotRingEntry ::=
                SEQUENCE {
                    concentratorSlotSlotIndex
                         INTEGER,
                    concentratorSlotRingIndex
                         INTEGER,
                    concentratorSlotRingAdminName
                         DisplayString,
                    concentratorSlotRingAdminSpeed
                         INTEGER,
                    concentratorSlotRingAdminState
                         INTEGER,
                    concentratorSlotRingZero
                         INTEGER,
                    concentratorSlotRingSinceZero
                         TimeTicks,
                    concentratorSlotRingChassisRing
                         Letter,
                    concentratorSlotRingOperName
                         DisplayString,
                    concentratorSlotRingOperSpeed
                         INTEGER,
                    concentratorSlotRingOperState
                         INTEGER,
                    concentratorSlotRingChassisRingsAllowed
                         OCTET STRING
            }
    
            concentratorSlotSlotIndex OBJECT-TYPE
                SYNTAX INTEGER
                ACCESS read-only
                STATUS mandatory
                DESCRIPTION
                    "This variable identifies the slot of the chassis."
                ::= { concentratorSlotRingEntry 1 }
    
            concentratorSlotRingIndex OBJECT-TYPE
                SYNTAX INTEGER
                ACCESS read-only
                STATUS mandatory
                DESCRIPTION
                    "This variable identifies the ring within the slot."
                ::= { concentratorSlotRingEntry 2 }
    
            concentratorSlotRingAdminName OBJECT-TYPE
                SYNTAX DisplayString (SIZE (0..16))
                ACCESS read-write
                STATUS mandatory
                DESCRIPTION
                    "This variable represents the user defined name of
                    the ring."
                ::= { concentratorSlotRingEntry 3 }
    
            concentratorSlotRingAdminSpeed OBJECT-TYPE
                SYNTAX INTEGER { mbps4(1), mbps16(2) }
                ACCESS read-write
                STATUS mandatory
                DESCRIPTION
                    "This variable represents the user defined speed of
                    the ring."
                ::= { concentratorSlotRingEntry 4 }
    
            concentratorSlotRingAdminState OBJECT-TYPE
                SYNTAX INTEGER { isolated(1), inserted(2) }
                ACCESS read-write
                STATUS mandatory
                DESCRIPTION
                    "This variable defines whether the slot ring is to
                    be inserted into the defined chassis ring or is to
                    be isolated."
                ::= { concentratorSlotRingEntry 5 }
    
            concentratorSlotRingZero OBJECT-TYPE
                SYNTAX INTEGER { ready(1), execute(2) }
                ACCESS read-write
                STATUS mandatory
                DESCRIPTION
                    "This variable is used to control the slot ring's
                    counters.  The agent always returns 'ready' for this
                    value.  Setting the value to 'ready' has no effect."
                ::= { concentratorSlotRingEntry 6 }
    
            concentratorSlotRingSinceZero OBJECT-TYPE
                SYNTAX TimeTicks
                ACCESS read-only
                STATUS mandatory
                DESCRIPTION
                    "This variable reflects the number of time ticks
                    since the counters were last zeroed.  This variable
                    is set to zero when concentratoSlotRingZero is
                    written with the value 2"
                ::= { concentratorSlotRingEntry 7 }
    
            concentratorSlotRingChassisRing OBJECT-TYPE
                SYNTAX Letter
                ACCESS read-write
                STATUS mandatory
                DESCRIPTION
                    "This variable represents the chassis ring into
                    which the slot ring is to be inserted if it is to be
                    inserted."
                ::= { concentratorSlotRingEntry 8 }
    
            concentratorSlotRingOperName OBJECT-TYPE
                SYNTAX DisplayString (SIZE (0..16))
                ACCESS read-only
                STATUS mandatory
                DESCRIPTION
                    "This variable represents the name currently being
                    used to identify the slot ring.  If inserted, this
                    name will be the user defined name of the chassis
                    ring into which it is inserted.  If isolated, this
                    name will be the user defined name of the slot
                    ring."
                ::= { concentratorSlotRingEntry 9 }
    
            concentratorSlotRingOperSpeed OBJECT-TYPE
                SYNTAX INTEGER { mbps4(1), mbps16(2) }
                ACCESS read-only
                STATUS mandatory
                DESCRIPTION
                    "This variable represents the current speed of the
                    slot ring.  If inserted, this speed will be the user
                    defined speed of the chassis ring into which it is
                    inserted.  If isolated, this speed will be the user
                    defined speed of the slot ring."
                ::= { concentratorSlotRingEntry 10 }
    
            concentratorSlotRingOperState OBJECT-TYPE
                SYNTAX INTEGER { isolated(1), inserted(2) }
                ACCESS read-only
                STATUS mandatory
                DESCRIPTION
                    "This variable indicates whether the slot ring is
                    inserted into the defined chassis ring or is
                    isolated."
                ::= { concentratorSlotRingEntry 11 }
    
            concentratorSlotRingChassisRingsAllowed OBJECT-TYPE
                SYNTAX OCTET STRING
                ACCESS read-only
                STATUS mandatory
                DESCRIPTION
                    "The list of chassis rings into which this slot ring
                    may be inserted.  The OCTET STRING contains a bit
                    map, with a bit for 'none' (indicating it may be
                    isolated) and one bit for each chassis ring, and
                    enough octets for all chassis rings.  The high order
                    bit of the first octet corresponds to 'none' and
                    each subsequent bit in ascending order corresponds
                    to the chassis rings in order beginning with A."
                ::= { concentratorSlotRingEntry 12 }
    
            -- The chassis ring group contains information and status
            -- for the rings of the chassis:
    
            concentratorChassisRingTable OBJECT-TYPE
                SYNTAX SEQUENCE OF ConcentratorChassisRingEntry
                ACCESS not-accessible
                STATUS mandatory
                DESCRIPTION
                    "Table of descriptive and status information about
                    the rings of a the chassis."
                ::= { xConcentrator 8 }
    
            concentratorChassisRingEntry OBJECT-TYPE
                SYNTAX ConcentratorChassisRingEntry
                ACCESS not-accessible
                STATUS mandatory
                DESCRIPTION
                    "An entry in the table containing information about
                    a specific ring."
                INDEX { concentratorChassisRingIndex }
                ::= { concentratorChassisRingTable 1 }
    
            ConcentratorChassisRingEntry ::=
                SEQUENCE {
                    concentratorChassisRingIndex
                         Letter,
                    concentratorChassisRingName
                         DisplayString,
                    concentratorChassisRingSpeed
                         INTEGER,
                    concentratorChassisRingTopologyChanges
                         Counter,
                    concentratorChassisRingZero
                         INTEGER,
                    concentratorChassisRingSinceZero
                         TimeTicks
                }
    
            concentratorChassisRingIndex OBJECT-TYPE
                SYNTAX Letter
                ACCESS read-only
                STATUS mandatory
                DESCRIPTION
                    "This variable identifies the ring of the chassis."
                ::= { concentratorChassisRingEntry 1 }
    
            concentratorChassisRingName OBJECT-TYPE
                SYNTAX DisplayString (SIZE (0..14))
                ACCESS read-write
                STATUS mandatory
                DESCRIPTION
                    "This variable represents the name of the ring.  All
                    segments of a given chassis ring will have the same
                    base name, All segment of that ring will appear as
                    'baseNamex' where x is the identified segment"
                ::= { concentratorChassisRingEntry 2 }
    
            concentratorChassisRingSpeed OBJECT-TYPE
                SYNTAX INTEGER { mbps4(1), mbps16(2) }
                ACCESS read-write
                STATUS mandatory
                DESCRIPTION
                    "This variable indicates the speed of the ring
                    segment.  All segments of a given chassis ring are
                    at the same speed."
                ::= { concentratorChassisRingEntry 3 }
    
            concentratorChassisRingTopologyChanges OBJECT-TYPE
                SYNTAX Counter
                ACCESS read-only
                STATUS mandatory
                DESCRIPTION
                    "This variable reflects the number of times the
                    topology has changed for this ring.  This variable
                    is set to zero when concentratorChassisRingZero is
                    written with the value 2."
                ::= { concentratorChassisRingEntry 4 }
    
            concentratorChassisRingZero OBJECT-TYPE
                SYNTAX INTEGER { ready(1), execute(2) }
                ACCESS read-write
                STATUS mandatory
                DESCRIPTION
                    "This variable is used to control the ring's
                    counters.  The agent always returns 'ready' for this
                    value.  Setting the value to 'ready' has no effect."
                ::= { concentratorChassisRingEntry 5 }
    
            concentratorChassisRingSinceZero OBJECT-TYPE
                SYNTAX TimeTicks
                ACCESS read-only
                STATUS mandatory
                DESCRIPTION
                    "This variable reflects the number of time ticks
                    since the counters were last zeroed.  This variable
                    is set to zero when concentratoChassisRingZero is
                    written with the value 2"
                ::= { concentratorChassisRingEntry 6 }
    
            -- The chassis ring topology group is a table which contains
            -- information and status concerningthe segments of the
            -- chassis rings:
    
            concentratorChassisRingTopologyTable OBJECT-TYPE
                SYNTAX SEQUENCE OF ConcentratorChassisRingTopologyEntry
                ACCESS not-accessible
                STATUS mandatory
                DESCRIPTION
                    "Table of descriptive and status information about
                    the segments of the chassis rings."
                ::= { xConcentrator 9 }
    
            concentratorChassisRingTopologyEntry OBJECT-TYPE
                SYNTAX ConcentratorChassisRingTopologyEntry
                ACCESS not-accessible
                STATUS mandatory
                DESCRIPTION
                    "An entry in the table containing information about
                    a specific ring segment."
                INDEX { concentratorChassisRingTopologySlotIndex,
                        concentratorChassisRingTopologyRingIndex }
                ::= { concentratorChassisRingTopologyTable 1 }
    
            ConcentratorChassisRingTopologyEntry ::=
                SEQUENCE {
                    concentratorChassisRingTopologySlotIndex
                         INTEGER,
                    concentratorChassisRingTopologyRingIndex
                         Letter,
                    concentratorChassisRingTopologyWrapUp
                         INTEGER,
                    concentratorChassisRingTopologyWrapDown
                         INTEGER,
                    concentratorChassisRingTopologyUpState
                         INTEGER,
                    concentratorChassisRingTopologyDownState
                         INTEGER,
                    concentratorChassisRingTopologySegment
                         INTEGER,
                    concentratorChassisRingTopologyName
                         DisplayString,
                    concentratorChassisRingTopologySpeed
                         INTEGER,
                    concentratorChassisRingTopologyCardType
                         IOType,
                    concentratorChassisRingTopologyAutoUpChanges
                         Counter,
                    concentratorChassisRingTopologyAutoDownChanges
                         Counter
    }
    
            concentratorChassisRingTopologySlotIndex OBJECT-TYPE
                SYNTAX INTEGER
                ACCESS read-only
                STATUS mandatory
                DESCRIPTION
                    "This variable identifies a slot number that is
                    included in the ring segment."
                ::= { concentratorChassisRingTopologyEntry 1 }
    
            concentratorChassisRingTopologyRingIndex OBJECT-TYPE
                SYNTAX Letter
                ACCESS read-only
                STATUS mandatory
                DESCRIPTION
                    "This variable identifies the ring of the chassis."
                ::= { concentratorChassisRingTopologyEntry 2 }
    
            concentratorChassisRingTopologyWrapUp OBJECT-TYPE
                SYNTAX INTEGER { unwrap(1), wrap(2) }
                ACCESS read-only
                STATUS mandatory
                DESCRIPTION
                    "This variable represents the upper wrap state for
                    the chassis ring which passes through this slot.  By
                    setting this variable to Wrap, the user can create a
                    segment which would contain this slot, and all slots
                    above this one which are on the same segment. "
                ::= { concentratorChassisRingTopologyEntry 3 }
    
            concentratorChassisRingTopologyWrapDown OBJECT-TYPE
                SYNTAX INTEGER { unwrap(1), wrap(2) }
                ACCESS read-only
                STATUS mandatory
                DESCRIPTION
                    "This variable represents the lower wrap state for
                    the chassis ring which passes through this slot.  By
                    setting this variable to Wrap, the user can create a
                    segment which would contain this slot, and all slots
                    below this one which are on the same segment. "
                ::= { concentratorChassisRingTopologyEntry 4 }
    
            concentratorChassisRingTopologyUpState OBJECT-TYPE
                SYNTAX INTEGER { static(1), dynamic(2) }
                ACCESS read-only
                STATUS mandatory
                DESCRIPTION
                    "This variable represents the type of upper wrap for
                    the chassis ring which passes through this slot. "
                ::= { concentratorChassisRingTopologyEntry 5 }
    
            concentratorChassisRingTopologyDownState OBJECT-TYPE
                SYNTAX INTEGER { static(1), dynamic(2) }
                ACCESS read-only
                STATUS mandatory
                DESCRIPTION
                    "This variable represents the type of lower wrap for
                    the chassis ring which passes through this slot. "
                ::= { concentratorChassisRingTopologyEntry 6 }
    
            concentratorChassisRingTopologySegment OBJECT-TYPE
                SYNTAX INTEGER
                ACCESS read-only
                STATUS mandatory
                DESCRIPTION
                    "This variable represents the segment number for the
                    chassis ring which passes through this slot. "
                ::= { concentratorChassisRingTopologyEntry 7 }
    
            concentratorChassisRingTopologyName OBJECT-TYPE
                SYNTAX DisplayString (SIZE (0..16))
                ACCESS read-only
                STATUS mandatory
                DESCRIPTION
                    "This variable represents the name of the ring
                    segment.  The ring segment name is the base ring
                    name with '-segment number' appended to the end."
                ::= { concentratorChassisRingTopologyEntry 8 }
    
            concentratorChassisRingTopologySpeed OBJECT-TYPE
                SYNTAX INTEGER { mbps4(1), mbps16(2) }
                ACCESS read-only
                STATUS mandatory
                DESCRIPTION
                    "This variable indicates the speed of the ring
                    segment.  All segments of a given chassis ring are
                    at the same speed as the parent ring."
                ::= { concentratorChassisRingTopologyEntry 9 }
    
            concentratorChassisRingTopologyCardType OBJECT-TYPE
                SYNTAX IOType
                ACCESS read-only
                STATUS mandatory
                DESCRIPTION
                    "This variable represents the type of the I/O card."
                ::= { concentratorChassisRingTopologyEntry 10}
    
            concentratorChassisRingTopologyAutoUpChanges OBJECT-TYPE
                SYNTAX Counter
                ACCESS read-only
                STATUS mandatory
                DESCRIPTION
                    "This variable reflects the number of times the
                    topology has changed for this ring due to a dynamic
                    wrap up.  This variable is set to zero when
                    concentratorSlotRingZero is written with the value
                    2."
                ::= { concentratorChassisRingTopologyEntry 11 }
    
            concentratorChassisRingTopologyAutoDownChanges OBJECT-TYPE
                SYNTAX Counter
                ACCESS read-only
                STATUS mandatory
                DESCRIPTION
                    "This variable reflects the number of times the
                    topology has changed for this ring due to a dynamic
                    wrap down.  This variable is set to zero when
                    concentratorSlotRingZero is written with the value
                    2."
                ::= { concentratorChassisRingTopologyEntry 12 }
    
            -- The port group contains information and status concerning
            -- the ports of a concentrator:
    
            concentratorPortTable OBJECT-TYPE
                SYNTAX SEQUENCE OF ConcentratorPortEntry
                ACCESS not-accessible
                STATUS mandatory
                DESCRIPTION
                    "Table of information and status concerning the
                    ports of a concentrator."
                ::= { xConcentrator 10 }
    
            concentratorPortEntry OBJECT-TYPE
                SYNTAX ConcentratorPortEntry
                ACCESS not-accessible
                STATUS mandatory
                DESCRIPTION
                    "An entry in the table containing control and status
                    information for a port."
                INDEX { concentratorSlotIndex, concentratorPortIndex }
                ::= { concentratorPortTable 1 }
    
            ConcentratorPortEntry ::=
                SEQUENCE {
                    concentratorPortSlotIndex
                         INTEGER,
                    concentratorPortIndex
                         INTEGER,
                    concentratorPortName
                         DisplayString,
                    concentratorPortType
                         INTEGER,
                    concentratorPortZero
                         INTEGER,
                    concentratorPortSinceZero
                         TimeTicks,
                    concentratorPortAdminState
                         INTEGER,
                    concentratorPortOperState
                         INTEGER,
                    concentratorPortInsertions
                         Counter,
                    concentratorPortInsertFailures
                         Counter,
                    concentratorPortAdminInsert
                         INTEGER,
                    concentratorPortOperInsert
                         INTEGER,
                    concentratorPortSpeed
                         INTEGER,
                    concentratorPortAdminLoopback
                         INTEGER,
                    concentratorPortStationType
                         INTEGER,
                    concentratorPortAdminTrunkInsert
                         INTEGER,
                    concentratorPortSlotRingsAllowed
                         OCTET STRING
            }
    
            concentratorPortSlotIndex OBJECT-TYPE
                SYNTAX INTEGER
                ACCESS read-only
                STATUS mandatory
                DESCRIPTION
                    "This variable identifies the slot of the chassis."
                ::= { concentratorPortEntry 1 }
    
            concentratorPortIndex OBJECT-TYPE
                SYNTAX INTEGER
                ACCESS read-only
                STATUS mandatory
                DESCRIPTION
                    "This variable identifies target port."
                ::= { concentratorPortEntry 2 }
    
            concentratorPortName OBJECT-TYPE
                SYNTAX DisplayString (SIZE (0..16))
                ACCESS read-write
                STATUS mandatory
                DESCRIPTION
                    "This variable represents the user defined name of
                    the port."
                ::= { concentratorPortEntry 3 }
    
            concentratorPortType OBJECT-TYPE
                SYNTAX INTEGER { rj45(1), fiber(2) }
                ACCESS read-only
                STATUS mandatory
                DESCRIPTION
                    "This variable represents the type of connector
                    provided for the port."
                ::= { concentratorPortEntry 4 }
    
            concentratorPortZero OBJECT-TYPE
                SYNTAX INTEGER { ready(1), execute(2) }
                ACCESS read-write
                STATUS mandatory
                DESCRIPTION
                    "This variable is used to control the ports
                    counters.  The agent always returns 'ready' for this
                    value.  Setting the value to 'ready' has no effect."
                ::= { concentratorPortEntry 5 }
    
            concentratorPortSinceZero OBJECT-TYPE
                SYNTAX TimeTicks
                ACCESS read-only
                STATUS mandatory
                DESCRIPTION
                    "This variable reflects the number of time ticks
                    since the counters were las zeroed.  This variable
                    is set to zero when concentratorPortZero is written
                    with the value 2"
                ::= { concentratorPortEntry 6 }
    
            concentratorPortAdminState OBJECT-TYPE
                SYNTAX INTEGER { disabled(1), enabled(2) }
                ACCESS read-write
                STATUS mandatory
                DESCRIPTION
                    "This variable reflects the enable/disable state of
                    the port."
                ::= { concentratorPortEntry 7 }
    
            concentratorPortOperState OBJECT-TYPE
                SYNTAX INTEGER { inserted(1), notInserted(2), rateMismatch(3) }
                ACCESS read-only
                STATUS mandatory
                DESCRIPTION
                    "This variable reflects the enable/disable state of
                    the port."
                ::= { concentratorPortEntry 8 }
    
            concentratorPortInsertions OBJECT-TYPE
                SYNTAX Counter
                ACCESS read-only
                STATUS mandatory
                DESCRIPTION
                    "This variable reflects the number of times the port
                    was inserted into the ring."
                ::= { concentratorPortEntry 9 }
    
            concentratorPortInsertFailures OBJECT-TYPE
                SYNTAX Counter
                ACCESS read-only
                STATUS mandatory
                DESCRIPTION
                    "This variable reflects the number of times the port
                    was not inserted due to a data rate mismatch."
                ::= { concentratorPortEntry 10 }
    
            concentratorPortAdminInsert OBJECT-TYPE
                SYNTAX INTEGER { auto(1),
                                 ring1(2),
                                 ring2(3),
                                 ring3(4),
                                 ring4(5),
                                 ring5(6),
                                 ring6(7),
                                 ring7(8),
                                 ring8(9),
                                 ring9(10),
                                 ring10(11) }
                ACCESS read-write
                STATUS mandatory
                DESCRIPTION
                    "This variable reflects the desired insertion of the
                    port.  Auto indicates to insert the port into the
                    first slot ring with a matching data rate beginning
                    with 1."
                ::= { concentratorPortEntry 11 }
    
            concentratorPortOperInsert OBJECT-TYPE
                SYNTAX INTEGER { notInserted(1),
                  ring1(2),
                  ring2(3),
                  ring3(4),
                  ring4(5),
                  ring5(6),
                  ring6(7),
                  ring7(8),
                  ring8(9),
                  ring9(10),
                  ring10(11) }
                ACCESS read-only
                STATUS mandatory
                DESCRIPTION
                    "This variable reflects the slot ring to which the
                    port is attached."
                ::= { concentratorPortEntry 12 }
    
            concentratorPortSpeed OBJECT-TYPE
                SYNTAX INTEGER { mbs4(1), mbs16(2) }
                ACCESS read-only
                STATUS mandatory
                DESCRIPTION
                    "This variable reflects the measured speed of the
                    port."
                ::= { concentratorPortEntry 13 }
    
            concentratorPortAdminLoopback OBJECT-TYPE
                SYNTAX INTEGER { insert(1), loopback(2) }
                ACCESS read-write
                STATUS mandatory
                DESCRIPTION
                    "This variable reflects the whether this port will
                    be inserted into a ring or the data loop backed."
                ::= { concentratorPortEntry 14 }
    
            concentratorPortStationType OBJECT-TYPE
                SYNTAX INTEGER { station(1), trunk(2) }
                ACCESS read-write
                STATUS mandatory
                DESCRIPTION
                    "This variable reflects the concentrator port type."
                ::= { concentratorPortEntry 15 }
    
            concentratorPortAdminTrunkInsert OBJECT-TYPE
                SYNTAX INTEGER { ready(1), execute(2) }
                ACCESS read-write
                STATUS mandatory
                DESCRIPTION
                    "This variable is used to control the insertion of
                    trunk ports.  When set to 'execute' the trunk port
                    will be inserted into the ring immediately and not
                    wait for the trunk timer to expire. The agent always
                    returns 'ready' for this value.  Setting the value
                    to 'ready' has no effect."
                ::= { concentratorPortEntry 16 }
    
            concentratorPortSlotRingsAllowed OBJECT-TYPE
                SYNTAX OCTET STRING
                ACCESS read-only
                STATUS mandatory
                DESCRIPTION
                    "The list of slot rings into which this port may be
                    inserted.  The OCTET STRING contains a bit map, with
                    a bit for 'none' (indicating it may be isolated) and
                    one bit for each slot ring, and enough octets for
                    all slot rings.  The high order bit of the first
                    octet corresponds to 'none' and each subsequent bit
                    in ascending order corresponds to the slot rings in
                    order beginning with 1."
                ::= { concentratorPortEntry 17 }

            END
