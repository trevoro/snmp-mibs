-- Copyright 1993 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.

-- Revision History
-- Version   Date	Name		Description
-- 1.0       1-Dec-93   W. Meltzer      Initial Release from rev G
-- 1.1       12-May-95  W. Meltzer      Removed range for dmaNodeNum
--
DMA200-MIB DEFINITIONS ::= BEGIN

IMPORTS
	enterprises		FROM RFC1155-SMI
	DisplayString		FROM RFC1213-MIB
	TRAP-TYPE		FROM RFC-1215
	OBJECT-TYPE		FROM RFC-1212;



gdc		OBJECT IDENTIFIER ::= { enterprises 498 }
sc		OBJECT IDENTIFIER ::= { gdc 3 }
dmaSystem	OBJECT IDENTIFIER ::= { sc 7 }


-- groups in the DMA-200 MIB module


-- dmaMaster	OBJECT IDENTIFIER ::= { dmaSystem 1 }

-- dmaNode	OBJECT IDENTIFIER ::= { dmaSystem 2 }

-- dmaElement	OBJECT IDENTIFIER ::= { dmaSystem 3 }



--
-- The DMA Master group
--     Implementation of this group is mandatory for all systems.
--



dmaMaster	OBJECT IDENTIFIER ::= { dmaSystem 1 }

dmaMasterFSterminate	OBJECT-TYPE
	SYNTAX	INTEGER {
			disconnect(1)
		}
	ACCESS	write-only
	STATUS	mandatory
	DESCRIPTION
		"When set, this object will terminate a terminal session
		from the front panel FS port. The terminal will display a
		message to the user that access is terminated."
		::= { dmaMaster 1 }


dmaMasterSupvAccess	OBJECT-TYPE
	SYNTAX	INTEGER {
			none(1),
			local(2),
			global(3)
		}
	ACCESS	read-only
	STATUS	mandatory
	DESCRIPTION
		"The value of the supervisory port terminal access on the
		DMA-200 master as sent by the trap. Note: when in global
		access, this can't be read."
		::= { dmaMaster 2 }


dmaMasterModemCmd	OBJECT-TYPE
	SYNTAX	DisplayString (SIZE (0..256))
	ACCESS	read-write
	STATUS	mandatory
	DESCRIPTION
		"This is the modem 'AT' command string which can be sent
		for modem configuration. When read, it gives the last
		response from the modem. If the modem response is greater
		than 256 bytes in length, the first 256 bytes are read."
	::= { dmaMaster 3 }


dmaMasterDialPrefix	OBJECT-TYPE
	SYNTAX	DisplayString (SIZE (0..16))
	ACCESS	read-write
	STATUS	mandatory
	DESCRIPTION
		"This is the modem 'AT' command string which is sent to the
		modem before the DialPhoneNumber. The default is ATD."
	::= { dmaMaster 4 }


dmaMasterDialPhoneNumber	OBJECT-TYPE
	SYNTAX	DisplayString (SIZE (0..16))
	ACCESS	read-write
	STATUS	mandatory
	DESCRIPTION
		"The phone number of the remote node (DMA-200 slave or
		PMC-100 slave) to be dialled. If no dial-out phone number is
		generated, this value should be set to a zero length string."
	::= { dmaMaster 5 }


dmaMasterDialing   OBJECT-TYPE
	SYNTAX	INTEGER {
                        connect(1),
                        disconnect(2)
		}
	ACCESS	write-only
	STATUS  mandatory
	DESCRIPTION
		"The value initiating the dial or disconnect activity
		of the DMA-200 master dial-out port. No dialing is
		initiated if the phone number value is a zero string."
	::= { dmaMaster 6 }


dmaMasterDialPortStatus  OBJECT-TYPE
	SYNTAX	INTEGER {
			readyOffline(1),
			dialing(2),
			connectedOnline(3)
		}
	ACCESS	read-only
	STATUS	mandatory
	DESCRIPTION
		"The DMA-200 modem port status at the time of the
		SNMP status request."
	::= { dmaMaster 7 }


dmaMasterResumeScan  OBJECT-TYPE
	SYNTAX	INTEGER
	ACCESS	write-only
	STATUS	mandatory
	DESCRIPTION
		"When written, the DMA200 cancels the internal delay timer
		and resumes scanning the Network Elements."
	::= { dmaMaster 8 }


dmaMasterScanCtrl  OBJECT-TYPE
	SYNTAX	INTEGER {
			dmaScanOff(1),
			dmaScanOn(2)
		}
	ACCESS	read-write
	STATUS	mandatory
	DESCRIPTION
		"This object is stored in non-volatile memory and
		controls the scanning process. The first time the unit
		is powered, the non-volatile memory is set to dmaScanOff.
		Setting dmaScanOn will begin the scan process. Setting
		dmaScanOff will stop the scan process and clear any current
		alarm states."
	::= { dmaMaster 9 }


--
-- The Node group
--     Implementation of this group is mandatory for all systems.
--     The information in this group must be entered by the network
--     manager on the SNMP management station.
--

dmaNode		OBJECT IDENTIFIER ::= { dmaSystem 2 }


dmaNodeNum	OBJECT-TYPE
	SYNTAX	INTEGER
	ACCESS	read-only
	STATUS	mandatory
	DESCRIPTION
		"Number of DMA-200 and PMC-100 nodes in the system.
		 Firmware revisions E- and below have a maximum of 20 nodes
		 Firmware revisions F- and above have a maximum of 40 nodes"
	::= { dmaNode 1 }


dmaNodeTable	OBJECT-TYPE
	SYNTAX	SEQUENCE OF DmaNodeEntry
	ACCESS	not-accessible
	STATUS	mandatory
	DESCRIPTION
		"A table that contains information about the nodes in
		the system."
	::= { dmaNode 2 }


dmaNodeEntry	OBJECT-TYPE
	SYNTAX	DmaNodeEntry
	ACCESS	not-accessible
	STATUS	mandatory
	DESCRIPTION
		"A list of information for each node in the system."
	INDEX	{ dmaNodeIndex }
	::= { dmaNodeTable 1 }


DmaNodeEntry ::=
	SEQUENCE {
		dmaNodeIndex
		INTEGER,
		dmaNodeValid
		INTEGER,
		dmaNodePhoneNumber
		DisplayString,
		dmaNodeName
		DisplayString
	}


dmaNodeIndex	OBJECT-TYPE
	SYNTAX	INTEGER (1..20)
	ACCESS	read-only
	STATUS	mandatory
	DESCRIPTION
		"The value indicates the node number for which this
		entry contains management information."
	::= { dmaNodeEntry 1 }


dmaNodeValid	OBJECT-TYPE
	SYNTAX	INTEGER {
			valid(1),
			invalid(2)
		}
	ACCESS	read-write
	STATUS	mandatory
	DESCRIPTION
		"The value indicates the status of the table row entry
		for the purpose of creation and deletion of new node
		instances."
	::= { dmaNodeEntry 2 }


dmaNodePhoneNumber    OBJECT-TYPE
	SYNTAX	DisplayString (SIZE (0..16))
	ACCESS	read-write
	STATUS	mandatory
	DESCRIPTION
		"The phone number of the slave DMA-200 or slave PMC-
		100. If no phone number is generated, this value
		should be set to a zero length string."
	::= { dmaNodeEntry 3 }


dmaNodeName	OBJECT-TYPE
	SYNTAX	DisplayString (SIZE (0..8))
	ACCESS	read-write
	STATUS	mandatory
	DESCRIPTION
		"A textual description of the node ID such as the name
		or location of the node site.  If no name or location
		identification is generated, this value should be set
		to a zero length string."
	::= { dmaNodeEntry 4 }



--
-- The Network Element group
--     Implementation of this group is mandatory for all systems
--


dmaElement  OBJECT IDENTIFIER ::= { dmaSystem 3 }


dmaElementConfigTable   OBJECT-TYPE
	SYNTAX	SEQUENCE OF DmaElementEntry
	ACCESS	not-accessible
	STATUS	mandatory
	DESCRIPTION
		"A table that contains information about all Network
		Elements in the system."
	::= { dmaElement 1 }


dmaElementEntry	OBJECT-TYPE
	SYNTAX	DmaElementEntry
	ACCESS	not-accessible
	STATUS	mandatory
	DESCRIPTION
		"A list of information for each Network Element"
	INDEX	{ dmaElementIndex }
	::= { dmaElementConfigTable 1 }


DmaElementEntry ::=
	SEQUENCE {
		dmaElementIndex
		INTEGER,
		dmaElementRemoteIndex
		INTEGER,
		dmaElementValid
		INTEGER,
		dmaElementType
		INTEGER,
		dmaElementStatus
		INTEGER,
		dmaElementNode
		INTEGER
	}



dmaElementIndex   OBJECT-TYPE
	SYNTAX	INTEGER (0..255)
	ACCESS	read-only
	STATUS	mandatory
	DESCRIPTION
		"The value indicates the Network Element numeric
		address for which this entry contains management information."
	::= { dmaElementEntry 1 }


dmaElementRemoteIndex	OBJECT-TYPE
	SYNTAX	INTEGER (0..255)
	ACCESS	read-write
	STATUS	mandatory
	DESCRIPTION
		"The value indicates the numeric address of the remote
		Network Element on the oposite end of the line."
	::= { dmaElementEntry 2 }


dmaElementValid	OBJECT-TYPE
	SYNTAX	INTEGER {
			valid(1),
			invalid(2)
		}
	ACCESS  read-write
	STATUS  mandatory
	DESCRIPTION
		"The value indicates the status of the table row entry
		for the purpose of creation and deletion of new Network
		Element instances."
	::= { dmaElementEntry 3 }


dmaElementType	OBJECT-TYPE
	SYNTAX	INTEGER {
			other(1),
                        dc551(2),
                        dc552A(3),
                        dc552A-1(4),
                        dc552A-V11(5),
                        dc552A-1-V11(6)
		}
	ACCESS	read-write
	STATUS	mandatory
	DESCRIPTION
		"The value indicates the type the T1-CSU Network Element.
		 This value is set by the manager and sent with traps."
	::= { dmaElementEntry 4 }


dmaElementStatus	OBJECT-TYPE
	SYNTAX	INTEGER {
			statusOK(1),
			statusMajor(2),
			statusMinor(3),
			statusNotResponding(4),
			statusCommErr(5),
			statusMismatchDC551(6),
			statusMismatchDC552A(7),
			statusMismatchDC552A-1(8),
                        statusMismatchDC552A-V11(9),
                        statusMismatchDC552A-1-V11(10)
		}
	ACCESS	read-only
	STATUS	mandatory
	DESCRIPTION
		"The value indicates the communication status of the
		supervisory connection between the DMA-200 Master and
		the Network Element at the time of the SNMP status request."
	::= { dmaElementEntry 5 }


dmaElementNode	OBJECT-TYPE
	SYNTAX  INTEGER
	ACCESS  read-write
	STATUS  mandatory
	DESCRIPTION
		"The value indicates the node number to which this Network
		Element is attached. Same as the corresponding dmaNodeIndex.
		A value of zero indicates that this Network Element is
		attached to no node."
	::= { dmaElementEntry 6 }



--
-- The dma specific traps
--     Implementation of this group is mandatory for all systems
--


dmaAccess	TRAP-TYPE
	ENTERPRISE	dmaSystem
	VARIABLES	{ dmaMasterSupvAccess }
	DESCRIPTION
		"The dmaAccess trap is sent whenever the following occurs:
		value	Condition
		-----	---------
		local	User plugs in a terminal to the front panel
		global	User enters global mode
		local	User enters local mode
		none	User removes front panel terminal"
	::= 1


dmaElementAlarm	TRAP-TYPE
	ENTERPRISE	dmaSystem
        VARIABLES       {
                          dmaElementIndex,
                          dmaElementType,
                          dmaElementStatus,
                          dmaNodeName
                        }
	DESCRIPTION
		"The dmaElementAlarm trap is sent: a) whenever the dma scans
		the active network elements and detects a change in status.
		The element number and the current status are sent. This way
		the trap is sent when an alarm occurs and when it clears.
		b) whenever a network element is logged on to by the DMA
		and a mismatch in dmaElementType is found."
	::= 2

END
