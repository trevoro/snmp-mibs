Nortel-MsCarrier-MscPassport-PorsTrunksMIB
DEFINITIONS ::= BEGIN



IMPORTS

      OBJECT-TYPE
   FROM RFC-1212

      mscPassportMIBs
   FROM Nortel-MsCarrier-MscPassport-UsefulDefinitionsMIB

      RowPointer,
      DisplayString,
      StorageType,
      RowStatus,
      Integer32,
      Unsigned32
   FROM Nortel-MsCarrier-MscPassport-StandardTextualConventionsMIB

      AsciiString,
      NonReplicated
   FROM Nortel-MsCarrier-MscPassport-TextualConventionsMIB

      mscTrk,
      mscTrkIndex
   FROM Nortel-MsCarrier-MscPassport-TrunksMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     PorsTrunks Enterprise MIB."

porsTrunksMIB OBJECT IDENTIFIER ::= { mscPassportMIBs 39 }










-- Trunk/n PathAdmin
-- This component manages all path related activities on behalf of the 
-- trunk. This component is provisioned with a maximum count of 
-- LogicalChannels that it is allowed to create and a maximum percent 
-- of the trunk's outgoing bandwidth that it is permitted to allocate to 
-- these LogicalChannels.

mscTrkPa OBJECT IDENTIFIER ::= { mscTrk 4 }



mscTrkPaRowStatusTable OBJECT-TYPE
   SYNTAX     SEQUENCE OF MscTrkPaRowStatusEntry
   ACCESS     not-accessible
   STATUS     mandatory
   DESCRIPTION
     "This entry controls the addition and deletion of 
      mscTrkPa components."
::= { mscTrkPa 1 }

mscTrkPaRowStatusEntry OBJECT-TYPE
   SYNTAX     MscTrkPaRowStatusEntry
   ACCESS     not-accessible
   STATUS     mandatory
   DESCRIPTION
     "A single entry in the table represents a single 
      mscTrkPa component."
   INDEX {
      mscTrkIndex,
      mscTrkPaIndex }
::= { mscTrkPaRowStatusTable 1 }

MscTrkPaRowStatusEntry ::= SEQUENCE {
   mscTrkPaRowStatus
      RowStatus,
   mscTrkPaComponentName
      DisplayString,
   mscTrkPaStorageType
      StorageType,
   mscTrkPaIndex
      NonReplicated }

mscTrkPaRowStatus OBJECT-TYPE
   SYNTAX     RowStatus 
   ACCESS     read-write
   STATUS     mandatory
   DESCRIPTION
     "This variable is used as the basis for SNMP naming of
      mscTrkPa components.
      These components can be added and deleted."
::= { mscTrkPaRowStatusEntry 1 }

mscTrkPaComponentName OBJECT-TYPE
   SYNTAX     DisplayString 
   ACCESS     read-only
   STATUS     mandatory
   DESCRIPTION
     "This variable provides the component's string name for
      use with the ASCII Console Interface"
::= { mscTrkPaRowStatusEntry 2 }

mscTrkPaStorageType OBJECT-TYPE
   SYNTAX     StorageType 
   ACCESS     read-only
   STATUS     mandatory
   DESCRIPTION
     "This variable represents the storage type value for the
      mscTrkPa tables."
::= { mscTrkPaRowStatusEntry 4 }

mscTrkPaIndex OBJECT-TYPE
   SYNTAX     NonReplicated 
   ACCESS     not-accessible
   STATUS     mandatory
   DESCRIPTION
     "This variable represents the index for the mscTrkPa tables."
::= { mscTrkPaRowStatusEntry 10 }

mscTrkPaProvTable OBJECT-TYPE
   SYNTAX     SEQUENCE OF MscTrkPaProvEntry
   ACCESS     not-accessible
   STATUS     mandatory
   DESCRIPTION
     "This group contains all provisionable attributes relevant to path 
      oriented traffic on a trunk. These attributes provide the maximum 
      number of Logical Channels that are permitted under a Trunk/n and 
      the maximum total bandwidth they are allowed to occupy as a 
      percentage of the outgoing trunk bandwidth."
::= { mscTrkPa 10 }

mscTrkPaProvEntry OBJECT-TYPE
   SYNTAX     MscTrkPaProvEntry
   ACCESS     not-accessible
   STATUS     mandatory
   DESCRIPTION
     "An entry in the mscTrkPaProvTable."
   INDEX {
      mscTrkIndex,
      mscTrkPaIndex }
::= { mscTrkPaProvTable 1 }

MscTrkPaProvEntry ::= SEQUENCE {
   mscTrkPaMaxLc
      Unsigned32,
   mscTrkPaMaxReservedBwOut
      Unsigned32,
   mscTrkPaTrunkSecurity
      Unsigned32,
   mscTrkPaSupportedTrafficTypes
      OCTET STRING,
   mscTrkPaTrunkType
      INTEGER,
   mscTrkPaCustomerParameter
      Unsigned32,
   mscTrkPaTrunkCost
      Unsigned32 }

mscTrkPaMaxLc OBJECT-TYPE
   SYNTAX     Unsigned32 (0..65435)
   ACCESS     read-write
   STATUS     mandatory
   DESCRIPTION
     "This attribute indicates the number of Logical Channels (LCh/n) 
      supported on this trunk. This attribute is used to allocate memory on 
      the trunk FP for the PORS forwarding tables.Unless running in 
      mapped mode on ATM hardware, the PathAdmin will add 100 
      channels to maxLc to reduce the chances of allocation clashes. 
      However, you should never see more than maxLc channels in use 
      for any extended period of time. On ATM hardware in mapped 
      mode the PathAdmin will only add 10 channels to maxLc to permit 
      more efficient use of the available VCC space.
      
      The PathAdmin may not be able to honor a request for maxLc 
      channels. This will happen when the neighbor PathAdmin asks for 
      less channels than this PathAdmin. To resolve the conflict the 
      PathAdmin will always pick the minimum of the two maxLc values. 
      This minimum value is called the negotiatedMaxLc and can be 
      viewed as an operational parameter of the PathAdmin.
      
      Note that in mapped mode on ATM hardware, the value of this 
      attribute provides an upper bound to the number of VCCs that this 
      Trunk/n PathAdmin can occupy. It is not a guarantee that maxLc 
      VCCs will be available to this PathAdmin because the VCC space is 
      a shared resource on the card or port."
   DEFVAL     { 512 }
::= { mscTrkPaProvEntry 1 }

mscTrkPaMaxReservedBwOut OBJECT-TYPE
   SYNTAX     Unsigned32 (0..100)
   ACCESS     read-write
   STATUS     mandatory
   DESCRIPTION
     "This attribute controls the percentage of trunk bandwidth which 
      may be reserved by outgoing path oriented traffic on the trunk. The 
      sum of requiredBandwidth attributes for all paths on this trunk must 
      not exceed this attribute. Setting this attribute to zero (0) prevents 
      paths from being established on this trunk. The limit of reserved 
      bandwidth for incoming path oriented traffic is set using the same 
      attribute on the trunk component on the other end of the trunk. If 
      this attribute is set to 100% connectionless traffic is given a 
      minimum of 1Kbit per second for administrative traffic. This 
      attribute may now be changed without the trunk being restaging. If 
      the value is decreased calls may be bumped as necessary to free up 
      bandwdith. Increasing the value will have no impact on existing 
      calls and new calls will be able to use the new bandwidth."
   DEFVAL     { 50 }
::= { mscTrkPaProvEntry 2 }

mscTrkPaTrunkSecurity OBJECT-TYPE
   SYNTAX     Unsigned32 (0..7)
   ACCESS     read-write
   STATUS     mandatory
   DESCRIPTION
     "This attribute indicates the security level of the trunk. Zero(0) 
      represents the most secure trunk and seven(7) represents the least 
      secure. The path's minimum security requirement is indicated by 
      the Plc requiredSecurity attribute, with values identical in range and 
      meaning to this attribute. PORS ensures that the route selected does 
      not contain a trunk whose PathAdmin trunkSecurity attribute is 
      numerically greater than the path's requiredSecurity."
   DEFVAL     { 0 }
::= { mscTrkPaProvEntry 3 }

mscTrkPaSupportedTrafficTypes OBJECT-TYPE
   SYNTAX     OCTET STRING (SIZE (1))
   ACCESS     read-write
   STATUS     mandatory
   DESCRIPTION
     "This attribute indicates the type of traffic that can be transmitted on 
      the trunk. There are eight(8) possible traffic types, and the trunk can 
      transmit all of them if desired. The voice, data and video traffic 
      types are defined, and five(5) other traffic types can be defined by 
      the network administration. This attribute is used in the route 
      selection process to limit the route to trunks that support the traffic 
      type carried by the path. The requiredTrafficType attribute of the 
      PLC indicates the type of traffic carried on the path.

      Description of bits:
      voice(0)
      data(1)
      video(2)
      trafficType1(3)
      trafficType2(4)
      trafficType3(5)
      trafficType4(6)
      trafficType5(7)"
   DEFVAL     { 'f8'H }
::= { mscTrkPaProvEntry 4 }

mscTrkPaTrunkType OBJECT-TYPE
   SYNTAX     INTEGER  {
                 terrestrial(0),
                 satellite(1),
                 trunkType1(2),
                 trunkType2(3),
                 trunkType3(4),
                 trunkType4(5),
                 trunkType5(6),
                 trunkType6(7) }
   ACCESS     read-write
   STATUS     mandatory
   DESCRIPTION
     "This attribute lists the type of the trunk. There can be up to eight(8) 
      types of trunks. The terrestrial and satellite trunk types have been 
      defined, leaving six(6) remaining types that can be defined by the 
      network administration. The set of allowed trunk types for a path is 
      indicated in the permittedTrunkType attribute of the PLC. When 
      selecting a route, PORS only chooses trunks whose PathAdmin 
      trunkType are in the permittedTrunkTypes set of the path."
   DEFVAL     { terrestrial }
::= { mscTrkPaProvEntry 5 }

mscTrkPaCustomerParameter OBJECT-TYPE
   SYNTAX     Unsigned32 (0..7)
   ACCESS     read-write
   STATUS     mandatory
   DESCRIPTION
     "This attribute indicates the customer defined parameter for the 
      trunk. Its value, a number from zero(0) to seven(7), is chosen by a 
      network administration to have a meaning specific to their network, 
      thus allowing them to customize the use of their trunks. A 
      complementary PLC attribute, requiredCustomerParameter, also 
      has a value from zero(0) to seven(7). The Route Selector does not 
      consider trunks whose PathAdmin customerParameter is greater 
      than the requiredCustomerParameter of the path."
   DEFVAL     { 0 }
::= { mscTrkPaProvEntry 6 }

mscTrkPaTrunkCost OBJECT-TYPE
   SYNTAX     Unsigned32 (1..255)
   ACCESS     read-write
   STATUS     mandatory
   DESCRIPTION
     "This attribute is the cost metric for the trunk. This value is assigned 
      by the network administration to represent the network cost of using 
      this trunk. It can be related to distance, speed, dollars, or any other 
      factor that could be taken into consideration. If the 
      trunkAttributeToMinimize is set to trunkCost, PORS finds a route 
      with the smallest sum of the PathAdmin trunkCost attribute over all 
      trunks. The trunk cost can be increased or decreased without 
      disrupting the service to the link. If it is increased and the PORS 
      optimization feature is enabled calls will move off this link to lower 
      cost links when possible. If the cost is decreased new calls will be 
      attracted to this link."
   DEFVAL     { 128 }
::= { mscTrkPaProvEntry 7 }

mscTrkPaOperTable OBJECT-TYPE
   SYNTAX     SEQUENCE OF MscTrkPaOperEntry
   ACCESS     not-accessible
   STATUS     mandatory
   DESCRIPTION
     "This group contains all operational attributes relevant to path 
      oriented and connectionless bandwidth utilization and path activity 
      on a trunk."
::= { mscTrkPa 11 }

mscTrkPaOperEntry OBJECT-TYPE
   SYNTAX     MscTrkPaOperEntry
   ACCESS     not-accessible
   STATUS     mandatory
   DESCRIPTION
     "An entry in the mscTrkPaOperTable."
   INDEX {
      mscTrkIndex,
      mscTrkPaIndex }
::= { mscTrkPaOperTable 1 }

MscTrkPaOperEntry ::= SEQUENCE {
   mscTrkPaState
      AsciiString,
   mscTrkPaUsedLc
      Unsigned32,
   mscTrkPaNegotiatedMaxLc
      Unsigned32,
   mscTrkPaMaxReservableBwOut
      Unsigned32,
   mscTrkPaOverReservedBwOut
      Unsigned32,
   mscTrkPaUnreservedBwOut
      Unsigned32,
   mscTrkPaClashCount
      Unsigned32,
   mscTrkPaNegotiatedSupportedTrafficTypes
      OCTET STRING,
   mscTrkPaNegotiatedTrunkSecurity
      Unsigned32,
   mscTrkPaNegotiatedCustomerParameter
      Unsigned32,
   mscTrkPaNegotiatedTrunkCost
      Unsigned32,
   mscTrkPaNegotiatedAtmMode
      INTEGER,
   mscTrkPaNegotiatedTrunkDelay
      Unsigned32,
   mscTrkPaNegotiatedTrunkType
      INTEGER }

mscTrkPaState OBJECT-TYPE
   SYNTAX     AsciiString (SIZE (1..80))
   ACCESS     read-only
   STATUS     mandatory
   DESCRIPTION
     "This attribute gives the operational state of the PathAdmin 
      component. The PathAdmin may be up, down, goingDown, staging 
      or downWaitingRestage."
::= { mscTrkPaOperEntry 1 }

mscTrkPaUsedLc OBJECT-TYPE
   SYNTAX     Unsigned32 (0..4294967295)
   ACCESS     read-only
   STATUS     mandatory
   DESCRIPTION
     "This attribute gives the total number of Logical Channels currently 
      busy on the trunk. When this number reaches maxLc, no more paths 
      are allowed to instantiate through this trunk. Note that it is possible 
      for usedLc to be less than maxLc but for there to be no currently 
      free LogicalChannels. This is because a LogicalChannel can be in 
      one of several intermediate states between free and busy."
::= { mscTrkPaOperEntry 2 }

mscTrkPaNegotiatedMaxLc OBJECT-TYPE
   SYNTAX     Unsigned32 (0..4294967295)
   ACCESS     read-only
   STATUS     mandatory
   DESCRIPTION
     "This attribute gives the actual value of maxLc that the PathAdmin 
      has decided on after negotiation with the far end PathAdmin. If 
      there is disagreement between the two PathAdmin's maxLc 
      provisionable attributes the smaller of the two is chosen on both 
      sides. This attribute reflects the minimum of these two maxLc's."
::= { mscTrkPaOperEntry 3 }

mscTrkPaMaxReservableBwOut OBJECT-TYPE
   SYNTAX     Unsigned32 (0..4294967295)
   ACCESS     read-only
   STATUS     mandatory
   DESCRIPTION
     "This attribute gives the total bandwidth that this PathAdmin is 
      allowed to reserve. This number is computed by multiplying the 
      parent trunk's measuredSpeedToIf attribute by the 
      maxReservedBwOut provisionable attribute of this PathAdmin."
::= { mscTrkPaOperEntry 4 }

mscTrkPaOverReservedBwOut OBJECT-TYPE
   SYNTAX     Unsigned32 (0..4294967295)
   ACCESS     read-only
   STATUS     mandatory
   DESCRIPTION
     "When bumping is required to free up enough bandwidth for a new 
      path there exists a short period of time when both the new path and 
      the soon to be bumped path are occupying the same bandwidth. 
      This means that the total amount of reserved bandwidth will exceed 
      maxReservableBwOut. When this happens the unreservedBwOut 
      attribute will be 0 and the overReservedBwOut attribute will be non-
      zero to indicate by how much we are currently overcommitted. This 
      value should quickly drop back to zero as the bumping starts to 
      clear the lower holdingPriority calls."
::= { mscTrkPaOperEntry 5 }

mscTrkPaUnreservedBwOut OBJECT-TYPE
   SYNTAX     Unsigned32 (0..4294967295)
   ACCESS     read-only
   STATUS     mandatory
   DESCRIPTION
     "This attribute gives the total of amount of bandwidth that is still 
      available for reservation by new connections. When this number 
      reaches 0 the PathAdmin will no longer admit new connections to 
      the trunk. This number represents available bandwidth in the 
      outward going direction. To determine the inward available 
      bandwidth you must query the PathAdmin at the other end of this 
      Trunk."
::= { mscTrkPaOperEntry 6 }

mscTrkPaClashCount OBJECT-TYPE
   SYNTAX     Unsigned32 (0..4294967295)
   ACCESS     read-only
   STATUS     mandatory
   DESCRIPTION
     "This attribute gives the total number of path setup requests that 
      resulted in an LCh/n or Vcc/x.y clash. A large value for this number 
      is an indicator of poor performance by the PathAdmin in its 
      allocation of LCh/n or Vcc/x.y components. In general the channels 
      will be allocated in opposite orders at each end of the Trunk but this 
      may not always be the case. Note that as the PathAdmin runs out of 
      LCh/n or Vcc/x.y components the number of clashes will increase."
::= { mscTrkPaOperEntry 7 }

mscTrkPaNegotiatedSupportedTrafficTypes OBJECT-TYPE
   SYNTAX     OCTET STRING (SIZE (1))
   ACCESS     read-only
   STATUS     mandatory
   DESCRIPTION
     "This attribute gives the actual value of supportedTrafficTypes that 
      the PathAdmin has decided on after negotiation with the far end 
      PathAdmin. If there is disagreement between the two PathAdmin's 
      supportedTrafficTypes provisionable attributes the union of the two 
      is chosen on both sides. This attribute reflects the union of these two 
      supportedTrafficTypes 's. It is this union that is advertised to all 
      other nodes in the network and which is used for routing decisions.

      Description of bits:
      voice(0)
      data(1)
      video(2)
      trafficType1(3)
      trafficType2(4)
      trafficType3(5)
      trafficType4(6)
      trafficType5(7)"
::= { mscTrkPaOperEntry 9 }

mscTrkPaNegotiatedTrunkSecurity OBJECT-TYPE
   SYNTAX     Unsigned32 (0..7)
   ACCESS     read-only
   STATUS     mandatory
   DESCRIPTION
     "This attribute gives the actual value of the trunkSecurity that the 
      PathAdmin has decided on after negotiation with the far end 
      PathAdmin. If there is disagreement between the two PathAdmin's 
      trunkSecurity provisionable attributes the larger of the two is chosen 
      on both sides. This attribute reflects the maximum of these two 
      trunkSecurity's."
::= { mscTrkPaOperEntry 10 }

mscTrkPaNegotiatedCustomerParameter OBJECT-TYPE
   SYNTAX     Unsigned32 (0..7)
   ACCESS     read-only
   STATUS     mandatory
   DESCRIPTION
     "This attribute gives the actual value of customerParameter that the 
      PathAdmin has decided on after negotiation with the far end 
      PathAdmin. If there is disagreement between the two PathAdmin's 
      customerParameter provisionable attributes the larger of the two is 
      chosen on both sides. This attribute reflects the maximum of these 
      two customerParameter's."
::= { mscTrkPaOperEntry 11 }

mscTrkPaNegotiatedTrunkCost OBJECT-TYPE
   SYNTAX     Unsigned32 (1..255)
   ACCESS     read-only
   STATUS     mandatory
   DESCRIPTION
     "This attribute gives the actual value of trunkCost that the 
      PathAdmin has decided on after negotiation with the far end 
      PathAdmin. If there is disagreement between the two PathAdmin's 
      trunkCost provisionable attributes the larger of the two is chosen on 
      both sides. This attribute reflects the maximum of these two 
      trunkCost's."
::= { mscTrkPaOperEntry 12 }

mscTrkPaNegotiatedAtmMode OBJECT-TYPE
   SYNTAX     INTEGER  {
                 multiplexing(0),
                 mapping(1),
                 notApplicable(2) }
   ACCESS     read-only
   STATUS     mandatory
   DESCRIPTION
     "This attribute gives the actual value of PathAdmin Atm mode that 
      the PathAdmin has decided on after negotiation with the far end 
      PathAdmin. This is only applicable to ATM cards since the mode on 
      non ATM hardware is not specified. The multiplexing mode implies 
      that all voice traffic will be multiplexed onto the Atm 
      atmConnection Vcc and all data will be multiplexed onto the Trunk 
      Atm atmConnection Vcc. The mapping mode implies that each 
      unique logical channel will be allocated its own Vcc. The mode 
      notApplicable implies either this is not ATM hardware or that no 
      Atm subcomponent exists under this or the peer PathAdmin."
::= { mscTrkPaOperEntry 13 }

mscTrkPaNegotiatedTrunkDelay OBJECT-TYPE
   SYNTAX     Unsigned32 (0..1500)
   ACCESS     read-only
   STATUS     mandatory
   DESCRIPTION
     "This attribute gives the actual value of parent trunk's half round trip 
      delay (propagation delay) that the PathAdmin has decided on after 
      negotiation with the far end PathAdmin. If there is disagreement 
      between the two PathAdmins the larger of the two propagation 
      delays is chosen on both sides. This attribute reflects the maximum 
      of these two propagation delays."
::= { mscTrkPaOperEntry 14 }

mscTrkPaNegotiatedTrunkType OBJECT-TYPE
   SYNTAX     INTEGER  {
                 terrestrial(0),
                 satellite(1),
                 trunkType1(2),
                 trunkType2(3),
                 trunkType3(4),
                 trunkType4(5),
                 trunkType5(6),
                 trunkType6(7) }
   ACCESS     read-only
   STATUS     mandatory
   DESCRIPTION
     "This attribute gives the actual value of trunkType that the 
      PathAdmin has decided on after negotiation with the far end 
      PathAdmin. If there is disagreement between the two PathAdmin's 
      trunkType provisionable attributes the provisioned values are used 
      on both sides. That is, both sides maintain their provisioned value.."
::= { mscTrkPaOperEntry 15 }

mscTrkPaRbwTable OBJECT-TYPE
   SYNTAX     SEQUENCE OF MscTrkPaRbwEntry
   ACCESS     not-accessible
   STATUS     mandatory
   DESCRIPTION
     "This attribute gives the total bandwidth reserved by paths for each 
      of five (5) holding priorities. For example the bandwidth used by 
      holdingPriority 0 paths is shown in the left most value."
::= { mscTrkPa 214 }

mscTrkPaRbwEntry OBJECT-TYPE
   SYNTAX     MscTrkPaRbwEntry
   ACCESS     not-accessible
   STATUS     mandatory
   DESCRIPTION
     "An entry in the mscTrkPaRbwTable."
   INDEX {
      mscTrkIndex,
      mscTrkPaIndex,
      mscTrkPaRbwIndex }
::= { mscTrkPaRbwTable 1 }

MscTrkPaRbwEntry ::= SEQUENCE {
   mscTrkPaRbwIndex
      Integer32,
   mscTrkPaRbwValue
      Unsigned32 }

mscTrkPaRbwIndex OBJECT-TYPE
   SYNTAX     Integer32 (0..4)
   ACCESS     not-accessible
   STATUS     mandatory
   DESCRIPTION
     "This variable represents the index for the mscTrkPaRbwTable."
::= { mscTrkPaRbwEntry 1 }

mscTrkPaRbwValue OBJECT-TYPE
   SYNTAX     Unsigned32 (0..4294967295)
   ACCESS     read-only
   STATUS     mandatory
   DESCRIPTION
     "This variable represents an individual value for the
      mscTrkPaRbwTable."
::= { mscTrkPaRbwEntry 2 }

mscTrkPaPacntTable OBJECT-TYPE
   SYNTAX     SEQUENCE OF MscTrkPaPacntEntry
   ACCESS     not-accessible
   STATUS     mandatory
   DESCRIPTION
     "This attribute gives the total number of path instantiation attempts 
      this trunk has processed since its creation. This number includes 
      successful and unsuccessful attempts. This attribute provides five 
      (5) values of this count, one for each path holdingPriority."
::= { mscTrkPa 215 }

mscTrkPaPacntEntry OBJECT-TYPE
   SYNTAX     MscTrkPaPacntEntry
   ACCESS     not-accessible
   STATUS     mandatory
   DESCRIPTION
     "An entry in the mscTrkPaPacntTable."
   INDEX {
      mscTrkIndex,
      mscTrkPaIndex,
      mscTrkPaPacntIndex }
::= { mscTrkPaPacntTable 1 }

MscTrkPaPacntEntry ::= SEQUENCE {
   mscTrkPaPacntIndex
      Integer32,
   mscTrkPaPacntValue
      Unsigned32 }

mscTrkPaPacntIndex OBJECT-TYPE
   SYNTAX     Integer32 (0..4)
   ACCESS     not-accessible
   STATUS     mandatory
   DESCRIPTION
     "This variable represents the index for the mscTrkPaPacntTable."
::= { mscTrkPaPacntEntry 1 }

mscTrkPaPacntValue OBJECT-TYPE
   SYNTAX     Unsigned32 (0..4294967295)
   ACCESS     read-only
   STATUS     mandatory
   DESCRIPTION
     "This variable represents an individual value for the
      mscTrkPaPacntTable."
::= { mscTrkPaPacntEntry 2 }

mscTrkPaPfcntTable OBJECT-TYPE
   SYNTAX     SEQUENCE OF MscTrkPaPfcntEntry
   ACCESS     not-accessible
   STATUS     mandatory
   DESCRIPTION
     "This attribute gives the total number of path instantiation failures 
      that have happened since the creation of this trunk. This attribute 
      provides five (5) values of this count, one for each path 
      holdingPriority."
::= { mscTrkPa 216 }

mscTrkPaPfcntEntry OBJECT-TYPE
   SYNTAX     MscTrkPaPfcntEntry
   ACCESS     not-accessible
   STATUS     mandatory
   DESCRIPTION
     "An entry in the mscTrkPaPfcntTable."
   INDEX {
      mscTrkIndex,
      mscTrkPaIndex,
      mscTrkPaPfcntIndex }
::= { mscTrkPaPfcntTable 1 }

MscTrkPaPfcntEntry ::= SEQUENCE {
   mscTrkPaPfcntIndex
      Integer32,
   mscTrkPaPfcntValue
      Unsigned32 }

mscTrkPaPfcntIndex OBJECT-TYPE
   SYNTAX     Integer32 (0..4)
   ACCESS     not-accessible
   STATUS     mandatory
   DESCRIPTION
     "This variable represents the index for the mscTrkPaPfcntTable."
::= { mscTrkPaPfcntEntry 1 }

mscTrkPaPfcntValue OBJECT-TYPE
   SYNTAX     Unsigned32 (0..4294967295)
   ACCESS     read-only
   STATUS     mandatory
   DESCRIPTION
     "This variable represents an individual value for the
      mscTrkPaPfcntTable."
::= { mscTrkPaPfcntEntry 2 }

mscTrkPaPccntTable OBJECT-TYPE
   SYNTAX     SEQUENCE OF MscTrkPaPccntEntry
   ACCESS     not-accessible
   STATUS     mandatory
   DESCRIPTION
     "This attribute gives the total number of path clear requests this trunk 
      has processed since its creation. This attribute provides five (5) 
      values of this count, one for each path holdingPriority."
::= { mscTrkPa 217 }

mscTrkPaPccntEntry OBJECT-TYPE
   SYNTAX     MscTrkPaPccntEntry
   ACCESS     not-accessible
   STATUS     mandatory
   DESCRIPTION
     "An entry in the mscTrkPaPccntTable."
   INDEX {
      mscTrkIndex,
      mscTrkPaIndex,
      mscTrkPaPccntIndex }
::= { mscTrkPaPccntTable 1 }

MscTrkPaPccntEntry ::= SEQUENCE {
   mscTrkPaPccntIndex
      Integer32,
   mscTrkPaPccntValue
      Unsigned32 }

mscTrkPaPccntIndex OBJECT-TYPE
   SYNTAX     Integer32 (0..4)
   ACCESS     not-accessible
   STATUS     mandatory
   DESCRIPTION
     "This variable represents the index for the mscTrkPaPccntTable."
::= { mscTrkPaPccntEntry 1 }

mscTrkPaPccntValue OBJECT-TYPE
   SYNTAX     Unsigned32 (0..4294967295)
   ACCESS     read-only
   STATUS     mandatory
   DESCRIPTION
     "This variable represents an individual value for the
      mscTrkPaPccntTable."
::= { mscTrkPaPccntEntry 2 }

mscTrkPaPbcntTable OBJECT-TYPE
   SYNTAX     SEQUENCE OF MscTrkPaPbcntEntry
   ACCESS     not-accessible
   STATUS     mandatory
   DESCRIPTION
     "This attribute gives the total number of path bumping requests this 
      trunk has processed since its creation. This attribute provides 5 
      values of this count, one for each path holdingPriority."
::= { mscTrkPa 218 }

mscTrkPaPbcntEntry OBJECT-TYPE
   SYNTAX     MscTrkPaPbcntEntry
   ACCESS     not-accessible
   STATUS     mandatory
   DESCRIPTION
     "An entry in the mscTrkPaPbcntTable."
   INDEX {
      mscTrkIndex,
      mscTrkPaIndex,
      mscTrkPaPbcntIndex }
::= { mscTrkPaPbcntTable 1 }

MscTrkPaPbcntEntry ::= SEQUENCE {
   mscTrkPaPbcntIndex
      Integer32,
   mscTrkPaPbcntValue
      Unsigned32 }

mscTrkPaPbcntIndex OBJECT-TYPE
   SYNTAX     Integer32 (0..4)
   ACCESS     not-accessible
   STATUS     mandatory
   DESCRIPTION
     "This variable represents the index for the mscTrkPaPbcntTable."
::= { mscTrkPaPbcntEntry 1 }

mscTrkPaPbcntValue OBJECT-TYPE
   SYNTAX     Unsigned32 (0..4294967295)
   ACCESS     read-only
   STATUS     mandatory
   DESCRIPTION
     "This variable represents an individual value for the
      mscTrkPaPbcntTable."
::= { mscTrkPaPbcntEntry 2 }

-- 
-- *** THIS SUBTREE CURRENTLY NOT IMPLEMENTED ***
-- 

-- Trunk/n LogicalChannel/n
-- This component is automatically created when a new path sets up 
-- over the Trunk and is deleted when that path terminates. An 
-- application component name followed by a series of 
-- LogicalChannel component names followed by an application 
-- component name serve to uniquely identify a path. Issuing a clear 
-- to this component will cause the entire path to collapse and all 
-- resources to be freed. Normally the end point components will 
-- attempt to reroute after a clear and may even reroute over this same 
-- trunk.

mscTrkLCh OBJECT IDENTIFIER ::= { mscTrk 5 }



mscTrkLChRowStatusTable OBJECT-TYPE
   SYNTAX     SEQUENCE OF MscTrkLChRowStatusEntry
   ACCESS     not-accessible
   STATUS     mandatory
   DESCRIPTION
     "*** THIS TABLE CURRENTLY NOT IMPLEMENTED ***

      This entry controls the addition and deletion of 
      mscTrkLCh components."
::= { mscTrkLCh 1 }

mscTrkLChRowStatusEntry OBJECT-TYPE
   SYNTAX     MscTrkLChRowStatusEntry
   ACCESS     not-accessible
   STATUS     mandatory
   DESCRIPTION
     "A single entry in the table represents a single 
      mscTrkLCh component."
   INDEX {
      mscTrkIndex,
      mscTrkLChIndex }
::= { mscTrkLChRowStatusTable 1 }

MscTrkLChRowStatusEntry ::= SEQUENCE {
   mscTrkLChRowStatus
      RowStatus,
   mscTrkLChComponentName
      DisplayString,
   mscTrkLChStorageType
      StorageType,
   mscTrkLChIndex
      Integer32 }

mscTrkLChRowStatus OBJECT-TYPE
   SYNTAX     RowStatus 
   ACCESS     read-only
   STATUS     mandatory
   DESCRIPTION
     "This variable is used as the basis for SNMP naming of
      mscTrkLCh components.
      These components cannot be added nor deleted."
::= { mscTrkLChRowStatusEntry 1 }

mscTrkLChComponentName OBJECT-TYPE
   SYNTAX     DisplayString 
   ACCESS     read-only
   STATUS     mandatory
   DESCRIPTION
     "This variable provides the component's string name for
      use with the ASCII Console Interface"
::= { mscTrkLChRowStatusEntry 2 }

mscTrkLChStorageType OBJECT-TYPE
   SYNTAX     StorageType 
   ACCESS     read-only
   STATUS     mandatory
   DESCRIPTION
     "This variable represents the storage type value for the
      mscTrkLCh tables."
::= { mscTrkLChRowStatusEntry 4 }

mscTrkLChIndex OBJECT-TYPE
   SYNTAX     Integer32 (1..65535)
   ACCESS     not-accessible
   STATUS     mandatory
   DESCRIPTION
     "This variable represents the index for the mscTrkLCh tables."
::= { mscTrkLChRowStatusEntry 10 }

mscTrkLChOperTable OBJECT-TYPE
   SYNTAX     SEQUENCE OF MscTrkLChOperEntry
   ACCESS     not-accessible
   STATUS     mandatory
   DESCRIPTION
     "*** THIS TABLE CURRENTLY NOT IMPLEMENTED ***

      This group contains all operational attributes pertaining to the 
      Logical Channel component owned by this trunk."
::= { mscTrkLCh 10 }

mscTrkLChOperEntry OBJECT-TYPE
   SYNTAX     MscTrkLChOperEntry
   ACCESS     not-accessible
   STATUS     mandatory
   DESCRIPTION
     "An entry in the mscTrkLChOperTable."
   INDEX {
      mscTrkIndex,
      mscTrkLChIndex }
::= { mscTrkLChOperTable 1 }

MscTrkLChOperEntry ::= SEQUENCE {
   mscTrkLChNextHop
      RowPointer,
   mscTrkLChSetupPriority
      Unsigned32,
   mscTrkLChHoldingPriority
      Unsigned32,
   mscTrkLChEmissionPriority
      Unsigned32,
   mscTrkLChDiscardPriority
      Unsigned32,
   mscTrkLChRequiredTxBandwidth
      Unsigned32,
   mscTrkLChRequiredRxBandwidth
      Unsigned32,
   mscTrkLChMode
      INTEGER,
   mscTrkLChMaximumTransmissionUnit
      Unsigned32,
   mscTrkLChLocalConnection
      RowPointer }

mscTrkLChNextHop OBJECT-TYPE
   SYNTAX     RowPointer 
   ACCESS     read-only
   STATUS     mandatory
   DESCRIPTION
     "The nextHop is the name of the component across the bus which is 
      forwarding packets to us. Inversely the nextHop of our nextHop 
      component is us. More precisely, LCh/n components point to each 
      other across the bus via their nextHop attributes. In the case where 
      the next hop is an application the nextHop attribute will indicate the 
      component name of this application."
::= { mscTrkLChOperEntry 2 }

mscTrkLChSetupPriority OBJECT-TYPE
   SYNTAX     Unsigned32 (0..4)
   ACCESS     read-only
   STATUS     mandatory
   DESCRIPTION
     "This attribute gives the priority at which a path is established. Zero 
      (0) is the highest priority and four (4) is the lowest. When PORS 
      establishes a path through the network, it uses the setupPriority 
      attribute to determine its potential for bumping established paths to 
      acquire their bandwidth. The holdingPriority, a complementary 
      attribute of this component, indicates the priority a path maintains 
      once it is established. A new path can bump an existing path if the 
      new path's setupPriority is higher (or numerically less) than the 
      existing path's holdingPriority."
::= { mscTrkLChOperEntry 3 }

mscTrkLChHoldingPriority OBJECT-TYPE
   SYNTAX     Unsigned32 (0..4)
   ACCESS     read-only
   STATUS     mandatory
   DESCRIPTION
     "This attribute gives the priority that a path holds once it is 
      established. Zero (0) is the highest priority and four (4) is the 
      lowest. A path's holdingPriority determines its likelihood of being 
      bumped by a new path to acquire its bandwidth. The setupPriority, a 
      complementary attribute, indicates the priority of a path at 
      establishment time. A new path can bump an existing path if the 
      new path's setupPriority is higher (or numerically less) than the 
      existing path's holdingPriority."
::= { mscTrkLChOperEntry 4 }

mscTrkLChEmissionPriority OBJECT-TYPE
   SYNTAX     Unsigned32 (0..3)
   ACCESS     read-only
   STATUS     mandatory
   DESCRIPTION
     "This attribute indicates the urgency with which packets on the 
      LCh's path are emitted by this trunk. The emissionPriority 
      translates into the trunk's emission queue. Zero (0) indicates the 
      highest emissionPriority, while three (3) indicates the lowest. 
      Packets with a higher emissionPriority (or numerically less) are put 
      on an emission queue which is serviced before a queue which 
      accepts packets of a lower emissionPriority and hence experience 
      smaller delays traversing congested trunks."
::= { mscTrkLChOperEntry 5 }

mscTrkLChDiscardPriority OBJECT-TYPE
   SYNTAX     Unsigned32 (0..3)
   ACCESS     read-only
   STATUS     mandatory
   DESCRIPTION
     "This attribute indicates the importance of the packets on the path. 
      Zero (0) is used for paths carrying the most important traffic, and 
      two (3) is used for paths carrying the least important traffic. In times 
      of congestion, the discardPriority is used by packet forwarding on 
      the trunk to determine which packets are discarded first to reduce 
      the load. Packets with a higher discardPriority (or numerically less) 
      are discarded after packets with a lower discardPriority (or 
      numerically higher)."
::= { mscTrkLChOperEntry 6 }

mscTrkLChRequiredTxBandwidth OBJECT-TYPE
   SYNTAX     Unsigned32 (0..4294967295)
   ACCESS     read-only
   STATUS     mandatory
   DESCRIPTION
     "This attribute gives the bandwidth (in bits per second units) 
      reserved by this LCh/n for emitting packets on the trunk."
::= { mscTrkLChOperEntry 7 }

mscTrkLChRequiredRxBandwidth OBJECT-TYPE
   SYNTAX     Unsigned32 (0..4294967295)
   ACCESS     read-only
   STATUS     mandatory
   DESCRIPTION
     "This attribute gives the bandwidth (in bits per second units) 
      reserved by this LCh/n for receiving packets on the trunk."
::= { mscTrkLChOperEntry 8 }

mscTrkLChMode OBJECT-TYPE
   SYNTAX     INTEGER  {
                 unknown(0),
                 hdlcFrmMux(1),
                 aal5FrmMux(2),
                 spoFrmMux(3),
                 spoFrmMap(4),
                 aal5FrmMap(5),
                 cellMap(6) }
   ACCESS     read-only
   STATUS     mandatory
   DESCRIPTION
     "This attribute gives the operational mode of the LogicalChannel 
      component. It indicates what kind of transport is being performed 
      on the packets in the channel. There are 7 possible values of this 
      attribute as follows:
      
      unknown - not currently in busy state, type of forwarding not 
      determined yet.
      
      hdlcFrmMux - frames are being multiplexed (multiple LCh/n on 
      same port or channel) using HDLC encapsulation.
      
      aal5FrmMux - frames are being multiplexed (multiple LCh/n on 
      same ATM VCC) using the AAL5 segmentation and recombination 
      protocol. 
      
      spoFrmMux - frames are being multiplexed (multiple LCh/n on 
      same ATM VCC) using the Short Path Oriented segmentation and 
      recombination protocol. This is a proprietary protocol which 
      encapsulates voice frames into a single ATM cell unlike AAL5 
      which would require two cells to transport the 45 byte voice frames.
      
      aal5FrmMap - frames are being mapped (a single LCh/n per ATM 
      VCC) using the AAL5 segmentation and recombination protocol. 
      AAL5 mapped frames are forwarded by hardware in both directions 
      and require no CPU intervention.
      
      spoFrmMap - frames are being mapped (a single LCh/n per ATM 
      VCC) using the Short Path Oriented segmentation and 
      recombination protocol. SPO mapped frames are forwarded by 
      hardware in both directions and require no CPU intervention in all 
      but one special case. In particular CPU is required only if frames 
      are being forwarded to an LCh/n whose mode is spoFrmMux.
      
      cellMap - ATM cells are being relayed directly over the bus with no 
      segmentation and recombination protocol. The segmentation and 
      recombination is only done at transition points between frame based 
      cards and ATM cell based cards so this hop represents a pure 
      tandem cell hop, ATM card to ATM card. No CPU is required to 
      process these cells."
::= { mscTrkLChOperEntry 9 }

mscTrkLChMaximumTransmissionUnit OBJECT-TYPE
   SYNTAX     Unsigned32 (0..4294967295)
   ACCESS     read-only
   STATUS     mandatory
   DESCRIPTION
     "This attribute gives the size of the largest frame this service will 
      send. A value of 0 means that the Mtu is unknown. A value of 45 or 
      less (but non zero) means that ATM single cell transport will be 
      used wherever possible. Otherwise ATM AAL5 adaption layer 
      transport will be required to handle all frames."
::= { mscTrkLChOperEntry 10 }

mscTrkLChLocalConnection OBJECT-TYPE
   SYNTAX     RowPointer 
   ACCESS     read-only
   STATUS     mandatory
   DESCRIPTION
     "The localConnection attribute specifies the name of the connection 
      on the local interface. On ATM hardware this is in the form AtmIf/n 
      Vcc/x.y. On non ATM hardware this attribute is empty."
::= { mscTrkLChOperEntry 11 }




-- 
-- Version and Compliance statements
-- 



-- Object-Group Statement:
-- A list of all current accessible leaf objects.

-- OBJECTS { mscTrkLChComponentName,
--           mscTrkPaUsedLc,
--           mscTrkLChEmissionPriority,
--           mscTrkPaComponentName,
--           mscTrkPaRbwValue,
--           mscTrkPaTrunkCost,
--           mscTrkPaStorageType,
--           mscTrkLChLocalConnection,
--           mscTrkPaNegotiatedAtmMode,
--           mscTrkPaMaxLc,
--           mscTrkPaSupportedTrafficTypes,
--           mscTrkLChMode,
--           mscTrkPaUnreservedBwOut,
--           mscTrkPaCustomerParameter,
--           mscTrkPaMaxReservableBwOut,
--           mscTrkLChStorageType,
--           mscTrkLChDiscardPriority,
--           mscTrkPaNegotiatedTrunkDelay,
--           mscTrkPaTrunkSecurity,
--           mscTrkPaNegotiatedTrunkCost,
--           mscTrkPaTrunkType,
--           mscTrkLChRowStatus,
--           mscTrkPaClashCount,
--           mscTrkPaNegotiatedMaxLc,
--           mscTrkPaNegotiatedSupportedTrafficTypes,
--           mscTrkLChSetupPriority,
--           mscTrkPaPccntValue,
--           mscTrkPaOverReservedBwOut,
--           mscTrkPaNegotiatedCustomerParameter,
--           mscTrkPaRowStatus,
--           mscTrkPaState,
--           mscTrkLChRequiredRxBandwidth,
--           mscTrkPaPfcntValue,
--           mscTrkPaNegotiatedTrunkSecurity,
--           mscTrkPaNegotiatedTrunkType,
--           mscTrkLChRequiredTxBandwidth,
--           mscTrkPaPacntValue,
--           mscTrkLChHoldingPriority,
--           mscTrkPaMaxReservedBwOut,
--           mscTrkPaPbcntValue,
--           mscTrkLChNextHop,
--           mscTrkLChMaximumTransmissionUnit }
-- STATUS  mandatory
-- DESCRIPTION
--   "A list of all current accessible leaf objects."

porsTrunksGroup OBJECT IDENTIFIER ::= { porsTrunksMIB 1 }
porsTrunksGroupCA OBJECT IDENTIFIER ::= { porsTrunksGroup 1 }
porsTrunksGroupCA02 OBJECT IDENTIFIER ::= { porsTrunksGroupCA 3 }
porsTrunksGroupCA02A OBJECT IDENTIFIER ::= { porsTrunksGroupCA02 2 }



-- Agent-Capabilities Statement:

-- PRODUCT-RELEASE "MscPassport Release 1.2 PorsTrunks."
-- STATUS          mandatory
-- DESCRIPTION     "Carrier Passport PorsTrunks MIB: MIB Version CA02A,
--                  Software Version CA02S9C."
-- SUPPORTS        Nortel-MsCarrier-MscPassport-PorsTrunksMIB
--    INCLUDES     { porsTrunksGroupCA02A }

porsTrunksCapabilities OBJECT IDENTIFIER ::= { porsTrunksMIB 3 }
porsTrunksCapabilitiesCA OBJECT IDENTIFIER ::= { porsTrunksCapabilities 1 }
porsTrunksCapabilitiesCA02 OBJECT IDENTIFIER ::= { porsTrunksCapabilitiesCA 3 }
porsTrunksCapabilitiesCA02A OBJECT IDENTIFIER ::= { porsTrunksCapabilitiesCA02 2 }





END
