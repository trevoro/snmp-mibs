VPIEVENT-MIB DEFINITIONS ::= BEGIN
 

IMPORTS
	OBJECT-TYPE
		FROM RFC1155-SMI
	TRAP-TYPE
		FROM RFC-1215
	voiceprint,
	software
		FROM VPI-MIB;

--	voiceprint	OBJECT IDENTIFIER ::= { enterprises 15191 }
--	software        OBJECT IDENTIFIER ::= { voiceprint 1 }
	eventcenter	OBJECT IDENTIFIER ::= { software 1 }

-- EventCenter generic fields fields

        applicationId OBJECT-TYPE
                SYNTAX  INTEGER (1..2147483647)
                ACCESS  read-only
                STATUS  mandatory
                DESCRIPTION
                        "This is the Application's Registered ID number."
                ::= { eventcenter 1 }

        applicationName OBJECT-TYPE
                SYNTAX  OCTET STRING
                ACCESS  read-only
                STATUS  mandatory
                DESCRIPTION
                        "This is the Application's Registered Friendly Name."
                ::= { eventcenter 2 }

        processName OBJECT-TYPE
                SYNTAX  OCTET STRING (SIZE(0..25))
                ACCESS  read-only
                STATUS  mandatory
                DESCRIPTION
                        "This is the Application's Registered Friendly Name for a SubProcess."
                ::= { eventcenter 3 }


-- EventCenter Trap Fields

        logEventType OBJECT-TYPE
                SYNTAX  INTEGER
                ACCESS  read-only
                STATUS  mandatory
                DESCRIPTION
                        "This is the Application Specified Event Type for the Notification."
                ::= { eventcenter 4 }

	logEventName OBJECT-TYPE
                SYNTAX  OCTET STRING
                ACCESS  read-only
                STATUS  mandatory
                DESCRIPTION
                        "This is the Application Specified Friendly Name for the Notification."
                ::= { eventcenter 5 }

        logEventMessage OBJECT-TYPE
                SYNTAX  OCTET STRING (SIZE(0..200))
                ACCESS  read-only
                STATUS  mandatory
                DESCRIPTION
                        "This is the Application Specified Message for the Notification."
                ::= { eventcenter 6 }


-- EventCenter Traps

	eventNotif TRAP-TYPE
              ENTERPRISE  voiceprint
              VARIABLES   { applicationId, applicationName, processName, logEventType, logEventName, logEventMessage }
              DESCRIPTION
                          "An Application Triggered Event Notification."
              ::= 0
END
