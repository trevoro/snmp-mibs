-- *****************************************************************
-- tiaranet-bundle.mib:  Tiara Networks Bundle MIB
--
-- July,1st 1999, kumar 
--
-- Copyright (c) 1999-2000 by Tiara Networks, Inc.
-- All rights reserved.
--
-- *****************************************************************

TIARA-BUNDLE-MIB DEFINITIONS ::= BEGIN

IMPORTS
        MODULE-IDENTITY, OBJECT-TYPE, 
        IpAddress, Integer32                FROM SNMPv2-SMI
        TruthValue, RowStatus               FROM SNMPv2-TC
        DisplayString                       FROM RFC1213-MIB
        tiaraMgmt                           FROM TIARA-NETWORKS-SMI;

tiaraBundleMib MODULE-IDENTITY
        LAST-UPDATED    "9907010000Z" 
        ORGANIZATION    "Tiara Networks Inc."
        CONTACT-INFO
                "       Tiara Networks
                        Customer Support

                        525 Race Street, Suite 100,
                        San Jose, CA 95126
                        USA

                        Tel: +1 408-216-4700
                        Fax: +1 408-216-4701

                        E-mail: support@tiaranetworks.com"

        DESCRIPTION     "Bundle MIB for defining bundle parameters"
        REVISION        "9904230000Z"
        DESCRIPTION
                "Initial version of this MIB module."
        ::= { tiaraMgmt 13 } 


-- bundleTable definition
-- The following bundle table lists all parameters associated with a 
-- bundle.  Items such as encapsulation, IP address, and subnet mask
-- need to have proper values for the bundle to function properly.
-- Default values may not work.

bundleTable         OBJECT-TYPE
        SYNTAX          SEQUENCE OF BundleTableEntry
        MAX-ACCESS      not-accessible
        STATUS          current
        DESCRIPTION 
                        "Bundle management related 
                        parameters are defined in this table."
        ::= {tiaraBundleMib 1}

bundleTableEntry    OBJECT-TYPE
        SYNTAX          BundleTableEntry
        MAX-ACCESS      not-accessible
        STATUS          current
        DESCRIPTION     "Bundle parameter entries are listed in this 
                        table."
        INDEX           { bundleId }
        ::= {bundleTable 1}

BundleTableEntry ::= SEQUENCE {
        bundleId                         INTEGER,
        bundleName                       DisplayString,
        bundleContact                    DisplayString,
        bundleDescr                      DisplayString,
        bundleEncapsulation              INTEGER,
        bundleDropEs                     Integer32,
        bundleDropSes                    Integer32,
        bundleDropUas                    Integer32,
        bundleIpAddr                     IpAddress,
        bundleSubnetMask                 IpAddress,
        bundleSrcForwardingAddrPrimary   IpAddress,
        bundleSrcForwardingAddrSecondary IpAddress,
        bundleRestoreMethod              INTEGER,
        bundleLinkRestoralTime           Integer32,
        bundleStatus                     INTEGER,
        bundleLinkRestore                OCTET STRING (SIZE (4)),
        bundleNoOfLinks                  Integer32,
        bundleTotalBw                    Integer32,
        bundleRowStatus                  RowStatus   
        }

bundleId            OBJECT-TYPE
        SYNTAX          INTEGER 
        MAX-ACCESS      not-accessible  
        STATUS          current
        DESCRIPTION     "bundleId is the identifier of a bundle. To 
                        configure a bundle, this parameter must be 
                        used as the index. This is assigned internally 
                        by the Tiara system. Whenever a row creation 
                        needs to occur in the bundleTable, the 
                        bundleId is entered as 65535."
        ::= { bundleTableEntry 1}

bundleName          OBJECT-TYPE
        SYNTAX          DisplayString (SIZE (1..8))
        MAX-ACCESS      read-create
        STATUS          current
        DESCRIPTION     "Name of the bundle. To configure a bundle, 
                        this parameter must be set. That is, a 
                        descriptive name should be given to a bundle. 
                        The maximum length of a bundle name is 8 
                        characters. This parameter is set once during 
                        the creation of a bundle. A bundle can not be 
                        renamed." 
        ::= { bundleTableEntry 2}

bundleContact       OBJECT-TYPE
        SYNTAX          DisplayString (SIZE (1..15))
        MAX-ACCESS      read-create
        STATUS          current
        DESCRIPTION     "Name of the person who can be contacted 
                        for information about the bundle. The maximum 
                        length for this parameter is 15 characters. 
                        This parameter can be set after the bundle 
                        is named and before the links are assigned."
        DEFVAL          { "" }
        ::= { bundleTableEntry 3}

bundleDescr         OBJECT-TYPE
        SYNTAX          DisplayString (SIZE (1..25))
        MAX-ACCESS      read-create
        STATUS          current
        DESCRIPTION     "Brief description of the bundle. The maximum 
                        length of this parameter is 25 characters. 
                        This parameter can be set after the bundle
                        is named and before the links are assigned."
        DEFVAL          { "" }
        ::= { bundleTableEntry 4 }

bundleEncapsulation OBJECT-TYPE
        SYNTAX      INTEGER {
                        noEncap(1),
                        ppp(2),
                        hdlc(3),
                        frameRelay(4)
                    }
        MAX-ACCESS      read-create
        STATUS          current
        DESCRIPTION     "Specifies the type of protocol encapsulation 
                        for the bundle. To configure protocol-specific 
                        parameters for a bundle, the bundle must first 
                        be encapsulated with that protocol. To 
                        unconfigure the encapsulation type, this 
                        variable should be set to noEncap."
        DEFVAL          { noEncap }
        ::= { bundleTableEntry 5 }

bundleDropEs        OBJECT-TYPE
        SYNTAX          Integer32
        UNITS           "seconds"
        MAX-ACCESS      read-create
        STATUS          current
        DESCRIPTION     "The length of time in seconds that the error 
                        condition Errored Seconds exists before a link is 
                        dropped. This parameter can be configured only 
                        for multilink bundles and after the 
                        bundle is encapsulated." 
        DEFVAL          { 0 } 
        ::= { bundleTableEntry 6}

bundleDropSes       OBJECT-TYPE
        SYNTAX          Integer32
        UNITS           "seconds"
        MAX-ACCESS      read-create
        STATUS          current
        DESCRIPTION     "The length of time in seconds that the error
                        condition Severely Errored Seconds exists 
                        before a link is dropped. This parameter can 
                        be configured only for multilink bundles and 
                        after the bundle is encapsulated."
        DEFVAL          { 0 } 
    ::= { bundleTableEntry 7}

bundleDropUas       OBJECT-TYPE
        SYNTAX          Integer32
        UNITS           "seconds"
        MAX-ACCESS      read-create
        STATUS          current
        DESCRIPTION     "The length of time in seconds that the error
                        condition Unavailable Seconds exists before a 
                        link is dropped. This parameter can be 
                        configured only for multilink bundles and 
                        after the bundle is encapsulated."
        DEFVAL          { 0 } 
        ::= { bundleTableEntry 8}

bundleIpAddr        OBJECT-TYPE
        SYNTAX          IpAddress
        MAX-ACCESS      read-create
        STATUS          current
        DESCRIPTION     "The bundle's source IP address. This is one 
                        of the parameters required to set up IP 
                        multiplexing for a bundle. This parameter 
                        can be configured only when the bundle is 
                        encapsulated. Also the parameters bundleIpAddr 
                        and bundleSubnetMask have to be set together 
                        during the same request. To unconfigure the IP 
                        address, a set operation is performed with 
                        the value 0.0.0.0" 
        DEFVAL          { 0 }  
        ::= { bundleTableEntry 9}

bundleSubnetMask    OBJECT-TYPE
        SYNTAX          IpAddress
        MAX-ACCESS      read-create
        STATUS          current
        DESCRIPTION     "This parameter represents the source subnet 
                        mask address. This is one of the parameters 
                        required to set up IP multiplexing for a 
                        bundle. This parameter is set along with the 
                        bundleIpAddr parameter during the same 
                        request." 
        DEFVAL          { 0 }  
        ::= { bundleTableEntry 10}

bundleSrcForwardingAddrPrimary  OBJECT-TYPE
        SYNTAX          IpAddress
        MAX-ACCESS      read-create
        STATUS          current
        DESCRIPTION     "The bundle's destination IP address. This is 
                        one of the parameters required to set up IP 
                        multiplexing for a bundle. This parameter can 
                        be configured when the bundle has been 
                        configured for IP multiplexing. To unconfigure 
                        the source forwarding address, a set operation 
                        is performed with the value 0.0.0.0. This is
                        the primary source forwarding address" 
        DEFVAL          { 0 }  
        ::= { bundleTableEntry 11}

bundleSrcForwardingAddrSecondary OBJECT-TYPE
        SYNTAX          IpAddress
        MAX-ACCESS      read-create
        STATUS          current
        DESCRIPTION     "The bundle's secondary or backup destination 
                        address. This address will be used only if  
                        the primary address uses an ethernet interface
                        and failover is enabled on that interface and
                        the interface goes down. The secondary source
                        forwarding address is an optional parameter, 
                        it should be a gateway on the alternate
                        ethernet This parameter is set along with the
                        primary source forwarding address parameter. 
                        To unconfigure this parameter a set operation 
                        is performed with the value 0.0.0.0 for the
                        primary address, or a primary address is set
                        with no secondary, or both primary and 
                        secondary are set to 0.0.0.0"
        DEFVAL          { 0 }  
        ::= { bundleTableEntry 12}

bundleRestoreMethod OBJECT-TYPE
        SYNTAX      INTEGER {
                        manual(1),
                        automatic(2)}
        MAX-ACCESS      read-write
        STATUS          current
        DESCRIPTION     "bundleRestoreMethod defines how a dropped 
                        link of a multilink bundle will be restored. 
                        It can be done either manually or 
                        automatically. If the restore mode is 
                        automatic, the parameter bundleLinkRestoralTime 
                        should be set (in seconds) during the same 
                        request." 
        DEFVAL          { automatic }
        ::= { bundleTableEntry 13 }

bundleLinkRestoralTime  OBJECT-TYPE
        SYNTAX          Integer32
        UNITS           "seconds"
        MAX-ACCESS      read-create
        STATUS          current
        DESCRIPTION     "Error-free time interval (in seconds) that 
                        must pass before a link is automatically 
                        restored. This parameter can be set when the 
                        bundleRestoreMethod is automatic." 
        DEFVAL          { 120 }
        ::= { bundleTableEntry 14 }

bundleStatus        OBJECT-TYPE
        SYNTAX      INTEGER {
                        enable(1),
                        disable(2)
                    }
        MAX-ACCESS      read-write
        STATUS          current
        DESCRIPTION     "bundleStatus shutdowns the bundle. Although 
                        the default is 'enable,' the bundle remains 
                        disabled until all necessary parameters are 
                        present" 
        DEFVAL          { enable }
        ::= { bundleTableEntry 15 }

bundleLinkRestore   OBJECT-TYPE
        SYNTAX          OCTET STRING (SIZE (4)) 
        MAX-ACCESS      read-write
        STATUS          current
        DESCRIPTION     "bundleLinkRestore specifies the links to be 
                        restored manually. This parameter is configured 
                        when the value of bundleRestoreMethod is manual. 
                        The user needs to specify the link/s to be 
                        restored. LSB in the OCTET STRING represents 
                        T1 Number 1. For example, to restore links 1-4 
                        the value should be set to 000F"
        ::= { bundleTableEntry 16 }

bundleNoOfLinks     OBJECT-TYPE
        SYNTAX          Integer32
        MAX-ACCESS      read-only
        STATUS          current
        DESCRIPTION     "Indicates the number of links configured in 
                        the bundle." 
        ::= { bundleTableEntry 17 }

bundleTotalBw       OBJECT-TYPE
        SYNTAX          Integer32
        UNITS           "kbps"
        MAX-ACCESS      read-only
        STATUS          current
        DESCRIPTION     "Indicates the total bandwidth for this bundle.
                        The bundle bandwidth is the aggregated band-
                        widths of all the links assigned to a 
                        particular bundle." 
    ::= { bundleTableEntry 18 }

bundleRowStatus OBJECT-TYPE
        SYNTAX          RowStatus
        MAX-ACCESS      read-create
        STATUS          current
        DESCRIPTION     "bundleRowStatus is used to add/delete a row 
                        in the table. Adding or deleting a row 
                        corresponds to creating a bundle or deleting
                        a bundle.  In order to add a row to the bundle 
                        table, a set on this parameter should be done 
                        with the value 4 (createAndGo) and 
                        bundleId parameter set with the value of 65535. 
                        A request to create a row can be 
                        completed successfully only if a set on the 
                        bundleRowStatus and a set on the bundleName 
                        come in the same request. To delete a row 
                        this parameter has to be set with the value 6
                        (destroy)." 
        ::= { bundleTableEntry 19}

-- bundleLinkTable definition
bundleLinkTable     OBJECT-TYPE
        SYNTAX          SEQUENCE OF BundleLinkEntry
        MAX-ACCESS      not-accessible
        STATUS          current
        DESCRIPTION     "All the parameters related to the assigned 
                        links of a bundle are defined in 
                        bundleLinkTable. A row in this table can be 
                        created when a bundle with the corresponding 
                        bundleId already exists in the bundleTable."
        ::= { tiaraBundleMib 2 }

bundleLinkEntry     OBJECT-TYPE
        SYNTAX          BundleLinkEntry
        MAX-ACCESS      not-accessible
        STATUS          current
        DESCRIPTION     "Link parameters that relate to a 
                        given bundle are specified in this table."
        INDEX           { bundleId , bundleLinkT1Num }
        ::= { bundleLinkTable 1 }

BundleLinkEntry ::= SEQUENCE {
        bundleLinkT1Num         Integer32,  
        bundleLinkTimeSlots     OCTET STRING (SIZE (4)),
        bundleLinkType          INTEGER,
        bundleLinkSpeed         INTEGER,
        bundleLinkInvertedData  TruthValue,
        bundleLinkPhysIfNum    INTEGER,
        bundleLinkDiffDelay     Integer32,
        bundleLinkBw            Integer32,
        bundleLinkStatus        INTEGER,
        bundleLinkRowStatus     RowStatus
        }

bundleLinkT1Num     OBJECT-TYPE
        SYNTAX          Integer32 
        MAX-ACCESS      not-accessible
        STATUS          current
        DESCRIPTION     "bundleLinkT1Num is the number of the T1 link 
                        being added to a specific bundle. For example, 
                        to assign link number 4, the value of this 
                        parameter should be set to 4. However, the 
                        design of SNMP's link creation is different 
                        from that of the system CLI. In SNMP, only 
                        one link can be created at a time whereas in 
                        the system CLI, multiple links can be 
                        configured in a single request. This parameter 
                        is mandatory for row creation in the interfaces 
                        with CT3 and T1 link types ."      
       ::= { bundleLinkEntry 1 }

bundleLinkTimeSlots OBJECT-TYPE
        SYNTAX          OCTET STRING (SIZE (4)) 
        MAX-ACCESS      read-create 
        STATUS          current
        DESCRIPTION     "bundleLinkTimeSlots indicates the DS0 channels 
                        in a fractional T1 link. The LSB in the OCTET 
                        STRING represents DS0 channel number 1. For 
                        example, to assign DS0 channels 1-4, the value 
                        of this parameter should be set to 000F"
        DEFVAL          { "00ffffff" }
        ::= { bundleLinkEntry 2 }


bundleLinkType      OBJECT-TYPE
        SYNTAX          INTEGER {
                            ct3(1),
                            t1(2),
                            e1(3),
                            hssi(4),
                            t3(5)
                        }
        MAX-ACCESS      read-create
        STATUS          current
        DESCRIPTION     "bundleLinkType specifies the interface type 
                        (i.e., CT3, T1, T3, and HSSI) of the link 
                        being assigned to the bundle. This is a 
                        mandatory parameter for Row creation in the 
                        bundleLinkTable." 
        ::= { bundleLinkEntry 3 }

bundleLinkSpeed     OBJECT-TYPE
        SYNTAX          INTEGER {
                            kbps56(1),
                            kbps64(2)
                        }
        MAX-ACCESS      read-create
        STATUS          current
        DESCRIPTION     "The bundleLinkSpeed specifies the transmission 
                        speed of all DS0 channels in a bundle." 
        DEFVAL          { 2 }
        ::= { bundleLinkEntry 4 }

bundleLinkInvertedData  OBJECT-TYPE
        SYNTAX          TruthValue
        MAX-ACCESS      read-create
        STATUS          current
        DESCRIPTION     "Setting bundleLinkInvertedData parameter to 
                        true will have the system invert data on all 
                        DS0 channels before transmission. Data 
                        inversion is used only for HDLC-encapsulated 
                        bundles." 
        DEFVAL          { false }
        ::= { bundleLinkEntry 5 }

bundleLinkPhysIfNum OBJECT-TYPE
        SYNTAX          INTEGER
        MAX-ACCESS      read-create
        STATUS          current
        DESCRIPTION     "bundleLinkPhysIfNum specifies the interface
                        number of the interface type such as CT3, 
                        HSSI, T3 on which this link is being created. 
                        This variable holds significance only for 
                        link types CT3, HSSI and T3. It is a 
                        mandatory variable for row creation for link 
                        types CT3, HSSI, and T3."
        DEFVAL          { 0 }
        ::= { bundleLinkEntry 6 }
    
bundleLinkDiffDelay OBJECT-TYPE
        SYNTAX          Integer32
        UNITS           "milli-seconds"
        MAX-ACCESS      read-only
        STATUS          current
        DESCRIPTION     "bundleLinkDiffDelay specifies the maximum 
                        differential delay allowed on the links in a 
                        multilink bundle.  If the packet delay on any 
                        link exceeds the differential delay set for a 
                        bundle, that link is dropped from the bundle." 
        ::= { bundleLinkEntry 7}

bundleLinkBw        OBJECT-TYPE
        SYNTAX          Integer32
        UNITS           "kbps"
        MAX-ACCESS      read-only
        STATUS          current
        DESCRIPTION     "bundleLinkBw indicates the bandwidth of the 
                        link.  The bandwidth of an individual link 
                        depends upon its configuration.  For example, 
                        in a link of type T1, its bandwidth will 
                        depend upon whether the link is a full T1 or 
                        a fractional T1 consisting of 24 DS0 timeslots."
        ::= { bundleLinkEntry 8}

bundleLinkStatus    OBJECT-TYPE
        SYNTAX          INTEGER {
                            up(1),
                            down(2)
                        }   
        MAX-ACCESS      read-only
        STATUS          current
        DESCRIPTION     "bundleLinkStatus indicates whether a 
                        particular link in a bundle is up or down.  
                        The link can go down due to various reasons 
                        such as differential delay, a broken link, 
                        or negotiation problems at the far end."
        ::= { bundleLinkEntry 9}

bundleLinkRowStatus OBJECT-TYPE
        SYNTAX          RowStatus
        MAX-ACCESS      read-create
        STATUS          current
        DESCRIPTION     "bundleLinkRowStatus is used to add or delete 
                        a row in the table. To create a row, this 
                        parameter is set to value 4(createAndGo). To 
                        delete a row, this parameter is set to a value 
                        6(destroy)." 
        ::= { bundleLinkEntry 10}

END
