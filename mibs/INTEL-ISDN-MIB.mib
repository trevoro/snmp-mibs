INTEL-ISDN-MIB DEFINITIONS ::= BEGIN

-- Copyright (C) 1997 Intel Corporation. All rights reserved.
--
-- Intel Private ISDN MIB, 06-06-1997
--
-- This MIB provides objects for ISDN
--
-- Change History:
-- <date> <change>
--

IMPORTS
	Counter FROM RFC1155-SMI
    mib2ext                    FROM INTEL-GEN-MIB
    OBJECT-TYPE                FROM RFC-1212;

isdn             OBJECT IDENTIFIER ::= { mib2ext 29 }
isdnSigChan      OBJECT IDENTIFIER ::= { isdn 1 }
isdnDchan        OBJECT IDENTIFIER ::= { isdn 2 }
isdnPhys         OBJECT IDENTIFIER ::= { isdn 3 }
isdnCallCtrl     OBJECT IDENTIFIER ::= { isdn 4 }

isdnSigChanTable OBJECT-TYPE
    SYNTAX SEQUENCE OF IsdnSigChanEntry
    ACCESS not-accessible
    STATUS mandatory
    DESCRIPTION "Table containing configuration and operational parameters
                 for all ISDN Signalling Channels on this managed device."
    ::= { isdnSigChan 1 }

isdnSigChanEntry OBJECT-TYPE
    SYNTAX IsdnSigChanEntry
    ACCESS not-accessible
    STATUS mandatory
    DESCRIPTION "An entry in the ISDN Signalling Channel Table."
    INDEX { isdnSigChanIfIndex }
    ::= { isdnSigChanTable 1 }

IsdnSigChanEntry ::= SEQUENCE {
                        isdnSigChanIfIndex
                           INTEGER,
                        isdnSigChanL2State
                           Counter,
                        isdnSigChanCES
                           Counter,
                        isdnSigChanSAPI
                           Counter,
                        isdnSigChanCallCollisions
                           Counter,
                        isdnSigChanAddressCheckFails
                           Counter
                        }

isdnSigChanIfIndex OBJECT-TYPE
    SYNTAX INTEGER
    ACCESS read-only
    STATUS mandatory
    DESCRIPTION "Interface index for this signalling channel."
    ::= { isdnSigChanEntry 1 }

isdnSigChanL2State OBJECT-TYPE
    SYNTAX INTEGER {
       teiUnassigned(1),
       assignAwaitTei(2),
       establishAwaitTei(3),
       teiAssigned(4),
       awaitEstablishment(5),
       awaitRelease(6),
       multipleFrameEstablished(7),
       timerRecovery(8)
    }
    ACCESS read-only
    STATUS mandatory
    DESCRIPTION "Signalling layer-2 state (Q.921)."
    ::= { isdnSigChanEntry 2 }

isdnSigChanCES OBJECT-TYPE
    SYNTAX Counter
    ACCESS read-only
    STATUS mandatory
    DESCRIPTION "Connection Endpoint Suffix (CES) for this signalling channel."
    ::= { isdnSigChanEntry 3 }

isdnSigChanSAPI OBJECT-TYPE
    SYNTAX Counter
    ACCESS read-only
    STATUS mandatory
    DESCRIPTION "Service Access Point Identifier (SAPI) for this
                 signalling channel"
    ::= { isdnSigChanEntry 4 }

isdnSigChanCallCollisions OBJECT-TYPE
    SYNTAX Counter
    ACCESS read-only
    STATUS mandatory
    DESCRIPTION
            "The number of calls over this signalling channel which failed
             because of collision."
    ::= { isdnSigChanEntry 5 }

isdnSigChanAddressCheckFails OBJECT-TYPE
    SYNTAX Counter
    ACCESS read-only
    STATUS mandatory
    DESCRIPTION
            "The number of incoming calls over this signalling channel
             which were refused because of address mismatch."
    ::= { isdnSigChanEntry 6 }

isdnDchanTable OBJECT-TYPE
    SYNTAX SEQUENCE OF IsdnDchanEntry
    ACCESS not-accessible
    STATUS mandatory
    DESCRIPTION "Table containing statistics for all ISDN D-Channels on
                 this managed device."
    ::= { isdnDchan 1 }

isdnDchanEntry OBJECT-TYPE
    SYNTAX IsdnDchanEntry
    ACCESS not-accessible
    STATUS mandatory
    DESCRIPTION "An entry in the ISDN D-Channel Table."
    INDEX { isdnDchanIfIndex }
    ::= { isdnDchanTable 1 }

IsdnDchanEntry ::= SEQUENCE {
                        isdnDchanIfIndex
                           INTEGER,
                        isdnDchanRxShort
                           Counter,
                        isdnDchanRxLong
                           Counter,
                        isdnDchanRxCRCerror
                           Counter,
                        isdnDchanRxResidual
                           Counter,
                        isdnDchanRxAborts
                           Counter,
                        isdnDchanRxOverrun
                           Counter,
                        isdnDchanRxLostSync
                           Counter,
                        isdnDchanRxBufferLack
                           Counter,
                        isdnDchanRxApplnotready
                           Counter,
                        isdnDchanRxUnknownProto
                           Counter,
                        isdnDchanTxDiscardedProto
                           Counter,
                        isdnDchanTxDiscardedData
                           Counter,
                        isdnDchanTxUnderrun
                           Counter,
                        isdnDchanTxCollision
                           Counter
                        }

isdnDchanIfIndex OBJECT-TYPE
    SYNTAX INTEGER
    ACCESS read-only
    STATUS mandatory
    DESCRIPTION "The Ifindex of this D-channel."
    ::= { isdnDchanEntry 1 }

isdnDchanRxShort OBJECT-TYPE
    SYNTAX Counter
    ACCESS read-only
    STATUS mandatory
    DESCRIPTION
        "The number of frames received which were discarded
         due to the frame length being too short."
    ::= { isdnDchanEntry 2 }

isdnDchanRxLong OBJECT-TYPE
    SYNTAX Counter
    ACCESS read-only
    STATUS mandatory
    DESCRIPTION
        "The number of frames received which were discarded
         due to the frame length being too long."
    ::= { isdnDchanEntry 3 }

isdnDchanRxCRCerror OBJECT-TYPE
    SYNTAX Counter
    ACCESS read-only
    STATUS mandatory
    DESCRIPTION
        "The number of frames received which were discarded
         due to Cyclic Redundancy Check (CRC) errors. This
         figure indicates the number of bit errors occuring
         over the WAN link."
    ::= { isdnDchanEntry 4 }

isdnDchanRxResidual OBJECT-TYPE
    SYNTAX Counter
    ACCESS read-only
    STATUS mandatory
    DESCRIPTION
        "The number of times the frame contained residual
         bits. This should not occur."
    ::= { isdnDchanEntry 5 }

isdnDchanRxAborts OBJECT-TYPE
    SYNTAX Counter
    ACCESS read-only
    STATUS mandatory
    DESCRIPTION
        "The number of times the High-Level Data Link Control
         (HDLC) 'Abort' signal was received, indicating that
         the received packet should be ignored."
    ::= { isdnDchanEntry 6 }

isdnDchanRxOverrun OBJECT-TYPE
    SYNTAX Counter
    ACCESS read-only
    STATUS mandatory
    DESCRIPTION
        "The number of frames which were lost due to bus
         overload within the router. This should not occur."
    ::= { isdnDchanEntry 7 }

isdnDchanRxLostSync OBJECT-TYPE
    SYNTAX Counter
    ACCESS read-only
    STATUS mandatory
    DESCRIPTION
        "The number of frames which were lost due to drop
         of signal on the line."
    ::= { isdnDchanEntry 8 }

isdnDchanRxBufferLack OBJECT-TYPE
    SYNTAX Counter
    ACCESS read-only
    STATUS mandatory
    DESCRIPTION
        "The number of received frames which were lost due to
         RAM (buffer) overload within the router."
    ::= { isdnDchanEntry 9 }

isdnDchanRxApplnotready OBJECT-TYPE
    SYNTAX Counter
    ACCESS read-only
    STATUS mandatory
    DESCRIPTION
        "The number of received frames which were discarded since
         there was a temporary situation with no upper layer
         to receive the frame."
    ::= { isdnDchanEntry 10 }

isdnDchanRxUnknownProto OBJECT-TYPE
    SYNTAX Counter
    ACCESS read-only
    STATUS mandatory
    DESCRIPTION "The number of incoming frames which were discarded
                 due to unknown protocol field."
    ::= { isdnDchanEntry 11 }

isdnDchanTxDiscardedProto OBJECT-TYPE
    SYNTAX Counter
    ACCESS read-only
    STATUS mandatory
    DESCRIPTION
        "The number of protocol frames for transmission which were
          lost due to RAM (buffer) overload within the router."
    ::= { isdnDchanEntry 12 }

isdnDchanTxDiscardedData OBJECT-TYPE
    SYNTAX Counter
    ACCESS read-only
    STATUS mandatory
    DESCRIPTION
        "The number of data frames for transmission which were
         lost due to RAM (buffer) overload within the router."
    ::= { isdnDchanEntry 13 }

isdnDchanTxUnderrun OBJECT-TYPE
    SYNTAX Counter
    ACCESS read-only
    STATUS mandatory
    DESCRIPTION
        "The number of frames for transmission that were not
         successfully transmitted due to CPU (processor)
         overload within the router."
    ::= { isdnDchanEntry 14 }

isdnDchanTxCollision OBJECT-TYPE
    SYNTAX Counter
    ACCESS read-only
    STATUS mandatory
    DESCRIPTION "The number of outgoing frames which were discarded
                 due to collisions that occured during transmission."
    ::= { isdnDchanEntry 15 }

isdnPhysTable OBJECT-TYPE
    SYNTAX SEQUENCE OF IsdnPhysEntry
    ACCESS not-accessible
    STATUS mandatory
    DESCRIPTION "Table containing physical layer status for all
                 ISDN ports on this managed device."
    ::= { isdnPhys 1 }

isdnPhysEntry OBJECT-TYPE
    SYNTAX IsdnPhysEntry
    ACCESS not-accessible
    STATUS mandatory
    DESCRIPTION "An entry in the ISDN physical layer Table."
    INDEX { isdnPhysIfIndex }
    ::= { isdnPhysTable 1 }

IsdnPhysEntry ::= SEQUENCE {
                        isdnPhysIfIndex
                           INTEGER,
                        isdnPhysL1State
                           Counter,
                        isdnPhysL1Alarm
                           Counter
                        }

isdnPhysIfIndex OBJECT-TYPE
    SYNTAX INTEGER
    ACCESS read-only
    STATUS mandatory
    DESCRIPTION "IfIndex for this ISDN port."
    ::= { isdnPhysEntry 1 }

isdnPhysL1State OBJECT-TYPE
    SYNTAX INTEGER {
       inactive(1),
       sensing(2),
       deactivated(3),
       awaitingSignal(4),
       identifyingInput(5),
       synchronized(6),
       activated(7),
       lostFraming(8),
       lossOfPower(100),
       operational(101),
       fault1(102),
       fault2(103),
       fault3(104),
       fault4(105),
       powerOn(106),
       incomingCall(107),
       testing(108)
    }
    ACCESS read-only
    STATUS mandatory
    DESCRIPTION "Physical layer state for this ISDN port."
    ::= { isdnPhysEntry 2 }

isdnPhysL1Alarm OBJECT-TYPE
    SYNTAX INTEGER {
       noCableInserted(1),
       lossOfSignal(2),
       txCableNotConnected(3),
       alarmIndicationSignal(4),
       remoteAlarmIndication(5),
       noMultiFrameAlignment(6),
       noBasicFrameAlignment(7),
       noSyncPattern(8),
       ncrc4(9),
       crce0(10),
       crce1(11),
       ebit0(12),
       ebit1(13)
    }
    ACCESS read-only
    STATUS mandatory
    DESCRIPTION "Primary Rate Interface alarm for this ISDN port.
                 This entry is unused for BRI. 0 means noDetectedProblem"
    ::= { isdnPhysEntry 3 }

isdnCallCtrlTable OBJECT-TYPE
    SYNTAX SEQUENCE OF IsdnCallCtrlEntry
    ACCESS not-accessible
    STATUS mandatory
    DESCRIPTION "Table containing configuration and operational parameters
                 for all ISDN links on this managed device."
    ::= { isdnCallCtrl 1 }

isdnCallCtrlEntry OBJECT-TYPE
    SYNTAX IsdnCallCtrlEntry
    ACCESS not-accessible
    STATUS mandatory
    DESCRIPTION "An entry in the ISDN link Table."
    INDEX { isdnCallCtrlSigchanIfIndex }
    ::= { isdnCallCtrlTable 1 }

IsdnCallCtrlEntry ::= SEQUENCE {
                        isdnCallCtrlSigchanIfIndex
                           INTEGER,
                        isdnCallCtrlBchanIfIndex
                           INTEGER,
                        isdnCallCtrlLocalNumber
                           OCTET STRING,
                        isdnCallCtrlLocalSubaddr
                           OCTET STRING,
                        isdnCallCtrlRemoteNumber
                           OCTET STRING,
                        isdnCallCtrlRemoteSubaddr
                           OCTET STRING,
                        isdnCallCtrlL3State
                           INTEGER,
                        isdnCallCtrlCallRef
                           INTEGER,
                        isdnCallCtrlChannelNum
                           INTEGER,
                        isdnCallCtrlOutCallsConnected
                           Counter,
                        isdnCallCtrlOutCallsFailed
                           Counter,
                        isdnCallCtrlInCallsConnected
                           Counter,
                        isdnCallCtrlInCallsRefused
                           Counter,
                        isdnCallCtrlCallCollisions
                           Counter,
                        isdnCallCtrlCauseCode
                           INTEGER,
                        isdnCallCtrlLocationCode
                           INTEGER,
                        isdnCallCtrlCauseText
                           OCTET STRING
                        }

isdnCallCtrlSigchanIfIndex OBJECT-TYPE
    SYNTAX INTEGER
    ACCESS read-only
    STATUS mandatory
    DESCRIPTION "Interface index for the current signalling-channel
                 associated with this link. The index is zero if no
                 signalling-channel is associated."
    ::= { isdnCallCtrlEntry 1 }

isdnCallCtrlBchanIfIndex OBJECT-TYPE
    SYNTAX INTEGER
    ACCESS read-only
    STATUS mandatory
    DESCRIPTION "Interface index for the current B-channel
                 associated with this link. The index is
                 zero if no B-channel is allocated."
    ::= { isdnCallCtrlEntry 2 }

isdnCallCtrlLocalNumber OBJECT-TYPE
    SYNTAX OCTET STRING (SIZE(22))
    ACCESS read-only
    STATUS mandatory
    DESCRIPTION "The local ISDN number for this link."
    ::= { isdnCallCtrlEntry 3 }

isdnCallCtrlLocalSubaddr OBJECT-TYPE
    SYNTAX OCTET STRING (SIZE(14))
    ACCESS read-only
    STATUS mandatory
    DESCRIPTION "The local ISDN subaddress for this link."
    ::= { isdnCallCtrlEntry 4 }

isdnCallCtrlRemoteNumber OBJECT-TYPE
    SYNTAX OCTET STRING (SIZE(22))
    ACCESS read-only
    STATUS mandatory
    DESCRIPTION
            "The ISDN number the current or last call is or was
             connected to."
    ::= { isdnCallCtrlEntry 5 }

isdnCallCtrlRemoteSubaddr OBJECT-TYPE
    SYNTAX OCTET STRING (SIZE(14))
    ACCESS read-only
    STATUS mandatory
    DESCRIPTION
            "The ISDN subaddress the current or last call is or was
             connected to."
    ::= { isdnCallCtrlEntry 6 }

isdnCallCtrlL3State OBJECT-TYPE
    SYNTAX INTEGER {
       callInit(1),
       overlapSending(2),
       outCallProc(3),
       callDelivered(4),
       undef5(5),
       callPresent(6),
       callReceived(7),
       connectRequest(8),
       inCallProc(9),
       callActive(10),
       disconnectRequest(11),
       disconnectInd(12),
       passiveAwaitingConf(13),
       callPassive(14),
       suspendRequest(15),
       undef16(16),
       resumeRequest(17),
       undef18(18),
       releaseRequest(19),
       registerRequest(20),
       cancelRequest(21),
       undef22(22),
       undef23(23),
       undef24(24),
       overlapReceive(25),
       idleState(26),
       establishWait(27),
       asaiTr1State(28),
       u10HoldRequest(29),
       u10TransferRequest(30),
       u10ConferenceRequest(31),
       u10ReconnectRequest(32),
       u10AwaitingDisc(33),
       u10CallOnHold(34),
       deactivated(35),
       reactivateRequested(36),
       deactivateRequested(37),
       ni1HoldReqU3(38),
       ni1HoldReqU4(39),
       ni1HoldReqU10(40),
       ni1RetrieveU3(41),
       ni1RetrieveU4(42),
       ni1RetrieveU10(43),
       ni1HoldActiveU3(44),
       ni1HoldActiveU4(45),
       ni1HoldActiveU10(46),
       broadcastState(47)
    }
    ACCESS read-only
    STATUS mandatory
    DESCRIPTION "Signalling layer-3 state (Q.931 and custom).
                 0 means nullState."
    ::= { isdnCallCtrlEntry 7 }

isdnCallCtrlCallRef OBJECT-TYPE
    SYNTAX INTEGER
    ACCESS read-only
    STATUS mandatory
    DESCRIPTION "Signalling layer-3 call reference (Q.931)."
    ::= { isdnCallCtrlEntry 8 }

isdnCallCtrlChannelNum OBJECT-TYPE
    SYNTAX INTEGER
    ACCESS read-only
    STATUS mandatory
    DESCRIPTION "The current B-channel number associated with this link."
    ::= { isdnCallCtrlEntry 9 }

isdnCallCtrlOutCallsConnected OBJECT-TYPE
    SYNTAX Counter
    ACCESS read-only
    STATUS mandatory
    DESCRIPTION
            "The number of outgoing calls on this link which were
             actually connected."
    ::= { isdnCallCtrlEntry 10 }

isdnCallCtrlOutCallsFailed OBJECT-TYPE
    SYNTAX Counter
    ACCESS read-only
    STATUS mandatory
    DESCRIPTION
            "The number of outgoing calls on this link
             which failed."
    ::= { isdnCallCtrlEntry 11 }

isdnCallCtrlInCallsConnected OBJECT-TYPE
    SYNTAX Counter
    ACCESS read-only
    STATUS mandatory
    DESCRIPTION
            "The number of incoming calls on this link
             which were actually connected."
    ::= { isdnCallCtrlEntry 12 }

isdnCallCtrlInCallsRefused OBJECT-TYPE
    SYNTAX Counter
    ACCESS read-only
    STATUS mandatory
    DESCRIPTION
            "The number of incoming calls on this link
             which were refused."
    ::= { isdnCallCtrlEntry 13 }

isdnCallCtrlCallCollisions OBJECT-TYPE
    SYNTAX Counter
    ACCESS read-only
    STATUS mandatory
    DESCRIPTION
            "The number of calls on this link which failed
             because of collision."
    ::= { isdnCallCtrlEntry 14 }

isdnCallCtrlCauseCode OBJECT-TYPE
    SYNTAX INTEGER
    ACCESS read-only
    STATUS mandatory
    DESCRIPTION
            "The encoded network cause value associated with the last
             call.
             This object will be updated whenever a call is started
             or cleared.
             The value of this object will depend on the interface type
             as well as on the protocol and protocol version being
             used on this interface. Some references for possible cause
             values are given below."
    REFERENCE
            "- Bellcore SR-NWT-001953, Generic Guidelines for
               ISDN Terminal Equipment On Basic Access Interfaces,
               chapter 5.2.5.8.
             - Bellcore SR-NWT-002343, ISDN Primary Rate Interface
               Generic Guidelines for Customer Premises Equipment,
               chapter 8.2.5.8.
             - ITU-T Q.931, Appendix I.
             - ITU-T X.25, CAUSE and DIAGNOSTIC field values.
             - German Telekom FTZ 1TR6, chapter 3.2.3.4.4.4."
    ::= { isdnCallCtrlEntry 15 }

isdnCallCtrlLocationCode OBJECT-TYPE
    SYNTAX INTEGER
    ACCESS read-only
    STATUS mandatory
    DESCRIPTION
            "The encoded network cause location value associated with
             the last call.
             This object will be updated whenever a call is started
             or cleared."
    ::= { isdnCallCtrlEntry 16 }

isdnCallCtrlCauseText OBJECT-TYPE
    SYNTAX OCTET STRING (SIZE(100))
    ACCESS read-only
    STATUS mandatory
    DESCRIPTION
            "ASCII text describing the reason for the last call
             termination.
             This object will be updated whenever a call is started
             or cleared."
    ::= { isdnCallCtrlEntry 17 }

END
