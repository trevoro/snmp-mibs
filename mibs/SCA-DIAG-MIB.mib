SCA-DIAG-MIB DEFINITIONS ::= BEGIN

-- Copyright (C) 1997 Intel Corporation. All rights reserved.
--
-- ScaNet Private Diagnostics MIB, 05-03-1997
--
-- This MIB provides objects for Diagnostics.
--
-- Change History:
-- <date> <change>
--

IMPORTS
    TimeTicks                  FROM RFC1155-SMI
    scanet                     FROM SCANET-MIB
    OBJECT-TYPE                FROM RFC-1212;


  diag        OBJECT IDENTIFIER ::= { scanet 47 }
  diagList    OBJECT IDENTIFIER ::= { diag 1 }
  diagTest    OBJECT IDENTIFIER ::= { diag 2 }


-- List group

diagListNumberOfEntries OBJECT-TYPE
    SYNTAX INTEGER
    ACCESS read-write
    STATUS mandatory
    DESCRIPTION "Number of entries in Diagnostics Table
                 (Set value to 0 to delete all entries)"
    ::= { diagList 1 }

diagListNumberOfErrorEntries OBJECT-TYPE
    SYNTAX INTEGER
    ACCESS read-only
    STATUS mandatory
    DESCRIPTION "Number of errors in Diagnostics Table"
    ::= { diagList 2 }

diagListLastUpdateTime OBJECT-TYPE
    SYNTAX TimeTicks
    ACCESS read-only
    STATUS mandatory
    DESCRIPTION "Time of last change in Diagnostics Table in timeticks since boot"
    ::= { diagList 3 }


diagListTable OBJECT-TYPE
    SYNTAX SEQUENCE OF DiagListEntry
    ACCESS not-accessible
    STATUS mandatory
    DESCRIPTION "Diagnostics Table"
    ::= { diagList 4 }

diagListEntry OBJECT-TYPE
    SYNTAX DiagListEntry
    ACCESS not-accessible
    STATUS mandatory
    DESCRIPTION ""
    INDEX { diagListIndex }
    ::= { diagListTable 1 }

DiagListEntry ::= SEQUENCE {
                        diagListIndex
                           INTEGER,
                        diagListLevel
                           INTEGER,
                        diagListCode
                           INTEGER,
                        diagListIfindex
                           INTEGER,
                        diagListTimeStamp
                           TimeTicks,
                        diagListDescription
                           OCTET STRING,
                        diagListAdvice
                           OCTET STRING
                        }

diagListIndex OBJECT-TYPE
    SYNTAX INTEGER
    ACCESS read-only
    STATUS mandatory
    DESCRIPTION "Position in table."
    ::= { diagListEntry 1 }

diagListLevel OBJECT-TYPE
    SYNTAX INTEGER {
                warning(32),
                error(64),
                fatalError(96)
        }
    ACCESS read-only
    STATUS mandatory
    DESCRIPTION "Error level."
    ::= { diagListEntry 2 }

diagListCode OBJECT-TYPE
    SYNTAX INTEGER
    ACCESS read-only
    STATUS mandatory
    DESCRIPTION "Number that uniquely identifies a specific situation.
                 Set code to zero to delete the entry."
    ::= { diagListEntry 3 }

diagListIfindex OBJECT-TYPE
    SYNTAX INTEGER
    ACCESS read-only
    STATUS mandatory
    DESCRIPTION "Interface index."
    ::= { diagListEntry 4 }

diagListTimeStamp OBJECT-TYPE
    SYNTAX TimeTicks
    ACCESS read-only
    STATUS mandatory
    DESCRIPTION "Time of (re)insertion in timeticks since boot."
    ::= { diagListEntry 5 }

diagListDescription OBJECT-TYPE
    SYNTAX OCTET STRING (SIZE(160))
    ACCESS read-only
    STATUS mandatory
    DESCRIPTION "Description of the problem."
    ::= { diagListEntry 6 }

diagListAdvice OBJECT-TYPE
    SYNTAX OCTET STRING (SIZE(160))
    ACCESS read-only
    STATUS mandatory
    DESCRIPTION "Advice"
    ::= { diagListEntry 7 }




-- Test Group

diagTestTable OBJECT-TYPE
    SYNTAX SEQUENCE OF DiagTestEntry
    ACCESS not-accessible
    STATUS mandatory
    DESCRIPTION ""
    ::= { diagTest 1 }

diagTestEntry OBJECT-TYPE
    SYNTAX DiagTestEntry
    ACCESS not-accessible
    STATUS mandatory
    DESCRIPTION ""
    INDEX { diagTestType }
    ::= { diagTestTable 1 }

DiagTestEntry ::= SEQUENCE {
                        diagTestType
                           INTEGER,
                        diagTestDescription
                           OCTET STRING,
                        diagTestStatus
                           INTEGER
                        }

diagTestType OBJECT-TYPE
    SYNTAX INTEGER
    ACCESS read-only
    STATUS mandatory
    DESCRIPTION "Test type"
    ::= { diagTestEntry 1 }


diagTestDescription OBJECT-TYPE
    SYNTAX OCTET STRING (SIZE(40))
    ACCESS read-only
    STATUS mandatory
    DESCRIPTION "Test description"
    ::= { diagTestEntry 2 }


diagTestStatus OBJECT-TYPE
    SYNTAX INTEGER {
                ready(1),
                test(2),
                testing(3)
        }
    ACCESS read-write
    STATUS mandatory
    DESCRIPTION "Test status. Begin a test by setting the value to
    test(2) and then wait for it to go from testing(3) to ready(1)."
    ::= { diagTestEntry 3 }






END
