--
-- This SMIv2 module has been generated by smidump 0.2-cvs. Do not edit.
--

SONUS-DS3-MIB DEFINITIONS ::= BEGIN

IMPORTS
    Integer32, MODULE-IDENTITY, NOTIFICATION-TYPE, OBJECT-TYPE
        FROM SNMPv2-SMI
    DisplayString, RowStatus
        FROM SNMPv2-TC
    sonusDs3Index, sonusEventClass, sonusEventDescription, 
    sonusEventLevel, sonusPortIndex, sonusShelfIndex, sonusSlotIndex
        FROM SONUS-COMMON-MIB
    sonusCircuitMIBs
        FROM SONUS-SMI
    SonusAdminAction, SonusAdminState, SonusName, SonusServiceState
        FROM SONUS-TC;

sonusDsx3MIB MODULE-IDENTITY
    LAST-UPDATED    "200102030000Z"
    ORGANIZATION    
            "Sonus Networks, Inc."
    CONTACT-INFO    
            "   Customer Support    
             Sonus Networks, Inc,
             5 Carlisle Road
             Westford, MA 01886
             USA
             
             Tel: 978-692-8999
             Fax: 978-392-9118
             E-mail: cs.snmp@sonusnet.com"
    DESCRIPTION     
            "The MIB Module DS3 management."
    ::= { sonusCircuitMIBs 2 }


sonusDsx3MIBObjects OBJECT IDENTIFIER
    ::= { sonusDsx3MIB 1 }

sonusDsx3Admn OBJECT IDENTIFIER
    ::= { sonusDsx3MIBObjects 1 }

sonusDsx3AdmnNextIndex OBJECT IDENTIFIER
    ::= { sonusDsx3Admn 1 }

sonusDsx3AdmnTable OBJECT-TYPE
    SYNTAX          SEQUENCE OF SonusDsx3AdmnEntry
    MAX-ACCESS      not-accessible
    STATUS          current
    DESCRIPTION     
            "Table of Sonus Enterprise Configurations for all DS3s"
    ::= { sonusDsx3Admn 2 }

sonusDsx3AdmnEntry OBJECT-TYPE
    SYNTAX          SonusDsx3AdmnEntry
    MAX-ACCESS      not-accessible
    STATUS          current
    DESCRIPTION     
            "Entry in Table consisting of the all the Sonus Enterprise DS3 Configurations"
    INDEX           { sonusDsx3AdmnShelfIndex, sonusDsx3AdmnSlotIndex, 
                      sonusDsx3AdmnPortIndex, sonusDsx3AdmnDs3Index }
    ::= { sonusDsx3AdmnTable 1 }

SonusDsx3AdmnEntry ::=
    SEQUENCE {
        sonusDsx3AdmnRowStatus          RowStatus,
        sonusDsx3AdmnName               SonusName,
        sonusDsx3AdmnShelfIndex         Integer32,
        sonusDsx3AdmnSlotIndex          Integer32,
        sonusDsx3AdmnPortIndex          Integer32,
        sonusDsx3AdmnDs3Index           Integer32,
        sonusDsx3AdmnIfIndex            Integer32,
        sonusDsx3AdmnState              SonusAdminState,
        sonusDsx3AdmnTimeout            Integer32,
        sonusDsx3AdmnMode               SonusServiceState,
        sonusDsx3AdmnAction             SonusAdminAction,
        sonusDsx3AdmnAvailDs1s          BITS,
        sonusDsx3AdmnDs1ModeOverride    SonusAdminState,
        sonusDsx3AdmnInitCounters       SonusAdminState,
        sonusDsx3AdmnCircuitId          DisplayString
    }

sonusDsx3AdmnRowStatus OBJECT-TYPE
    SYNTAX          RowStatus
    MAX-ACCESS      read-write
    STATUS          current
    DESCRIPTION     
            "DS3, Needed for SNMP"
    ::= { sonusDsx3AdmnEntry 1 }

sonusDsx3AdmnName OBJECT-TYPE
    SYNTAX          SonusName
    MAX-ACCESS      read-write
    STATUS          current
    DESCRIPTION     
            "Name of this DS3"
    ::= { sonusDsx3AdmnEntry 2 }

sonusDsx3AdmnShelfIndex OBJECT-TYPE
    SYNTAX          Integer32
    MAX-ACCESS      read-only
    STATUS          current
    DESCRIPTION     
            "Shelf index for this table"
    ::= { sonusDsx3AdmnEntry 3 }

sonusDsx3AdmnSlotIndex OBJECT-TYPE
    SYNTAX          Integer32
    MAX-ACCESS      read-only
    STATUS          current
    DESCRIPTION     
            "Slot index for this table"
    ::= { sonusDsx3AdmnEntry 4 }

sonusDsx3AdmnPortIndex OBJECT-TYPE
    SYNTAX          Integer32
    MAX-ACCESS      read-only
    STATUS          current
    DESCRIPTION     
            "Port index for this table"
    ::= { sonusDsx3AdmnEntry 5 }

sonusDsx3AdmnDs3Index OBJECT-TYPE
    SYNTAX          Integer32
    MAX-ACCESS      read-only
    STATUS          current
    DESCRIPTION     
            "Ds3 Index into this table"
    ::= { sonusDsx3AdmnEntry 6 }

sonusDsx3AdmnIfIndex OBJECT-TYPE
    SYNTAX          Integer32
    MAX-ACCESS      read-only
    STATUS          current
    DESCRIPTION     
            "Ds3 If Index. Same as the If index of the standard table"
    ::= { sonusDsx3AdmnEntry 7 }

sonusDsx3AdmnState OBJECT-TYPE
    SYNTAX          SonusAdminState
    MAX-ACCESS      read-write
    STATUS          current
    DESCRIPTION     
            "State of DS3, Enabled/Disabled"
    ::= { sonusDsx3AdmnEntry 8 }

sonusDsx3AdmnTimeout OBJECT-TYPE
    SYNTAX          Integer32 (0..1440)
    MAX-ACCESS      read-write
    STATUS          current
    DESCRIPTION     
            "Max time in minutes before dryup takes place"
    DEFVAL          { 5 }
    ::= { sonusDsx3AdmnEntry 9 }

sonusDsx3AdmnMode OBJECT-TYPE
    SYNTAX          SonusServiceState
    MAX-ACCESS      read-write
    STATUS          current
    DESCRIPTION     
            "DS3 is in service or out of service."
    DEFVAL          { outOfService }
    ::= { sonusDsx3AdmnEntry 10 }

sonusDsx3AdmnAction OBJECT-TYPE
    SYNTAX          SonusAdminAction
    MAX-ACCESS      read-write
    STATUS          current
    DESCRIPTION     
            "Force out of service or wait for dryup"
    DEFVAL          { dryUp }
    ::= { sonusDsx3AdmnEntry 11 }

sonusDsx3AdmnAvailDs1s OBJECT-TYPE
    SYNTAX          BITS { ds1x1(0), ds1x2(1), ds1x3(2), ds1x4(3), 
                        ds1x5(4), ds1x6(5), ds1x7(6), ds1x8(7), ds1x9(8), 
                        ds1x10(9), ds1x11(10), ds1x12(11), ds1x13(12), 
                        ds1x14(13), ds1x15(14), ds1x16(15), ds1x17(16), 
                        ds1x18(17), ds1x19(18), ds1x20(19), ds1x21(20), 
                        ds1x22(21), ds1x23(22), ds1x24(23), ds1x25(24), 
                        ds1x26(25), ds1x27(26), ds1x28(27) }
    MAX-ACCESS      read-write
    STATUS          current
    DESCRIPTION     
            "Bitstring map of Ds1s that are available on this DS3."
    ::= { sonusDsx3AdmnEntry 12 }

sonusDsx3AdmnDs1ModeOverride OBJECT-TYPE
    SYNTAX          SonusAdminState
    MAX-ACCESS      read-write
    STATUS          current
    DESCRIPTION     
            "This flag controls whether the mode and state of the DS1's
             carried in the DS3 are modified when the mode and state of
             the DS3 is modified. If this flag is set to Enabled, the DS1
             state and mode are not changed when the DS3 mode and state
             are changed."
    DEFVAL          { disabled }
    ::= { sonusDsx3AdmnEntry 13 }

sonusDsx3AdmnInitCounters OBJECT-TYPE
    SYNTAX          SonusAdminState
    MAX-ACCESS      read-write
    STATUS          current
    DESCRIPTION     
            "Used to initialize all counters. Once enabled clears all T3 counters."
    DEFVAL          { disabled }
    ::= { sonusDsx3AdmnEntry 14 }

sonusDsx3AdmnCircuitId OBJECT-TYPE
    SYNTAX          DisplayString (SIZE(1..23))
    MAX-ACCESS      read-write
    STATUS          current
    DESCRIPTION     
            "The Circuit Id."
    ::= { sonusDsx3AdmnEntry 15 }

sonusDsx3StatTable OBJECT-TYPE
    SYNTAX          SEQUENCE OF SonusDsx3StatEntry
    MAX-ACCESS      not-accessible
    STATUS          current
    DESCRIPTION     
            "Table of Sonus Enterprise status for all DS3s"
    ::= { sonusDsx3MIBObjects 2 }

sonusDsx3StatEntry OBJECT-TYPE
    SYNTAX          SonusDsx3StatEntry
    MAX-ACCESS      not-accessible
    STATUS          current
    DESCRIPTION     
            "Entry in Table consisting of the all the Sonus Enterprise DS3 Status"
    INDEX           { sonusDsx3StatShelfIndex, sonusDsx3StatSlotIndex, 
                      sonusDsx3StatPortIndex, sonusDsx3StatDs3Index }
    ::= { sonusDsx3StatTable 1 }

SonusDsx3StatEntry ::=
    SEQUENCE {
        sonusDsx3StatShelfIndex         Integer32,
        sonusDsx3StatSlotIndex          Integer32,
        sonusDsx3StatPortIndex          Integer32,
        sonusDsx3StatDs3Index           Integer32,
        sonusDsx3StatValidIntervals     Integer32,
        sonusDsx3StatDs3LCV             Integer32,
        sonusDsx3StatDs3FERR            Integer32,
        sonusDsx3StatDs3EXZS            Integer32,
        sonusDsx3StatDs3PERR            Integer32,
        sonusDsx3StatDs3CPERR           Integer32,
        sonusDsx3StatDs3FEBE            Integer32,
        sonusDsx3StatDs3AIS             Integer32,
        sonusDsx3StatDs3LOS             Integer32,
        sonusDsx3StatLineStatStr        DisplayString,
        sonusDsx3StatLoopbackStr        DisplayString,
        sonusDsx3StatOperStatus         INTEGER
    }

sonusDsx3StatShelfIndex OBJECT-TYPE
    SYNTAX          Integer32
    MAX-ACCESS      read-only
    STATUS          current
    DESCRIPTION     
            "Shelf index for this table"
    ::= { sonusDsx3StatEntry 1 }

sonusDsx3StatSlotIndex OBJECT-TYPE
    SYNTAX          Integer32
    MAX-ACCESS      read-only
    STATUS          current
    DESCRIPTION     
            "Slot index for this table"
    ::= { sonusDsx3StatEntry 2 }

sonusDsx3StatPortIndex OBJECT-TYPE
    SYNTAX          Integer32
    MAX-ACCESS      read-only
    STATUS          current
    DESCRIPTION     
            "Port index for this table"
    ::= { sonusDsx3StatEntry 3 }

sonusDsx3StatDs3Index OBJECT-TYPE
    SYNTAX          Integer32
    MAX-ACCESS      read-only
    STATUS          current
    DESCRIPTION     
            "Ds3 Index into this table"
    ::= { sonusDsx3StatEntry 4 }

sonusDsx3StatValidIntervals OBJECT-TYPE
    SYNTAX          Integer32
    MAX-ACCESS      read-only
    STATUS          current
    DESCRIPTION     
            "Number of intervals worth of Performance Data that is valid"
    ::= { sonusDsx3StatEntry 5 }

sonusDsx3StatDs3LCV OBJECT-TYPE
    SYNTAX          Integer32
    MAX-ACCESS      read-only
    STATUS          current
    DESCRIPTION     
            "Total number of line code violations"
    ::= { sonusDsx3StatEntry 6 }

sonusDsx3StatDs3FERR OBJECT-TYPE
    SYNTAX          Integer32
    MAX-ACCESS      read-only
    STATUS          current
    DESCRIPTION     
            "Total number of framing errors"
    ::= { sonusDsx3StatEntry 7 }

sonusDsx3StatDs3EXZS OBJECT-TYPE
    SYNTAX          Integer32
    MAX-ACCESS      read-only
    STATUS          current
    DESCRIPTION     
            "Total number of Excessive zeroes violations"
    ::= { sonusDsx3StatEntry 8 }

sonusDsx3StatDs3PERR OBJECT-TYPE
    SYNTAX          Integer32
    MAX-ACCESS      read-only
    STATUS          current
    DESCRIPTION     
            "Total number of parity errors"
    ::= { sonusDsx3StatEntry 9 }

sonusDsx3StatDs3CPERR OBJECT-TYPE
    SYNTAX          Integer32
    MAX-ACCESS      read-only
    STATUS          current
    DESCRIPTION     
            "Total number of C-Bit parity errors"
    ::= { sonusDsx3StatEntry 10 }

sonusDsx3StatDs3FEBE OBJECT-TYPE
    SYNTAX          Integer32
    MAX-ACCESS      read-only
    STATUS          current
    DESCRIPTION     
            "Total number of FEBE errors"
    ::= { sonusDsx3StatEntry 11 }

sonusDsx3StatDs3AIS OBJECT-TYPE
    SYNTAX          Integer32
    MAX-ACCESS      read-only
    STATUS          current
    DESCRIPTION     
            "Total number of AIS errors"
    ::= { sonusDsx3StatEntry 12 }

sonusDsx3StatDs3LOS OBJECT-TYPE
    SYNTAX          Integer32
    MAX-ACCESS      read-only
    STATUS          current
    DESCRIPTION     
            "Total number of Loss of signal errors"
    ::= { sonusDsx3StatEntry 13 }

sonusDsx3StatLineStatStr OBJECT-TYPE
    SYNTAX          DisplayString (SIZE(1..16))
    MAX-ACCESS      read-only
    STATUS          current
    DESCRIPTION     
            "String display for DS3 line status"
    ::= { sonusDsx3StatEntry 14 }

sonusDsx3StatLoopbackStr OBJECT-TYPE
    SYNTAX          DisplayString (SIZE(1..32))
    MAX-ACCESS      read-only
    STATUS          current
    DESCRIPTION     
            "String display for DS3 loopback status"
    ::= { sonusDsx3StatEntry 15 }

sonusDsx3StatOperStatus OBJECT-TYPE
    SYNTAX          INTEGER { up(1), down(2), dryingUp(3) }
    MAX-ACCESS      read-only
    STATUS          current
    DESCRIPTION     
            "The actual status of the DS3 interface. Interface is 
             Up if it is administratively in service and there are no
             line failures or hardware failures. Interface is Down if
             it is administratively in service and there are line
             failures or hardware failures, or if it is administratively
             out of service. Interface is DryingUp if it is administratively
             out of service and is drying up (no new	calls, still carrying
             in-progress calls)."
    ::= { sonusDsx3StatEntry 16 }

sonusDsx3MIBNotifications OBJECT IDENTIFIER
    ::= { sonusDsx3MIB 2 }

sonusDsx3MIBNotificationsPrefix OBJECT IDENTIFIER
    ::= { sonusDsx3MIBNotifications 0 }

sonusDsx3MIBNotificationsObjects OBJECT IDENTIFIER
    ::= { sonusDsx3MIBNotifications 1 }

sonusDs3OutOfServiceReason OBJECT-TYPE
    SYNTAX          INTEGER { maintenance(1) }
    MAX-ACCESS      read-only
    STATUS          current
    DESCRIPTION     
            "The reason for DS3 going out of service"
    ::= { sonusDsx3MIBNotificationsObjects 1 }

sonusDs3OutOfServiceType OBJECT-TYPE
    SYNTAX          INTEGER { admin(1), hwFailure(2) }
    MAX-ACCESS      read-only
    STATUS          current
    DESCRIPTION     
            "The type of operation which caused DS3 to go out of service"
    ::= { sonusDsx3MIBNotificationsObjects 2 }

sonusDs3ThresholdType OBJECT-TYPE
    SYNTAX          INTEGER { currentLineCodeViolation(1), 
                        currentPbitParity(2), currentCbitParity(3), 
                        currentSeverelyErroredFramingSecs(4), 
                        currentLineErrorSeconds(5), 
                        currentPbitParityErroredSeconds(6), 
                        currentCbitParityErroredSeconds(7), 
                        currentPbitSeverelyErroredSeconds(8), 
                        currentLineSeverelyErroredSeconds(9), 
                        currentUnavailableSeconds(10), 
                        totalLineCodeViolation(11), totalPbitParity(12), 
                        totalCbitParity(13), 
                        totalSeverelyErroredFramingSecs(14), 
                        totalLineErrorSeconds(15), 
                        totalPbitParityErroredSeconds(16), 
                        totalCbitParityErroredSeconds(17), 
                        totalPbitSeverelyErroredSeconds(18), 
                        totalLineSeverelyErroredSeconds(19), 
                        totalUnavailableSeconds(20) }
    MAX-ACCESS      read-only
    STATUS          current
    DESCRIPTION     
            "Type of threshold that was crossed which caused a threshold crossing trap"
    ::= { sonusDsx3MIBNotificationsObjects 3 }

sonusDs3LineState OBJECT-TYPE
    SYNTAX          INTEGER { green(1), red(2), rai(3), ais(4), 
                        hwfailure(5) }
    MAX-ACCESS      read-only
    STATUS          current
    DESCRIPTION     
            "The type of Alarm or failure which caused DS3 to go out of service"
    ::= { sonusDsx3MIBNotificationsObjects 4 }

sonusDs3AdmnState OBJECT-TYPE
    SYNTAX          INTEGER { disabled(1), enabled(2), deleted(3), 
                        inservice(4), dryingUp(5) }
    MAX-ACCESS      read-only
    STATUS          current
    DESCRIPTION     
            "The administrative state of the DS3."
    ::= { sonusDsx3MIBNotificationsObjects 5 }

sonusDsx3AdminChangeNotification NOTIFICATION-TYPE
    OBJECTS         { sonusShelfIndex, sonusSlotIndex, sonusPortIndex, 
                      sonusDs3Index, sonusDs3AdmnState, 
                      sonusEventDescription, sonusEventClass, 
                      sonusEventLevel }
    STATUS          current
    DESCRIPTION     
            "A sonusDsx3AdminChangeNotification trap indicates the DS3 administration 
             changes."
    ::= { sonusDsx3MIBNotificationsPrefix 1 }

sonusDsx3OutOfServiceNotification NOTIFICATION-TYPE
    OBJECTS         { sonusShelfIndex, sonusSlotIndex, sonusPortIndex, 
                      sonusDs3Index, sonusDs3OutOfServiceReason, 
                      sonusDs3OutOfServiceType, sonusEventDescription, 
                      sonusEventClass, sonusEventLevel }
    STATUS          current
    DESCRIPTION     
            "A sonusDsx3OutOfServiceNotification trap indicates that a DS3
             went out of service. The reason indicates the reason why and
             type indicates the type of failure."
    ::= { sonusDsx3MIBNotificationsPrefix 2 }

sonusDsx3ThresholdCrossingNotification NOTIFICATION-TYPE
    OBJECTS         { sonusShelfIndex, sonusSlotIndex, sonusPortIndex, 
                      sonusDs3Index, sonusDs3ThresholdType, 
                      sonusEventDescription, sonusEventClass, 
                      sonusEventLevel }
    STATUS          current
    DESCRIPTION     
            "A sonusDsx3ThresholdCrossingNotification trap indicates that a DS3
             threshold has been crossed. The type indicates the type of threshold."
    ::= { sonusDsx3MIBNotificationsPrefix 3 }

sonusDsx3LineStatusChangeNotification NOTIFICATION-TYPE
    OBJECTS         { sonusShelfIndex, sonusSlotIndex, sonusPortIndex, 
                      sonusDs3Index, sonusDs3LineState, 
                      sonusEventDescription, sonusEventClass, 
                      sonusEventLevel }
    STATUS          current
    DESCRIPTION     
            "A sonusDsx3LineStatusChangeNotification trap indicates the DS3 state changes. 
             It is used to notify DS3 Alarms states"
    ::= { sonusDsx3MIBNotificationsPrefix 4 }

END -- end of module SONUS-DS3-MIB.
