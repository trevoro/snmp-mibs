Wellfleet-WFMPC-MIB DEFINITIONS ::= BEGIN

-- Created by slakkapr
-- Creation date: 17-Nov-1997


    IMPORTS

      Counter
        FROM RFC1155-SMI
      OBJECT-TYPE
        FROM RFC-1212
      wfmpcObjects
        FROM Wellfleet-COMMON-MIB;

    --
    --  MPOA Client Objects
    --

    wfmpcEntryTable OBJECT-TYPE
        SYNTAX SEQUENCE OF WfmpcEntry
        ACCESS not-accessible
        STATUS mandatory
        DESCRIPTION
                "MPC base entry table.
                "
        ::= {wfmpcObjects 1}

    wfmpcEntry OBJECT-TYPE
                SYNTAX  WfmpcEntry
                ACCESS  not-accessible
                STATUS  mandatory
                DESCRIPTION
                "An MPC base entry description"
        INDEX   { wfmpcSlot}
	::= { wfmpcEntryTable 1 }

    WfmpcEntry ::= SEQUENCE {
	        wfmpcDelete			INTEGER,
		wfmpcDisable			INTEGER,
		wfmpcSlot			INTEGER,
		wfmpcCct			INTEGER,
	        wfmpcMsgNum			INTEGER,
         	wfmpcMsgSendEnable          	INTEGER,
	        wfmpcMPSAtmAddr          	OCTET STRING,
        	wfmpcSetupVCtoMPS             	INTEGER,
	        wfmpcMPCAtmAddr          	OCTET STRING,
        	wfmpcCIPNackFlag         	INTEGER
    	}

    wfmpcDelete  OBJECT-TYPE
	        SYNTAX  INTEGER {
                    created(1),
                    deleted(2)
                }
        ACCESS  read-write
        STATUS  mandatory
        DESCRIPTION
                "Indication to create or delete an MPC base Entry
                from the MIB "
        DEFVAL  { created }
        ::= { wfmpcEntry 1 }

    wfmpcDisable OBJECT-TYPE
        SYNTAX  INTEGER {
		enabled(1),
                disabled(2)
        }
	ACCESS  read-write
	STATUS  mandatory
	DESCRIPTION
	"Enables or Disables MPC Subsystem."
	DEFVAL  { enabled }
	::= { wfmpcEntry 2 }

    wfmpcSlot OBJECT-TYPE
        SYNTAX  INTEGER
        ACCESS  read-only
        STATUS      mandatory
        DESCRIPTION
            "The Slot number of the slot on which this MPC is instantiated."
        ::= { wfmpcEntry 3 }

    wfmpcCct	OBJECT-TYPE
        SYNTAX  INTEGER
        ACCESS  read-write
        STATUS  mandatory
        DESCRIPTION
	"This corresponds to the circuit number associated with the
	 ATM Driver "
	::= { wfmpcEntry 4 }   
 
    wfmpcMsgNum OBJECT-TYPE
	SYNTAX  INTEGER
        ACCESS  read-write
        STATUS  mandatory
        DESCRIPTION
        "Send the gived message to DestId."
	::= { wfmpcEntry 5 }

    wfmpcMsgSendEnable  OBJECT-TYPE
	SYNTAX  INTEGER {
		enabled(1),
                disabled(2)
		}
        ACCESS  read-write
        STATUS  mandatory
        DESCRIPTION
	"Send the MPOA message to MPS if enabled."
	DEFVAL { disabled}
	::= { wfmpcEntry 6 }

    wfmpcMPSAtmAddr OBJECT-TYPE
        SYNTAX  OCTET STRING
        ACCESS  read-write
        STATUS  mandatory
        DESCRIPTION
                "The remote MPS's ATM Address to which we have to send
                 MPOA Resolution Request."
        DEFVAL { "0x390000000000000000000000000000A2CB2C2804" }
        ::= { wfmpcEntry 7 }

    wfmpcSetupVCtoMPS  OBJECT-TYPE
	SYNTAX  INTEGER {
		enabled(1),
                disabled(2)
		}
        ACCESS  read-write
        STATUS  mandatory
        DESCRIPTION
	"(Re)Establish VC to MPS if SetupVC enabled."
	DEFVAL { disabled}
	::= { wfmpcEntry 8 }

    wfmpcMPCAtmAddr OBJECT-TYPE
        SYNTAX  OCTET STRING
        ACCESS  read-write
        STATUS  mandatory
        DESCRIPTION
                "This  MPC (emulator)'s Data ATM Address which is sent back
                 in Cache Imposition Reply."
        ::= { wfmpcEntry 9 }

    wfmpcCIPNackFlag OBJECT-TYPE
	SYNTAX  INTEGER {
		enabled(1),
                disabled(2)
		}
        ACCESS  read-write
        STATUS  mandatory
        DESCRIPTION
                "Flag which indicates CIP Nack or CIP Ack."
	DEFVAL { disabled}
	::= { wfmpcEntry 10 }

    --
    --  MPOA Client statistics group
    --

    wfmpcStatisticsTable OBJECT-TYPE
        SYNTAX       SEQUENCE OF WfmpcStatisticsEntry
        ACCESS   not-accessible
        STATUS       mandatory
        DESCRIPTION
                "This table represents the statistical information
                 for the MPCs, which this agent manages."
        ::= { wfmpcObjects 2 }

    wfmpcStatisticsEntry OBJECT-TYPE
        SYNTAX       WfmpcStatisticsEntry
        ACCESS   not-accessible
        STATUS       mandatory
        DESCRIPTION
                "Each row in this table contains statistics
                 for one MPOA server."
        INDEX   { wfmpcStatSlot,wfmpcStatIndex }
        ::= { wfmpcStatisticsTable 1 }

    WfmpcStatisticsEntry ::=
        SEQUENCE {
            wfmpcStatIndex                                  INTEGER,
            wfmpcStatRxMpoaResolveRequests                  Counter,
            wfmpcStatTxMpoaResolveReplyAcks                 Counter,
            wfmpcStatTxMpoaResolveReplyInsufECResources     Counter,
            wfmpcStatTxMpoaResolveReplyInsufSCResources     Counter,
            wfmpcStatTxMpoaResolveReplyInsufEitherResources Counter,
            wfmpcStatTxMpoaResolveReplyUnsupportedInetProt  Counter,
            wfmpcStatTxMpoaResolveReplyUnsupportedMacEncaps Counter,
            wfmpcStatTxMpoaResolveReplyUnspecifiedOther     Counter,
            wfmpcStatTxMpoaResolveReplyOtherOther           Counter,
	    wfmpcStatGiveupTimeExpireds                     Counter,
            wfmpcStatTxMpoaImpRequests                      Counter,
            wfmpcStatRxMpoaImpReplyAcks                     Counter,
            wfmpcStatRxMpoaImpReplyInsufECResources         Counter,
            wfmpcStatRxMpoaImpReplyInsufSCResources         Counter,
            wfmpcStatRxMpoaImpReplyInsufEitherResources     Counter,
            wfmpcStatRxMpoaImpReplyUnsupportedInetProt      Counter,
            wfmpcStatRxMpoaImpReplyUnsupportedMacEncaps     Counter,
            wfmpcStatRxMpoaImpReplyUnspecifiedOther         Counter,
            wfmpcStatRxMpoaImpReplyOtherOther               Counter,
            wfmpcStatRxMpoaEgressCachePurgeRequests         Counter,
            wfmpcStatTxMpoaEgressCachePurgeReplies          Counter,
            wfmpcStatTxMpoaTriggers                         Counter,
	    wfmpcStatSlot				    INTEGER
        }

    wfmpcStatIndex OBJECT-TYPE
        SYNTAX      INTEGER
        ACCESS      read-only
        STATUS      mandatory
        DESCRIPTION
                " This is the mpc index "
    ::= { wfmpcStatisticsEntry 1 }

    wfmpcStatRxMpoaResolveRequests OBJECT-TYPE
        SYNTAX      Counter
        ACCESS  read-only
        STATUS      mandatory
        DESCRIPTION
                "The number of MPOA Resolve Requests received
                 by this MPC which are translated to NHRP 
                 resolve requests.
                 Discontinuities in the value of this counter can occur
                 at re-initialization of the management system, and/or 
                 re-initialization of the MPC, and at other times, 
                 as indicated by the value of wfmpcDiscontinuityTime."
        ::= { wfmpcStatisticsEntry 2 }


     wfmpcStatTxMpoaResolveReplyAcks   OBJECT-TYPE
         SYNTAX      Counter
         ACCESS  read-only
         STATUS      mandatory
         DESCRIPTION
                 "The number of MPOA Resolve Replies transmitted by this MPC
                  which contain the MPOA CIE Code of 0x00 - Success.
                  Discontinuities in the value of this counter can occur
                  at re-initialization of the management system, and/or
                  re-initialization of the MPC, and at other times,
                  as indicated by the value of mpcDiscontinuityTime."
     REFERENCE "Multiprotocol Over ATM.  AF-MPOA-0087.000. Page 62."
        ::= { wfmpcStatisticsEntry 3 }

    wfmpcStatTxMpoaResolveReplyInsufECResources  OBJECT-TYPE
    SYNTAX      Counter
    ACCESS  read-only
    STATUS      mandatory
    DESCRIPTION
       "The number of MPOA Resolve Replies transmitted by this MPC
        which contain the MPOA CIE Code of 0x81 - Insufficient
        resources to accept egress cache entry.
        Discontinuities in the value of this counter can occur
        at re-initialization of the management system, and/or
        re-initialization of the MPC, and at other times,
        as indicated by the value of mpcDiscontinuityTime."
     REFERENCE "Multiprotocol Over ATM.  AF-MPOA-0087.000. Page 62."
     ::= { wfmpcStatisticsEntry 4 }

    wfmpcStatTxMpoaResolveReplyInsufSCResources   OBJECT-TYPE
    SYNTAX      Counter
    ACCESS  read-only
    STATUS      mandatory
    DESCRIPTION
       "The number of MPOA Resolve Replies transmitted by this MPC
        which contain the MPOA CIE Code of 0x82 - Insufficent resources
        to accept shortcut.
        Discontinuities in the value of this counter can occur
        at re-initialization of the management system, and/or
        re-initialization of the MPC, and at other times,
        as indicated by the value of mpcDiscontinuityTime."
     REFERENCE "Multiprotocol Over ATM.  AF-MPOA-0087.000. Page 62."
     ::= { wfmpcStatisticsEntry 5 }


   wfmpcStatTxMpoaResolveReplyInsufEitherResources   OBJECT-TYPE
   SYNTAX     Counter
   ACCESS  read-only
   STATUS      mandatory
   DESCRIPTION
      "The number of MPOA Resolve Replies transmitted by this MPC
       which contain the MPOA CIE CODE of 0x83 - Insufficient resources
       to accept either shortcut or egress cache entry.
       Discontinuities in the value of this counter can occur
       at re-initialization of the management system, and/or
       re-initialization of the MPC, and at other times,
       as indicated by the value of mpcDiscontinuityTime."
     REFERENCE "Multiprotocol Over ATM.  AF-MPOA-0087.000. Page 62."
     ::= { wfmpcStatisticsEntry 6 }

   wfmpcStatTxMpoaResolveReplyUnsupportedInetProt   OBJECT-TYPE
   SYNTAX     Counter
   ACCESS  read-only
   STATUS      mandatory
   DESCRIPTION
      "The number of MPOA Resolve Replies transmitted by this MPC
       which contain the MPOA CIE CODE of 0x84 - Unsupported Internetwork
       Layer protocol.
       Discontinuities in the value of this counter can occur
       at re-initialization of the management system, and/or
       re-initialization of the MPC, and at other times,
       as indicated by the value of mpcDiscontinuityTime."
     REFERENCE "Multiprotocol Over ATM.  AF-MPOA-0087.000. Page 62."
     ::= { wfmpcStatisticsEntry 7 }

   wfmpcStatTxMpoaResolveReplyUnsupportedMacEncaps   OBJECT-TYPE
   SYNTAX     Counter
   ACCESS  read-only
   STATUS      mandatory
   DESCRIPTION
      "The number of MPOA Resolve Replies transmitted by this MPC
       which contain the MPOA CIE CODE of 0x85 - Unsupported MAC
       layer encapsulation.
       Discontinuities in the value of this counter can occur
       at re-initialization of the management system, and/or
       re-initialization of the MPC, and at other times,
       as indicated by the value of mpcDiscontinuityTime."
     REFERENCE "Multiprotocol Over ATM.  AF-MPOA-0087.000. Page 62."
     ::= { wfmpcStatisticsEntry 8 }

   wfmpcStatTxMpoaResolveReplyUnspecifiedOther   OBJECT-TYPE
   SYNTAX     Counter
   ACCESS  read-only
   STATUS      mandatory
   DESCRIPTION
      "The number of MPOA Resolve Replies transmitted by this MPC
       which contain the MPOA CIE CODE of 0x88 - Unspecified/Other.
       Discontinuities in the value of this counter can occur
       at re-initialization of the management system, and/or
       re-initialization of the MPC, and at other times,
       as indicated by the value of mpcDiscontinuityTime."
     REFERENCE "Multiprotocol Over ATM.  AF-MPOA-0087.000. Page 62."
     ::= { wfmpcStatisticsEntry 9 }

   wfmpcStatTxMpoaResolveReplyOtherOther   OBJECT-TYPE
   SYNTAX     Counter
   ACCESS  read-only
   STATUS      mandatory
   DESCRIPTION
      "The number of MPOA Resolve Replies transmitted by this MPC
       which are not counted above.  NOTE - this would include
       NHRP errors.
       Discontinuities in the value of this counter can occur
       at re-initialization of the management system, and/or
       re-initialization of the MPC, and at other times,
       as indicated by the value of mpcDiscontinuityTime."
     REFERENCE "Multiprotocol Over ATM.  AF-MPOA-0087.000. Page 62."
     ::= { wfmpcStatisticsEntry 10 }

    wfmpcStatGiveupTimeExpireds OBJECT-TYPE
        SYNTAX      Counter
        ACCESS  read-only
        STATUS      mandatory
        DESCRIPTION
                "The number of times the MPC Give up Time (MPC-p6)
                 has expired while waiting for a reply from a
                 re-originated MPOA resolution request, i.e. a
                 reply for a translated NHRP resolution request.

                 Discontinuities in the value of this counter can occur
                 at re-initialization of the management system, and/or
                 re-initialization of the MPC, and at other times,
                 as indicated by the value of mpcDiscontinuityTime."
        ::= { wfmpcStatisticsEntry 11 }

    wfmpcStatTxMpoaImpRequests OBJECT-TYPE
        SYNTAX      Counter
        ACCESS  read-only
        STATUS      mandatory
        DESCRIPTION
                "The number of MPOA Cache Imposition Requests
                 transmitted by this MPC.

                 Discontinuities in the value of this counter can occur
                 at re-initialization of the management system, and/or
                 re-initialization of the MPC, and at other times,
                 as indicated by the value of mpcDiscontinuityTime."
        ::= { wfmpcStatisticsEntry 12 }

    wfmpcStatRxMpoaImpReplyAcks OBJECT-TYPE
        SYNTAX      Counter
        ACCESS  read-only
        STATUS      mandatory
        DESCRIPTION
                "The number of successful MPOA Cache Imposition Replies
                 received by this MPC which contain an MPOA CIE Code of 0x00,
                 Success.

                 Discontinuities in the value of this counter can occur
                 at re-initialization of the management system, and/or
                 re-initialization of the MPC, and at other times,
                 as indicated by the value of mpcDiscontinuityTime."
        ::= { wfmpcStatisticsEntry 13 }

     wfmpcStatRxMpoaImpReplyInsufECResources   OBJECT-TYPE
       SYNTAX      Counter
       ACCESS  read-only
       STATUS      mandatory
       DESCRIPTION
          "The number of MPOA Cache Imposition Replies received by this
           MPC which contain the MPOA CIE Code of 0x81, Insufficient
           resources to accept egress cache entry.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 14 }


     wfmpcStatRxMpoaImpReplyInsufSCResources   OBJECT-TYPE
       SYNTAX      Counter
       ACCESS  read-only
       STATUS      mandatory
       DESCRIPTION
          "The number of MPOA Cache Imposition Replies received by this
           MPC which contain the MPOA CIE Code of 0x82 - Insufficient
           resources to accept shortcut.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 15 }

     wfmpcStatRxMpoaImpReplyInsufEitherResources   OBJECT-TYPE
       SYNTAX      Counter
       ACCESS  read-only
       STATUS      mandatory
       DESCRIPTION
          "The number of MPOA Cache Imposition Replies received by this
           MPC which contain the MPOA CIE Code of 0x83 - Insufficient
           resources to accept either shortcut or egress cache entry.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 16 }


     wfmpcStatRxMpoaImpReplyUnsupportedInetProt   OBJECT-TYPE
       SYNTAX      Counter
       ACCESS  read-only
       STATUS      mandatory
       DESCRIPTION
          "The number of MPOA Cache Imposition Replies received by this
           MPC which contain the MPOA CIE Code of 0x84 - Unsupported
           Internetwork Layer protocol.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 17 }

     wfmpcStatRxMpoaImpReplyUnsupportedMacEncaps   OBJECT-TYPE
       SYNTAX      Counter
       ACCESS  read-only
       STATUS      mandatory
       DESCRIPTION
          "The number of MPOA Cache Imposition Replies received by this
           MPC which contain the MPOA CIE Code of 0x85 - Unsupported
           MAC layer encapsulation.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 18 }

     wfmpcStatRxMpoaImpReplyUnspecifiedOther   OBJECT-TYPE
       SYNTAX      Counter
       ACCESS  read-only
       STATUS      mandatory
       DESCRIPTION
          "The number of MPOA Cache Imposition Replies received by this
           MPC which contain the MPOA CIE Code of 0x88 - Unspecified/Other.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 19 }

    wfmpcStatRxMpoaImpReplyOtherOther   OBJECT-TYPE
       SYNTAX      Counter
       ACCESS  read-only
       STATUS      mandatory
       DESCRIPTION
          "The number of MPOA Cache Imposition Replies received by this
           MPC which are not counted previously.  NOTE - this would
           include NHRP errors.
           Discontinuities in the value of this counter can occur
           at re-initialization of the management system, and/or
           re-initialization of the MPC, and at other times,
           as indicated by the value of mpcDiscontinuityTime."
       REFERENCE "Multiprotocol Over ATM. AF-MPOA-0087.000. Page 62."
       ::= { wfmpcStatisticsEntry 20 }

    wfmpcStatRxMpoaEgressCachePurgeRequests OBJECT-TYPE
        SYNTAX      Counter
        ACCESS  read-only
        STATUS      mandatory
        DESCRIPTION
                "The number of MPOA Egress Cache Purges Requests
                 received by this MPC.
                 Discontinuities in the value of this counter can occur
                 at re-initialization of the management system, and/or
                 re-initialization of the MPC, and at other times,
                 as indicated by the value of mpcDiscontinuityTime."
         ::= { wfmpcStatisticsEntry 21 }

    wfmpcStatTxMpoaEgressCachePurgeReplies OBJECT-TYPE
        SYNTAX      Counter
        ACCESS  read-only
        STATUS      mandatory
        DESCRIPTION
                "The number of MPOA Egress Cache Purge Replies
                 transmitted by this MPC.
                 Discontinuities in the value of this counter can occur
                 at re-initialization of the management system, and/or
                 re-initialization of the MPC, and at other times,
                 as indicated by the value of mpcDiscontinuityTime."
         ::= { wfmpcStatisticsEntry 22 }

    wfmpcStatTxMpoaTriggers OBJECT-TYPE
        SYNTAX      Counter
        ACCESS  read-only
        STATUS      mandatory
        DESCRIPTION
                "The number of MPOA Trigger messages transmitted by this MPC.
                 Discontinuities in the value of this counter can occur
                 at re-initialization of the management system, and/or
                 re-initialization of the MPC, and at other times,
                 as indicated by the value of mpcDiscontinuityTime."
        REFERENCE "Multiprotocol Over ATM.  AF-MPOA-0087.000.
                   Section 4.7.2.1 MPOA Trigger"
         ::= { wfmpcStatisticsEntry 23 }

    wfmpcStatSlot OBJECT-TYPE
        SYNTAX  INTEGER
        ACCESS  read-only
        STATUS      mandatory
        DESCRIPTION
            "The Slot number of the slot on which this MPC is instantiated."
         ::= { wfmpcStatisticsEntry 24 }

END
