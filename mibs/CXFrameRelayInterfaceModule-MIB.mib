CXFrameRelayInterfaceModule-MIB DEFINITIONS ::= BEGIN


IMPORTS
   Counter,TimeTicks       FROM RFC1155-SMI
   OBJECT-TYPE     FROM RFC-1212

--  Proprietary frame relay interface MIB
   cxFrameRelayInterfaceModule, Alias, SapIndex 
            FROM   CXProduct-SMI
   DLCI                    FROM  CXFrameRelay-MIB;

-- Proprietary Data Types
SubRef  ::=     INTEGER (0..255)



--  System route connection interval object


frimSRConnectInterval OBJECT-TYPE
        SYNTAX  INTEGER (1..65535)
   ACCESS  read-write
   STATUS  mandatory
   DESCRIPTION
"Determines the number of seconds to wait before attempting to 
re-establish a broken connection on a particular system route.

Range of Values: 1 - 65, 535

Default Value: 30

Configuration Changed: administrative "
        DEFVAL {30 }
   ::= { cxFrameRelayInterfaceModule 1 }



--  The cost of frame relay service object


frimServiceCost        OBJECT-TYPE
   SYNTAX  INTEGER 
   ACCESS  read-write
   STATUS  mandatory
   DESCRIPTION
"Determines the cost of Frame Relay service to be registered in the CX 
1000's Inter-Application software layer.

Range of Values: 0 - 65, 535

Default Value: 10

Configuration Changed: administrative "
   ::= { cxFrameRelayInterfaceModule 2 }



--  Service Access Point Configuration Table

--  The table describing parameters required to configure a frame relay module
--  service access point.

--  The table describing statistics available for monitoring any frame relay
--  interface module service access point.


frimSapTable OBJECT-TYPE
   SYNTAX  SEQUENCE OF FrimSapEntry
   ACCESS  not-accessible
   STATUS  mandatory
   DESCRIPTION
"A table containing configuration and statistical information about each 
frame relay interface module service access point."
   ::= { cxFrameRelayInterfaceModule 3 }


   frimSapEntry OBJECT-TYPE
      SYNTAX  FrimSapEntry
      ACCESS  not-accessible
      STATUS  mandatory
      DESCRIPTION
"The parameters for a particular frame relay module service access point."
      INDEX { frimSapId }
      ::= { frimSapTable 1 }


   FrimSapEntry ::=
      SEQUENCE {
         frimSapId                                       SapIndex,
         frimSapRowStatus                                INTEGER,
         frimSapType                                     INTEGER,
         frimSapAlias                                    Alias,
         frimSapCompanionAlias                   Alias,
         frimSapMaxDlcis                         INTEGER,
         frimSapMaxErrorFrames                   INTEGER,
         frimSapMonitorFrames                    INTEGER,
         frimSapFrWindowSize                     INTEGER,
         frimSapControlStats                             INTEGER,
         frimSapstatRxDataFrames                 Counter,
         frimSapstatRxDataOctets                 Counter,
         frimSapstatTxDataFrames                 Counter,
         frimSapstatTxDataOctets                 Counter,
         frimSapstatUnopenedServiceDiscards      Counter,
         frimSapstatPvcDownDiscards                      Counter,
         frimSapstatUserSuccessfulOpens          Counter,
         frimSapstatUserUnsuccessfulOpens                Counter,
         frimSapstatSRSuccessfulConnects         Counter,
         frimSapstatSRUnsuccessfulConnects               Counter,
         frimSapstatTxResets                             Counter,
         frimSapstatRxBECN                               Counter,
         frimSapstatRxFECN                               Counter
         }



   frimSapId OBJECT-TYPE
      SYNTAX  SapIndex
      ACCESS  read-only
      STATUS  mandatory
      DESCRIPTION
"Indicates the row containing objects for configuring (or monitoring) a 
SAP associated either with the SAP in the Inter-Application software or 
with the SAP in the Frame Relay software layer.

Options:
0: IAM-related upper SAP

1: Frame Relay-related lower SAP

Default Value: none"
      ::= { frimSapEntry 1 }


   frimSapRowStatus OBJECT-TYPE
      SYNTAX  INTEGER {
               invalid (1),
               valid   (2)
               }
      ACCESS  read-write
      STATUS  mandatory
      DESCRIPTION
"Determines whether this SAP is to be removed from service (i.e. 
invalidated) within the FRIM software layer.

Options:
invalid (1): Row is deleted from the table immediately, however values are 
still in effect until the next reset. 

valid (2): Use this value to add a new row to the table, or modify an 
existing row.

Default Value: none

Configuration Changed: administrative "
      ::= { frimSapEntry 2 }


   frimSapType OBJECT-TYPE
      SYNTAX  INTEGER {
               lower   (1),
               upper   (2)
               }
      ACCESS  read-write
      STATUS  mandatory
      DESCRIPTION
"Determines this SAP's type.

Options:
lower (1): SAP is a lower type (leads to the Frame Relay software layer)

upper (2): SAP is an upper type (leads to the Inter-Application software 
layer)

Default Value: none

Configuration Changed: administrative "
      ::= { frimSapEntry 3 }


   frimSapAlias OBJECT-TYPE
      SYNTAX  Alias
      ACCESS  read-write
      STATUS  mandatory
      DESCRIPTION
"Determines the textual name uniquely identifying this SAP.

Range of Values:
CX1000: 0 - 35 alphanumeric characters beginning with a non-numeric character

CX900: 0 - 16 alphanumeric characters beginning with a non-numeric character 

Default Value:
frimUpper1 (for frimSapId 0)

frimsap1 (for frimSapId 1)

Configuration Changed: administrative "
      ::= { frimSapEntry 4 }


   frimSapCompanionAlias OBJECT-TYPE
      SYNTAX  Alias
      ACCESS  read-write
      STATUS  mandatory
      DESCRIPTION
"Determines the textual name identifying the companion SAP either in the 
Inter-Application software layer or the Frame Relay software layer that 
will communicate with this SAP.

Options:
undefined (for frimSapId 0)

frsap41 (for frimSapId 1)

Range of Values:
CX1000: 0 - 35 alphanumeric characters beginning with a non-numeric character

CX900: 0 - 16 alphanumeric characters beginning with a non-numeric character 

Configuration Changed: administrative "
      ::= { frimSapEntry 5 }


   frimSapMaxDlcis OBJECT-TYPE
      SYNTAX  INTEGER (1..1022)
      ACCESS  read-write
      STATUS  mandatory
      DESCRIPTION
"Determines the maximum number of virtual circuits allowed for this SAP. 
This object is meaningful only if 'frimSapType' for this SAP is set to 
'lower'.

Range of Values: 1 - 1, 022

Default Value: 32

Configuration Changed: administrative "
      DEFVAL { 32 }
      ::= { frimSapEntry 6 }


   frimSapMaxErrorFrames OBJECT-TYPE
      SYNTAX  INTEGER (1..14)
      ACCESS  read-write
      STATUS  mandatory
      DESCRIPTION
"Determines the number of frames having FECN and/or BECN bits set that can 
be received within the total number of frames defined in 
'frimSapMonitorFrames' before the system reports a circuit to be 
congested. This object is meaningful only if 'frimSapType' for this SAP is 
set to 'upper'.

Range of Values: 1 - 14

Default Value: 10

Configuration Changed: operative "
      DEFVAL { 10 }
      ::= { frimSapEntry 7 }


   frimSapMonitorFrames OBJECT-TYPE
      SYNTAX  INTEGER (1..14)
      ACCESS  read-write
      STATUS  mandatory
      DESCRIPTION
"Determines the total number of frames that will be monitored at any one 
time for frames having the FECN and/or BECN bits set. It also defines how 
many frames must be received without FECN and/or BECN bits set before the 
system decides that a congested circuit has returned to a normal state. 
This object is meaningful only if 'frimSapType' for this SAP is set to 
'upper'.

Range of Values: 1 - 14

Default Value: 14

Configuration Changed: operative "
      DEFVAL {14 }
      ::= { frimSapEntry 8}


   frimSapFrWindowSize OBJECT-TYPE
      SYNTAX  INTEGER (3..300)
      ACCESS  read-write
      STATUS  mandatory
      DESCRIPTION
"Indicates the maximum number of outstanding data buffers supported by 
this SAP. This object is meaningful only if 'frimSapType' for this SAP is 
set to 'lower'.

Range of Values: 3 - 300

Default Value: 150

Configuration Changed: administrative "
      DEFVAL { 150 }
      ::= { frimSapEntry 9 }


-- gap (11) for future configuration parameters  
--      1 already used up for "frimSapControlStats"


   frimSapControlStats OBJECT-TYPE
      SYNTAX  INTEGER {
               clearSapStats           (1)
               }
      ACCESS  write-only
      STATUS  mandatory
      DESCRIPTION
"Controls the handling of statistics for this SAP.

Options:
clearSapStats: clears all statistics at this SAP

Default Value: none

Configuration Changed: operative"
      ::= { frimSapEntry 19 }


   frimSapstatRxDataFrames OBJECT-TYPE
      SYNTAX  Counter
      ACCESS  read-only
      STATUS  mandatory
      DESCRIPTION
"Indicates the number of data frames that have been received at this SAP 
across all virtual circuits since the last power-up.

Range of Values: 0 - 4, 294, 967, 295

Default Value: none"
      ::= { frimSapEntry 20 }


   frimSapstatRxDataOctets OBJECT-TYPE
      SYNTAX  Counter
      ACCESS  read-only
      STATUS  mandatory
      DESCRIPTION
"Indicates the number of data octets that have been received at this SAP 
across all virtual circuits since the last power-up.

Range of Values: 0 - 4, 294, 967, 295

Default Value: none"
      ::= { frimSapEntry 21 }


   frimSapstatTxDataFrames OBJECT-TYPE
      SYNTAX  Counter
      ACCESS  read-only
      STATUS  mandatory
      DESCRIPTION
"Indicates the number of data frames that have been sent from this SAP 
across all virtual circuits since the last power-up.

Range of Values: 0 - 4, 294, 967, 295

Default Value: none"
      ::= { frimSapEntry 22 }


   frimSapstatTxDataOctets OBJECT-TYPE
      SYNTAX  Counter
      ACCESS  read-only
      STATUS  mandatory
      DESCRIPTION
"Indicates the number of data octets that have been sent from this SAP 
across all virtual circuits since the last power-up.

Range of Values: 0 - 4, 294, 967, 295

Default Value: none"
      ::= { frimSapEntry 23 }


   frimSapstatUnopenedServiceDiscards OBJECT-TYPE
      SYNTAX  Counter
      ACCESS  read-only
      STATUS  mandatory
      DESCRIPTION
"Indicates the number of data frames that have been discarded at this SAP 
since the last power-up because the status of the PVC used by this SAP was 
inactive.

Range of Values: 0 - 4, 294, 967, 295

Default Value: none"
      ::= { frimSapEntry 24}


   frimSapstatPvcDownDiscards OBJECT-TYPE
      SYNTAX  Counter
      ACCESS  read-only
      STATUS  mandatory
      DESCRIPTION
"Indicates the number of received data frames that have been discarded at 
this SAP since the last power-up due to failure of the PVC associated with 
this SAP. This object is meaningful only if 'frimSapType' for this SAP is 
set to 'upper'.

Range of Values: 0 - 4, 294, 967, 295

Default Value: none"
      ::= { frimSapEntry 25}


   frimSapstatUserSuccessfulOpens OBJECT-TYPE
      SYNTAX  Counter
      ACCESS  read-only
      STATUS  mandatory
      DESCRIPTION
"Indicates the number of services that have been opened at this SAP since 
the last power-up. This object is meaningful only if 'frimSapType' for 
this SAP is set to 'upper'.

Range of Values: 0 - 4, 294, 967, 295

Default Value: none"
      ::= { frimSapEntry 26}


   frimSapstatUserUnsuccessfulOpens OBJECT-TYPE
      SYNTAX  Counter
      ACCESS  read-only
      STATUS  mandatory
      DESCRIPTION
"Indicates the number of times the FRIM software layer was unable to open 
a service for a user. This object is meaningful only if 'frimSapType' for 
this SAP is set to 'upper'.

Range of Values: 0 - 4, 294, 967, 295

Default Value: none"
      ::= { frimSapEntry 27}


   frimSapstatSRSuccessfulConnects OBJECT-TYPE
      SYNTAX  Counter
      ACCESS  read-only
      STATUS  mandatory
      DESCRIPTION
"Indicates the number of system route connections that have been 
established at this SAP since the last power-up. This object is meaningful 
only if 'frimSapType' for this SAP is set to 'upper'.

Range of Values: 0 - 4, 294, 967, 295

Default Value: none"
      ::= { frimSapEntry 28}


   frimSapstatSRUnsuccessfulConnects OBJECT-TYPE
      SYNTAX  Counter
      ACCESS  read-only
      STATUS  mandatory
      DESCRIPTION
"Indicates the number of times the FRIM software layer attempted but 
failed to establish a system route connection between two Frame Relay 
service providers. This object is meaningful only if 'frimSapType' for 
this SAP is set to 'upper'.

Range of Values: 0 - 4, 294, 967, 295

Default Value: none"
      ::= { frimSapEntry 29}


   frimSapstatTxResets OBJECT-TYPE
      SYNTAX  Counter
      ACCESS  read-only
      STATUS  mandatory
      DESCRIPTION
"Indicates the number of resets that the FRIM software layer has generated 
at this SAP since the last power-up. This object is meaningful only if 
'frimSapType' for this SAP is set to 'upper'.

Range of Values: 0 - 4, 294, 967, 295

Default Value: none"
      ::= { frimSapEntry 30 }


   frimSapstatRxBECN OBJECT-TYPE
      SYNTAX  Counter
      ACCESS  read-only
      STATUS  mandatory
      DESCRIPTION
"Indicates the number of data frames received with the BECN bit set at 
this SAP since the last power-up. This object is meaningful only if 
'frimSapType' for this SAP is set to 'lower'.

Range of Values: 0 - 4, 294, 967, 295

Default Value: none"
      ::= { frimSapEntry 31 }


   frimSapstatRxFECN OBJECT-TYPE
      SYNTAX  Counter
      ACCESS  read-only
      STATUS  mandatory
      DESCRIPTION
"Indicates the number of data frames received with the FECN bit set at 
this SAP since the last power-up. This object is meaningful only if 
'frimSapType' for this SAP is set to 'lower'.

Range of Values: 0 - 4, 294, 967, 295

Default Value: none"
      ::= { frimSapEntry 32 }


-- Frame Relay System Route Table

-- The table defines the frame relay system routes between any pair of 
-- frame relay service providers in the Network

frimSRTable OBJECT-TYPE
   SYNTAX  SEQUENCE OF FrimSREntry
   ACCESS  not-accessible
   STATUS  mandatory
   DESCRIPTION
" A table containing information about each frame relay system route."
   ::= {  cxFrameRelayInterfaceModule 6  }


frimSREntry OBJECT-TYPE
   SYNTAX          FrimSREntry
   ACCESS          not-accessible
   STATUS          mandatory
   DESCRIPTION
"The information for a particular frame relay system route."
   INDEX {  frimSRFrpCircuitSapId, frimSRFrpCircuitDlci, frimSRProtocolId, 
   frimSRSubRef }
   ::= { frimSRTable 1 }


   FrimSREntry ::=
         SEQUENCE {
               frimSRFrpCircuitSapId           SapIndex,
               frimSRFrpCircuitDlci            DLCI,
               frimSRProtocolId                INTEGER,
               frimSRSubRef                    SubRef,
               frimSRRefRangeEnd          SubRef,
               frimSRRowStatus                 INTEGER,
               frimSRDestFrpCircuitAlias       Alias,
               frimSRDestSubRef                SubRef,
               frimSRRouteStatus               INTEGER,
               frimSRClearStatus               INTEGER
                }


frimSRFrpCircuitSapId OBJECT-TYPE
   SYNTAX  SapIndex
   ACCESS  read-only
   STATUS  mandatory
   DESCRIPTION
"Indicates the 'frpCircuitSapNumber' of the lower SAP in the Frame Relay 
software layer that provides a system route.

Options:
1-16: BOP- or DXI-related lower SAPs

Default Value: none"
   ::= { frimSREntry 1 }


frimSRFrpCircuitDlci OBJECT-TYPE
   SYNTAX  DLCI
   ACCESS  read-only
   STATUS  mandatory
   DESCRIPTION
"Indicates the DLCI (Data Link Connection Identifier) of the virtual 
circuit using the SAP specified in the 'frpCircuitSapNumber'.

Range of Values: 1 - 1, 022

Default Value: none"
   ::= { frimSREntry 2 }


frimSRProtocolId    OBJECT-TYPE
   SYNTAX  INTEGER (1..16)
   ACCESS  read-only
   STATUS  mandatory
   DESCRIPTION
"Indicates the protocol used in the current connection on the virtual 
circuit.

Options:
pidFR: Frame Relay

pidLan:  LAN

pidX25:  X.25

pidCcm: Common Console (CX 1000 only)

pidGmf: Muxed traffic

pidLlc2: LLC2

Note: Protocol ID values 7 to 15 are user-definable.

Default Value: none"
   ::= { frimSREntry 3 }


frimSRSubRef OBJECT-TYPE
   SYNTAX  SubRef
   ACCESS  read-only
   STATUS  mandatory
   DESCRIPTION
"Indicates the reference that one user's segment of traffic will be 
assigned on the outbound PVC to distinguish it from traffic segments of 
other users of the same outbound PVC.

Note: This value and the value assigned for 'frimSRRefRangeEnd', if greater, 
form a range of identifiers that different users' traffic segments on the 
same outbound PVC can use to remain distinct from each other.

Range of Values: 0 - 255

Note: If set to '0', the FRIM software layer assumes an RFC 1490 header is 
already attached to data and therefore will not encapsulate it.

Default Value: none"
   ::= { frimSREntry 4 }


frimSRRefRangeEnd  OBJECT-TYPE
   SYNTAX  SubRef
   ACCESS  read-write
   STATUS  mandatory
   DESCRIPTION
"Determines the upper limit of a range of identifiers that different 
users' traffic segments on the same outbound PVC can use to remain 
distinct from each other.

Note: If the outbound PVC supports only a single protocol, this value must be 
the same as the value set in 'frimSRSubRef'.

Range of Values: 0 - 255

Default Value: none (value set in 'frimSRSubRef')

Configuration Changed: operative "
   ::= { frimSREntry 5 }



frimSRRowStatus OBJECT-TYPE
   SYNTAX  INTEGER {
                invalid     (1),
                valid          (2)
            }
   ACCESS  read-write
   STATUS  mandatory
   DESCRIPTION
"Determines whether this system route is to be deleted from FRIM software 
layer.

Range of Values:
invalid (1): row is flagged; after next reset values will be disabled and 
row will be deleted from table

valid (2): values are enabled

Default Value: valid (2)

Configuration Changed: operative "
   ::= { frimSREntry 6 }

frimSRDestFrpCircuitAlias OBJECT-TYPE
   SYNTAX  Alias
   ACCESS  read-write
   STATUS  mandatory
   DESCRIPTION
"Identifies the alias of a circuit specified in another software module 
that will link with the circuit being configured in the Frame Relay 
module.

Range of Values:
CX1000: 0 - 35 alphanumeric characters beginning with a non-numeric character

CX900 0 - 16 alphanumeric characters beginning with a non-numeric character 

Default Value: none

Configuration Changed: operative "
   ::= { frimSREntry 7 }



frimSRDestSubRef        OBJECT-TYPE
   SYNTAX  SubRef
   ACCESS  read-write
   STATUS  mandatory
   DESCRIPTION
"Determines the identifier that one user's traffic segment will have to 
distinguish it from another user's traffic segment sharing the same 
'frimSRDestFrpCircuitAlias'.

Note:
If 'frimSRSubRef' and 'frimSRRefRangeEnd' form a range of identifiers that 
different users' traffic segments on the same outbound PVC can use to 
remain distinct from each other, the first value for 'frimSRSubRef' will 
correspond to the first value for 'frimSRDestSubRef, the second value for 
the former must correspond to the second value for the latter and so on.

Range of Values: 0 - 255

Default Value: none (value set in 'frimSRSubRef'

Configuration Changed: operative "
   ::= { frimSREntry 8 }



-- gap (6)  for future added parameters


frimSRRouteStatus OBJECT-TYPE
   SYNTAX  INTEGER {
            notConnected    (1),
            inProgress      (2),
            connected               (3)
               }
   ACCESS  read-only
   STATUS  mandatory
   DESCRIPTION
"Indicates the status of a connection on the system route.

Options:
notConnected (1): no connection (destination may not exist or has refused 
connection)

inProgress (2): connection in progress

connected (3): connected

Default Value: none"
   ::= { frimSREntry 15 }


frimSRClearStatus OBJECT-TYPE
   SYNTAX  INTEGER {
               noFailure                (1),
               internalError                    (2),
               localAllocFailure             (3),
               remoteAllocFailure          (4),
               localNoAccess                 (5),
               remoteNoAccess                  (6),
               localPvcDown            (7),
               remotePvcDown   (8),
               localPvcBusy                   (9),
               remotePvcBusy                   (10),
               localFcnFailure                 (11),
               remoteFcnFailure            (12),
               localDsnFailure               (13),
               localRefInUse                  (14),
               remoteAliasNotFound     (15),
               remoteNoPvcService       (16)
               }
   ACCESS  read-only
   STATUS  mandatory
   DESCRIPTION
"Indicates the reason for a connection failure on the system route. This 
status is meaningful only between attempts to establish a system route. 
Successive failed attempts may or may not change the displayed value.

Options:
noFailure (1): no failure (connection has occurred)

internalError (2): internal system error

localAllocFailure (3): not enough memory in local device to establish 
system route at current time

remoteAllocFailure (4): not enough memory in remote device to establish 
system route at current time

localNoAccess (5): PVC in local device not configured

remoteNoAccess (6): PVC in remote dcevice not configured

localPvcDown (7): PVC in local device reported down

remotePvcDown (8): PVC in remote device reported down

localPvcBusy (9): PVC in local device is busy (PVC is SPE or PVC is MPE 
but 'frimSRSubRef' is in use)

remotePvcBusy (10): PVC in remote device is busy (PVC is SPE or PVC is MPE 
but 'frimSRSubRef' is in use)

localFcnFailure (11): local device does not support flow control type

remoteFcnFailure (12): remote device does not support flow control type

localDsnFailure (13): local device could not negotiate size of data unit 
because remote's maximum data unit was zero

localRefInUse (14): 'frimSRSubRef' in use in local device

remoteAliasNotFound (15): no PVC in the local device has this destination 
alias

remoteNoPvcService (16): remote device does not support PVCs

Default Value: none"
   ::= { frimSREntry 16 }




-- Frame Relay System Connection Table

-- The table defining all connections currently existing through the Frame 
-- Relay Interface Module.


frimSysConTable OBJECT-TYPE
   SYNTAX  SEQUENCE OF FrimSysConEntry
   ACCESS  not-accessible
   STATUS  mandatory
   DESCRIPTION
"A table containing information about current connections through the 
FRIM."
   ::= {  cxFrameRelayInterfaceModule 5  }


   frimSysConEntry OBJECT-TYPE
      SYNTAX  FrimSysConEntry
      ACCESS  not-accessible
      STATUS  mandatory
      DESCRIPTION
"The information for a particular connection through the FRIM."
      INDEX {
            frimSysConSapId,
            frimSysConDlci,
            frimSysConPid,
            frimSysConRef
         }
      ::= { frimSysConTable 1 }


   FrimSysConEntry ::=
      SEQUENCE {
         frimSysConSapId                 SapIndex,
         frimSysConDlci                  DLCI,
         frimSysConPid                   INTEGER,
         frimSysConRef                   SubRef,
         frimSysConRemoteSlot            INTEGER,
         frimSysConCreationTime          TimeTicks,
         frimSysConReqDataSize           INTEGER,
         frimSysConNegDataSize           INTEGER,
         frimSysConNegSizeExceededFrames Counter,
         frimSysConRefRangeEnd           SubRef
         }



   frimSysConSapId OBJECT-TYPE
      SYNTAX  SapIndex
      ACCESS  read-only
      STATUS  mandatory
      DESCRIPTION
"Indicates the 'frpCircuitSapNumber' of the lower SAP in the Frame Relay 
software layer through which a virtual circuit has been created and a 
connection has been made.

Options: 1 - 16 (BOP- or DXI-related lower SAPs)

Default Value: none"
      ::= { frimSysConEntry 1 }


   frimSysConDlci OBJECT-TYPE
      SYNTAX  DLCI
      ACCESS  read-only
      STATUS  mandatory
      DESCRIPTION
"Indicates the virtual circuit's DLCI (Data Link Connection Identifier) 
for a particular SAP.

Range of Values: 1 - 1,007

Default Value: none"
      ::= { frimSysConEntry 2 }


   frimSysConPid OBJECT-TYPE
      SYNTAX  INTEGER {
               pidFr           (1),
               pidLan          (2),
                                        pidX25          (3),
                                        pidCcm          (4),
                                        pidGmf          (5),
                                        pidLlc2         (6)
                                        }
      ACCESS  read-only
      STATUS  mandatory
      DESCRIPTION
"Indicates the protocol used in the current connection on the virtual 
circuit.

Options:
pidFr (1): Frame Relay

pidLan (2): LAN

pidX25 (3): X.25

pidCcm (4): Common Console (CX 1000 only)

pidGmf (5): Muxed traffic

pidLlc2 (6): LLC2

Note: Protocol ID values 7 to 15 are user-definable.

Default Value: none"
      ::= { frimSysConEntry 3 }


   frimSysConRef OBJECT-TYPE
      SYNTAX  SubRef
      ACCESS  read-only
      STATUS  mandatory
      DESCRIPTION
"Indicates the reference that one user's segment of traffic has been 
assigned on the outbound PVC to distinguish it from traffic segments of 
other users of the same outbound PVC that are using the same protocol.

Range of Values: 1 - 255

Default Value: none"
      ::= { frimSysConEntry 4 }


   frimSysConRemoteSlot OBJECT-TYPE
      SYNTAX  INTEGER
      ACCESS  read-only
      STATUS  mandatory
      DESCRIPTION
"Indicates the physical slot of the card in the local device that is 
receiving Frame Relay service.

Range of Values: 1 - 16

Default Value: none"
      ::= { frimSysConEntry 5 }


   frimSysConCreationTime OBJECT-TYPE
      SYNTAX  TimeTicks
      ACCESS  read-only
      STATUS  mandatory
      DESCRIPTION
"Indicates the system clock's time at which this connection was created.

Range of Values: system-generated

Default Value: none"
      ::= { frimSysConEntry 6 }


   frimSysConReqDataSize OBJECT-TYPE
      SYNTAX  INTEGER
      ACCESS  read-only
      STATUS  mandatory
      DESCRIPTION
"Indicates the data size of a frame requested at connection. If the 
request comes from another module in the local device, the application on 
that module determines the requested size. If the request comes from the 
Frame Relay module, 'bopSapOprPortMaxFrameSize' (default=1,600) minus 
overhead defined by 'frpSapAddressLength' (default=two bytes) and, if 
enabled, 'frpCircuitMultiProtEncaps' (six bytes if even data bytes in 
frame, or seven bytes if odd data bytes in frame) determines this size.

Range of Values: 32 - 4,096

Default Value: none"
      ::= { frimSysConEntry 7 }


   frimSysConNegDataSize OBJECT-TYPE
      SYNTAX  INTEGER
      ACCESS  read-only
      STATUS  mandatory
      DESCRIPTION
"Indicates the data size of a frame negotiated at connection when the 
requested size cannot be accommodated. If the requested size can be 
accommodated, the requested and negotiated sizes are the same.

Range of Values: 32 - 4,096

Default Value: none"
      ::= { frimSysConEntry 8 }


   frimSysConNegSizeExceededFrames OBJECT-TYPE
      SYNTAX  Counter
      ACCESS  read-only
      STATUS  mandatory
      DESCRIPTION
"Indicates the number of frames passing across the connection that have 
exceeded the negotiated data size.

Range of Values: 0 - 4, 294, 967, 295

Default Value: none"
      ::= { frimSysConEntry 9 }

        
   frimSysConRefRangeEnd  OBJECT-TYPE
      SYNTAX  SubRef
      ACCESS  read-only
      STATUS  mandatory
      DESCRIPTION
"Indicates the upper limit of a range of identifiers that different users' 
traffic segments on the same outbound PVC can use to remain distinct from 
each other.

Range of Values: 0 - 255

Default Value: none"
      ::= { frimSysConEntry 10 }
END
