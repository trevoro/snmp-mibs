-- This is the MIB definition for the Mission Critical enterprise OIDs

         MISSION-CRITICAL-MIB DEFINITIONS ::= BEGIN

         IMPORTS
		DisplayString FROM SNMPv2-TC
                 Counter, TimeTicks, enterprises
                       FROM RFC1155-SMI
                 OBJECT-TYPE
                       FROM RFC-1212
--               DisplayString
--                     FROM RFC-1213
			TRAP-TYPE FROM RFC-1215;

-- the head of the MCS tree

         missionCritical         OBJECT IDENTIFIER ::= { enterprises 2349 }
         mcsCompanyInfo          OBJECT IDENTIFIER ::= { missionCritical 1 }
         mcsSoftware             OBJECT IDENTIFIER ::= { missionCritical 2 }
-- MCS Enterprise Event Manager Product ( formerly SeNTry )
         eemProductInfo          OBJECT IDENTIFIER ::= { mcsSoftware 1 }
-- MCS OnePoint Operations Manager Product
         omProductInfo          OBJECT IDENTIFIER ::=  { mcsSoftware 2 }
-- MCS Company Details

        ownershipDetails    OBJECT-TYPE
            SYNTAX    DisplayString (SIZE (1..255))
            ACCESS    read-only
            STATUS    mandatory
            DESCRIPTION
                "Details of the company providing this MIB"
            ::= { mcsCompanyInfo 1 }

        contactDetails    OBJECT-TYPE
            SYNTAX    DisplayString (SIZE (1..64))
            ACCESS    read-only
            STATUS    mandatory
            DESCRIPTION
                "Contact responsible for maintaining this MIB"
            ::= { mcsCompanyInfo 2 }


-- EEM ServiceInformation first

        eemService                 OBJECT IDENTIFIER ::= { eemProductInfo 1 }

        version OBJECT-TYPE
             SYNTAX  DisplayString (SIZE (1..16))
             ACCESS  read-only
             STATUS  mandatory
             DESCRIPTION
                 "The version of the EEM Agent running"
             ::= { eemService 1 }

         primaryServer OBJECT-TYPE 
             SYNTAX  DisplayString (SIZE (1..16))
             ACCESS  read-only
             STATUS  mandatory
             DESCRIPTION
                 "The Primary Server for this EEM Agent"
             ::= { eemService 2 }

         serviceState OBJECT-TYPE
             SYNTAX  INTEGER { up(1), down(2)} 
             ACCESS  read-only
             STATUS  mandatory
             DESCRIPTION
                 "State of the service.  Running is 1, stopped is 2"
             ::= { eemService 3 }

         serviceUpTime OBJECT-TYPE
             SYNTAX  TimeTicks
             ACCESS  read-only
             STATUS  mandatory
             DESCRIPTION
                 "No. of milliseconds since the service was started"
             ::= { eemService 4 }

         redTrapCount OBJECT-TYPE
             SYNTAX  Counter
             ACCESS  read-only
             STATUS  deprecated
             DESCRIPTION
                 "The number of red alert traps sent since the service was started"
             ::= { eemService 5 }

         orangeTrapCount OBJECT-TYPE
             SYNTAX  Counter
             ACCESS  read-only
             STATUS  deprecated
             DESCRIPTION
                 "The number of orange alert traps sent since the service was started"
             ::= { eemService 6 }

         amberTrapCount OBJECT-TYPE
             SYNTAX  Counter
             ACCESS  read-only
             STATUS  deprecated
             DESCRIPTION
                 "The number of yellow alert traps sent since the service was started"
             ::= { eemService 7 }

         blueTrapCount OBJECT-TYPE
             SYNTAX  Counter
             ACCESS  read-only
             STATUS  deprecated
             DESCRIPTION
                 "The number of blue alert traps sent since the service was started"
             ::= { eemService 8 }

         greenTrapCount OBJECT-TYPE
             SYNTAX  Counter
             ACCESS  read-only
             STATUS  deprecated
             DESCRIPTION
                 "The number of Green Alert Traps since the service was started"
             ::= { eemService 9 }

--
--  The information for the event EEM sent as a trap is held as an object identifier
--

        eemLastTrap                 OBJECT IDENTIFIER ::= { eemProductInfo 2 }

--
-- If configured to do so, the SeNTry Sender will send the following
-- enterprise-specific Trap when it encounters an alert.
--     100   red
--     200   orange
--     300   yellow
--     400   blue
--     500   green
-- These traps contains multiple varbinds which describe the
-- alert values.  Varbinds are EEMLastTrap items 2-8
-- 

         trapTime OBJECT-TYPE
             SYNTAX  TimeTicks
             ACCESS  read-only
             STATUS  deprecated
             DESCRIPTION
                 "Time of the last trap sent"
             ::= { eemLastTrap 1 }

         alertLevel OBJECT-TYPE
             SYNTAX  INTEGER {
                red(1), orange(2), yellow(3), blue(4), green(5) }
             ACCESS  read-only
             STATUS  mandatory
             DESCRIPTION
                 "Alert level of the last trap sent. red=1, orange=2, yellow=3, blue=4, green=5"
             ::= { eemLastTrap 2 }

         logType OBJECT-TYPE
             SYNTAX  INTEGER {
                ntevent(1), application(2), snmp(3), wbem(4),
                activemonitoring(5),performancemonitoring(6),
                timedevent(7),
                -- fill in others here
                eem(99)
                 }
             ACCESS  read-only
             STATUS  mandatory
             DESCRIPTION
                 "Log type generating the last trap sent. system=1,application=2,security=3 (fill in others here) EEM=99"
             ::= { eemLastTrap 3 }

         server OBJECT-TYPE
             SYNTAX  DisplayString (SIZE (1..255)) 
             ACCESS  read-only
             STATUS  mandatory
             DESCRIPTION
                 "Server generating  the last trap sent"
             ::= { eemLastTrap 4 }

         source OBJECT-TYPE
             SYNTAX  DisplayString (SIZE (1..255)) 
             ACCESS  read-only
             STATUS  mandatory
             DESCRIPTION
                 "Source generating  the last trap sent"
             ::= { eemLastTrap 5 }

         user OBJECT-TYPE
             SYNTAX  DisplayString (SIZE (1..255)) 
             ACCESS  read-only
             STATUS  mandatory
             DESCRIPTION
                 "User generating  the last trap sent"
             ::= { eemLastTrap 6 }

         eventID OBJECT-TYPE
             SYNTAX  INTEGER 
             ACCESS  read-only
             STATUS  mandatory
             DESCRIPTION
                 "Event ID of the last trap sent"
             ::= { eemLastTrap 7 }

         description OBJECT-TYPE
             SYNTAX  DisplayString (SIZE (1..1024)) 
             ACCESS  read-only
             STATUS  mandatory
             DESCRIPTION
                 "Text description of the last trap sent"
             ::= { eemLastTrap 8 }

         genericTrapNumber  OBJECT-TYPE
            SYNTAX    INTEGER
            ACCESS    read-only
            STATUS    mandatory
            DESCRIPTION
                "The generic trap number of the last trap sent"
            ::= { eemLastTrap 9 }

--
-- GenericTrapNumber value of SNMP_GENERICTRAP_ENTERSPECIFIC=6
-- is an enterprise-specific trap, which will be coupled with an
-- enterprise-specific Trap number as specified in SpecificTrapNumber
--
-- Setting this value causes the MCS Extention Agent to send the
-- appropriate SeNTry EEM generic trap.  This can be used to test
-- the trap functionality.  When sending an enterprise-specific trap,
-- be sure to set the SpecificTrapNumber and other EEMLastTrap values
-- as they will be varbinds.
-- 

        specificTrapNumber  OBJECT-TYPE
            SYNTAX    INTEGER
            ACCESS    read-only
            STATUS    mandatory
            DESCRIPTION
                "The user specific trap number of the last trap sent"
            ::= { eemLastTrap 10 }

--
-- Service start/stop traps
--

        serviceGoingDown		TRAP-TYPE
            ENTERPRISE	    eemProductInfo
--ERROR     VARIABLES       { }
            DESCRIPTION
                           "The SeNTry EEM Sender service is stopping."
            ::= 2

        serviceComingUp		TRAP-TYPE
            ENTERPRISE	    eemProductInfo
--ERROR     VARIABLES       { }
            DESCRIPTION
                           "The SeNTry EEM Sender service is starting."
            ::= 3

        gathererServiceGoingDown	TRAP-TYPE
            ENTERPRISE	    eemProductInfo
--ERROR     VARIABLES       { }
            DESCRIPTION
                           "The SeNTry EEM Gatherer service is stopping."
            ::= 4

        gathererServiceComingUp		TRAP-TYPE
            ENTERPRISE	    eemProductInfo
--ERROR     VARIABLES       { }
            DESCRIPTION
                           "The SeNTry EEM Gatherer service is starting."
            ::= 5

--
-- The following traps indicate that the Sender has encountered an alert
-- 

        eemRedAlert          		TRAP-TYPE
            ENTERPRISE	    eemProductInfo
            VARIABLES       { alertLevel,
                              logType, 
                              server,
                              source,
                              user,
                              eventID,
                              description
                            }
            DESCRIPTION
                           "A SeNTry EEM red alert has been generated."
            ::= 100

        eemOrangeAlert          		TRAP-TYPE
            ENTERPRISE	    eemProductInfo
            VARIABLES       { alertLevel,
                              logType, 
                              server,
                              source,
                              user,
                              eventID,
                              description
                            }
            DESCRIPTION
                           "A SeNTry EEM orange alert has been generated."
            ::= 200

        eemYellowAlert          		TRAP-TYPE
            ENTERPRISE	    eemProductInfo
            VARIABLES       { alertLevel,
                              logType, 
                              server,
                              source,
                              user,
                              eventID,
                              description
                            }
            DESCRIPTION
                           "A SeNTry EEM yellow alert has been generated."
            ::= 300

        eemBlueAlert          		TRAP-TYPE
            ENTERPRISE	    eemProductInfo
            VARIABLES       { alertLevel,
                              logType, 
                              server,
                              source,
                              user,
                              eventID,
                              description
                            }
            DESCRIPTION
                           "A SeNTry EEM blue alert has been generated."
            ::= 400

        eemGreenAlert          		TRAP-TYPE
            ENTERPRISE	    eemProductInfo
            VARIABLES       { alertLevel,
                              logType, 
                              server,
                              source,
                              user,
                              eventID,
                              description
                            }
            DESCRIPTION
                           "A SeNTry EEM green alert has been generated."
            ::= 500

-- OnePoint Operations Manager Service Information
--   nothing right now

        omService                 OBJECT IDENTIFIER ::= { omProductInfo 1 }

--
--  The information for the event OOM sent as a trap is held as an object identifier
--

        omLastTrap                 OBJECT IDENTIFIER ::= { omProductInfo 2 }


         omTrapTime OBJECT-TYPE
             SYNTAX  TimeTicks
             ACCESS  read-only
             STATUS  deprecated
             DESCRIPTION
                 "Time of the last trap sent."
             ::= { omLastTrap 1 }

         omAlertLevel OBJECT-TYPE
             SYNTAX  INTEGER
             ACCESS  read-only
             STATUS  mandatory
             DESCRIPTION
                 "Alert level of the last trap sent."
             ::= { omLastTrap 2 }

         omAlertLevelName OBJECT-TYPE
             SYNTAX  DisplayString (SIZE (0..255))
             ACCESS  read-only
             STATUS  mandatory
             DESCRIPTION
                 "A textual description of the alert level for the last trap sent."
             ::= { omLastTrap 3 }

         omServer OBJECT-TYPE
             SYNTAX  DisplayString (SIZE (0..255)) 
             ACCESS  read-only
             STATUS  mandatory
             DESCRIPTION
                 "Server generating the last trap sent."
             ::= { omLastTrap 4 }

         omSource OBJECT-TYPE
             SYNTAX  DisplayString (SIZE (0..255)) 
             ACCESS  read-only
             STATUS  mandatory
             DESCRIPTION
                 "Source generating the last trap sent."
             ::= { omLastTrap 5 }

         omOwner OBJECT-TYPE
             SYNTAX  DisplayString (SIZE (0..255)) 
             ACCESS  read-only
             STATUS  mandatory
             DESCRIPTION
                 "User generating  the last trap sent."
             ::= { omLastTrap 6 }

         omDescription OBJECT-TYPE
             SYNTAX  DisplayString (SIZE (0..1024)) 
             ACCESS  read-only
             STATUS  mandatory
             DESCRIPTION
                 "Text description of the last trap sent."
             ::= { omLastTrap 7 }

         omCustomField1 OBJECT-TYPE
             SYNTAX  DisplayString (SIZE (0..1024)) 
             ACCESS  read-only
             STATUS  mandatory
             DESCRIPTION
                 "Custom Field 1 defined by user"
             ::= { omLastTrap 8 }

         omCustomField2 OBJECT-TYPE
             SYNTAX  DisplayString (SIZE (0..1024)) 
             ACCESS  read-only
             STATUS  mandatory
             DESCRIPTION
                 "Custom Field 2 defined by user"
             ::= { omLastTrap 9 }

         omCustomField3 OBJECT-TYPE
             SYNTAX  DisplayString (SIZE (0..1024)) 
             ACCESS  read-only
             STATUS  mandatory
             DESCRIPTION
                 "Custom Field 3 defined by user"
             ::= { omLastTrap 10 }

         omCustomField4 OBJECT-TYPE
             SYNTAX  DisplayString (SIZE (0..1024)) 
             ACCESS  read-only
             STATUS  mandatory
             DESCRIPTION
                 "Custom Field 4 defined by user"
             ::= { omLastTrap 11 }

         omCustomField5 OBJECT-TYPE
             SYNTAX  DisplayString (SIZE (0..1024)) 
             ACCESS  read-only
             STATUS  mandatory
             DESCRIPTION
                 "Custom Field 5 defined by user"
             ::= { omLastTrap 12 }

         omAlertURL OBJECT-TYPE
             SYNTAX  DisplayString (SIZE (0..2048)) 
             ACCESS  read-only
             STATUS  mandatory
             DESCRIPTION
                 "URL used to view alert details"
             ::= { omLastTrap 13 }

         omGenericTrapNumber  OBJECT-TYPE
            SYNTAX    INTEGER
            ACCESS    read-only
            STATUS    mandatory
            DESCRIPTION
                "The generic trap number of the last trap sent."
            ::= { omLastTrap 14 }

--
-- GenericTrapNumber value of SNMP_GENERICTRAP_ENTERSPECIFIC=6
-- is an enterprise-specific trap, which will be coupled with an
-- enterprise-specific Trap number as specified in SpecificTrapNumber
--
-- Setting this value causes the MCS Extention Agent to send the
-- appropriate SeNTry EEM generic trap.  This can be used to test
-- the trap functionality.  When sending an enterprise-specific trap,
-- be sure to set the SpecificTrapNumber and other EEMLastTrap values
-- as they will be varbinds.
-- 

        omSpecificTrapNumber  OBJECT-TYPE
            SYNTAX    INTEGER
            ACCESS    read-only
            STATUS    mandatory
            DESCRIPTION
                "The user specific trap number of the last trap sent"
            ::= { omLastTrap 15 }

--
-- The following traps indicate are generated by the SNMP Response processor
-- There is one for each AlertLevel.  If we change the AlertLevels available
-- then the trap definitions need to change as well.
-- 

        omBlueAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Blue Alert has been generated."
            ::= 10

        omGreenAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Green Alert has been generated."
            ::= 20

        omYellowAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Yellow Alert has been generated."
            ::= 30

        omOrangeAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Orange Alert has been generated."
            ::= 40

        omRedCriticalErrorAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Critical Error Alert has been generated."
            ::= 50

        omRedSecurityBreachAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Security Breach Alert has been generated."
            ::= 60

        omRedServiceUnavailableAlert          		TRAP-TYPE
            ENTERPRISE	    omProductInfo
            VARIABLES       { omAlertLevel,
							  omAlertLevelName,
                              omServer,
                              omSource,
                              omOwner,
                              omDescription,
                              omCustomField1,
                              omCustomField2,
                              omCustomField3,
                              omCustomField4,
                              omCustomField5,
							  omAlertURL
                            }
            DESCRIPTION
                           "A OnePoint Operations Manager Service Unavailable Alert has been generated."
            ::= 70
END
