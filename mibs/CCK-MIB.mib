CCK-MIB DEFINITIONS ::= BEGIN

-- Title:      RADWARE
--             This Private MIB supports the Vgate
-- Version:    2.9
-- Date:       27 Oct 1995
-- By:         RMA (Radware MIB Authority)
-- E-mail:     US:            support@radware.com
--             International: support_int@radware.com
--
IMPORTS
       NetworkAddress,
       IpAddress,
       Counter,
       Gauge,
       enterprises
              FROM RFC1155-SMI
       OBJECT-TYPE
              FROM RFC-1212
       DisplayString,
       PhysAddress,
       ipAddrEntry
              FROM RFC1213-MIB
       TRAP-TYPE
                    FROM RFC-1215
       rsCCK
                    FROM RADWARE-MIB;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }




rsCCKElementTable OBJECT-TYPE
    SYNTAX SEQUENCE OF RsCCKElementEntry
    ACCESS not-accessible
    STATUS  mandatory
    DESCRIPTION
      "Table for the device's connectivity checks checked elements"
    ::=  {rsCCK 1}

rsCCKElementEntry OBJECT-TYPE
    SYNTAX RsCCKElementEntry
    ACCESS not-accessible
    STATUS  mandatory
    DESCRIPTION
       "the row definition for this table"
   INDEX { rsCCKElementId }
    ::=  {rsCCKElementTable 1}

RsCCKElementEntry ::= SEQUENCE {
  rsCCKElementId           INTEGER,
  rsCCKElementDescription  DisplayString,
  rsCCKElementGroup        DisplayString,
  rsCCKElementIsActive     INTEGER,
  rsCCKElementIsAvailable  INTEGER,
  rsCCKElementDftAddr      IpAddress,
  rsCCKElementRowStatus    RowStatus
  }

rsCCKElementId OBJECT-TYPE
    SYNTAX INTEGER
    ACCESS  read-only
    STATUS  mandatory
    DESCRIPTION
      "connectivity check's checked element ID"
    ::=  {rsCCKElementEntry 1}

rsCCKElementDescription OBJECT-TYPE
    SYNTAX  DisplayString (SIZE(0..80))
    ACCESS  read-only
    STATUS  mandatory
    DESCRIPTION
      "connectivity check's checked element description"
    ::=  {rsCCKElementEntry 2}

rsCCKElementGroup OBJECT-TYPE
    SYNTAX  DisplayString (SIZE(0..80))
    ACCESS  read-only
    STATUS  mandatory
    DESCRIPTION
      "connectivity check's checked element description"
    ::=  {rsCCKElementEntry 3}

rsCCKElementIsActive OBJECT-TYPE
    SYNTAX  INTEGER {
       active(1),
       inactive(2)
    }
    ACCESS  read-only
    STATUS  mandatory
    DESCRIPTION
      "connectivity check's checked element active status"
    ::=  {rsCCKElementEntry 4}

rsCCKElementIsAvailable OBJECT-TYPE
    SYNTAX  INTEGER {
       available(1),
       unavailable(2)
    }
    ACCESS  read-only
    STATUS  mandatory
    DESCRIPTION
      "connectivity check's checked element available status"
    ::=  {rsCCKElementEntry 5}

rsCCKElementDftAddr OBJECT-TYPE
    SYNTAX  IpAddress
    ACCESS read-only
    STATUS  mandatory
    DESCRIPTION
      "connectivity check's checked element's default ip address"
    ::=  {rsCCKElementEntry 6}

rsCCKElementRowStatus OBJECT-TYPE
    SYNTAX  RowStatus
    ACCESS  read-only
    STATUS  mandatory
    DESCRIPTION
      "connectivity check's checked element row status"
    ::=  {rsCCKElementEntry 7}


--------------------------
rsCCKHealthChkTable OBJECT-TYPE
    SYNTAX SEQUENCE OF RsCCKHealthChkEntry
    ACCESS not-accessible
    STATUS  mandatory
    DESCRIPTION
      "Table for the device's connectivity checks health checks"
    ::=  {rsCCK 2}

rsCCKHealthChkEntry OBJECT-TYPE
    SYNTAX RsCCKHealthChkEntry
    ACCESS not-accessible
    STATUS  mandatory
    DESCRIPTION
       "The row definition for this table"
   INDEX { rsCCKHealthChkName }
    ::=  {rsCCKHealthChkTable 1}

RsCCKHealthChkEntry ::= SEQUENCE {
  rsCCKHealthChkName        DisplayString,
  rsCCKHealthChkId          INTEGER,
  rsCCKHealthChkMethod      INTEGER,
  rsCCKHealthChkStatus      INTEGER,
  rsCCKHealthChkDstAddr     IpAddress,
  rsCCKHealthChkNextHop     IpAddress,
  rsCCKHealthChkDstPort     INTEGER,
  rsCCKHealthChkArguments   DisplayString,
  rsCCKHealthChkInterval    INTEGER,
  rsCCKHealthChkRetries     INTEGER,
  rsCCKHealthChkTimeout     INTEGER,
  rsCCKHealthChkRowStatus   RowStatus
  }

rsCCKHealthChkName OBJECT-TYPE
    SYNTAX  DisplayString (SIZE(0..80))
    ACCESS read-only
    STATUS  mandatory
    DESCRIPTION
      "connectivity check's health check name"
    ::=  {rsCCKHealthChkEntry 1}

rsCCKHealthChkId OBJECT-TYPE
    SYNTAX  INTEGER
    ACCESS read-write
    STATUS  mandatory
    DESCRIPTION
      "connectivity check's health check identifier"
    ::=  {rsCCKHealthChkEntry 2}

rsCCKHealthChkMethod OBJECT-TYPE
    SYNTAX  INTEGER
    ACCESS read-write
    STATUS  mandatory
    DESCRIPTION
      "connectivity check's health check method"
    ::=  {rsCCKHealthChkEntry 3}

rsCCKHealthChkStatus OBJECT-TYPE
    SYNTAX  INTEGER {
	unknown(1),
	failed(2),
	passed(3)
    }
    ACCESS read-only
    STATUS  mandatory
    DESCRIPTION
      "connectivity check's health check status"
    ::=  {rsCCKHealthChkEntry 4}

rsCCKHealthChkDstAddr OBJECT-TYPE
    SYNTAX  IpAddress
    ACCESS read-write
    STATUS  mandatory
    DESCRIPTION
      "connectivity check's health check destination address"
    ::=  {rsCCKHealthChkEntry 5}

rsCCKHealthChkNextHop OBJECT-TYPE
    SYNTAX  IpAddress
    ACCESS read-write
    STATUS  mandatory
    DESCRIPTION
      "connectivity check's health check next hop"
    ::=  {rsCCKHealthChkEntry 6}

rsCCKHealthChkDstPort OBJECT-TYPE
    SYNTAX  INTEGER
    ACCESS read-write
    STATUS  mandatory
    DESCRIPTION
      "connectivity check's health check destination port"
    ::=  {rsCCKHealthChkEntry 7}

rsCCKHealthChkArguments OBJECT-TYPE
    SYNTAX  DisplayString (SIZE(0..80))
    ACCESS read-write
    STATUS  mandatory
    DESCRIPTION
      "connectivity check's health check argument list"
    ::=  {rsCCKHealthChkEntry 8}

rsCCKHealthChkInterval OBJECT-TYPE
    SYNTAX  INTEGER
    ACCESS read-write
    STATUS  mandatory
    DESCRIPTION
      "connectivity check's health check interval in seconds"
    ::=  {rsCCKHealthChkEntry 9}

rsCCKHealthChkRetries OBJECT-TYPE
    SYNTAX  INTEGER
    ACCESS read-write
    STATUS  mandatory
    DESCRIPTION
      "connectivity check's health check number of retries before failing"
    ::=  {rsCCKHealthChkEntry 10}

rsCCKHealthChkTimeout OBJECT-TYPE
    SYNTAX  INTEGER
    ACCESS read-write
    STATUS  mandatory
    DESCRIPTION
      "connectivity check's health check timeout in seconds"
    ::=  {rsCCKHealthChkEntry 11}

rsCCKHealthChkRowStatus OBJECT-TYPE
    SYNTAX  RowStatus
    ACCESS  read-write
    STATUS  mandatory
    DESCRIPTION
      "connectivity check's health check row status"
    ::=  {rsCCKHealthChkEntry 12}


--------------------------
rsCCKChkBindingTable OBJECT-TYPE
    SYNTAX SEQUENCE OF RsCCKChkBindingEntry
    ACCESS not-accessible
    STATUS  mandatory
    DESCRIPTION
      "Table for health check - element bindings"
    ::=  {rsCCK 3}

rsCCKChkBindingEntry OBJECT-TYPE
    SYNTAX RsCCKChkBindingEntry
    ACCESS not-accessible
    STATUS  mandatory
    DESCRIPTION
       "The row definition for this table"
   INDEX { rsCCKChkBindingHealthChk, rsCCKChkBindingElement }
    ::=  {rsCCKChkBindingTable 1}

RsCCKChkBindingEntry ::= SEQUENCE {
  rsCCKChkBindingHealthChk   INTEGER,
  rsCCKChkBindingElement     INTEGER,
  rsCCKChkBindingGroup       INTEGER,
  rsCCKChkBindingMandatory   INTEGER,
  rsCCKChkBindingRowStatus   RowStatus
  }

rsCCKChkBindingHealthChk OBJECT-TYPE
    SYNTAX  INTEGER
    ACCESS read-only
    STATUS  mandatory
    DESCRIPTION
      "the bound health check id"
    ::=  {rsCCKChkBindingEntry 1}

rsCCKChkBindingElement OBJECT-TYPE
    SYNTAX  INTEGER
    ACCESS read-only
    STATUS  mandatory
    DESCRIPTION
      "the bound element id"
    ::=  {rsCCKChkBindingEntry 2}

rsCCKChkBindingGroup OBJECT-TYPE
    SYNTAX  INTEGER
    ACCESS read-write
    STATUS  mandatory
    DESCRIPTION
      "the bound element group"
    ::=  {rsCCKChkBindingEntry 3}

rsCCKChkBindingMandatory OBJECT-TYPE
     SYNTAX INTEGER {
       ismandatory(1),
       isnon-mandatory(2)
     }
     ACCESS read-write
     STATUS mandatory
     DESCRIPTION
      "connectivity check's binding relation - mandatory or not"
    ::=  {rsCCKChkBindingEntry 4}

rsCCKChkBindingRowStatus OBJECT-TYPE
    SYNTAX  RowStatus
    ACCESS  read-write
    STATUS  mandatory
    DESCRIPTION
      "health cehck's binding check row status"
    ::=  {rsCCKChkBindingEntry 5}

--------------------------
rsCCKChkMethodTable OBJECT-TYPE
    SYNTAX SEQUENCE OF RsCCKChkMethodEntry
    ACCESS not-accessible
    STATUS  mandatory
    DESCRIPTION
      "connectivity check's check methods table"
    ::=  {rsCCK 4}

rsCCKChkMethodEntry OBJECT-TYPE
    SYNTAX RsCCKChkMethodEntry
    ACCESS not-accessible
    STATUS  mandatory
    DESCRIPTION
       "The row definition for this table"
   INDEX { rsCCKChkMethodId }
    ::=  {rsCCKChkMethodTable 1}

RsCCKChkMethodEntry ::= SEQUENCE {
  rsCCKChkMethodId          INTEGER,
  rsCCKChkMethodDescription DisplayString,
  rsCCKChkMethodRowStatus   RowStatus
  }

rsCCKChkMethodId OBJECT-TYPE
    SYNTAX  INTEGER
    ACCESS read-only
    STATUS  mandatory
    DESCRIPTION
      "connectivity check's check method's id"
    ::=  {rsCCKChkMethodEntry 1}

rsCCKChkMethodDescription OBJECT-TYPE
    SYNTAX  DisplayString (SIZE(0..80))
    ACCESS read-only
    STATUS  mandatory
    DESCRIPTION
      "connectivity check's check method's description"
    ::=  {rsCCKChkMethodEntry 2}

rsCCKChkMethodRowStatus OBJECT-TYPE
    SYNTAX  RowStatus
    ACCESS  read-only
    STATUS  mandatory
    DESCRIPTION
      "connectivity check's check method's row status"
    ::=  {rsCCKChkMethodEntry 3}


--------------------------
rsCCKPktSequenceTable OBJECT-TYPE
    SYNTAX SEQUENCE OF RsCCKPktSequenceEntry
    ACCESS not-accessible
    STATUS  mandatory
    DESCRIPTION
      "connectivity check's packet sequence table"
    ::=  {rsCCK 5}

rsCCKPktSequenceEntry OBJECT-TYPE
    SYNTAX RsCCKPktSequenceEntry
    ACCESS not-accessible
    STATUS  mandatory
    DESCRIPTION
       "The row definition for this table"
   INDEX { rsCCKPktSequenceSeqId, rsCCKPktSequencePktId }
    ::=  {rsCCKPktSequenceTable 1}

RsCCKPktSequenceEntry ::= SEQUENCE {
  rsCCKPktSequenceSeqId       INTEGER,
  rsCCKPktSequencePktId       INTEGER,
  rsCCKPktSequenceType        INTEGER,
  rsCCKPktSequenceString      DisplayString,
  rsCCKPktSequenceDescription DisplayString,
  rsCCKPktSequenceRowStatus   RowStatus
  }

rsCCKPktSequenceSeqId OBJECT-TYPE
    SYNTAX  INTEGER
    ACCESS read-write
    STATUS  mandatory
    DESCRIPTION
      "packet sequence id"
    ::=  {rsCCKPktSequenceEntry 1}

rsCCKPktSequencePktId OBJECT-TYPE
    SYNTAX  INTEGER
    ACCESS read-write
    STATUS  mandatory
    DESCRIPTION
      "packet's sequence number within the packet sequence"
    ::=  {rsCCKPktSequenceEntry 2}

rsCCKPktSequenceType OBJECT-TYPE
    SYNTAX  INTEGER {
       send (1),
       receive(2)
    }
    ACCESS read-write
    STATUS  mandatory
    DESCRIPTION
      "packet type (send/receive)"
    ::=  {rsCCKPktSequenceEntry 3}

rsCCKPktSequenceString OBJECT-TYPE
    SYNTAX  DisplayString (SIZE(0..80))
    ACCESS read-write
    STATUS  mandatory
    DESCRIPTION
      "packet data (for send)/match pattern (for receive)"
    ::=  {rsCCKPktSequenceEntry 4}

rsCCKPktSequenceDescription OBJECT-TYPE
    SYNTAX  DisplayString (SIZE(0..80))
    ACCESS read-write
    STATUS  mandatory
    DESCRIPTION
      "packet description"
    ::=  {rsCCKPktSequenceEntry 5}

rsCCKPktSequenceRowStatus OBJECT-TYPE
    SYNTAX  RowStatus
    ACCESS  read-write
    STATUS  mandatory
    DESCRIPTION
      "connectivity check's packet sequence's row status"
    ::=  {rsCCKPktSequenceEntry 6}


--------------------------
rsCCKArgDelimiter  OBJECT-TYPE
    SYNTAX  DisplayString (SIZE(0..1))
    ACCESS  read-write
    STATUS  mandatory
    DESCRIPTION
      "Connectivity checks additional argument delimiter character"
    ::=  {rsCCK 6}


--------------------------
rsCCKNextElementId  OBJECT-TYPE
    SYNTAX  INTEGER
    ACCESS  read-write
    STATUS  mandatory
    DESCRIPTION
      "Connectivity checks next element id"
    ::=  {rsCCK 7}

--------------------------
rsCCKNextCheckId  OBJECT-TYPE
    SYNTAX  INTEGER
    ACCESS  read-write
    STATUS  mandatory
    DESCRIPTION
      "Connectivity checks next health check id"
    ::=  {rsCCK 8}

--------------------------
rsCCKStatus  OBJECT-TYPE
    SYNTAX  INTEGER {
       enable(1),
       disable(2)
    }
    ACCESS  read-write
    STATUS  mandatory
    DESCRIPTION
      "Connectivity checks enable switch"
    ::=  {rsCCK 9}

  END
