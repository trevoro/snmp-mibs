--			Ascend mibvdslnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBVDSLNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibvdslNetworkProfile  OBJECT IDENTIFIER ::= { configuration 9}

	-- The mibvdslNetworkProfile table
	--
	-- This table contains parameters for the mibvdslNetworkProfile profile
	--

    mibvdslNetworkProfileTable	OBJECT-TYPE
	SYNTAX		SEQUENCE OF MibvdslNetworkProfileEntry
	ACCESS		not-accessible
	STATUS		mandatory
	DESCRIPTION	"A list of mibvdslNetworkProfile profile entries."
	::= { mibvdslNetworkProfile 1 }

    mibvdslNetworkProfileEntry	OBJECT-TYPE
	SYNTAX		MibvdslNetworkProfileEntry
	ACCESS		not-accessible
	STATUS		mandatory
	DESCRIPTION	"A mibvdslNetworkProfile entry containing objects that
			 maps to the parameters of mibvdslNetworkProfile profile."
	INDEX		{ vdslNetworkProfile-Shelf-o, vdslNetworkProfile-Slot-o, vdslNetworkProfile-Item-o }
	::= { mibvdslNetworkProfileTable 1 }

    MibvdslNetworkProfileEntry ::=
	SEQUENCE {
	    vdslNetworkProfile-Shelf-o
		INTEGER,
	    vdslNetworkProfile-Slot-o
		INTEGER,
	    vdslNetworkProfile-Item-o
		INTEGER,
	    vdslNetworkProfile-Name
		DisplayString,
	    vdslNetworkProfile-PhysicalAddress-Shelf
		INTEGER,
	    vdslNetworkProfile-PhysicalAddress-Slot
		INTEGER,
	    vdslNetworkProfile-PhysicalAddress-ItemNumber
		INTEGER,
	    vdslNetworkProfile-Enabled
		INTEGER,
	    vdslNetworkProfile-SparingMode
		INTEGER,
	    vdslNetworkProfile-IgnoreLineup
		INTEGER,
	    vdslNetworkProfile-LineConfig-NailedGroup
		INTEGER,
	    vdslNetworkProfile-LineConfig-VpSwitchingVpi
		INTEGER,
	    vdslNetworkProfile-LineConfig-UpStreamFixedRate
		INTEGER,
	    vdslNetworkProfile-LineConfig-DownStreamFixedRate
		INTEGER,
	    vdslNetworkProfile-LineConfig-ConfigLoopback
		INTEGER,
	    vdslNetworkProfile-LineConfig-PsdValue
		INTEGER,
	    vdslNetworkProfile-LineConfig-LinkStatecmd
		INTEGER,
	    vdslNetworkProfile-Action-o
		INTEGER
	}

    vdslNetworkProfile-Shelf-o	OBJECT-TYPE
	SYNTAX	INTEGER
	ACCESS	read-only
	STATUS	mandatory
	DESCRIPTION	""
	::= { mibvdslNetworkProfileEntry 1 }

    vdslNetworkProfile-Slot-o	OBJECT-TYPE
	SYNTAX	INTEGER
	ACCESS	read-only
	STATUS	mandatory
	DESCRIPTION	""
	::= { mibvdslNetworkProfileEntry 2 }

    vdslNetworkProfile-Item-o	OBJECT-TYPE
	SYNTAX	INTEGER
	ACCESS	read-only
	STATUS	mandatory
	DESCRIPTION	""
	::= { mibvdslNetworkProfileEntry 3 }

    vdslNetworkProfile-Name	OBJECT-TYPE
	SYNTAX	DisplayString
	ACCESS	read-write
	STATUS	mandatory
	DESCRIPTION	"For future use. The current design does not use the name field but instead references Vdsl lines by the physical address; we may in the future support referencing Vdsl lines by name as well as by address. The name consists of a null terminated ascii string supplied by the user; it defaults to the ascii form of the Vdsl line physical address."
	::= { mibvdslNetworkProfileEntry 4 }

    vdslNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibvdslNetworkProfileEntry 11 }

    vdslNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibvdslNetworkProfileEntry 12 }

    vdslNetworkProfile-PhysicalAddress-ItemNumber	OBJECT-TYPE
	SYNTAX	INTEGER
	ACCESS	read-write
	STATUS	mandatory
	DESCRIPTION	"A number that specifies an addressable entity within the context of shelf and slot."
	::= { mibvdslNetworkProfileEntry 13 }

    vdslNetworkProfile-Enabled	OBJECT-TYPE
	SYNTAX	INTEGER {
		    no (1),
		    yes (2)
		}
	ACCESS	read-write
	STATUS	mandatory
	DESCRIPTION	"TRUE if the line is enabled, otherwise FALSE."
	::= { mibvdslNetworkProfileEntry 16 }

    vdslNetworkProfile-SparingMode	OBJECT-TYPE
	SYNTAX	INTEGER {
		    inactive (1),
		    manual (2),
		    automatic (3)
		}
	ACCESS	read-write
	STATUS	mandatory
	DESCRIPTION	"Port sparing operational mode for this port."
	::= { mibvdslNetworkProfileEntry 17 }

    vdslNetworkProfile-IgnoreLineup	OBJECT-TYPE
	SYNTAX	INTEGER {
		    systemDefined (1),
		    no (2),
		    yes (3)
		}
	ACCESS	read-write
	STATUS	mandatory
	DESCRIPTION	"Ignore line up value for this port."
	::= { mibvdslNetworkProfileEntry 18 }

    vdslNetworkProfile-LineConfig-NailedGroup	OBJECT-TYPE
	SYNTAX	INTEGER
	ACCESS	read-write
	STATUS	mandatory
	DESCRIPTION	"A number that identifies the this unique physical DSL line."
	::= { mibvdslNetworkProfileEntry 19 }

    vdslNetworkProfile-LineConfig-VpSwitchingVpi	OBJECT-TYPE
	SYNTAX	INTEGER
	ACCESS	read-write
	STATUS	mandatory
	DESCRIPTION	"The Vpi to be used for the VP switching. Rest of the VPIs within valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY."
	::= { mibvdslNetworkProfileEntry 20 }

    vdslNetworkProfile-LineConfig-UpStreamFixedRate	OBJECT-TYPE
	SYNTAX	INTEGER {
		    n-1206667 (1),
		    n-965333 (2),
		    n-1930667 (3),
		    n-3861333 (4)
		}
	ACCESS	read-write
	STATUS	mandatory
	DESCRIPTION	"The following Up/Down stream rate relationships are supported: (0.965Mbps/19.306Mbps); (1.930Mbps/11.463Mbps); (3.861Mbps/11.463Mbps); (3.861Mbps/15.626Mbps). Up Stream range: 0.965Mbps - 3.861Mbps."
	::= { mibvdslNetworkProfileEntry 22 }

    vdslNetworkProfile-LineConfig-DownStreamFixedRate	OBJECT-TYPE
	SYNTAX	INTEGER {
		    n-1206667 (1),
		    n-11463333 (2),
		    n-15626333 (3),
		    n-19306667 (4)
		}
	ACCESS	read-write
	STATUS	mandatory
	DESCRIPTION	"The following Up/Down stream rate relationships are supported: (0.965Mbps/19.306Mbps); (1.930Mbps/11.463Mbps); (3.861Mbps/11.463Mbps); (3.861Mbps/15.626Mbps). Down Stream range: 11.463Mbps - 15.626Mbps."
	::= { mibvdslNetworkProfileEntry 23 }

    vdslNetworkProfile-LineConfig-ConfigLoopback	OBJECT-TYPE
	SYNTAX	INTEGER {
		    disable (1),
		    digital (2),
		    analog (3)
		}
	ACCESS	read-write
	STATUS	mandatory
	DESCRIPTION	"Configuration of different modem loopbacks."
	::= { mibvdslNetworkProfileEntry 24 }

    vdslNetworkProfile-LineConfig-PsdValue	OBJECT-TYPE
	SYNTAX	INTEGER {
		    n-53dbm (1),
		    n-60dbm (2)
		}
	ACCESS	read-write
	STATUS	mandatory
	DESCRIPTION	"Configuration of PSD parameter. It defines the power that is allowed to be sent to the line."
	::= { mibvdslNetworkProfileEntry 25 }

    vdslNetworkProfile-LineConfig-LinkStatecmd	OBJECT-TYPE
	SYNTAX	INTEGER {
		    autoConnectCmd (16),
		    disconnectState (1),
		    connectState (2),
		    quietState (3),
		    idleReqState (4),
		    backToServState (5),
		    changeIdleParamState (6),
		    changeWarmStartParamState (7),
		    changeCurrentParamState (8)
		}
	ACCESS	read-write
	STATUS	mandatory
	DESCRIPTION	"Sets the link connect state. Use this to control status of the VDSL link connect state machine. The auto-connect-cmd will train modem up to the final service. All the other commands are used to manualy operate the VDSL link connect state machine."
	::= { mibvdslNetworkProfileEntry 26 }

    vdslNetworkProfile-Action-o	OBJECT-TYPE
	SYNTAX	INTEGER {
		    noAction (1),
		    createProfile (2),
		    deleteProfile (3)
		}
	ACCESS	read-write
	STATUS	mandatory
	DESCRIPTION	""
	::= { mibvdslNetworkProfileEntry 14 }

END
