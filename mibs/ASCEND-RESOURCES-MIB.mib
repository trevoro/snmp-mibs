-- $Id: resource.mib,v 29.3 1999/03/15 23:54:04 mkrasnic Exp $
--
--			Access Resources MIB
--
--			Ascend Communications, Inc
--			1701 Harbor Bay Pkwy
--			Alameda, CA 94502
--			+1 510 769 6001
--			info@ascend.com
--
--		Copyright (c) 1993-1998 Ascend Communications, Inc.
--		All rights reserved.
--
--	Overview:
--
--	Resources MIB is part of the Ascend Enterprise MIB, it reports
--	current availability of access resources such as modems, HDLC
--	channels, and slave Digital Signal Processors (DSPs) in the system.
--
-- 11 Aug 98	kn	Initially created
-- 19 Feb 99	kn	Remove reference to CHASSIS-MIB in text description.
-- 12 Mar 99	mk	Corrected a spelling error in SYNTAX resourceCallType.


ASCEND-RESOURCES-MIB DEFINITIONS ::= BEGIN

    IMPORTS
	Counter
	    FROM RFC1155-SMI
        OBJECT-TYPE
            FROM RFC-1212
        resourcesGroup
            FROM ASCEND-MIB;

    --
    -- resourceUsageTable
    --
    -- This table reports current usage of resources in a particular slot.
    --

    resourceUsageTable	OBJECT-TYPE
	SYNTAX		SEQUENCE OF ResourceUsageEntry
	ACCESS		not-accessible
	STATUS		mandatory
	DESCRIPTION	"A list of slot entries that report their
			resources usage."
	::= { resourcesGroup 1 }

    resourceUsageEntry	OBJECT-TYPE
	SYNTAX		ResourceUsageEntry
	ACCESS		not-accessible
	STATUS		mandatory
	DESCRIPTION	"A list of entries that contain information about 
			resource usage such as available,busy, suspect, 
			disabled, dead."
	INDEX		{ usageSlotIndex }
	::= { resourceUsageTable 1 }

    ResourceUsageEntry ::=
	SEQUENCE {
            usageSlotIndex
		INTEGER,
	    usageAvailable
		INTEGER,
            usageBusy
                INTEGER,
	    usageSuspect
		INTEGER,
	    usageDisabled
		INTEGER,
            usageDead
                INTEGER
	}

    usageSlotIndex	OBJECT-TYPE
	SYNTAX		INTEGER
	ACCESS		read-only
	STATUS		mandatory
	DESCRIPTION	"A unique value for each slot in the system.
			The slot identified by a particular value of this 
			index is the same slot as identified by the same
			value of slotIndex."
	::= { resourceUsageEntry 1 }

    usageAvailable      OBJECT-TYPE
	SYNTAX		INTEGER
	ACCESS		read-only
	STATUS		mandatory
	DESCRIPTION	"The number of resources in this slot that are 
			available to be assigned for incoming/outgoing calls."
	::= { resourceUsageEntry 2 }

    usageBusy	        OBJECT-TYPE
	SYNTAX		INTEGER
	ACCESS		read-only
	STATUS		mandatory
	DESCRIPTION	"The number of resources in this slot that are 
			currently being assigned for incoming/outgoing calls."
	::= { resourceUsageEntry 3 }

    usageSuspect	OBJECT-TYPE
	SYNTAX		INTEGER
	ACCESS		read-only
	STATUS		mandatory
	DESCRIPTION	"The number of resources in this slot that are in 
			suspect state.  They are tried after resources 
			in the available pool are exhausted."
	::= { resourceUsageEntry 4 }

    usageDisabled	OBJECT-TYPE
	SYNTAX		INTEGER
	ACCESS		read-only
	STATUS		mandatory
	DESCRIPTION	"The number of resources in this slot that are 
			administratively disabled. Resources in disabled 
			pool will not be assigned for incoming/outgoing 
			calls."
	::= { resourceUsageEntry 5 }

    usageDead	        OBJECT-TYPE
	SYNTAX		INTEGER
	ACCESS		read-only
	STATUS		mandatory
	DESCRIPTION	"The number of resources in this slot taht are in fault
			state.  Resources in dead pool will not be assigned
			for incoming/outgoing calls."
	::= { resourceUsageEntry 6 }


    --
    -- resourceTable
    --
    -- resourceTable describes properties of each individual terminating
    -- resource in the system.   A terminating resource  could be a modem, 
    -- an HDLC channel, or a DSP channel.
    --

    resourceTable	OBJECT-TYPE
	SYNTAX		SEQUENCE OF ResourceEntry
	ACCESS		not-accessible
	STATUS		mandatory
	DESCRIPTION	"A list of individual terminating resource items."
	::= { resourcesGroup 2 }

    resourceEntry	OBJECT-TYPE
	SYNTAX		ResourceEntry
	ACCESS		not-accessible
	STATUS		mandatory
	DESCRIPTION	"Entry holding information about an individual
			item properties."
	INDEX		{ resourceSlotIndex, resourcePortIndex }
	::= { resourceTable 1 }

    ResourceEntry ::=
	SEQUENCE {
	    resourceSlotIndex
		INTEGER,
	    resourcePortIndex
		INTEGER,
	    resourceConfig
		INTEGER,
	    resourceState
		INTEGER,
	    resourceCallType
		INTEGER,
	    resourceCallDirection
		INTEGER,
	    resourceUsedCounts
		Counter,
	    resourceBadCounts
		Counter,
	    resourceLast32
		INTEGER
	}

    resourceSlotIndex	OBJECT-TYPE
	SYNTAX		INTEGER
	ACCESS		read-only
	STATUS		mandatory
	DESCRIPTION	"A unique value for each slot in the system.
			The slot identified by a particular value of this 
			index is the same slot as identified by the same
			value of slotIndex."
	::= { resourceEntry 1 }

    resourcePortIndex	OBJECT-TYPE
	SYNTAX		INTEGER
	ACCESS		read-only
	STATUS		mandatory
	DESCRIPTION	"A unique value for each port/channel in each slot."
	::= { resourceEntry 2 }

    resourceConfig	OBJECT-TYPE
	SYNTAX		INTEGER {
                            other(1),		-- none of the following
                            enable(2),
                            disable(3),
                            disableAndChannel(4)
			}
	ACCESS		read-write
	STATUS		mandatory
	DESCRIPTION	"The resource item  configuration state. SETs are
			allowed only if the corresponding slot card 
			adminstation state is enabled.
			Note: 
			disableAndChannel(4) is the same as disable(3) and 
			also disable one b-channel on a T1 line.  This 
			option is only available for modems in T1 network."
	::= { resourceEntry 3 }

    resourceState	OBJECT-TYPE
	SYNTAX		INTEGER {
			    notApplicable(1),	-- item is non-existent
                            other(2),		-- none of the following
			    failedPost(3),
                            idle(4),
                            online(5),
			    virtualConnect(6),
                            disabled(7),
			    disabledChan(8),
			    reserved(9)
			}
	ACCESS		read-only
	STATUS		mandatory
	DESCRIPTION	"The state of this resource item."
	::= { resourceEntry 4 }

    resourceCallType	OBJECT-TYPE
	SYNTAX		INTEGER {
			    notApplicable(1),	
			    other(2),		-- none of the following
			    async(3),
			    sync(4),
			    isdnSync(5),
			    isdnAsyncV120(6),
			    isdnAsyncV110(7),
			    virtual(8),
			    isdnAsyncV32(9),
			    isdnAsyncVdsp(10)
			}
	ACCESS		read-only
	STATUS		mandatory
	DESCRIPTION	"Type of calls is being served.
			If the resourceState variable is not online(5) or
			virtualConnect(6), this variable returns 
			notApplicable(1).
			If the resourceState variable is online(5) or
			virtualConnect(6) and the type of call is not
			defined, this variable returns other(2) which
			indicates an unknown call type."
	::= { resourceEntry 5 }

    resourceCallDirection OBJECT-TYPE
	SYNTAX		INTEGER {
			    notApplicable(1),	
                            other(2),		-- none of the following
                            originated(3),	-- dialed out
                            answered(4)		-- answered call
			}
	ACCESS		read-only
	STATUS		mandatory
	DESCRIPTION	"Call direction associated with this item.
			If the resourceState variable is not online(5) or
			virtualConnect(6), this variable returns 
			notApplicable(1).
			If the resourceState variable is online(5) or
			virtualConnect(6) and it is neither outgoing call
			nor incoming call, this variable returns none(2) 
			which indicates an unknown call direction."
	::= { resourceEntry 6 }

    resourceUsedCounts	OBJECT-TYPE
	SYNTAX		Counter
	ACCESS		read-only
	STATUS		mandatory
	DESCRIPTION	"The number of times this resource was utilized."
	::= { resourceEntry 7 }

    resourceBadCounts	OBJECT-TYPE
	SYNTAX		Counter
	ACCESS		read-only
	STATUS		mandatory
	DESCRIPTION	"The number of times this resource failed."
	::= { resourceEntry 8 }

    resourceLast32	OBJECT-TYPE
	SYNTAX		INTEGER
	ACCESS		read-only
	STATUS		mandatory
	DESCRIPTION	"A 32-bit mask of the last 32 times this resource 
			was tried. A '0' in the bit position indicates 
			failure while a '1' indicates success."
	::= { resourceEntry 9 }

END
