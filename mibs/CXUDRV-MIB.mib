CXUDRV-MIB DEFINITIONS ::= BEGIN


IMPORTS
	Counter         FROM RFC1155-SMI
	OBJECT-TYPE     FROM RFC-1212
	cxUDrv          FROM CXProduct-SMI;

--  U-Interface Transceiver Driver Configuration Table

--  The table describing:
--      statistics available for monitoring any ISDN U-Interface daughter card

udrvTable OBJECT-TYPE
	SYNTAX  SEQUENCE OF UdrvEntry
	ACCESS  not-accessible
	STATUS  mandatory
	DESCRIPTION
"A table containing statistics of the U interface transceiver driver."
	::= { cxUDrv 10 }


	udrvEntry OBJECT-TYPE
		SYNTAX  UdrvEntry
		ACCESS  not-accessible
		STATUS  mandatory
		DESCRIPTION
"The parameters for a specific ISDN U-Interface daughter card."
		INDEX { udrvSlotNumberIndex }
		::= { udrvTable 1 }


	UdrvEntry ::=
		SEQUENCE {
-- Parameters
			udrvSlotNumberIndex                     INTEGER,
-- Control
			udrvClearStat                           INTEGER,
			udrvPortUp                              INTEGER,
			udrvPortReset                           INTEGER,
-- Status
			udrvPortStatus                          INTEGER,
-- Statistics           
			udrvFebe                                Counter,
			udrvNebe                                Counter,
			udrvActivation                          Counter,
			udrvDeactivation                                Counter,
			udrvTransition                          Counter
			}


	udrvSlotNumberIndex OBJECT-TYPE
		SYNTAX  INTEGER (1..6)
		ACCESS  read-only
		STATUS  mandatory
		DESCRIPTION
"Indicates the row containing objects for controlling (or monitoring) an 
I/O card in the CX900.

Range of Values: 1-6

Default Value: none"
		::= { udrvEntry 1 }
	

	udrvClearStat OBJECT-TYPE
		SYNTAX  INTEGER
		ACCESS  write-only
		STATUS  mandatory
		DESCRIPTION
"Clears the statistics counter for this I/O card.

Options:

clearStats : clears statistics

Default value: none"
		::= { udrvEntry 20}


	udrvPortUp OBJECT-TYPE
		SYNTAX  INTEGER
		ACCESS  write-only
		STATUS  mandatory
		DESCRIPTION
"Brings up the port on this I/O card.

Options:

portUp: forces port into 'up' state

Default Value: none"
		::= { udrvEntry 21}


	udrvPortReset OBJECT-TYPE
		SYNTAX  INTEGER
		ACCESS  write-only
		STATUS  mandatory
		DESCRIPTION
"Resets the port on this I/O card.

Options:
portReset: forces port to reset

Default Value: none"
		::= { udrvEntry 23}


	udrvPortStatus OBJECT-TYPE
		SYNTAX  INTEGER{
					portDown                        (1),
					portUp                          (2)
				}
		ACCESS  read-only
		STATUS  mandatory
		DESCRIPTION
"Indicates the status of the port on this I/O card.

Options:
portDown (1): port is down

portUp (2): port is up

Default Value: none"
		::= { udrvEntry 30 }


	udrvFebe OBJECT-TYPE
		SYNTAX  Counter
		ACCESS  read-only
		STATUS  mandatory
		DESCRIPTION
"Indicates the number of far-end block errors received by this I/O card.

Range of Values: 0-65, 535

Default Value: none"
		::= { udrvEntry 40 }


	udrvNebe OBJECT-TYPE
		SYNTAX  Counter
		ACCESS  read-only
		STATUS  mandatory
		DESCRIPTION
"Indicates the number of near-end block errors received by this I/O card.

Range of Values: 0-65, 535

Default Value: none"
		::= { udrvEntry 41 }


	udrvActivation OBJECT-TYPE
		SYNTAX  Counter
		ACCESS  read-only
		STATUS  mandatory
		DESCRIPTION
"Indicates the number of activation requests received by this I/O card.

Range of Values: 0-4, 294, 967, 295

Default Value: none"
		::= { udrvEntry 42 }


	udrvDeactivation OBJECT-TYPE
		SYNTAX  Counter
		ACCESS  read-only
		STATUS  mandatory
		DESCRIPTION
"Indicates the number of deactivation requests received by this I/O card.

Range of Values: 0-4, 294, 967, 295

Default Value: none"
		::= { udrvEntry 43 }


	udrvTransition OBJECT-TYPE
		SYNTAX  Counter
		ACCESS  read-only
		STATUS  mandatory
		DESCRIPTION
"Indicates the number of down-to-up or up-to-down transitions that have 
occurred on this I/O card's port.

Range of Values: 0-4, 294, 967, 295

Default Value: none"
		::= { udrvEntry 44 }
END
