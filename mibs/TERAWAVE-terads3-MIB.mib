TERAWAVE-terads3-MIB DEFINITIONS ::= BEGIN
        -- Created by sml2mib compiler 
        IMPORTS

 enterprises,  OBJECT-TYPE,  Counter,  Gauge,  TimeTicks
        FROM RFC1155-SMI
		  Gauge32 FROM SNMPv2-SMI;

terawave OBJECT IDENTIFIER ::=  { enterprises 4513 }

teraCDS3Group OBJECT IDENTIFIER ::=  { terawave 8 }

     -- teraDSX3ConfigTable

teraDSX3ConfigTable OBJECT-TYPE
     SYNTAX SEQUENCE OF TeraDSX3ConfigTableEntryType
     ACCESS not-accessible
     STATUS mandatory
     DESCRIPTION
          " table teraDSX3ConfigTable"
     ::= { teraCDS3Group 1 }

teraDSX3ConfigTableEntry OBJECT-TYPE
          SYNTAX TeraDSX3ConfigTableEntryType
          ACCESS not-accessible
          STATUS mandatory
          DESCRIPTION
               " table entry teraDSX3ConfigTableEntry "
          INDEX {                   teraDs3LineIndex }
     ::= { teraDSX3ConfigTable 1 }

TeraDSX3ConfigTableEntryType ::= SEQUENCE {
          teraDs3LineIndex   
             INTEGER,
          teraDs3OOFCriteria   
             INTEGER,
          teraDs3AISBitsChkSchm   
             INTEGER,
          teraDs3RcvFEACCriteria   
             INTEGER,
          teraDs3FEACLoopCheck   
             INTEGER,
          teraDs3DS1FarEndLoopStatus   
             INTEGER,
          teraDs3DS1NearEndLoopStatus   
             INTEGER,
          teraDs37DayTotalTimeElapsed   
             INTEGER (1..86400),
          teraDs3ExtendValidTotalIntervals   
             INTEGER (0..7),
          teraDs3ExtendInvalidTotalIntervals   
             INTEGER (0..7)
}

teraDs3LineIndex OBJECT-TYPE
          SYNTAX INTEGER
          ACCESS read-only
          STATUS mandatory
          DESCRIPTION
               ""
          ::= { teraDSX3ConfigTableEntry 1 }

teraDs3OOFCriteria OBJECT-TYPE
          SYNTAX INTEGER
                  {
                  bits3Of8(1),
                  bits3Of16(2)
                  }
          ACCESS read-write
          STATUS mandatory
          DESCRIPTION
               ""
          ::= { teraDSX3ConfigTableEntry 2 }

teraDs3AISBitsChkSchm OBJECT-TYPE
          SYNTAX INTEGER
                  {
                  checkCbits(1),
                  ignoreBits(2)
                  }
          ACCESS read-write
          STATUS mandatory
          DESCRIPTION
               ""
          ::= { teraDSX3ConfigTableEntry 3 }

teraDs3RcvFEACCriteria OBJECT-TYPE
          SYNTAX INTEGER
                  {
                  fEACCodes4Of5(1),
                  fEACCodes8Of16(2)
                  }
          ACCESS read-write
          STATUS mandatory
          DESCRIPTION
               ""
          ::= { teraDSX3ConfigTableEntry 4 }

teraDs3FEACLoopCheck OBJECT-TYPE
          SYNTAX INTEGER
                  {
                  disable(1),
                  enable(2)
                  }
          ACCESS read-write
          STATUS mandatory
          DESCRIPTION
               ""
          ::= { teraDSX3ConfigTableEntry 5 }

teraDs3DS1FarEndLoopStatus OBJECT-TYPE
          SYNTAX INTEGER
                  {
                  none(0),
                  dS1-1(1),
                  dS1-2(2),
                  dS1-3(3),
                  dS1-4(4),
                  dS1-5(5),
                  dS1-6(6),
                  dS1-7(7),
                  dS1-8(8),
                  dS1-9(9),
                  dS1-10(10),
                  dS1-11(11),
                  dS1-12(12),
                  dS1-13(13),
                  dS1-14(14),
                  dS1-15(15),
                  dS1-16(16),
                  dS1-17(17),
                  dS1-18(18),
                  dS1-19(19),
                  dS1-20(20),
                  dS1-21(21),
                  dS1-22(22),
                  dS1-23(23),
                  dS1-24(24),
                  dS1-25(25),
                  dS1-26(26),
                  dS1-27(27),
                  dS1-28(28),
                  all-DS1(29)
                  }
          ACCESS read-only
          STATUS mandatory
          DESCRIPTION
               ""
          ::= { teraDSX3ConfigTableEntry 6 }

teraDs3DS1NearEndLoopStatus OBJECT-TYPE
          SYNTAX INTEGER
                  {
                  none(0),
                  dS1-1(1),
                  dS1-2(2),
                  dS1-3(3),
                  dS1-4(4),
                  dS1-5(5),
                  dS1-6(6),
                  dS1-7(7),
                  dS1-8(8),
                  dS1-9(9),
                  dS1-10(10),
                  dS1-11(11),
                  dS1-12(12),
                  dS1-13(13),
                  dS1-14(14),
                  dS1-15(15),
                  dS1-16(16),
                  dS1-17(17),
                  dS1-18(18),
                  dS1-19(19),
                  dS1-20(20),
                  dS1-21(21),
                  dS1-22(22),
                  dS1-23(23),
                  dS1-24(24),
                  dS1-25(25),
                  dS1-26(26),
                  dS1-27(27),
                  dS1-28(28),
                  all-DS1(29)
                  }
          ACCESS read-only
          STATUS mandatory
          DESCRIPTION
               ""
          ::= { teraDSX3ConfigTableEntry 7 }

teraDs37DayTotalTimeElapsed OBJECT-TYPE
          SYNTAX INTEGER (1..86400)
          ACCESS read-only
          STATUS mandatory
          DESCRIPTION
               ""
          ::= { teraDSX3ConfigTableEntry 8 }

teraDs3ExtendValidTotalIntervals OBJECT-TYPE
          SYNTAX INTEGER (0..7)
          ACCESS read-only
          STATUS mandatory
          DESCRIPTION
               ""
          ::= { teraDSX3ConfigTableEntry 9 }

teraDs3ExtendInvalidTotalIntervals OBJECT-TYPE
          SYNTAX INTEGER (0..7)
          ACCESS read-only
          STATUS mandatory
          DESCRIPTION
               ""
          ::= { teraDSX3ConfigTableEntry 10 }

     -- teraDSX37DayTotalTable

teraDSX37DayTotalTable OBJECT-TYPE
     SYNTAX SEQUENCE OF TeraDSX37DayTotalTableEntryType
     ACCESS not-accessible
     STATUS mandatory
     DESCRIPTION
          " table teraDSX37DayTotalTable"
     ::= { teraCDS3Group 2 }

teraDSX37DayTotalTableEntry OBJECT-TYPE
          SYNTAX TeraDSX37DayTotalTableEntryType
          ACCESS not-accessible
          STATUS mandatory
          DESCRIPTION
               " table entry teraDSX37DayTotalTableEntry "
          INDEX {                   teraDS37DayTotalIndex,                  teraDS37DayTotalNumber }
     ::= { teraDSX37DayTotalTable 1 }

TeraDSX37DayTotalTableEntryType ::= SEQUENCE {
          teraDS37DayTotalIndex   
             INTEGER,
          teraDS37DayTotalNumber   
             INTEGER (1..7),
          teraDS37DayTotalPESs   
             Gauge32,
          teraDS37DayTotalPSESs   
             Gauge32,
          teraDS37DayTotalSEFSs   
             Gauge32,
          teraDS37DayTotalUASs   
             Gauge32,
          teraDS37DayTotalLCVs   
             Gauge32,
          teraDS37DayTotalPCVs   
             Gauge32,
          teraDS37DayTotalLESs   
             Gauge32,
          teraDS37DayTotalCCVs   
             Gauge32,
          teraDS37DayTotalCESs   
             Gauge32,
          teraDS37DayTotalCSESs   
             Gauge32,
          teraDS37DayTotalValidData   
             INTEGER
}

teraDS37DayTotalIndex OBJECT-TYPE
          SYNTAX INTEGER
          ACCESS read-only
          STATUS mandatory
          DESCRIPTION
               ""
          ::= { teraDSX37DayTotalTableEntry 1 }

teraDS37DayTotalNumber OBJECT-TYPE
          SYNTAX INTEGER (1..7)
          ACCESS read-only
          STATUS mandatory
          DESCRIPTION
               ""
          ::= { teraDSX37DayTotalTableEntry 2 }

teraDS37DayTotalPESs OBJECT-TYPE
          SYNTAX Gauge32
          ACCESS read-only
          STATUS mandatory
          DESCRIPTION
               ""
          ::= { teraDSX37DayTotalTableEntry 3 }

teraDS37DayTotalPSESs OBJECT-TYPE
          SYNTAX Gauge32
          ACCESS read-only
          STATUS mandatory
          DESCRIPTION
               ""
          ::= { teraDSX37DayTotalTableEntry 4 }

teraDS37DayTotalSEFSs OBJECT-TYPE
          SYNTAX Gauge32
          ACCESS read-only
          STATUS mandatory
          DESCRIPTION
               ""
          ::= { teraDSX37DayTotalTableEntry 5 }

teraDS37DayTotalUASs OBJECT-TYPE
          SYNTAX Gauge32
          ACCESS read-only
          STATUS mandatory
          DESCRIPTION
               ""
          ::= { teraDSX37DayTotalTableEntry 6 }

teraDS37DayTotalLCVs OBJECT-TYPE
          SYNTAX Gauge32
          ACCESS read-only
          STATUS mandatory
          DESCRIPTION
               ""
          ::= { teraDSX37DayTotalTableEntry 7 }

teraDS37DayTotalPCVs OBJECT-TYPE
          SYNTAX Gauge32
          ACCESS read-only
          STATUS mandatory
          DESCRIPTION
               ""
          ::= { teraDSX37DayTotalTableEntry 8 }

teraDS37DayTotalLESs OBJECT-TYPE
          SYNTAX Gauge32
          ACCESS read-only
          STATUS mandatory
          DESCRIPTION
               ""
          ::= { teraDSX37DayTotalTableEntry 9 }

teraDS37DayTotalCCVs OBJECT-TYPE
          SYNTAX Gauge32
          ACCESS read-only
          STATUS mandatory
          DESCRIPTION
               ""
          ::= { teraDSX37DayTotalTableEntry 10 }

teraDS37DayTotalCESs OBJECT-TYPE
          SYNTAX Gauge32
          ACCESS read-only
          STATUS mandatory
          DESCRIPTION
               ""
          ::= { teraDSX37DayTotalTableEntry 11 }

teraDS37DayTotalCSESs OBJECT-TYPE
          SYNTAX Gauge32
          ACCESS read-only
          STATUS mandatory
          DESCRIPTION
               ""
          ::= { teraDSX37DayTotalTableEntry 12 }

teraDS37DayTotalValidData OBJECT-TYPE
          SYNTAX INTEGER
          ACCESS read-only
          STATUS mandatory
          DESCRIPTION
               ""
          ::= { teraDSX37DayTotalTableEntry 13 }

     -- teraDSX3FarEnd7DayTotalTable

teraDSX3FarEnd7DayTotalTable OBJECT-TYPE
     SYNTAX SEQUENCE OF TeraDSX3FarEnd7DayTotalTableEntryType
     ACCESS not-accessible
     STATUS mandatory
     DESCRIPTION
          " table teraDSX3FarEnd7DayTotalTable"
     ::= { teraCDS3Group 3 }

teraDSX3FarEnd7DayTotalTableEntry OBJECT-TYPE
          SYNTAX TeraDSX3FarEnd7DayTotalTableEntryType
          ACCESS not-accessible
          STATUS mandatory
          DESCRIPTION
               " table entry teraDSX3FarEnd7DayTotalTableEntry "
          INDEX {                   teraDSX3FarEnd7DayTotalIndex,                  teraDS3FarEnd7DayTotalNumber }
     ::= { teraDSX3FarEnd7DayTotalTable 1 }

TeraDSX3FarEnd7DayTotalTableEntryType ::= SEQUENCE {
          teraDSX3FarEnd7DayTotalIndex   
             INTEGER,
          teraDS3FarEnd7DayTotalNumber   
             INTEGER (1..7),
          teraDS3FarEnd7DayTotalCESs   
             Gauge32,
          teraDS3FarEnd7DayTotalCSESs   
             Gauge32,
          teraDS3FarEnd7DayTotalCCVs   
             Gauge32,
          teraDS3FarEnd7DayTotalUASs   
             Gauge32,
          teraDS3FarEnd7DayTotalValidData   
             INTEGER
}

teraDSX3FarEnd7DayTotalIndex OBJECT-TYPE
          SYNTAX INTEGER
          ACCESS read-only
          STATUS mandatory
          DESCRIPTION
               ""
          ::= { teraDSX3FarEnd7DayTotalTableEntry 1 }

teraDS3FarEnd7DayTotalNumber OBJECT-TYPE
          SYNTAX INTEGER (1..7)
          ACCESS read-only
          STATUS mandatory
          DESCRIPTION
               ""
          ::= { teraDSX3FarEnd7DayTotalTableEntry 2 }

teraDS3FarEnd7DayTotalCESs OBJECT-TYPE
          SYNTAX Gauge32
          ACCESS read-only
          STATUS mandatory
          DESCRIPTION
               ""
          ::= { teraDSX3FarEnd7DayTotalTableEntry 3 }

teraDS3FarEnd7DayTotalCSESs OBJECT-TYPE
          SYNTAX Gauge32
          ACCESS read-only
          STATUS mandatory
          DESCRIPTION
               ""
          ::= { teraDSX3FarEnd7DayTotalTableEntry 4 }

teraDS3FarEnd7DayTotalCCVs OBJECT-TYPE
          SYNTAX Gauge32
          ACCESS read-only
          STATUS mandatory
          DESCRIPTION
               ""
          ::= { teraDSX3FarEnd7DayTotalTableEntry 5 }

teraDS3FarEnd7DayTotalUASs OBJECT-TYPE
          SYNTAX Gauge32
          ACCESS read-only
          STATUS mandatory
          DESCRIPTION
               ""
          ::= { teraDSX3FarEnd7DayTotalTableEntry 6 }

teraDS3FarEnd7DayTotalValidData OBJECT-TYPE
          SYNTAX INTEGER
          ACCESS read-only
          STATUS mandatory
          DESCRIPTION
               ""
          ::= { teraDSX3FarEnd7DayTotalTableEntry 7 }

     -- teradsx3CurrentTable

teradsx3CurrentTable OBJECT-TYPE
     SYNTAX SEQUENCE OF Teradsx3CurrentTableEntryType
     ACCESS not-accessible
     STATUS mandatory
     DESCRIPTION
          " table teradsx3CurrentTable"
     ::= { teraCDS3Group 4 }

teradsx3CurrentTableEntry OBJECT-TYPE
          SYNTAX Teradsx3CurrentTableEntryType
          ACCESS not-accessible
          STATUS mandatory
          DESCRIPTION
               " table entry teradsx3CurrentTableEntry "
          INDEX {                   teradsx3CurrentIndex }
     ::= { teradsx3CurrentTable 1 }

Teradsx3CurrentTableEntryType ::= SEQUENCE {
          teradsx3CurrentIndex   
             INTEGER,
          teradsx3ESB-L   
             INTEGER,
          teradsx3LOSS-L   
             Gauge32,
          teradsx3ESB-P   
             Gauge32,
          teradsx3SAS-P   
             Gauge32,
          teradsx3AISS-P   
             Gauge32,
          teradsx3UASP-P   
             Gauge32,
          teradsx3ESCP-PFE   
             Gauge32,
          teradsx3ESBCP-PFE   
             Gauge32,
          teradsx3SASCP-PFE   
             Gauge32
}

teradsx3CurrentIndex OBJECT-TYPE
          SYNTAX INTEGER
          ACCESS read-only
          STATUS mandatory
          DESCRIPTION
               ""
          ::= { teradsx3CurrentTableEntry 1 }

teradsx3ESB-L OBJECT-TYPE
          SYNTAX INTEGER
          ACCESS read-only
          STATUS mandatory
          DESCRIPTION
               ""
          ::= { teradsx3CurrentTableEntry 2 }

teradsx3LOSS-L OBJECT-TYPE
          SYNTAX Gauge32
          ACCESS read-only
          STATUS mandatory
          DESCRIPTION
               ""
          ::= { teradsx3CurrentTableEntry 3 }

teradsx3ESB-P OBJECT-TYPE
          SYNTAX Gauge32
          ACCESS read-only
          STATUS mandatory
          DESCRIPTION
               ""
          ::= { teradsx3CurrentTableEntry 4 }

teradsx3SAS-P OBJECT-TYPE
          SYNTAX Gauge32
          ACCESS read-only
          STATUS mandatory
          DESCRIPTION
               ""
          ::= { teradsx3CurrentTableEntry 5 }

teradsx3AISS-P OBJECT-TYPE
          SYNTAX Gauge32
          ACCESS read-only
          STATUS mandatory
          DESCRIPTION
               ""
          ::= { teradsx3CurrentTableEntry 6 }

teradsx3UASP-P OBJECT-TYPE
          SYNTAX Gauge32
          ACCESS read-only
          STATUS mandatory
          DESCRIPTION
               ""
          ::= { teradsx3CurrentTableEntry 7 }

teradsx3ESCP-PFE OBJECT-TYPE
          SYNTAX Gauge32
          ACCESS read-only
          STATUS mandatory
          DESCRIPTION
               ""
          ::= { teradsx3CurrentTableEntry 8 }

teradsx3ESBCP-PFE OBJECT-TYPE
          SYNTAX Gauge32
          ACCESS read-only
          STATUS mandatory
          DESCRIPTION
               ""
          ::= { teradsx3CurrentTableEntry 9 }

teradsx3SASCP-PFE OBJECT-TYPE
          SYNTAX Gauge32
          ACCESS read-only
          STATUS mandatory
          DESCRIPTION
               ""
          ::= { teradsx3CurrentTableEntry 10 }

     -- teradsx3IntervalTable

teradsx3IntervalTable OBJECT-TYPE
     SYNTAX SEQUENCE OF Teradsx3IntervalTableEntryType
     ACCESS not-accessible
     STATUS mandatory
     DESCRIPTION
          " table teradsx3IntervalTable"
     ::= { teraCDS3Group 5 }

teradsx3IntervalTableEntry OBJECT-TYPE
          SYNTAX Teradsx3IntervalTableEntryType
          ACCESS not-accessible
          STATUS mandatory
          DESCRIPTION
               " table entry teradsx3IntervalTableEntry "
          INDEX {                   terads3IntervalIndex,                  terads3IntervalNumber }
     ::= { teradsx3IntervalTable 1 }

Teradsx3IntervalTableEntryType ::= SEQUENCE {
          terads3IntervalIndex   
             INTEGER,
          terads3IntervalNumber   
             INTEGER (1..96),
          terads3Intervalteradsx3ESB-L   
             Gauge32,
          terads3Intervalteradsx3LOSS-L   
             Gauge32,
          terads3Intervalteradsx3ESB-P   
             Gauge32,
          terads3Intervalteradsx3SAS-P   
             Gauge32,
          terads3Intervalteradsx3AISS-P   
             Gauge32,
          terads3Intervalteradsx3UASP-P   
             Gauge32,
          terads3Intervalteradsx3ESCP-PFE   
             Gauge32,
          terads3Intervalteradsx3ESBCP-PFE   
             Gauge32,
          terads3Intervalteradsx3SASCP-PFE   
             Gauge32,
          terads3IntervalValidData   
             INTEGER
}

terads3IntervalIndex OBJECT-TYPE
          SYNTAX INTEGER
          ACCESS read-only
          STATUS mandatory
          DESCRIPTION
               ""
          ::= { teradsx3IntervalTableEntry 1 }

terads3IntervalNumber OBJECT-TYPE
          SYNTAX INTEGER (1..96)
          ACCESS read-only
          STATUS mandatory
          DESCRIPTION
               ""
          ::= { teradsx3IntervalTableEntry 2 }

terads3Intervalteradsx3ESB-L OBJECT-TYPE
          SYNTAX Gauge32
          ACCESS read-only
          STATUS mandatory
          DESCRIPTION
               ""
          ::= { teradsx3IntervalTableEntry 3 }

terads3Intervalteradsx3LOSS-L OBJECT-TYPE
          SYNTAX Gauge32
          ACCESS read-only
          STATUS mandatory
          DESCRIPTION
               ""
          ::= { teradsx3IntervalTableEntry 4 }

terads3Intervalteradsx3ESB-P OBJECT-TYPE
          SYNTAX Gauge32
          ACCESS read-only
          STATUS mandatory
          DESCRIPTION
               ""
          ::= { teradsx3IntervalTableEntry 5 }

terads3Intervalteradsx3SAS-P OBJECT-TYPE
          SYNTAX Gauge32
          ACCESS read-only
          STATUS mandatory
          DESCRIPTION
               ""
          ::= { teradsx3IntervalTableEntry 6 }

terads3Intervalteradsx3AISS-P OBJECT-TYPE
          SYNTAX Gauge32
          ACCESS read-only
          STATUS mandatory
          DESCRIPTION
               ""
          ::= { teradsx3IntervalTableEntry 7 }

terads3Intervalteradsx3UASP-P OBJECT-TYPE
          SYNTAX Gauge32
          ACCESS read-only
          STATUS mandatory
          DESCRIPTION
               ""
          ::= { teradsx3IntervalTableEntry 8 }

terads3Intervalteradsx3ESCP-PFE OBJECT-TYPE
          SYNTAX Gauge32
          ACCESS read-only
          STATUS mandatory
          DESCRIPTION
               ""
          ::= { teradsx3IntervalTableEntry 9 }

terads3Intervalteradsx3ESBCP-PFE OBJECT-TYPE
          SYNTAX Gauge32
          ACCESS read-only
          STATUS mandatory
          DESCRIPTION
               ""
          ::= { teradsx3IntervalTableEntry 10 }

terads3Intervalteradsx3SASCP-PFE OBJECT-TYPE
          SYNTAX Gauge32
          ACCESS read-only
          STATUS mandatory
          DESCRIPTION
               ""
          ::= { teradsx3IntervalTableEntry 11 }

terads3IntervalValidData OBJECT-TYPE
          SYNTAX INTEGER
          ACCESS read-only
          STATUS mandatory
          DESCRIPTION
               ""
          ::= { teradsx3IntervalTableEntry 12 }

     -- teradsx3TotalTable

teradsx3TotalTable OBJECT-TYPE
     SYNTAX SEQUENCE OF Teradsx3TotalTableEntryType
     ACCESS not-accessible
     STATUS mandatory
     DESCRIPTION
          " table teradsx3TotalTable"
     ::= { teraCDS3Group 6 }

teradsx3TotalTableEntry OBJECT-TYPE
          SYNTAX Teradsx3TotalTableEntryType
          ACCESS not-accessible
          STATUS mandatory
          DESCRIPTION
               " table entry teradsx3TotalTableEntry "
          INDEX {                   terads3TotalIndex }
     ::= { teradsx3TotalTable 1 }

Teradsx3TotalTableEntryType ::= SEQUENCE {
          terads3TotalIndex   
             INTEGER,
          terads3Totalteradsx3ESB-L   
             Gauge32,
          terads3Totalteradsx3LOSS-L   
             Gauge32,
          terads3Totalteradsx3ESB-P   
             Gauge32,
          terads3Totalteradsx3SAS-P   
             Gauge32,
          terads3Totalteradsx3AISS-P   
             Gauge32,
          terads3Totalteradsx3UASP-P   
             Gauge32,
          terads3Totalteradsx3ESCP-PFE   
             Gauge32,
          terads3Totalteradsx3ESBCP-PFE   
             Gauge32,
          terads3Totalteradsx3SASCP-PFE   
             Gauge32,
          terads3TotalPerfStat   
             INTEGER
}

terads3TotalIndex OBJECT-TYPE
          SYNTAX INTEGER
          ACCESS read-only
          STATUS mandatory
          DESCRIPTION
               ""
          ::= { teradsx3TotalTableEntry 1 }

terads3Totalteradsx3ESB-L OBJECT-TYPE
          SYNTAX Gauge32
          ACCESS read-only
          STATUS mandatory
          DESCRIPTION
               ""
          ::= { teradsx3TotalTableEntry 2 }

terads3Totalteradsx3LOSS-L OBJECT-TYPE
          SYNTAX Gauge32
          ACCESS read-only
          STATUS mandatory
          DESCRIPTION
               ""
          ::= { teradsx3TotalTableEntry 3 }

terads3Totalteradsx3ESB-P OBJECT-TYPE
          SYNTAX Gauge32
          ACCESS read-only
          STATUS mandatory
          DESCRIPTION
               ""
          ::= { teradsx3TotalTableEntry 4 }

terads3Totalteradsx3SAS-P OBJECT-TYPE
          SYNTAX Gauge32
          ACCESS read-only
          STATUS mandatory
          DESCRIPTION
               ""
          ::= { teradsx3TotalTableEntry 5 }

terads3Totalteradsx3AISS-P OBJECT-TYPE
          SYNTAX Gauge32
          ACCESS read-only
          STATUS mandatory
          DESCRIPTION
               ""
          ::= { teradsx3TotalTableEntry 6 }

terads3Totalteradsx3UASP-P OBJECT-TYPE
          SYNTAX Gauge32
          ACCESS read-only
          STATUS mandatory
          DESCRIPTION
               ""
          ::= { teradsx3TotalTableEntry 7 }

terads3Totalteradsx3ESCP-PFE OBJECT-TYPE
          SYNTAX Gauge32
          ACCESS read-only
          STATUS mandatory
          DESCRIPTION
               ""
          ::= { teradsx3TotalTableEntry 8 }

terads3Totalteradsx3ESBCP-PFE OBJECT-TYPE
          SYNTAX Gauge32
          ACCESS read-only
          STATUS mandatory
          DESCRIPTION
               ""
          ::= { teradsx3TotalTableEntry 9 }

terads3Totalteradsx3SASCP-PFE OBJECT-TYPE
          SYNTAX Gauge32
          ACCESS read-only
          STATUS mandatory
          DESCRIPTION
               ""
          ::= { teradsx3TotalTableEntry 10 }

terads3TotalPerfStat OBJECT-TYPE
          SYNTAX INTEGER
                  {
                  ok(1),
                  clear(2)
                  }
          ACCESS read-write
          STATUS mandatory
          DESCRIPTION
               ""
          ::= { teradsx3TotalTableEntry 11 }

     -- teraDSX3tera7DayTotalTable

teraDSX3tera7DayTotalTable OBJECT-TYPE
     SYNTAX SEQUENCE OF TeraDSX3tera7DayTotalTableEntryType
     ACCESS not-accessible
     STATUS mandatory
     DESCRIPTION
          " table teraDSX3tera7DayTotalTable"
     ::= { teraCDS3Group 7 }

teraDSX3tera7DayTotalTableEntry OBJECT-TYPE
          SYNTAX TeraDSX3tera7DayTotalTableEntryType
          ACCESS not-accessible
          STATUS mandatory
          DESCRIPTION
               " table entry teraDSX3tera7DayTotalTableEntry "
          INDEX {                   teraDSX3tera7DayTotalIndex,                  teraDS3tera7DayTotalNumber }
     ::= { teraDSX3tera7DayTotalTable 1 }

TeraDSX3tera7DayTotalTableEntryType ::= SEQUENCE {
          teraDSX3tera7DayTotalIndex   
             INTEGER,
          teraDS3tera7DayTotalNumber   
             INTEGER (1..7),
          teraDS3tera7DayTotalteradsx3ESB-L   
             Gauge32,
          teraDS3tera7DayTotalteradsx3LOSS-L   
             Gauge32,
          teraDS3tera7DayTotalteradsx3ESB-P   
             Gauge32,
          teraDS3tera7DayTotalteradsx3SAS-P   
             Gauge32,
          teraDS3tera7DayTotalteradsx3AISS-P   
             Gauge32,
          teraDS3tera7DayTotalteradsx3UASP-P   
             Gauge32,
          teraDS3tera7DayTotalteradsx3ESCP-PFE   
             Gauge32,
          teraDS3tera7DayTotalteradsx3ESBCP-PFE   
             Gauge32,
          teraDS3tera7DayTotalteradsx3SASCP-PFE   
             Gauge32,
          teraDS3tera7DayTotalValidData   
             INTEGER
}

teraDSX3tera7DayTotalIndex OBJECT-TYPE
          SYNTAX INTEGER
          ACCESS read-only
          STATUS mandatory
          DESCRIPTION
               ""
          ::= { teraDSX3tera7DayTotalTableEntry 1 }

teraDS3tera7DayTotalNumber OBJECT-TYPE
          SYNTAX INTEGER (1..7)
          ACCESS read-only
          STATUS mandatory
          DESCRIPTION
               ""
          ::= { teraDSX3tera7DayTotalTableEntry 2 }

teraDS3tera7DayTotalteradsx3ESB-L OBJECT-TYPE
          SYNTAX Gauge32
          ACCESS read-only
          STATUS mandatory
          DESCRIPTION
               ""
          ::= { teraDSX3tera7DayTotalTableEntry 3 }

teraDS3tera7DayTotalteradsx3LOSS-L OBJECT-TYPE
          SYNTAX Gauge32
          ACCESS read-only
          STATUS mandatory
          DESCRIPTION
               ""
          ::= { teraDSX3tera7DayTotalTableEntry 4 }

teraDS3tera7DayTotalteradsx3ESB-P OBJECT-TYPE
          SYNTAX Gauge32
          ACCESS read-only
          STATUS mandatory
          DESCRIPTION
               ""
          ::= { teraDSX3tera7DayTotalTableEntry 5 }

teraDS3tera7DayTotalteradsx3SAS-P OBJECT-TYPE
          SYNTAX Gauge32
          ACCESS read-only
          STATUS mandatory
          DESCRIPTION
               ""
          ::= { teraDSX3tera7DayTotalTableEntry 6 }

teraDS3tera7DayTotalteradsx3AISS-P OBJECT-TYPE
          SYNTAX Gauge32
          ACCESS read-only
          STATUS mandatory
          DESCRIPTION
               ""
          ::= { teraDSX3tera7DayTotalTableEntry 7 }

teraDS3tera7DayTotalteradsx3UASP-P OBJECT-TYPE
          SYNTAX Gauge32
          ACCESS read-only
          STATUS mandatory
          DESCRIPTION
               ""
          ::= { teraDSX3tera7DayTotalTableEntry 8 }

teraDS3tera7DayTotalteradsx3ESCP-PFE OBJECT-TYPE
          SYNTAX Gauge32
          ACCESS read-only
          STATUS mandatory
          DESCRIPTION
               ""
          ::= { teraDSX3tera7DayTotalTableEntry 9 }

teraDS3tera7DayTotalteradsx3ESBCP-PFE OBJECT-TYPE
          SYNTAX Gauge32
          ACCESS read-only
          STATUS mandatory
          DESCRIPTION
               ""
          ::= { teraDSX3tera7DayTotalTableEntry 10 }

teraDS3tera7DayTotalteradsx3SASCP-PFE OBJECT-TYPE
          SYNTAX Gauge32
          ACCESS read-only
          STATUS mandatory
          DESCRIPTION
               ""
          ::= { teraDSX3tera7DayTotalTableEntry 11 }

teraDS3tera7DayTotalValidData OBJECT-TYPE
          SYNTAX INTEGER
          ACCESS read-only
          STATUS mandatory
          DESCRIPTION
               ""
          ::= { teraDSX3tera7DayTotalTableEntry 12 }

END
