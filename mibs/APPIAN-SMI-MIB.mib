--
--      Title:  Appian-MIB-SMI
--
--      Date:   11/1/99
--
--      Description:
--
--      This file contains the top level SMI definitions for the Appian 
--      Communications Inc. Enterprise MIB.  The MIB is designed to support a 
--      variety of Appian specific hardware platforms.
--
--      The purpose of this MIB definition file is two fold, a) to provide a
--      start for the Appian MIB hierarchy  and b) to provide a place to record
--      any Appian specific Macros.
--
--      Please follow the rules of MIB obsolescence and deprecation  when adding
--      or deleting MIB attributes, leafs or nodes.  AppianVista relies on the
--      structure not changing.
--
--      When considering adding a new node to the tree, please make sure to
--      to add it under the appropriate node categories below.  When there is
--      confusions, check with the author of this document.
--
--      If you have a well known type you wish to publish in our enterpris
--      tree, this is the place to define it.  These are well known types that
--      currently are not defined in a standard, but are common in Appian 
--      specific MIBs.  Enums are a great place to be defined here.  Please
--      only define common types which would be reused in sub-modules.  If its
--      common, but only to your portion of the tree, define in your root
--      level module.
--
--      Note: Each node in the tree below represents a unique ASN.1 source
--      file in our system.  Please preserve the number space and when adding
--      new nodes, try and keep them in separate files, explicitly named.
--
-- 
APPIAN-SMI-MIB DEFINITIONS ::= BEGIN

    IMPORTS
        TEXTUAL-CONVENTION, DisplayString                   FROM SNMPv2-TC
        
        enterprises, MODULE-IDENTITY, TimeTicks             FROM SNMPv2-SMI;

            
appian  MODULE-IDENTITY
    LAST-UPDATED    "0001270000Z"
    ORGANIZATION    "Appian Communications, Inc."
    CONTACT-INFO    "Douglas Theriault"

    DESCRIPTION     "Appian Communications Enterprise MIB Definitions"
                        
    REVISION        "0001270000Z"

    DESCRIPTION     "Draft engineering version.  Not for release."

    ::= { enterprises 2785 }
    
    --
    -- Appian Specific Textual Conventions, global common types
    --
    
    --
    -- Appian Admin Status Column
    --
    AcAdminStatus   ::= TEXTUAL-CONVENTION
    
    STATUS          current
    DESCRIPTION
        "It triggers the specified administrative action on a set of scalars or on
        a row in a table.
        
        activate(1) triggers the activation of a set of scalars or a row in a table.
          
        delete(2) triggers the deletion of a row in a table.
        
        inactivate(3) inactivates a set of scalars or a row in a table.
        
        The remaining enumerations listed below are for the generation of Traps
        used by the Appian SNMP Agent Simulator.  These enumerations are not 
        expected to be included when we ship our final enterprise MIB."
    
    SYNTAX  INTEGER {
                activate(1),
                delete(2),
                inactivate(3)
            }

    --
    -- Appian Operational Status Column
    --
    AcOpStatus      ::= TEXTUAL-CONVENTION
    
    STATUS          current
    DESCRIPTION
        "It describes the operability of a resource. Permitted values are:
        operational: the resource is partially or fully operable and available
        for use.
        offline: the resource requires a routine operation to be performed to
        place it online and make it available for use.
        initializing: the resource is undergoing initialization.
        selfTesting: the resource is undergoing a self-test procedure.
        provisioning: the resource is being provisioned.
        upgrading: the resource software, if applicable, is being upgraded.
        maintenance: the resource is currently under maintenance.
        standby: the resource is not providing service, but will take over the
        role of an associated operational resource if the latter fails.
        shuttingDown: the resource is in a termination phase.
        failed: the resource has an internal fault that prevents it from operating.
        hw-not-present: the resource has no hardware to provide service."
    SYNTAX  INTEGER {
                operational(1),
                offline(2),
                initializing(3),
                selfTesting(4),
                provisioning(5),
                upgrading(6),
                maintenance(7),
                standby(8),
                shuttingDown(9),
                failed(10),
                hw-not-present(11)
            }

    --
    -- Appian OSAP Slot Number
    --            
    AcSlotNumber    ::= TEXTUAL-CONVENTION
    
    STATUS  current
    DESCRIPTION
                "A physical slot number in an OSAP Chassis which is within the range
                of (1..16).  Or the value 100 to indicate an Ethernet port group."
    SYNTAX  INTEGER {
        ac0(0),
        ac1(1),
        ac2(2),
        ac3(3),
        ac4(4),
        ac5(5),
        ac6(6),
        ac7(7),
        ac8(8),
        ac9(9),
        ac10(10),
        ac11(11),
        ac12(12),
        ac13(13),
        ac14(14),
        ac15(15),
        ac16(16),
        ac100(100)
        }        


    --
    -- Appian OSAP Port Number
    --    
    AcPortNumber    ::= TEXTUAL-CONVENTION
    
    STATUS  current
    DESCRIPTION
                "A physical port number on a media i/o card which is within the range
                of (1..8)."
    SYNTAX  INTEGER (1..8)

    --
    -- Appian Last Change 
    --    
    AcLastChange    ::= TEXTUAL-CONVENTION

    STATUS  current
    DESCRIPTION
                "The last 'time' an entity is modified. The entity could be a single
                MIB object or a MIB table. For a table, modification to any objects
                in the table would apply.
                The last time is defined as the sysUpTime when the modification took
                place. The modification could be triggered by management systems,
                CLI commands, parameter synchronization and distribution protocols,
                and others. If there were no modification, it should have the value
                of 0."
    SYNTAX  TimeTicks

    --
    -- Appian MIB version stamp
    --
    AcMibVersion  ::= TEXTUAL-CONVENTION
    
    STATUS  current
    DESCRIPTION
        "An ASCII string which identifies the major and minor version of the Appian
        MIB currently supported by the active switch control processor.  The format
        for this string is '<major>.<minor>'. The string will support up to 9 
        characters in length.  The major.minor numbers are derived from the active
        switch controllers software version."
        
    SYNTAX  DisplayString (SIZE(0..9))

    --
    -- Appian Software Version Stamp
    --
    AcSwVersion  ::= TEXTUAL-CONVENTION
    
    STATUS  current
    DESCRIPTION
        "An ASCII string which identifies the major and minor version of the Appian
        software running on one or more modules within the chassis.  The format
        for this string is '<major>.<minor>.<patch>.<build>'. The string will support
        up to 19 characters in length."
        
    SYNTAX  DisplayString (SIZE(0..19))
    

    --
    -- Appian Node ID
    --    
    AcNodeId    ::= TEXTUAL-CONVENTION
    
    STATUS  current
    DESCRIPTION
        "A unique value assigned to each OSAP in a ring by the EMS system.  This is used
        in our MIB tables as part of an instance identifier so we can enable management
        of the ring as a single entity from any OSAP within the ring."
    SYNTAX  INTEGER (1..255)


    --
    -- Appian Ring ID
    --    
    AcRingId    ::= TEXTUAL-CONVENTION
    
    STATUS  current
    DESCRIPTION
        "A unique value assigned to each Appian Ring by the EMS system.  This is used
        in trap messages to help manage the event messages generated by a network of
        Appian Rings.  The number is rather large, and with a max of 16 or so nodes
        per ring gives an upper bound to the network to be approx. 1*10^6 nodes."
    SYNTAX  INTEGER (1..65535)
    

    --
    -- Appian Node Architecture
    --    
    AcNodeArchitecture    ::= TEXTUAL-CONVENTION
    
    STATUS  current
    DESCRIPTION
        "This value describes where this node is in the network.  The value
        describes the network/ring from the perspective of the node, not the
        network.
        * unconfigured: The node architecture has not been configured.
        * linear: The node is in a linear configuration.
        * ring: The node is part of a ring.
        * ring-interconnect: The node is in a ring and is used as the interconnect.
        * drop-and-continue-pri: The node is the primary in a drop and continue architecture.
        * drop-and-continue-sec: The node is the secondary in a drop and continue architecture.
        * subtending-pri: The node is the primary in a subtending ring architecture.
        * subtending-sec: The node is the secondary in a subtending ring architecture."
    SYNTAX  INTEGER {
        unconfigured(0),
        linear(1),
        ring(2),
        ring-interconnect(3),
        drop-and-continue-pri(4),
        drop-and-continue-sec(5),
        subtending-pri(6),
        subtending-sec(7)
        } 

    --
    -- Enterprise starts here.
    --
    acIdentifier            OBJECT IDENTIFIER ::= { appian 1 }
    acProductId             OBJECT IDENTIFIER ::= { acIdentifier 1 }

    --
    -- Appian Platforms
    --
    acOsap                  OBJECT IDENTIFIER ::= { appian 2 }

    acPport                 OBJECT IDENTIFIER ::= { acOsap 3 }
    acLport                 OBJECT IDENTIFIER ::= { acOsap 4 }
    acTrunks                OBJECT IDENTIFIER ::= { acOsap 6 }
    acServices              OBJECT IDENTIFIER ::= { acOsap 8 }


END
