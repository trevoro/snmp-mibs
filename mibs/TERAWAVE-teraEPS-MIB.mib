TERAWAVE-teraEPS-MIB DEFINITIONS ::= BEGIN
        -- Created by sml2mib compiler 
        IMPORTS

 enterprises,  OBJECT-TYPE,  Counter,  Gauge,  TimeTicks
        FROM RFC1155-SMI;

terawave OBJECT IDENTIFIER ::=  { enterprises 4513 }

teraEPSGroup OBJECT IDENTIFIER ::=  { terawave 12 }

     -- teraLevel1EPSConfigTable

teraLevel1EPSConfigTable OBJECT-TYPE
     SYNTAX SEQUENCE OF TeraLevel1EPSConfigTableEntryType
     ACCESS not-accessible
     STATUS mandatory
     DESCRIPTION
          " table teraLevel1EPSConfigTable"
     ::= { teraEPSGroup 1 }

teraLevel1EPSConfigTableEntry OBJECT-TYPE
          SYNTAX TeraLevel1EPSConfigTableEntryType
          ACCESS not-accessible
          STATUS mandatory
          DESCRIPTION
               " table entry teraLevel1EPSConfigTableEntry "
          INDEX {                   teraLevel1ConfigIndex }
     ::= { teraLevel1EPSConfigTable 1 }

TeraLevel1EPSConfigTableEntryType ::= SEQUENCE {
          teraLevel1ConfigIndex   
             INTEGER (1..20),
          teraLevel1ProtectingUnit   
             INTEGER (1..20),
          teraLevel1AdminProtectSwitch   
             INTEGER,
          teraLevel1AdminProtectStatus   
             INTEGER,
          teraLevel1AdminProtectSwitchReason   
             INTEGER,
          teraLevel1ProtectSwitchState   
             INTEGER,
          teraLevel1OperProtectSwitchReason   
             INTEGER,
          teraLevel1OperProtectSwitchSource   
             INTEGER
}

teraLevel1ConfigIndex OBJECT-TYPE
          SYNTAX INTEGER (1..20)
          ACCESS read-only
          STATUS mandatory
          DESCRIPTION
               ""
          ::= { teraLevel1EPSConfigTableEntry 1 }

teraLevel1ProtectingUnit OBJECT-TYPE
          SYNTAX INTEGER (1..20)
          ACCESS read-write
          STATUS mandatory
          DESCRIPTION
               ""
          ::= { teraLevel1EPSConfigTableEntry 2 }

teraLevel1AdminProtectSwitch OBJECT-TYPE
          SYNTAX INTEGER
                  {
                  none(0),
                  manual-w2p(1),
                  force-w2p(2),
                  lock(3),
                  release(4),
                  unlock(5),
                  manual-p2w(6),
                  force-p2w(7),
                  not-used(8)
                  }
          ACCESS read-write
          STATUS mandatory
          DESCRIPTION
               ""
          ::= { teraLevel1EPSConfigTableEntry 3 }

teraLevel1AdminProtectStatus OBJECT-TYPE
          SYNTAX INTEGER
                  {
                  none(0),
                  working(1),
                  protection(2)
                  }
          ACCESS read-write
          STATUS mandatory
          DESCRIPTION
               ""
          ::= { teraLevel1EPSConfigTableEntry 4 }

teraLevel1AdminProtectSwitchReason OBJECT-TYPE
          SYNTAX INTEGER
                  {
                  none(0),
                  forced(1),
                  locked(2),
                  manual(3),
                  auto(4)
                  }
          ACCESS read-only
          STATUS mandatory
          DESCRIPTION
               ""
          ::= { teraLevel1EPSConfigTableEntry 5 }

teraLevel1ProtectSwitchState OBJECT-TYPE
          SYNTAX INTEGER
                  {
                  standby(1),
                  active(2)
                  }
          ACCESS read-only
          STATUS mandatory
          DESCRIPTION
               ""
          ::= { teraLevel1EPSConfigTableEntry 6 }

teraLevel1OperProtectSwitchReason OBJECT-TYPE
          SYNTAX INTEGER
          ACCESS read-only
          STATUS mandatory
          DESCRIPTION
               ""
          ::= { teraLevel1EPSConfigTableEntry 7 }

teraLevel1OperProtectSwitchSource OBJECT-TYPE
          SYNTAX INTEGER
          ACCESS read-only
          STATUS mandatory
          DESCRIPTION
               ""
          ::= { teraLevel1EPSConfigTableEntry 8 }

     -- teraLinkEPSConfigTable

teraLinkEPSConfigTable OBJECT-TYPE
     SYNTAX SEQUENCE OF TeraLinkEPSConfigTableEntryType
     ACCESS not-accessible
     STATUS mandatory
     DESCRIPTION
          " table teraLinkEPSConfigTable"
     ::= { teraEPSGroup 2 }

teraLinkEPSConfigTableEntry OBJECT-TYPE
          SYNTAX TeraLinkEPSConfigTableEntryType
          ACCESS not-accessible
          STATUS mandatory
          DESCRIPTION
               " table entry teraLinkEPSConfigTableEntry "
          INDEX {                   teraLevel1ConfigIndex,                  teraPonIndex }
     ::= { teraLinkEPSConfigTable 1 }

TeraLinkEPSConfigTableEntryType ::= SEQUENCE {
          teraLinkProtectingUnitLevel1Index   
             INTEGER (1..16),
          teraLinkProtectingUnitPonIndex   
             INTEGER (2..33),
          teraLinkAdminProtectSwitch   
             INTEGER,
          teraLinkAdminProtectStatus   
             INTEGER,
          teraLinkAdminProtectSwitchReason   
             INTEGER
}

teraLinkProtectingUnitLevel1Index OBJECT-TYPE
          SYNTAX INTEGER (1..16)
          ACCESS read-write
          STATUS mandatory
          DESCRIPTION
               ""
          ::= { teraLinkEPSConfigTableEntry 1 }

teraLinkProtectingUnitPonIndex OBJECT-TYPE
          SYNTAX INTEGER (2..33)
          ACCESS read-write
          STATUS mandatory
          DESCRIPTION
               ""
          ::= { teraLinkEPSConfigTableEntry 2 }

teraLinkAdminProtectSwitch OBJECT-TYPE
          SYNTAX INTEGER
                  {
                  none(0),
                  manual-w2p(1),
                  force-w2p(2),
                  lock(3),
                  release(4),
                  unlock(5),
                  manual-p2w(6),
                  force-p2w(7),
                  not-used(8)
                  }
          ACCESS read-write
          STATUS mandatory
          DESCRIPTION
               ""
          ::= { teraLinkEPSConfigTableEntry 3 }

teraLinkAdminProtectStatus OBJECT-TYPE
          SYNTAX INTEGER
                  {
                  none(0),
                  working(1),
                  protection(2)
                  }
          ACCESS read-write
          STATUS mandatory
          DESCRIPTION
               ""
          ::= { teraLinkEPSConfigTableEntry 4 }

teraLinkAdminProtectSwitchReason OBJECT-TYPE
          SYNTAX INTEGER
                  {
                  none(0),
                  forced(1),
                  locked(2),
                  manual(3),
                  auto(4)
                  }
          ACCESS read-only
          STATUS mandatory
          DESCRIPTION
               ""
          ::= { teraLinkEPSConfigTableEntry 5 }

     -- teraLinkCardEPSConfigTable

teraLinkCardEPSConfigTable OBJECT-TYPE
     SYNTAX SEQUENCE OF TeraLinkCardEPSConfigTableEntryType
     ACCESS not-accessible
     STATUS mandatory
     DESCRIPTION
          " table teraLinkCardEPSConfigTable"
     ::= { teraEPSGroup 3 }

teraLinkCardEPSConfigTableEntry OBJECT-TYPE
          SYNTAX TeraLinkCardEPSConfigTableEntryType
          ACCESS not-accessible
          STATUS mandatory
          DESCRIPTION
               " table entry teraLinkCardEPSConfigTableEntry "
          INDEX {                   teraLevel1ConfigIndex,                  teraPonIndex,                  teraNELevel2Slot }
     ::= { teraLinkCardEPSConfigTable 1 }

TeraLinkCardEPSConfigTableEntryType ::= SEQUENCE {
          teraLinkCardProtectingUnitLevel1Index   
             INTEGER (1..16),
          teraLinkCardProtectingUnitPonIndex   
             INTEGER (2..33),
          teraLinkCardProtectingUnitLevel2Index   
             INTEGER (1..16),
          teraLinkCardAdminProtectSwitch   
             INTEGER,
          teraLinkCardAdminProtectSwitchReason   
             INTEGER,
          teraLinkCardProtectSwitchState   
             INTEGER,
          teraLinkCardOperProtectSwitchReason   
             INTEGER,
          teraLinkCardOperProtectSwitchSource   
             INTEGER,
          teraLinkCardAdminProtectStatus   
             INTEGER
}

teraLinkCardProtectingUnitLevel1Index OBJECT-TYPE
          SYNTAX INTEGER (1..16)
          ACCESS read-only
          STATUS mandatory
          DESCRIPTION
               ""
          ::= { teraLinkCardEPSConfigTableEntry 1 }

teraLinkCardProtectingUnitPonIndex OBJECT-TYPE
          SYNTAX INTEGER (2..33)
          ACCESS read-only
          STATUS mandatory
          DESCRIPTION
               ""
          ::= { teraLinkCardEPSConfigTableEntry 2 }

teraLinkCardProtectingUnitLevel2Index OBJECT-TYPE
          SYNTAX INTEGER (1..16)
          ACCESS read-only
          STATUS mandatory
          DESCRIPTION
               ""
          ::= { teraLinkCardEPSConfigTableEntry 3 }

teraLinkCardAdminProtectSwitch OBJECT-TYPE
          SYNTAX INTEGER
                  {
                  none(0),
                  manual-w2p(1),
                  force-w2p(2),
                  lock(3),
                  release(4),
                  unlock(5),
                  manual-p2w(6),
                  force-p2w(7),
                  not-used(8)
                  }
          ACCESS read-write
          STATUS mandatory
          DESCRIPTION
               ""
          ::= { teraLinkCardEPSConfigTableEntry 4 }

teraLinkCardAdminProtectSwitchReason OBJECT-TYPE
          SYNTAX INTEGER
                  {
                  none(0),
                  forced(1),
                  locked(2),
                  manual(3),
                  auto(4)
                  }
          ACCESS read-only
          STATUS mandatory
          DESCRIPTION
               ""
          ::= { teraLinkCardEPSConfigTableEntry 5 }

teraLinkCardProtectSwitchState OBJECT-TYPE
          SYNTAX INTEGER
                  {
                  standby(1),
                  active(2)
                  }
          ACCESS read-only
          STATUS mandatory
          DESCRIPTION
               ""
          ::= { teraLinkCardEPSConfigTableEntry 6 }

teraLinkCardOperProtectSwitchReason OBJECT-TYPE
          SYNTAX INTEGER
          ACCESS read-only
          STATUS mandatory
          DESCRIPTION
               ""
          ::= { teraLinkCardEPSConfigTableEntry 7 }

teraLinkCardOperProtectSwitchSource OBJECT-TYPE
          SYNTAX INTEGER
          ACCESS read-only
          STATUS mandatory
          DESCRIPTION
               ""
          ::= { teraLinkCardEPSConfigTableEntry 8 }

teraLinkCardAdminProtectStatus OBJECT-TYPE
          SYNTAX INTEGER
                  {
                  working(1),
                  protection(2)
                  }
          ACCESS read-only
          STATUS mandatory
          DESCRIPTION
               ""
          ::= { teraLinkCardEPSConfigTableEntry 9 }

     -- teraEPSTable (special)

END
