ACC-DS1 DEFINITIONS ::= BEGIN

    IMPORTS
	 OBJECT-TYPE FROM RFC1155-SMI
                           accTrapLogSeqNum FROM ACC-SYSTEM
	accBRG, DisplayString, RowStatus, IfIndex, SmdsAddress
             FROM ACC-MIB;

-- DS1 Extensions Group
	-- The DS1 Extensions Table contains ACC extensions to the DS1
	-- Configuration Table.
            accDs1ExtTable OBJECT-TYPE
		SYNTAX SEQUENCE OF AccDs1ExtEntry
		ACCESS not-accessible
		STATUS mandatory
		DESCRIPTION
		" The DS1 extension table."
		::= { accBRG 42 }
            accDs1ExtEntry OBJECT-TYPE
		SYNTAX AccDs1ExtEntry
		ACCESS not-accessible
		STATUS mandatory
		DESCRIPTION
		" An entry in the DS1 extension table."
		INDEX { accDs1ExtLineIndex }
		::= { accDs1ExtTable 1 }
            AccDs1ExtEntry ::= SEQUENCE {
		accDs1ExtLineIndex INTEGER,
		accDs1ExtLineLength INTEGER,
		accDS1ExtNfasGroup INTEGER,
		accDs1ExtInterfaceId INTEGER,
		accDs1ExtE1Type INTEGER,
		accDs1ExtXcvr INTEGER,
		accDs1ExtPrecedence INTEGER,
		accDs1ExtSignalGroup INTEGER,
		accDs1ExtNumberGroup INTEGER,
                accDs1ExtIntegAccess INTEGER,
                accDs1ExtSignalMode INTEGER,
                accDs1ExtCICBase INTEGER,
                accDs1ExtMessageLevel INTEGER,
                accDs1ExtServiceState INTEGER
		}
            accDs1ExtLineIndex OBJECT-TYPE
		SYNTAX INTEGER -- (1..'7fffffff'h)
		ACCESS read-only
		STATUS mandatory
		DESCRIPTION
		" This object is the identifier of a DS1 Interface on a
		  managed device.  It has the same value as dsx1LineIndex."
		::= { accDs1ExtEntry 1 }
            accDs1ExtLineLength OBJECT-TYPE
		SYNTAX INTEGER {
		short (1),		-- 0..133 feet		(15 db)
		medium (2),		-- 134..533 feet	(7.5 db)
		long (3)		-- 534..655 feet	(0 db)
		}
		ACCESS read-write
		STATUS mandatory
		DESCRIPTION
		" The approximate line length.  When equipped with a
		  DSX1 line interface module, this object selects the
		  transmit equalization.  When equipped with a CSU
		  interface module, this object selects the line build
		  out (LBO)."
		::= { accDs1ExtEntry 2 }
            accDS1ExtNfasGroup	OBJECT-TYPE
		SYNTAX INTEGER -- (0..'7fffffff'h)
		ACCESS read-write
		STATUS mandatory
		DESCRIPTION
		" The ifIndex of another DS1 interface whose common
		  signaling channel (e.g., ISDN D channel) carries
		  signaling information for this DS1 interface."
		::= { accDs1ExtEntry 3 }
            accDs1ExtInterfaceId OBJECT-TYPE
		SYNTAX INTEGER (0..31)
		ACCESS read-write
		STATUS mandatory
		DESCRIPTION
		" The internal interface on which signalling is received.
                  0 indicates the D-channel."
		::= { accDs1ExtEntry 4 }
            accDs1ExtE1Type OBJECT-TYPE
		SYNTAX INTEGER {
			normal (1),
			nordic (2)
			}
		ACCESS read-write
		STATUS mandatory
		DESCRIPTION
		" The type of E1 equipment to which the device is connected.
                  Only used to work around Nordic type switch anomolies."
		::= { accDs1ExtEntry 5 }
            accDs1ExtXcvr OBJECT-TYPE
		SYNTAX INTEGER {
			dsx1(1),
                        csu2(2),
                        hdsl-master(3),
                        hdsl-slave(4),
                        e1-120ohm(5),
                        hdsl(6),
                        e1-75ohm(7)
			}
		ACCESS read-write
		STATUS mandatory
		DESCRIPTION
		" The type of transceiver installed."
		::= { accDs1ExtEntry 6 }
            accDs1ExtPrecedence OBJECT-TYPE
		SYNTAX INTEGER {
			primary(1),
			secondary(2)
			}
		ACCESS read-write
		STATUS mandatory
		DESCRIPTION
	       "When the interface is provisioned as a PRI interface with 
	        D-channel backup, this object determines whether the D 
	        channel on this interface is the primary or secondary D 
	        channel."
		::= { accDs1ExtEntry 7 }
            accDs1ExtSignalGroup OBJECT-TYPE
		SYNTAX INTEGER (0..127)
		ACCESS read-write
		STATUS mandatory
		DESCRIPTION
	       "The index of the Signal group assigned to this interface.  
	        The value of the trunk group index is limited to the 
	        maximum number of PRI interfaces that can be installed on 
	        a given platform (3 for Amazon, 28 for Tigris).  A trunk 
	        group value of 0 indicates that the interface does not belong 
	        to a PRI trunk group.  Replaces accDs1ExtNfasGroup which 
	        has been deprecated."
		::= { accDs1ExtEntry 8 }
            accDs1ExtNumberGroup OBJECT-TYPE
		SYNTAX INTEGER 
		ACCESS read-write
		STATUS mandatory
		DESCRIPTION
	       "The index of the called number group assigned to this 
	        interface.  Number groups are defined in the Called Number 
	        Table.  A number group value of 0 indicates that no called 
	        number group has been assigned to this interface."
		::= { accDs1ExtEntry 9 }
	    accDs1ExtIntegAccess OBJECT-TYPE
		SYNTAX INTEGER {
			enabled (1),
			disabled (2)
		}
		ACCESS read-write
		STATUS mandatory
		DESCRIPTION
		" Indicates whether this interface has enabled integrated
		  access.  If enabled, the signal group is used as the
		  signaling channel for this interface. "
		::= { accDs1ExtEntry 10 }
            accDs1ExtSignalMode OBJECT-TYPE
            SYNTAX INTEGER {
                none (1),
                rbs (2),
                cas (3),
                ccs (4),
                nfas (5),
                etheric (6)
            }
            ACCESS read-write
            STATUS mandatory
            DESCRIPTION
            "Signaling mode for this DS1 interface"
            ::= { accDs1ExtEntry 11 }
            accDs1ExtCICBase OBJECT-TYPE
            SYNTAX INTEGER
            ACCESS read-write
            STATUS mandatory
            DESCRIPTION
            "CIC base to use for circuits on this DS1 interface."
            ::= { accDs1ExtEntry 12 }
            accDs1ExtMessageLevel OBJECT-TYPE
            SYNTAX INTEGER
            ACCESS read-write
            STATUS mandatory
            DESCRIPTION
            "Maintenance message level for this DS1 interface."
            ::= { accDs1ExtEntry 13 }
            accDs1ExtServiceState OBJECT-TYPE
                SYNTAX INTEGER {
                          ds1InService(1),
                          ds1OutOfService(2)
                          }
                ACCESS read-only
                STATUS mandatory
                DESCRIPTION
                " Describes DS1 service state.  Certain attributes
                  need to be in a specific state to be changed. "
                ::= { accDs1ExtEntry 14 }
	-- DS1 Circuit Group
	-- The DS1 circuit group consists of the DS1 Circuit
	-- Configuration Table.
            accDs1CircuitTable OBJECT-TYPE
		SYNTAX SEQUENCE OF AccDs1CircuitEntry
		ACCESS not-accessible
		STATUS mandatory
		DESCRIPTION
		" The DS1 circuit configuration table."
		::= { accBRG 43 }
            accDs1CircuitEntry OBJECT-TYPE
		SYNTAX AccDs1CircuitEntry
		ACCESS not-accessible
		STATUS mandatory
		DESCRIPTION
		" An entry in the DS1 circuit configuration table."
		INDEX { accDs1CircuitIndex }
		::= { accDs1CircuitTable 1 }
            AccDs1CircuitEntry ::= SEQUENCE {
		accDs1CircuitIndex INTEGER,
		accDs1CircuitAdi INTEGER,
		accDs1CircuitBandwidth INTEGER,
		accDs1CircuitBusyout INTEGER,
		accDs1CircuitInversion INTEGER,
		accDs1CircuitName DisplayString,
		accDs1CircuitConfigStatus INTEGER,
		accDs1CircuitLoopback INTEGER,
		accDs1CircuitRbs INTEGER,
		accDs1CircuitSuperrateMask INTEGER
		}
            accDs1CircuitIndex OBJECT-TYPE
		SYNTAX INTEGER -- (1..'7fffffff'h)
		ACCESS read-only
		STATUS mandatory
		DESCRIPTION
		" This object is the identifier of a circuit on a
		  managed DS1 interface.  It should have the same value
		  as ifIndex."
		::= { accDs1CircuitEntry 1 }
            accDs1CircuitAdi OBJECT-TYPE
		SYNTAX INTEGER {
		on (1),
		off (2)
		}
		ACCESS read-write
		STATUS mandatory
		DESCRIPTION
		" Enables or disables alternate digit inversion for a
		  circuit on a managed DS1 interface.  This object
		  applies only to E1 interfaces."
		::= { accDs1CircuitEntry 2 }
            accDs1CircuitBandwidth OBJECT-TYPE
		SYNTAX INTEGER {
		bandwidth-8 (1),
		bandwidth-16 (2),
		bandwidth-24 (3),
		bandwidth-32 (4),
		bandwidth-40 (5),
		bandwidth-48 (6),
		bandwidth-56 (7),
		bandwidth-64 (8)
		}
		ACCESS read-write
		STATUS mandatory
		DESCRIPTION
		" The bandwidth of the circuit in kilobits per second."
		::= { accDs1CircuitEntry 3 }
            accDs1CircuitBusyout OBJECT-TYPE
		SYNTAX INTEGER {
		busy (1),
		unbusy (2)
		}
		ACCESS read-write
		STATUS mandatory
		DESCRIPTION
		" The busyout status of a circuit.  If the status is
		  set to busy, the circuit is taken out of service and is
		  unable to carry user data."
		::= { accDs1CircuitEntry 4 }
            accDs1CircuitInversion OBJECT-TYPE
		SYNTAX INTEGER {
		on (1),
		off (2)
		}
		ACCESS read-write
		STATUS mandatory
		DESCRIPTION
		" Enables or disables circuit inversion for a circuit
		  on a managed DS1 interface.  This object applies only
		  to T1 interfaces."
		::= { accDs1CircuitEntry 5 }
            accDs1CircuitName OBJECT-TYPE
		SYNTAX DisplayString --(SIZE (0..16))
		ACCESS read-write
		STATUS mandatory
		DESCRIPTION
		" This object is used to associate a name with a
		  particular DS1 circuit."
		::= { accDs1CircuitEntry 6 }
            accDs1CircuitConfigStatus OBJECT-TYPE
		SYNTAX INTEGER {
		unconfig (1),
		static (2),
		dynamic (3)
		}
		ACCESS read-write
		STATUS mandatory
		DESCRIPTION
		" This object gives the configuration status for a
		  circuit entry, and may have the following values:
		  UNCONFIG	The circuit has not been configured
				or has been deleted
		  STATIC	The circuit has been configured manually
				(stored in NVM)
		  DYNAMIC	The circuit has been configured
				automatically (not stored in NVM)"
		::= { accDs1CircuitEntry 7 }
            accDs1CircuitLoopback OBJECT-TYPE
		SYNTAX INTEGER {
		none (1),
		loopback-a (2),
		loopback-c (3)
		}
		ACCESS read-write
		STATUS mandatory
		DESCRIPTION
		" This object represents the loopback status of the DS1
		  circuit.  Any active loopback can be removed by
		  setting the loopback status to none."
		::= { accDs1CircuitEntry 8 }
            accDs1CircuitRbs OBJECT-TYPE
		SYNTAX INTEGER {
		on (1),
		off (2)
		}
		ACCESS read-write
		STATUS mandatory
		DESCRIPTION
		" Enables or disables robbed bit signaling for a
		  circuit on a managed DS1 interface.  This object
		  applies only to T1 interfaces."
		::= { accDs1CircuitEntry 9 }
            accDs1CircuitSuperrateMask OBJECT-TYPE
		SYNTAX INTEGER -- (0..'7fffffff'h)
		ACCESS read-write
		STATUS mandatory
		DESCRIPTION
		" Specifies the time-slots used by a superrate
		  circuit.  Each bit which is set corresponds to a
		  time-slot which is allocated to the superrate
		  circuit.  2**n-1 corresponds to time-slot n."
		::= { accDs1CircuitEntry 10 }

END
