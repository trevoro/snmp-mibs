Nortel-Magellan-Passport-Frf5EpMIB
DEFINITIONS ::= BEGIN



IMPORTS

      OBJECT-TYPE
   FROM RFC-1212

      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      AsciiString,
      NonReplicated,
      HexString,
      IntegerSequence
   FROM Nortel-Magellan-Passport-TextualConventionsMIB

      mcsMgrIndex,
      mcsMgr
   FROM Nortel-Magellan-Passport-McsMgrMIB;




-- LAST-UPDATED   "9706300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Frf5Ep Enterprise MIB."

frf5EpMIB OBJECT IDENTIFIER ::= { passportMIBs 121 }










-- McsMgr Frf5EndPointGroup/n
-- The Frf5EpG component contains FRF.5 End Points that share a 
-- common destination NSAP address, and a list of address prefixes.

mcsMgrFrf5EpG OBJECT IDENTIFIER ::= { mcsMgr 14 }



mcsMgrFrf5EpGRowStatusTable OBJECT-TYPE
   SYNTAX     SEQUENCE OF McsMgrFrf5EpGRowStatusEntry
   ACCESS     not-accessible
   STATUS     mandatory
   DESCRIPTION
     "This entry controls the addition and deletion of 
      mcsMgrFrf5EpG components."
::= { mcsMgrFrf5EpG 1 }

mcsMgrFrf5EpGRowStatusEntry OBJECT-TYPE
   SYNTAX     McsMgrFrf5EpGRowStatusEntry
   ACCESS     not-accessible
   STATUS     mandatory
   DESCRIPTION
     "A single entry in the table represents a single 
      mcsMgrFrf5EpG component."
   INDEX {
      mcsMgrIndex,
      mcsMgrFrf5EpGIndex }
::= { mcsMgrFrf5EpGRowStatusTable 1 }

McsMgrFrf5EpGRowStatusEntry ::= SEQUENCE {
   mcsMgrFrf5EpGRowStatus
      RowStatus,
   mcsMgrFrf5EpGComponentName
      DisplayString,
   mcsMgrFrf5EpGStorageType
      StorageType,
   mcsMgrFrf5EpGIndex
      Integer32 }

mcsMgrFrf5EpGRowStatus OBJECT-TYPE
   SYNTAX     RowStatus 
   ACCESS     read-write
   STATUS     mandatory
   DESCRIPTION
     "This variable is used as the basis for SNMP naming of
      mcsMgrFrf5EpG components.
      These components can be added and deleted."
::= { mcsMgrFrf5EpGRowStatusEntry 1 }

mcsMgrFrf5EpGComponentName OBJECT-TYPE
   SYNTAX     DisplayString 
   ACCESS     read-only
   STATUS     mandatory
   DESCRIPTION
     "This variable provides the component's string name for
      use with the ASCII Console Interface"
::= { mcsMgrFrf5EpGRowStatusEntry 2 }

mcsMgrFrf5EpGStorageType OBJECT-TYPE
   SYNTAX     StorageType 
   ACCESS     read-only
   STATUS     mandatory
   DESCRIPTION
     "This variable represents the storage type value for the
      mcsMgrFrf5EpG tables."
::= { mcsMgrFrf5EpGRowStatusEntry 4 }

mcsMgrFrf5EpGIndex OBJECT-TYPE
   SYNTAX     Integer32 (1..8191)
   ACCESS     not-accessible
   STATUS     mandatory
   DESCRIPTION
     "This variable represents the index for the mcsMgrFrf5EpG tables."
::= { mcsMgrFrf5EpGRowStatusEntry 10 }


-- McsMgr Frf5EpG/n Address
-- This component contains the destination NSAP address used by all 
-- FRF.5 End Points provisioned under an Frf5EpG. The Address also 
-- provides the list of address prefixes directed to the end points under 
-- this group.

mcsMgrFrf5EpGAddr OBJECT IDENTIFIER ::= { mcsMgrFrf5EpG 2 }



mcsMgrFrf5EpGAddrRowStatusTable OBJECT-TYPE
   SYNTAX     SEQUENCE OF McsMgrFrf5EpGAddrRowStatusEntry
   ACCESS     not-accessible
   STATUS     mandatory
   DESCRIPTION
     "This entry controls the addition and deletion of 
      mcsMgrFrf5EpGAddr components."
::= { mcsMgrFrf5EpGAddr 1 }

mcsMgrFrf5EpGAddrRowStatusEntry OBJECT-TYPE
   SYNTAX     McsMgrFrf5EpGAddrRowStatusEntry
   ACCESS     not-accessible
   STATUS     mandatory
   DESCRIPTION
     "A single entry in the table represents a single 
      mcsMgrFrf5EpGAddr component."
   INDEX {
      mcsMgrIndex,
      mcsMgrFrf5EpGIndex,
      mcsMgrFrf5EpGAddrIndex }
::= { mcsMgrFrf5EpGAddrRowStatusTable 1 }

McsMgrFrf5EpGAddrRowStatusEntry ::= SEQUENCE {
   mcsMgrFrf5EpGAddrRowStatus
      RowStatus,
   mcsMgrFrf5EpGAddrComponentName
      DisplayString,
   mcsMgrFrf5EpGAddrStorageType
      StorageType,
   mcsMgrFrf5EpGAddrIndex
      NonReplicated }

mcsMgrFrf5EpGAddrRowStatus OBJECT-TYPE
   SYNTAX     RowStatus 
   ACCESS     read-only
   STATUS     mandatory
   DESCRIPTION
     "This variable is used as the basis for SNMP naming of
      mcsMgrFrf5EpGAddr components.
      These components cannot be added nor deleted."
::= { mcsMgrFrf5EpGAddrRowStatusEntry 1 }

mcsMgrFrf5EpGAddrComponentName OBJECT-TYPE
   SYNTAX     DisplayString 
   ACCESS     read-only
   STATUS     mandatory
   DESCRIPTION
     "This variable provides the component's string name for
      use with the ASCII Console Interface"
::= { mcsMgrFrf5EpGAddrRowStatusEntry 2 }

mcsMgrFrf5EpGAddrStorageType OBJECT-TYPE
   SYNTAX     StorageType 
   ACCESS     read-only
   STATUS     mandatory
   DESCRIPTION
     "This variable represents the storage type value for the
      mcsMgrFrf5EpGAddr tables."
::= { mcsMgrFrf5EpGAddrRowStatusEntry 4 }

mcsMgrFrf5EpGAddrIndex OBJECT-TYPE
   SYNTAX     NonReplicated 
   ACCESS     not-accessible
   STATUS     mandatory
   DESCRIPTION
     "This variable represents the index for the mcsMgrFrf5EpGAddr tables."
::= { mcsMgrFrf5EpGAddrRowStatusEntry 10 }

mcsMgrFrf5EpGAddrProvTable OBJECT-TYPE
   SYNTAX     SEQUENCE OF McsMgrFrf5EpGAddrProvEntry
   ACCESS     not-accessible
   STATUS     mandatory
   DESCRIPTION
     "This group contains the provisionable attributes of the Address 
      component."
::= { mcsMgrFrf5EpGAddr 10 }

mcsMgrFrf5EpGAddrProvEntry OBJECT-TYPE
   SYNTAX     McsMgrFrf5EpGAddrProvEntry
   ACCESS     not-accessible
   STATUS     mandatory
   DESCRIPTION
     "An entry in the mcsMgrFrf5EpGAddrProvTable."
   INDEX {
      mcsMgrIndex,
      mcsMgrFrf5EpGIndex,
      mcsMgrFrf5EpGAddrIndex }
::= { mcsMgrFrf5EpGAddrProvTable 1 }

McsMgrFrf5EpGAddrProvEntry ::= SEQUENCE {
   mcsMgrFrf5EpGAddrRemoteAddress
      AsciiString,
   mcsMgrFrf5EpGAddrCommentText
      AsciiString }

mcsMgrFrf5EpGAddrRemoteAddress OBJECT-TYPE
   SYNTAX     AsciiString (SIZE (0..44))
   ACCESS     read-write
   STATUS     mandatory
   DESCRIPTION
     "This attribute specifies the ATM End System Address (AESA) in 
      the ISO NSAP format that is used by each EndPoint under this 
      Frf5EpG to establish a VCC. For example, NSAP ATM address 
      '45000006138292323F000000000020480D002900'."
::= { mcsMgrFrf5EpGAddrProvEntry 1 }

mcsMgrFrf5EpGAddrCommentText OBJECT-TYPE
   SYNTAX     AsciiString (SIZE (0..750))
   ACCESS     read-write
   STATUS     mandatory
   DESCRIPTION
     "This optional attribute contains additional textual information to be 
      added by the network operator."
   DEFVAL     { ''H }  -- ""
::= { mcsMgrFrf5EpGAddrProvEntry 2 }

mcsMgrFrf5EpGAddrAddrPreTable OBJECT-TYPE
   SYNTAX     SEQUENCE OF McsMgrFrf5EpGAddrAddrPreEntry
   ACCESS     not-accessible
   STATUS     mandatory
   DESCRIPTION
     "This attribute specifies the list of prefixes directed to the EndPoints 
      under this Frf5EndPointGroup. The individual end point is selected 
      for each subconnection on the basis of its 
      supportedTransferPriorities.
      For example, E.164 prefix 'e.613722', X.121 prefix 'x.302'."
::= { mcsMgrFrf5EpGAddr 362 }

mcsMgrFrf5EpGAddrAddrPreEntry OBJECT-TYPE
   SYNTAX     McsMgrFrf5EpGAddrAddrPreEntry
   ACCESS     not-accessible
   STATUS     mandatory
   DESCRIPTION
     "An entry in the mcsMgrFrf5EpGAddrAddrPreTable."
   INDEX {
      mcsMgrIndex,
      mcsMgrFrf5EpGIndex,
      mcsMgrFrf5EpGAddrIndex,
      mcsMgrFrf5EpGAddrAddrPreValue }
::= { mcsMgrFrf5EpGAddrAddrPreTable 1 }

McsMgrFrf5EpGAddrAddrPreEntry ::= SEQUENCE {
   mcsMgrFrf5EpGAddrAddrPreValue
      AsciiString,
   mcsMgrFrf5EpGAddrAddrPreRowStatus
      RowStatus }

mcsMgrFrf5EpGAddrAddrPreValue OBJECT-TYPE
   SYNTAX     AsciiString (SIZE (3..17))
   ACCESS     read-write
   STATUS     mandatory
   DESCRIPTION
     "This variable represents both the value and the index for the
      mcsMgrFrf5EpGAddrAddrPreTable."
::= { mcsMgrFrf5EpGAddrAddrPreEntry 1 }

mcsMgrFrf5EpGAddrAddrPreRowStatus OBJECT-TYPE
   SYNTAX     RowStatus 
   ACCESS     write-only
   STATUS     mandatory
   DESCRIPTION
     "This variable is used to control the addition and deletion 
      of individual values of the mcsMgrFrf5EpGAddrAddrPreTable."
::= { mcsMgrFrf5EpGAddrAddrPreEntry 2 }


-- McsMgr Frf5EpG/n EndPoint/n
-- The EndPoint component represents a single ATM VCC that can 
-- multiplex multiple Frame Relay DLCIs.

mcsMgrFrf5EpGEp OBJECT IDENTIFIER ::= { mcsMgrFrf5EpG 3 }



mcsMgrFrf5EpGEpRowStatusTable OBJECT-TYPE
   SYNTAX     SEQUENCE OF McsMgrFrf5EpGEpRowStatusEntry
   ACCESS     not-accessible
   STATUS     mandatory
   DESCRIPTION
     "This entry controls the addition and deletion of 
      mcsMgrFrf5EpGEp components."
::= { mcsMgrFrf5EpGEp 1 }

mcsMgrFrf5EpGEpRowStatusEntry OBJECT-TYPE
   SYNTAX     McsMgrFrf5EpGEpRowStatusEntry
   ACCESS     not-accessible
   STATUS     mandatory
   DESCRIPTION
     "A single entry in the table represents a single 
      mcsMgrFrf5EpGEp component."
   INDEX {
      mcsMgrIndex,
      mcsMgrFrf5EpGIndex,
      mcsMgrFrf5EpGEpIndex }
::= { mcsMgrFrf5EpGEpRowStatusTable 1 }

McsMgrFrf5EpGEpRowStatusEntry ::= SEQUENCE {
   mcsMgrFrf5EpGEpRowStatus
      RowStatus,
   mcsMgrFrf5EpGEpComponentName
      DisplayString,
   mcsMgrFrf5EpGEpStorageType
      StorageType,
   mcsMgrFrf5EpGEpIndex
      Integer32 }

mcsMgrFrf5EpGEpRowStatus OBJECT-TYPE
   SYNTAX     RowStatus 
   ACCESS     read-write
   STATUS     mandatory
   DESCRIPTION
     "This variable is used as the basis for SNMP naming of
      mcsMgrFrf5EpGEp components.
      These components can be added and deleted."
::= { mcsMgrFrf5EpGEpRowStatusEntry 1 }

mcsMgrFrf5EpGEpComponentName OBJECT-TYPE
   SYNTAX     DisplayString 
   ACCESS     read-only
   STATUS     mandatory
   DESCRIPTION
     "This variable provides the component's string name for
      use with the ASCII Console Interface"
::= { mcsMgrFrf5EpGEpRowStatusEntry 2 }

mcsMgrFrf5EpGEpStorageType OBJECT-TYPE
   SYNTAX     StorageType 
   ACCESS     read-only
   STATUS     mandatory
   DESCRIPTION
     "This variable represents the storage type value for the
      mcsMgrFrf5EpGEp tables."
::= { mcsMgrFrf5EpGEpRowStatusEntry 4 }

mcsMgrFrf5EpGEpIndex OBJECT-TYPE
   SYNTAX     Integer32 (0..15)
   ACCESS     not-accessible
   STATUS     mandatory
   DESCRIPTION
     "This variable represents the index for the mcsMgrFrf5EpGEp tables."
::= { mcsMgrFrf5EpGEpRowStatusEntry 10 }

mcsMgrFrf5EpGEpStateTable OBJECT-TYPE
   SYNTAX     SEQUENCE OF McsMgrFrf5EpGEpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mcsMgrFrf5EpGEp 10 }

mcsMgrFrf5EpGEpStateEntry OBJECT-TYPE
   SYNTAX     McsMgrFrf5EpGEpStateEntry
   ACCESS     not-accessible
   STATUS     mandatory
   DESCRIPTION
     "An entry in the mcsMgrFrf5EpGEpStateTable."
   INDEX {
      mcsMgrIndex,
      mcsMgrFrf5EpGIndex,
      mcsMgrFrf5EpGEpIndex }
::= { mcsMgrFrf5EpGEpStateTable 1 }

McsMgrFrf5EpGEpStateEntry ::= SEQUENCE {
   mcsMgrFrf5EpGEpAdminState
      INTEGER,
   mcsMgrFrf5EpGEpOperationalState
      INTEGER,
   mcsMgrFrf5EpGEpUsageState
      INTEGER,
   mcsMgrFrf5EpGEpAvailabilityStatus
      OCTET STRING,
   mcsMgrFrf5EpGEpProceduralStatus
      OCTET STRING,
   mcsMgrFrf5EpGEpControlStatus
      OCTET STRING,
   mcsMgrFrf5EpGEpAlarmStatus
      OCTET STRING,
   mcsMgrFrf5EpGEpStandbyStatus
      INTEGER,
   mcsMgrFrf5EpGEpUnknownStatus
      INTEGER }

mcsMgrFrf5EpGEpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mcsMgrFrf5EpGEpStateEntry 1 }

mcsMgrFrf5EpGEpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mcsMgrFrf5EpGEpStateEntry 2 }

mcsMgrFrf5EpGEpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mcsMgrFrf5EpGEpStateEntry 3 }

mcsMgrFrf5EpGEpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mcsMgrFrf5EpGEpStateEntry 4 }

mcsMgrFrf5EpGEpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mcsMgrFrf5EpGEpStateEntry 5 }

mcsMgrFrf5EpGEpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mcsMgrFrf5EpGEpStateEntry 6 }

mcsMgrFrf5EpGEpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mcsMgrFrf5EpGEpStateEntry 7 }

mcsMgrFrf5EpGEpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mcsMgrFrf5EpGEpStateEntry 8 }

mcsMgrFrf5EpGEpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mcsMgrFrf5EpGEpStateEntry 9 }

mcsMgrFrf5EpGEpOperTable OBJECT-TYPE
   SYNTAX     SEQUENCE OF McsMgrFrf5EpGEpOperEntry
   ACCESS     not-accessible
   STATUS     mandatory
   DESCRIPTION
     "This group contains the operational attributes for the FRF.5 ATM 
      connection."
::= { mcsMgrFrf5EpGEp 11 }

mcsMgrFrf5EpGEpOperEntry OBJECT-TYPE
   SYNTAX     McsMgrFrf5EpGEpOperEntry
   ACCESS     not-accessible
   STATUS     mandatory
   DESCRIPTION
     "An entry in the mcsMgrFrf5EpGEpOperTable."
   INDEX {
      mcsMgrIndex,
      mcsMgrFrf5EpGIndex,
      mcsMgrFrf5EpGEpIndex }
::= { mcsMgrFrf5EpGEpOperTable 1 }

McsMgrFrf5EpGEpOperEntry ::= SEQUENCE {
   mcsMgrFrf5EpGEpLastVccClearCause
      Unsigned32,
   mcsMgrFrf5EpGEpConnectionTransferPriority
      Unsigned32,
   mcsMgrFrf5EpGEpServiceCategory
      INTEGER,
   mcsMgrFrf5EpGEpPeakCellRate01
      Unsigned32,
   mcsMgrFrf5EpGEpSustainedCellRate0
      Unsigned32,
   mcsMgrFrf5EpGEpSustainedCellRate01
      Unsigned32,
   mcsMgrFrf5EpGEpMaximumBurstSize0
      Unsigned32,
   mcsMgrFrf5EpGEpMaximumBurstSize01
      Unsigned32,
   mcsMgrFrf5EpGEpAvgFrameSize
      Unsigned32,
   mcsMgrFrf5EpGEpTrafficParmConversionPolicy
      INTEGER,
   mcsMgrFrf5EpGEpType
      INTEGER,
   mcsMgrFrf5EpGEpLastVccCauseDiag
      HexString }

mcsMgrFrf5EpGEpLastVccClearCause OBJECT-TYPE
   SYNTAX     Unsigned32 (0..255)
   ACCESS     read-only
   STATUS     mandatory
   DESCRIPTION
     "This attribute indicates the clear cause value of the last SPVC 
      release message received on the FRF.5 end point Vcc pipe."
::= { mcsMgrFrf5EpGEpOperEntry 4 }

mcsMgrFrf5EpGEpConnectionTransferPriority OBJECT-TYPE
   SYNTAX     Unsigned32 (0..15)
   ACCESS     read-only
   STATUS     mandatory
   DESCRIPTION
     "This attribute indicates the transfer priority used to establish the 
      ATM connection and to multiplex the Frame Relay DLCIs."
::= { mcsMgrFrf5EpGEpOperEntry 5 }

mcsMgrFrf5EpGEpServiceCategory OBJECT-TYPE
   SYNTAX     INTEGER  {
                 ubr(0),
                 cbr(1),
                 rtVbr(2),
                 nrtVbr(3) }
   ACCESS     read-only
   STATUS     mandatory
   DESCRIPTION
     "This attribute indicates the ATM service category that is used for 
      this connection."
::= { mcsMgrFrf5EpGEpOperEntry 6 }

mcsMgrFrf5EpGEpPeakCellRate01 OBJECT-TYPE
   SYNTAX     Unsigned32 (0..4294967295)
   ACCESS     read-only
   STATUS     mandatory
   DESCRIPTION
     "This attribute indicates the Peak Cell Rate (PCR) of the FRF.5 ATM 
      VCC for all cells (with CLP=0 and CLP=1).
      The pcr01 is derived from the End Point traffic parameters using the 
      conversion policy of the connectionTransferPriority. The 
      conversion policy is defined under the ModuleData 
      FrameRelayService AtmNetworking TransferPriority/n component."
::= { mcsMgrFrf5EpGEpOperEntry 8 }

mcsMgrFrf5EpGEpSustainedCellRate0 OBJECT-TYPE
   SYNTAX     Unsigned32 (0..4294967295)
   ACCESS     read-only
   STATUS     mandatory
   DESCRIPTION
     "This attribute indicates the Sustained Cell Rate (SCR) of the FRF.5 
      ATM VCC for high priority cells (with CLP=0).
      The scr0 is derived from the End Point traffic parameters using the 
      conversion policy of the connectionTransferPriority. The 
      conversion policy is defined under the ModuleData 
      FrameRelayService AtmNetworking TransferPriority/n component."
::= { mcsMgrFrf5EpGEpOperEntry 9 }

mcsMgrFrf5EpGEpSustainedCellRate01 OBJECT-TYPE
   SYNTAX     Unsigned32 (0..4294967295)
   ACCESS     read-only
   STATUS     mandatory
   DESCRIPTION
     "This attribute indicates the Sustained Cell Rate (SCR) of the FRF.5 
      ATM VCC for all cells (with CLP=0 and CLP=1).
      The scr01 is derived from the End Point traffic parameters using the 
      conversion policy of the connectionTransferPriority. The 
      conversion policy is defined under the ModuleData 
      FrameRelayService AtmNetworking TransferPriority/n component."
::= { mcsMgrFrf5EpGEpOperEntry 10 }

mcsMgrFrf5EpGEpMaximumBurstSize0 OBJECT-TYPE
   SYNTAX     Unsigned32 (0..4294967295)
   ACCESS     read-only
   STATUS     mandatory
   DESCRIPTION
     "This attribute indicates the Maximum Burst Size (MBS) of the 
      FRF.5 ATM VCC for high priority cells (with CLP=0).
      The mbs0 is derived from the End Point traffic parameters using the 
      conversion policy of the connectionTransferPriority. The 
      conversion policy is defined under the ModuleData 
      FrameRelayService AtmNetworking TransferPriority/n component."
::= { mcsMgrFrf5EpGEpOperEntry 11 }

mcsMgrFrf5EpGEpMaximumBurstSize01 OBJECT-TYPE
   SYNTAX     Unsigned32 (0..4294967295)
   ACCESS     read-only
   STATUS     mandatory
   DESCRIPTION
     "This attribute indicates the Maximum Burst Size (MBS) of the 
      FRF.5 ATM VCC for all cells (with CLP=0 and CLP=1).
      The mbs01 is derived from the End Point traffic parameters using 
      the conversion policy of the connectionTransferPriority. The 
      conversion policy is defined under the ModuleData 
      FrameRelayService AtmNetworking TransferPriority/n component."
::= { mcsMgrFrf5EpGEpOperEntry 12 }

mcsMgrFrf5EpGEpAvgFrameSize OBJECT-TYPE
   SYNTAX     Unsigned32 (1..8187)
   ACCESS     read-only
   STATUS     mandatory
   DESCRIPTION
     "This attribute indicates the average frame size that is used in the 
      traffic parameter conversion policy calculations for this end point."
   DEFVAL     { 128 }
::= { mcsMgrFrf5EpGEpOperEntry 13 }

mcsMgrFrf5EpGEpTrafficParmConversionPolicy OBJECT-TYPE
   SYNTAX     INTEGER  {
                 n3(3),
                 n4(4),
                 n5(5),
                 n6(6) }
   ACCESS     read-only
   STATUS     mandatory
   DESCRIPTION
     "This attribute indicates the traffic parameter conversion policy used 
      to specify the equivalent ATM bandwidth rate at this end point.
      
      Policy 3 characterizes the traffic in the following way:
      - ATM traffic descriptor type 6 is selected
      - PCR0+1 is based on the AR
      - SCR0+1 is based on the CIR and EIR
      - MBS0+1 is based on Bc,Be,CIR,EIR and AR
      - Takes into account that the instananeous rate of the frame relay 
      stream can burst above CIR and up tp the AR.
      
      Policy 4 characterizes the traffic in the following way:
      - ATM traffic descriptor type 7 or 8 is selected. Type 7 is chosen 
      when non-conforming cells are to be discarded and type 8 when 
      non-conforming cells are tagged by UPC traffic policer.
      - PCR0+1 is based on the AR
      - SCR0 is based on the CIR
      - MBS0 is based on Bc,CIR and AR
      - There is no direct characterization of EIR. The allowed EIR can be 
      derived using the difference between the AR and CIR.
      
      Policy 5 characterizes the traffic in the following way:
      - ATM traffic descriptor type 7 or 8 is selected . Type 7 is chosen 
      when non-conforming cells are to be discarded and type 8 when 
      non-conforming cells are tagged by UPC traffic policer
      - PCR0+1 is based on CIR and EIR
      - SCR0 is based on the CIR
      - MBS0 is based on the Bc,CIR and AR
      - The maximum PCR is no longer based on AR but based on the 
      CIR and EIR.
      
      Policy 6 characterizes the traffic in the following way:
      - ATM traffic descriptor type 3 is selected
      - PCR0+1 is based only on CIR."
::= { mcsMgrFrf5EpGEpOperEntry 14 }

mcsMgrFrf5EpGEpType OBJECT-TYPE
   SYNTAX     INTEGER  {
                 master(0),
                 slave(1) }
   ACCESS     read-only
   STATUS     mandatory
   DESCRIPTION
     "This attribute indicates the FRF.5 End Point type. If the value is 
      master, this End Point is responsible for initiating the call to set up 
      the FRF.5 ATM VCC. If the value is slave, this End Point receives 
      call setup requests from the remote end."
::= { mcsMgrFrf5EpGEpOperEntry 15 }

mcsMgrFrf5EpGEpLastVccCauseDiag OBJECT-TYPE
   SYNTAX     HexString (SIZE (1..8))
   ACCESS     read-only
   STATUS     mandatory
   DESCRIPTION
     "This attribute indicates the diagnostic value of the last SPVC release 
      message received on the FRF.5 end point Vcc pipe."
::= { mcsMgrFrf5EpGEpOperEntry 20 }


-- DsMgr Frf5EpG/n Ep/m LocalManagementInterface
-- This component defines the parameters for implementing the Frame 
-- Relay Forum FRF.5 Local Management Interface protocol.

mcsMgrFrf5EpGEpLmi OBJECT IDENTIFIER ::= { mcsMgrFrf5EpGEp 2 }



mcsMgrFrf5EpGEpLmiRowStatusTable OBJECT-TYPE
   SYNTAX     SEQUENCE OF McsMgrFrf5EpGEpLmiRowStatusEntry
   ACCESS     not-accessible
   STATUS     mandatory
   DESCRIPTION
     "This entry controls the addition and deletion of 
      mcsMgrFrf5EpGEpLmi components."
::= { mcsMgrFrf5EpGEpLmi 1 }

mcsMgrFrf5EpGEpLmiRowStatusEntry OBJECT-TYPE
   SYNTAX     McsMgrFrf5EpGEpLmiRowStatusEntry
   ACCESS     not-accessible
   STATUS     mandatory
   DESCRIPTION
     "A single entry in the table represents a single 
      mcsMgrFrf5EpGEpLmi component."
   INDEX {
      mcsMgrIndex,
      mcsMgrFrf5EpGIndex,
      mcsMgrFrf5EpGEpIndex,
      mcsMgrFrf5EpGEpLmiIndex }
::= { mcsMgrFrf5EpGEpLmiRowStatusTable 1 }

McsMgrFrf5EpGEpLmiRowStatusEntry ::= SEQUENCE {
   mcsMgrFrf5EpGEpLmiRowStatus
      RowStatus,
   mcsMgrFrf5EpGEpLmiComponentName
      DisplayString,
   mcsMgrFrf5EpGEpLmiStorageType
      StorageType,
   mcsMgrFrf5EpGEpLmiIndex
      NonReplicated }

mcsMgrFrf5EpGEpLmiRowStatus OBJECT-TYPE
   SYNTAX     RowStatus 
   ACCESS     read-write
   STATUS     mandatory
   DESCRIPTION
     "This variable is used as the basis for SNMP naming of
      mcsMgrFrf5EpGEpLmi components.
      These components can be added and deleted."
::= { mcsMgrFrf5EpGEpLmiRowStatusEntry 1 }

mcsMgrFrf5EpGEpLmiComponentName OBJECT-TYPE
   SYNTAX     DisplayString 
   ACCESS     read-only
   STATUS     mandatory
   DESCRIPTION
     "This variable provides the component's string name for
      use with the ASCII Console Interface"
::= { mcsMgrFrf5EpGEpLmiRowStatusEntry 2 }

mcsMgrFrf5EpGEpLmiStorageType OBJECT-TYPE
   SYNTAX     StorageType 
   ACCESS     read-only
   STATUS     mandatory
   DESCRIPTION
     "This variable represents the storage type value for the
      mcsMgrFrf5EpGEpLmi tables."
::= { mcsMgrFrf5EpGEpLmiRowStatusEntry 4 }

mcsMgrFrf5EpGEpLmiIndex OBJECT-TYPE
   SYNTAX     NonReplicated 
   ACCESS     not-accessible
   STATUS     mandatory
   DESCRIPTION
     "This variable represents the index for the mcsMgrFrf5EpGEpLmi tables."
::= { mcsMgrFrf5EpGEpLmiRowStatusEntry 10 }

mcsMgrFrf5EpGEpLmiParmsTable OBJECT-TYPE
   SYNTAX     SEQUENCE OF McsMgrFrf5EpGEpLmiParmsEntry
   ACCESS     not-accessible
   STATUS     mandatory
   DESCRIPTION
     "This group contains the provisionable attributes of the Local 
      Management Interface component."
::= { mcsMgrFrf5EpGEpLmi 10 }

mcsMgrFrf5EpGEpLmiParmsEntry OBJECT-TYPE
   SYNTAX     McsMgrFrf5EpGEpLmiParmsEntry
   ACCESS     not-accessible
   STATUS     mandatory
   DESCRIPTION
     "An entry in the mcsMgrFrf5EpGEpLmiParmsTable."
   INDEX {
      mcsMgrIndex,
      mcsMgrFrf5EpGIndex,
      mcsMgrFrf5EpGEpIndex,
      mcsMgrFrf5EpGEpLmiIndex }
::= { mcsMgrFrf5EpGEpLmiParmsTable 1 }

McsMgrFrf5EpGEpLmiParmsEntry ::= SEQUENCE {
   mcsMgrFrf5EpGEpLmiProcedures
      INTEGER,
   mcsMgrFrf5EpGEpLmiAsyncStatusReport
      INTEGER,
   mcsMgrFrf5EpGEpLmiErrorEventThreshold
      Unsigned32,
   mcsMgrFrf5EpGEpLmiEventCount
      Unsigned32,
   mcsMgrFrf5EpGEpLmiCheckPointTimer
      Unsigned32,
   mcsMgrFrf5EpGEpLmiSide
      INTEGER }

mcsMgrFrf5EpGEpLmiProcedures OBJECT-TYPE
   SYNTAX     INTEGER  {
                 none(0),
                 ansi(2),
                 ccitt(3) }
   ACCESS     read-write
   STATUS     mandatory
   DESCRIPTION
     "This attribute selects the procedures to be used for the Local 
      Management Interface. The following are the supported procedures:
      
      none: no Local Management Interface procedures are running on 
      the ATM VCC. This accomodates remote interworking functions 
      which do not implement LMI procedures. In this case, the 
      remaining attributes of this group will be ignored.
      
      ccitt: Local Management Interface procedures from the CCITT 
      specification are supported. Dlci/0 is used for the LMI protocol, to 
      comply with FRF.5. 
      
      ansi: Local Management Interface procedures from the ANSI 
      specification are supported. DLCI 0 is used for the LMI protocol."
   DEFVAL     { ccitt }
::= { mcsMgrFrf5EpGEpLmiParmsEntry 1 }

mcsMgrFrf5EpGEpLmiAsyncStatusReport OBJECT-TYPE
   SYNTAX     INTEGER  {
                 off(0),
                 on(1) }
   ACCESS     read-write
   STATUS     mandatory
   DESCRIPTION
     "This attribute selects the use of asynchronous PVC status report 
      procedures as specified in the CCITT specification (ITU-T Q.933, 
      Annex A), and the ANSI specification Annex D."
   DEFVAL     { on }
::= { mcsMgrFrf5EpGEpLmiParmsEntry 2 }

mcsMgrFrf5EpGEpLmiErrorEventThreshold OBJECT-TYPE
   SYNTAX     Unsigned32 (1..10)
   ACCESS     read-write
   STATUS     mandatory
   DESCRIPTION
     "For the network side procedure, an event is defined as follows: (1) 
      receipt of a STATUS ENQUIRY message, or (2) expiration of timer 
      T392. An error event is (1) nonreceipt of STATUS ENQUIRY in 
      T392 seconds; (2) invalid format of an LMI message; (3) invalid 
      receive sequence number.
      For the user side procedure, an event is defined as a polling cycle or 
      a status enquiry and status report exchange. An error event is (1) 
      non-receipt of a STATUS within the polling cycle, or (2) invalid 
      format of an LMI message, or (3) invalid sequence number.
      
      This attribute specifies the number of error events which, if they 
      occur within eventCount events, will cause a protocol error 
      condition. The condition is cleared after eventCount sequential 
      correct events occur.
      
      It must be less than or equal to eventCount (n393)."
   DEFVAL     { 3 }
::= { mcsMgrFrf5EpGEpLmiParmsEntry 3 }

mcsMgrFrf5EpGEpLmiEventCount OBJECT-TYPE
   SYNTAX     Unsigned32 (1..10)
   ACCESS     read-write
   STATUS     mandatory
   DESCRIPTION
     "This attribute specifies the number of contiguous events within 
      which no more than eventErrorThreshold error events are allowed.
      
      It must be greater than or equal to errorEventThreshold (n392)."
   DEFVAL     { 4 }
::= { mcsMgrFrf5EpGEpLmiParmsEntry 4 }

mcsMgrFrf5EpGEpLmiCheckPointTimer OBJECT-TYPE
   SYNTAX     Unsigned32 (5..255)
   ACCESS     read-write
   STATUS     mandatory
   DESCRIPTION
     "This attribute selects the time (in seconds) within which a STATUS 
      ENQUIRY message is expected. It must be greater than 
      linkVerificationTimer (t391)."
   DEFVAL     { 200 }
::= { mcsMgrFrf5EpGEpLmiParmsEntry 5 }

mcsMgrFrf5EpGEpLmiSide OBJECT-TYPE
   SYNTAX     INTEGER  {
                 network(0),
                 user(1),
                 both(2) }
   ACCESS     read-write
   STATUS     mandatory
   DESCRIPTION
     "This attribute selects the user side procedure (DTE), or the network 
      side procedure (DCE), or both the user side and the network side 
      procedures of the LMI. 
      
      This attribute can be set to user, network or both."
   DEFVAL     { both }
::= { mcsMgrFrf5EpGEpLmiParmsEntry 8 }

mcsMgrFrf5EpGEpLmiNniParmsTable OBJECT-TYPE
   SYNTAX     SEQUENCE OF McsMgrFrf5EpGEpLmiNniParmsEntry
   ACCESS     not-accessible
   STATUS     mandatory
   DESCRIPTION
     "This group contains the provisionable attributes of the FRF.5 LMI 
      procedures which are unique to NNI."
::= { mcsMgrFrf5EpGEpLmi 11 }

mcsMgrFrf5EpGEpLmiNniParmsEntry OBJECT-TYPE
   SYNTAX     McsMgrFrf5EpGEpLmiNniParmsEntry
   ACCESS     not-accessible
   STATUS     mandatory
   DESCRIPTION
     "An entry in the mcsMgrFrf5EpGEpLmiNniParmsTable."
   INDEX {
      mcsMgrIndex,
      mcsMgrFrf5EpGIndex,
      mcsMgrFrf5EpGEpIndex,
      mcsMgrFrf5EpGEpLmiIndex }
::= { mcsMgrFrf5EpGEpLmiNniParmsTable 1 }

McsMgrFrf5EpGEpLmiNniParmsEntry ::= SEQUENCE {
   mcsMgrFrf5EpGEpLmiFullStatusPollingCycles
      Unsigned32,
   mcsMgrFrf5EpGEpLmiLinkVerificationTimer
      Unsigned32 }

mcsMgrFrf5EpGEpLmiFullStatusPollingCycles OBJECT-TYPE
   SYNTAX     Unsigned32 (1..255)
   ACCESS     read-write
   STATUS     mandatory
   DESCRIPTION
     "This attribute specifies how frequently the FRF.5 LMI initiates a 
      Status Enquiry for a full PVC status report. A polling cycle is a 
      Status Enquiry and Status Report exchange."
   DEFVAL     { 1 }
::= { mcsMgrFrf5EpGEpLmiNniParmsEntry 1 }

mcsMgrFrf5EpGEpLmiLinkVerificationTimer OBJECT-TYPE
   SYNTAX     Unsigned32 (5..255)
   ACCESS     read-write
   STATUS     mandatory
   DESCRIPTION
     "This attribute specifies how frequently the FRF.5 LMI initiates a 
      Status Enquiry for link integrity verification. It must be less than 
      checkPointTimer (t392)."
   DEFVAL     { 180 }
::= { mcsMgrFrf5EpGEpLmiNniParmsEntry 2 }

mcsMgrFrf5EpGEpLmiStateTable OBJECT-TYPE
   SYNTAX     SEQUENCE OF McsMgrFrf5EpGEpLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mcsMgrFrf5EpGEpLmi 12 }

mcsMgrFrf5EpGEpLmiStateEntry OBJECT-TYPE
   SYNTAX     McsMgrFrf5EpGEpLmiStateEntry
   ACCESS     not-accessible
   STATUS     mandatory
   DESCRIPTION
     "An entry in the mcsMgrFrf5EpGEpLmiStateTable."
   INDEX {
      mcsMgrIndex,
      mcsMgrFrf5EpGIndex,
      mcsMgrFrf5EpGEpIndex,
      mcsMgrFrf5EpGEpLmiIndex }
::= { mcsMgrFrf5EpGEpLmiStateTable 1 }

McsMgrFrf5EpGEpLmiStateEntry ::= SEQUENCE {
   mcsMgrFrf5EpGEpLmiAdminState
      INTEGER,
   mcsMgrFrf5EpGEpLmiOperationalState
      INTEGER,
   mcsMgrFrf5EpGEpLmiUsageState
      INTEGER }

mcsMgrFrf5EpGEpLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mcsMgrFrf5EpGEpLmiStateEntry 1 }

mcsMgrFrf5EpGEpLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mcsMgrFrf5EpGEpLmiStateEntry 2 }

mcsMgrFrf5EpGEpLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mcsMgrFrf5EpGEpLmiStateEntry 3 }

mcsMgrFrf5EpGEpLmiPsiTable OBJECT-TYPE
   SYNTAX     SEQUENCE OF McsMgrFrf5EpGEpLmiPsiEntry
   ACCESS     not-accessible
   STATUS     mandatory
   DESCRIPTION
     "This group provides the protocol status of the Local Management 
      Interface."
::= { mcsMgrFrf5EpGEpLmi 13 }

mcsMgrFrf5EpGEpLmiPsiEntry OBJECT-TYPE
   SYNTAX     McsMgrFrf5EpGEpLmiPsiEntry
   ACCESS     not-accessible
   STATUS     mandatory
   DESCRIPTION
     "An entry in the mcsMgrFrf5EpGEpLmiPsiTable."
   INDEX {
      mcsMgrIndex,
      mcsMgrFrf5EpGIndex,
      mcsMgrFrf5EpGEpIndex,
      mcsMgrFrf5EpGEpLmiIndex }
::= { mcsMgrFrf5EpGEpLmiPsiTable 1 }

McsMgrFrf5EpGEpLmiPsiEntry ::= SEQUENCE {
   mcsMgrFrf5EpGEpLmiProtocolStatus
      INTEGER }

mcsMgrFrf5EpGEpLmiProtocolStatus OBJECT-TYPE
   SYNTAX     INTEGER  {
                 errorCondition(0),
                 normalCondition(1) }
   ACCESS     read-only
   STATUS     mandatory
   DESCRIPTION
     "This attribute indicates whether the LMI is in an error condition or 
      whether the protocol is behaving normally. This attribute will be set 
      to errorCondition after enough LMI errors have been detected to 
      warrant a change in condition. This occurs when n392 of the last 
      n393 events are in error.
      The error condition is lifted when a sufficient number of 
      consecutive events has occurred without error. This occurs when 
      n393 consecutive good events take place.
      The consequence of an error condition is that all DLCIs on this 
      interface will become inactive in both directions."
   DEFVAL     { normalCondition }
::= { mcsMgrFrf5EpGEpLmiPsiEntry 1 }

mcsMgrFrf5EpGEpLmiStatsTable OBJECT-TYPE
   SYNTAX     SEQUENCE OF McsMgrFrf5EpGEpLmiStatsEntry
   ACCESS     not-accessible
   STATUS     mandatory
   DESCRIPTION
     "This group contains the operational statistics for the FRF.5 NNI 
      Local Management Interface."
::= { mcsMgrFrf5EpGEpLmi 14 }

mcsMgrFrf5EpGEpLmiStatsEntry OBJECT-TYPE
   SYNTAX     McsMgrFrf5EpGEpLmiStatsEntry
   ACCESS     not-accessible
   STATUS     mandatory
   DESCRIPTION
     "An entry in the mcsMgrFrf5EpGEpLmiStatsTable."
   INDEX {
      mcsMgrIndex,
      mcsMgrFrf5EpGIndex,
      mcsMgrFrf5EpGEpIndex,
      mcsMgrFrf5EpGEpLmiIndex }
::= { mcsMgrFrf5EpGEpLmiStatsTable 1 }

McsMgrFrf5EpGEpLmiStatsEntry ::= SEQUENCE {
   mcsMgrFrf5EpGEpLmiKeepAliveStatusToInterface
      Counter32,
   mcsMgrFrf5EpGEpLmiFullStatusToInterface
      Counter32,
   mcsMgrFrf5EpGEpLmiKeepAliveStatusEnqFromInterface
      Counter32,
   mcsMgrFrf5EpGEpLmiFullStatusEnqFromInterface
      Counter32,
   mcsMgrFrf5EpGEpLmiNetworkSideEventHistory
      AsciiString,
   mcsMgrFrf5EpGEpLmiUserSideEventHistory
      AsciiString,
   mcsMgrFrf5EpGEpLmiProtocolErrors
      Counter32,
   mcsMgrFrf5EpGEpLmiUnexpectedIes
      Counter32,
   mcsMgrFrf5EpGEpLmiSequenceErrors
      Counter32,
   mcsMgrFrf5EpGEpLmiStatusSequenceErrors
      Counter32,
   mcsMgrFrf5EpGEpLmiUnexpectedReports
      Counter32,
   mcsMgrFrf5EpGEpLmiPollingVerifTimeouts
      Counter32,
   mcsMgrFrf5EpGEpLmiNoStatusReportCount
      Counter32,
   mcsMgrFrf5EpGEpLmiKeepAliveEnqToIf
      Counter32,
   mcsMgrFrf5EpGEpLmiFullStatusEnqToIf
      Counter32 }

mcsMgrFrf5EpGEpLmiKeepAliveStatusToInterface OBJECT-TYPE
   SYNTAX     Counter32 
   ACCESS     read-only
   STATUS     mandatory
   DESCRIPTION
     "This attribute counts the Local Management Interface keep alive 
      status messages sent to the ATM VCC in response to a status 
      enquiry for keep alive status. When the maximum count is reached 
      it wraps to zero."
::= { mcsMgrFrf5EpGEpLmiStatsEntry 1 }

mcsMgrFrf5EpGEpLmiFullStatusToInterface OBJECT-TYPE
   SYNTAX     Counter32 
   ACCESS     read-only
   STATUS     mandatory
   DESCRIPTION
     "This attribute counts the Local Management Interface full status 
      messages sent to the ATM VCC in response to a status enquiry for 
      keep alive or full status. When the maximum count is reached it 
      wraps to zero."
::= { mcsMgrFrf5EpGEpLmiStatsEntry 2 }

mcsMgrFrf5EpGEpLmiKeepAliveStatusEnqFromInterface OBJECT-TYPE
   SYNTAX     Counter32 
   ACCESS     read-only
   STATUS     mandatory
   DESCRIPTION
     "This attribute counts the Local Management Interface valid keep 
      alive status enquiry messages received from the ATM VCC. When 
      the maximum count is reached it wraps to zero."
::= { mcsMgrFrf5EpGEpLmiStatsEntry 3 }

mcsMgrFrf5EpGEpLmiFullStatusEnqFromInterface OBJECT-TYPE
   SYNTAX     Counter32 
   ACCESS     read-only
   STATUS     mandatory
   DESCRIPTION
     "This attribute counts the Local Management Interface valid full 
      status enquiry messages received from the ATM VCC. When the 
      maximum count is reached it wraps to zero."
::= { mcsMgrFrf5EpGEpLmiStatsEntry 4 }

mcsMgrFrf5EpGEpLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The left most 
      event is the most recent to occur. The provisioned eventCount 
      dictates the maximum number of events displayed. A good event is 
      triggered by receipt of a valid status enquiry message. An error 
      event is either a T392 timer expiry or receipt of a status enquiry 
      with an incorrect sequence number."
::= { mcsMgrFrf5EpGEpLmiStatsEntry 5 }

mcsMgrFrf5EpGEpLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The left most 
      event is the most recent to occur. The provisioned eventCount 
      dictates the maximum number of events displayed. A good event is 
      triggered by receipt of a valid status message. An error event is 
      either a T391 timer expiry or receipt of a status message with an 
      incorrect sequence number."
::= { mcsMgrFrf5EpGEpLmiStatsEntry 6 }

mcsMgrFrf5EpGEpLmiProtocolErrors OBJECT-TYPE
   SYNTAX     Counter32 
   ACCESS     read-only
   STATUS     mandatory
   DESCRIPTION
     "This attribute counts the number of Local Management Interface 
      protocol errors. It is the sum of the sequence (sequenceErrors and 
      statusSequenceErrors) and timeout (pollingVerifTimeouts and 
      noStatusReportCount) errors. When the maximum count is reached 
      it wraps to zero."
::= { mcsMgrFrf5EpGEpLmiStatsEntry 7 }

mcsMgrFrf5EpGEpLmiUnexpectedIes OBJECT-TYPE
   SYNTAX     Counter32 
   ACCESS     read-only
   STATUS     mandatory
   DESCRIPTION
     "This attribute counts the number of Local Managament Interface 
      frames received with an Information Element identifier that is 
      unknown or unexpected. An unexpected Information Element is not 
      a protocol error. When the maximum count is reached, this counter 
      wraps to zero."
::= { mcsMgrFrf5EpGEpLmiStatsEntry 8 }

mcsMgrFrf5EpGEpLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is reached the counter wraps to zero."
::= { mcsMgrFrf5EpGEpLmiStatsEntry 9 }

mcsMgrFrf5EpGEpLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is reached the 
      counter wraps to zero."
::= { mcsMgrFrf5EpGEpLmiStatsEntry 10 }

mcsMgrFrf5EpGEpLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is reached the counter wraps to zero."
::= { mcsMgrFrf5EpGEpLmiStatsEntry 11 }

mcsMgrFrf5EpGEpLmiPollingVerifTimeouts OBJECT-TYPE
   SYNTAX     Counter32 
   ACCESS     read-only
   STATUS     mandatory
   DESCRIPTION
     "This attribute counts the checkPointTimer (T392) expiries occurring 
      on the Local Management Interface. When the maximum count is 
      reached the counter wraps to zero."
::= { mcsMgrFrf5EpGEpLmiStatsEntry 12 }

mcsMgrFrf5EpGEpLmiNoStatusReportCount OBJECT-TYPE
   SYNTAX     Counter32 
   ACCESS     read-only
   STATUS     mandatory
   DESCRIPTION
     "This attribute counts the number of times when no status report or 
      an invalid status report comes from the external network. This 
      attribute is incremented:
      i) after a status enquiry is sent out and the T391 timer expires 
      without having a status report received.
      ii) if an invalid status report is received.
      
      When the maximum count is reached it wraps to zero."
::= { mcsMgrFrf5EpGEpLmiStatsEntry 13 }

mcsMgrFrf5EpGEpLmiKeepAliveEnqToIf OBJECT-TYPE
   SYNTAX     Counter32 
   ACCESS     read-only
   STATUS     mandatory
   DESCRIPTION
     "This attribute counts the number of Local Management Interface 
      keep alive enquiry status messages sent to the external user device 
      for keep alive status. When the maximum count is reached it wraps 
      to zero."
::= { mcsMgrFrf5EpGEpLmiStatsEntry 14 }

mcsMgrFrf5EpGEpLmiFullStatusEnqToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { mcsMgrFrf5EpGEpLmiStatsEntry 15 }


-- McsMgr Frf5EpG/n Ep/n EndPointDescriptor
-- This component describes the ATM SPVC which supports the 
-- FRF.5 connection.

mcsMgrFrf5EpGEpEpd OBJECT IDENTIFIER ::= { mcsMgrFrf5EpGEp 3 }



mcsMgrFrf5EpGEpEpdRowStatusTable OBJECT-TYPE
   SYNTAX     SEQUENCE OF McsMgrFrf5EpGEpEpdRowStatusEntry
   ACCESS     not-accessible
   STATUS     mandatory
   DESCRIPTION
     "This entry controls the addition and deletion of 
      mcsMgrFrf5EpGEpEpd components."
::= { mcsMgrFrf5EpGEpEpd 1 }

mcsMgrFrf5EpGEpEpdRowStatusEntry OBJECT-TYPE
   SYNTAX     McsMgrFrf5EpGEpEpdRowStatusEntry
   ACCESS     not-accessible
   STATUS     mandatory
   DESCRIPTION
     "A single entry in the table represents a single 
      mcsMgrFrf5EpGEpEpd component."
   INDEX {
      mcsMgrIndex,
      mcsMgrFrf5EpGIndex,
      mcsMgrFrf5EpGEpIndex,
      mcsMgrFrf5EpGEpEpdIndex }
::= { mcsMgrFrf5EpGEpEpdRowStatusTable 1 }

McsMgrFrf5EpGEpEpdRowStatusEntry ::= SEQUENCE {
   mcsMgrFrf5EpGEpEpdRowStatus
      RowStatus,
   mcsMgrFrf5EpGEpEpdComponentName
      DisplayString,
   mcsMgrFrf5EpGEpEpdStorageType
      StorageType,
   mcsMgrFrf5EpGEpEpdIndex
      NonReplicated }

mcsMgrFrf5EpGEpEpdRowStatus OBJECT-TYPE
   SYNTAX     RowStatus 
   ACCESS     read-only
   STATUS     mandatory
   DESCRIPTION
     "This variable is used as the basis for SNMP naming of
      mcsMgrFrf5EpGEpEpd components.
      These components cannot be added nor deleted."
::= { mcsMgrFrf5EpGEpEpdRowStatusEntry 1 }

mcsMgrFrf5EpGEpEpdComponentName OBJECT-TYPE
   SYNTAX     DisplayString 
   ACCESS     read-only
   STATUS     mandatory
   DESCRIPTION
     "This variable provides the component's string name for
      use with the ASCII Console Interface"
::= { mcsMgrFrf5EpGEpEpdRowStatusEntry 2 }

mcsMgrFrf5EpGEpEpdStorageType OBJECT-TYPE
   SYNTAX     StorageType 
   ACCESS     read-only
   STATUS     mandatory
   DESCRIPTION
     "This variable represents the storage type value for the
      mcsMgrFrf5EpGEpEpd tables."
::= { mcsMgrFrf5EpGEpEpdRowStatusEntry 4 }

mcsMgrFrf5EpGEpEpdIndex OBJECT-TYPE
   SYNTAX     NonReplicated 
   ACCESS     not-accessible
   STATUS     mandatory
   DESCRIPTION
     "This variable represents the index for the mcsMgrFrf5EpGEpEpd tables."
::= { mcsMgrFrf5EpGEpEpdRowStatusEntry 10 }

mcsMgrFrf5EpGEpEpdProvTable OBJECT-TYPE
   SYNTAX     SEQUENCE OF McsMgrFrf5EpGEpEpdProvEntry
   ACCESS     not-accessible
   STATUS     mandatory
   DESCRIPTION
     "This group contains the provisionable attributes of the FRF.5 End 
      Point."
::= { mcsMgrFrf5EpGEpEpd 10 }

mcsMgrFrf5EpGEpEpdProvEntry OBJECT-TYPE
   SYNTAX     McsMgrFrf5EpGEpEpdProvEntry
   ACCESS     not-accessible
   STATUS     mandatory
   DESCRIPTION
     "An entry in the mcsMgrFrf5EpGEpEpdProvTable."
   INDEX {
      mcsMgrIndex,
      mcsMgrFrf5EpGIndex,
      mcsMgrFrf5EpGEpIndex,
      mcsMgrFrf5EpGEpEpdIndex }
::= { mcsMgrFrf5EpGEpEpdProvTable 1 }

McsMgrFrf5EpGEpEpdProvEntry ::= SEQUENCE {
   mcsMgrFrf5EpGEpEpdRemoteConnectionIdentifier
      IntegerSequence,
   mcsMgrFrf5EpGEpEpdConnectionTransferPriority
      Unsigned32,
   mcsMgrFrf5EpGEpEpdCommittedInformationRate
      Unsigned32,
   mcsMgrFrf5EpGEpEpdExcessInformationRate
      Unsigned32,
   mcsMgrFrf5EpGEpEpdCommittedBurstSize
      Unsigned32,
   mcsMgrFrf5EpGEpEpdType
      INTEGER,
   mcsMgrFrf5EpGEpEpdAccessRate
      Unsigned32,
   mcsMgrFrf5EpGEpEpdExcessBurstSize
      Unsigned32 }

mcsMgrFrf5EpGEpEpdRemoteConnectionIdentifier OBJECT-TYPE
   SYNTAX     IntegerSequence (SIZE (3..9))
   ACCESS     read-write
   STATUS     mandatory
   DESCRIPTION
     "This attribute specifies the remote connection identifier. It either 
      represents the VPI.VCI logical channel number assignment of a 
      remote ATM interface, or the Endpoint.Frf5EndPointGroup 
      instances of a remote Passport FRF.5 EndPoint."
::= { mcsMgrFrf5EpGEpEpdProvEntry 3 }

mcsMgrFrf5EpGEpEpdConnectionTransferPriority OBJECT-TYPE
   SYNTAX     Unsigned32 (0..15)
   ACCESS     read-write
   STATUS     mandatory
   DESCRIPTION
     "This attribute specifies the transfer priority used to establish the 
      ATM connection. The EndPoint references the ModuleData 
      FrameRelayService AtmNetworking TransferPriority/n component 
      to determine the ATM service category to be used by the 
      connection.
      This attribute is also used to determine which EndPoint within an 
      Frf5EndPointGroup is to multiplex a particular FrAtm Dlci.
      DESCRIPTION"
::= { mcsMgrFrf5EpGEpEpdProvEntry 4 }

mcsMgrFrf5EpGEpEpdCommittedInformationRate OBJECT-TYPE
   SYNTAX     Unsigned32 (0..50000000)
   ACCESS     read-write
   STATUS     mandatory
   DESCRIPTION
     "This attribute specifies the committed information rate (CIR), and 
      represents the rate at which the network FRF.5 ATM VCC agrees to 
      transfer information under normal conditions. A conservative CIR 
      value would be the sum of the CIRs of all the individual FrAtm 
      Dlcis multiplexed by the VCC.
      The cir is converted into ATM service parameters according to the 
      conversion policy specified by the connectionTransferPriority 
      attribute. The conversion policy is defined under the ModuleData 
      FrameRelayService AtmNetworking TransferPriority/n component."
   DEFVAL     { 64000 }
::= { mcsMgrFrf5EpGEpEpdProvEntry 5 }

mcsMgrFrf5EpGEpEpdExcessInformationRate OBJECT-TYPE
   SYNTAX     Unsigned32 (0..50000000)
   ACCESS     read-write
   STATUS     mandatory
   DESCRIPTION
     "This attribute specifies the excess information rate (EIR), and 
      represents the rate at which the network FRF.5 ATM VCC attempts 
      to transfer information. A conservative EIR value would be the sum 
      of the EIRs of all the individual FrAtm Dlcis multiplexed by the 
      VCC.
      The eir is converted into ATM service parameters according to the 
      conversion policy specified by the connectionTransferPriority 
      attribute. The conversion policy is defined under the ModuleData 
      FrameRelayService AtmNetworking TransferPriority/n component."
   DEFVAL     { 0 }
::= { mcsMgrFrf5EpGEpEpdProvEntry 6 }

mcsMgrFrf5EpGEpEpdCommittedBurstSize OBJECT-TYPE
   SYNTAX     Unsigned32 (0..50000000)
   ACCESS     read-write
   STATUS     mandatory
   DESCRIPTION
     "This attribute specifies the committed burst size (Bc), and represents 
      the amount of data that the network FRF.5 ATM VCC agrees to 
      transfer under normal conditions. A conservative Bc value would be 
      the sum of the Bcs of all the individual FrAtm Dlcis multiplexed by 
      the VCC.
      The bc is converted into ATM service parameters according to the 
      conversion policy specified by the connectionTransferPriority 
      attribute. The conversion policy is defined under the ModuleData 
      FrameRelayService AtmNetworking TransferPriority/n component."
   DEFVAL     { 16000 }
::= { mcsMgrFrf5EpGEpEpdProvEntry 7 }

mcsMgrFrf5EpGEpEpdType OBJECT-TYPE
   SYNTAX     INTEGER  {
                 master(0),
                 slave(1) }
   ACCESS     read-write
   STATUS     mandatory
   DESCRIPTION
     "This attribute specifies the FRF.5 End Point type. If the value is 
      provisioned as master, this End Point is responsible for initiating 
      the SPVC call to set up the FRF.5 ATM VCC. If the value is 
      provisioned as slave, this End Point receives call setup requests 
      from a master remote end."
   DEFVAL     { master }
::= { mcsMgrFrf5EpGEpEpdProvEntry 8 }

mcsMgrFrf5EpGEpEpdAccessRate OBJECT-TYPE
   SYNTAX     Unsigned32 (0..50000000)
   ACCESS     read-write
   STATUS     mandatory
   DESCRIPTION
     "This attribute represents the access rate of the FRF.5 EndPoint. A 
      conservative value would be the sum of the access rates of all the 
      FrAtms' that have DLCIs multiplexed by the VCC. The access rate 
      is converted into ATM service parameters when conversion policies 
      3, 4 and 5 are used. For policy 6, this attribute is ignored."
   DEFVAL     { 1536000 }
::= { mcsMgrFrf5EpGEpEpdProvEntry 9 }

mcsMgrFrf5EpGEpEpdExcessBurstSize OBJECT-TYPE
   SYNTAX     Unsigned32 (0..50000000)
   ACCESS     read-write
   STATUS     mandatory
   DESCRIPTION
     "This attribute specifies the excess burst size (Be), and represents the 
      amount of uncommitted data that the network FRF.5 ATM VCC 
      agrees to transfer under normal conditions. A conservative Be value 
      would be the sum of the Bes of all the individual FrAtm Dlcis 
      multiplexed by the VCC.
      The be is converted into ATM service parameters according to the 
      conversion policy specified by the connectionTransferPriority 
      attribute. The conversion policy is defined under the ModuleData 
      FrameRelayService AtmNetworking TransferPriority/n component."
   DEFVAL     { 0 }
::= { mcsMgrFrf5EpGEpEpdProvEntry 10 }

mcsMgrFrf5EpGEpEpdCidDataTable OBJECT-TYPE
   SYNTAX     SEQUENCE OF McsMgrFrf5EpGEpEpdCidDataEntry
   ACCESS     not-accessible
   STATUS     mandatory
   DESCRIPTION
     "This group contains the attribute for a component's Customer 
      Identifier (CID). Refer to the attribute description for a detailed 
      explanation of CIDs."
::= { mcsMgrFrf5EpGEpEpd 11 }

mcsMgrFrf5EpGEpEpdCidDataEntry OBJECT-TYPE
   SYNTAX     McsMgrFrf5EpGEpEpdCidDataEntry
   ACCESS     not-accessible
   STATUS     mandatory
   DESCRIPTION
     "An entry in the mcsMgrFrf5EpGEpEpdCidDataTable."
   INDEX {
      mcsMgrIndex,
      mcsMgrFrf5EpGIndex,
      mcsMgrFrf5EpGEpIndex,
      mcsMgrFrf5EpGEpEpdIndex }
::= { mcsMgrFrf5EpGEpEpdCidDataTable 1 }

McsMgrFrf5EpGEpEpdCidDataEntry ::= SEQUENCE {
   mcsMgrFrf5EpGEpEpdCustomerIdentifier
      Unsigned32 }

mcsMgrFrf5EpGEpEpdCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mcsMgrFrf5EpGEpEpdCidDataEntry 1 }

-- 
-- *** THIS SUBTREE CURRENTLY NOT IMPLEMENTED ***
-- 

-- McsMgr Frf5EpGrp/n Ep/n DataLinkConnectionIdentifier/n
-- This component represents a logical connection multiplexed inside 
-- the FRF.5 ATM VCC.

mcsMgrFrf5EpGEpDlci OBJECT IDENTIFIER ::= { mcsMgrFrf5EpGEp 4 }



mcsMgrFrf5EpGEpDlciRowStatusTable OBJECT-TYPE
   SYNTAX     SEQUENCE OF McsMgrFrf5EpGEpDlciRowStatusEntry
   ACCESS     not-accessible
   STATUS     mandatory
   DESCRIPTION
     "*** THIS TABLE CURRENTLY NOT IMPLEMENTED ***

      This entry controls the addition and deletion of 
      mcsMgrFrf5EpGEpDlci components."
::= { mcsMgrFrf5EpGEpDlci 1 }

mcsMgrFrf5EpGEpDlciRowStatusEntry OBJECT-TYPE
   SYNTAX     McsMgrFrf5EpGEpDlciRowStatusEntry
   ACCESS     not-accessible
   STATUS     mandatory
   DESCRIPTION
     "A single entry in the table represents a single 
      mcsMgrFrf5EpGEpDlci component."
   INDEX {
      mcsMgrIndex,
      mcsMgrFrf5EpGIndex,
      mcsMgrFrf5EpGEpIndex,
      mcsMgrFrf5EpGEpDlciIndex }
::= { mcsMgrFrf5EpGEpDlciRowStatusTable 1 }

McsMgrFrf5EpGEpDlciRowStatusEntry ::= SEQUENCE {
   mcsMgrFrf5EpGEpDlciRowStatus
      RowStatus,
   mcsMgrFrf5EpGEpDlciComponentName
      DisplayString,
   mcsMgrFrf5EpGEpDlciStorageType
      StorageType,
   mcsMgrFrf5EpGEpDlciIndex
      Integer32 }

mcsMgrFrf5EpGEpDlciRowStatus OBJECT-TYPE
   SYNTAX     RowStatus 
   ACCESS     read-only
   STATUS     mandatory
   DESCRIPTION
     "This variable is used as the basis for SNMP naming of
      mcsMgrFrf5EpGEpDlci components.
      These components cannot be added nor deleted."
::= { mcsMgrFrf5EpGEpDlciRowStatusEntry 1 }

mcsMgrFrf5EpGEpDlciComponentName OBJECT-TYPE
   SYNTAX     DisplayString 
   ACCESS     read-only
   STATUS     mandatory
   DESCRIPTION
     "This variable provides the component's string name for
      use with the ASCII Console Interface"
::= { mcsMgrFrf5EpGEpDlciRowStatusEntry 2 }

mcsMgrFrf5EpGEpDlciStorageType OBJECT-TYPE
   SYNTAX     StorageType 
   ACCESS     read-only
   STATUS     mandatory
   DESCRIPTION
     "This variable represents the storage type value for the
      mcsMgrFrf5EpGEpDlci tables."
::= { mcsMgrFrf5EpGEpDlciRowStatusEntry 4 }

mcsMgrFrf5EpGEpDlciIndex OBJECT-TYPE
   SYNTAX     Integer32 (16..1007 | 1022)
   ACCESS     not-accessible
   STATUS     mandatory
   DESCRIPTION
     "This variable represents the index for the mcsMgrFrf5EpGEpDlci tables."
::= { mcsMgrFrf5EpGEpDlciRowStatusEntry 10 }

mcsMgrFrf5EpGEpDlciOperTable OBJECT-TYPE
   SYNTAX     SEQUENCE OF McsMgrFrf5EpGEpDlciOperEntry
   ACCESS     not-accessible
   STATUS     mandatory
   DESCRIPTION
     "*** THIS TABLE CURRENTLY NOT IMPLEMENTED ***

      This group contains the operational attributes for the FRF.5 DLCI."
::= { mcsMgrFrf5EpGEpDlci 10 }

mcsMgrFrf5EpGEpDlciOperEntry OBJECT-TYPE
   SYNTAX     McsMgrFrf5EpGEpDlciOperEntry
   ACCESS     not-accessible
   STATUS     mandatory
   DESCRIPTION
     "An entry in the mcsMgrFrf5EpGEpDlciOperTable."
   INDEX {
      mcsMgrIndex,
      mcsMgrFrf5EpGIndex,
      mcsMgrFrf5EpGEpIndex,
      mcsMgrFrf5EpGEpDlciIndex }
::= { mcsMgrFrf5EpGEpDlciOperTable 1 }

McsMgrFrf5EpGEpDlciOperEntry ::= SEQUENCE {
   mcsMgrFrf5EpGEpDlciABitStatusToIf
      INTEGER,
   mcsMgrFrf5EpGEpDlciABitReasonToIf
      INTEGER,
   mcsMgrFrf5EpGEpDlciABitStatusFromIf
      INTEGER,
   mcsMgrFrf5EpGEpDlciABitReasonFromIf
      INTEGER,
   mcsMgrFrf5EpGEpDlciAccessConnectionComponent
      AsciiString }

mcsMgrFrf5EpGEpDlciABitStatusToIf OBJECT-TYPE
   SYNTAX     INTEGER  {
                 inactive(0),
                 active(1) }
   ACCESS     read-only
   STATUS     mandatory
   DESCRIPTION
     "This attribute indicates the most recent A-bit status sent to the ATM 
      VCC. If the value is inactive, the reason for the LMI failure is given 
      by the aBitReasonToNetwork."
   DEFVAL     { inactive }
::= { mcsMgrFrf5EpGEpDlciOperEntry 1 }

mcsMgrFrf5EpGEpDlciABitReasonToIf OBJECT-TYPE
   SYNTAX     INTEGER  {
                 notApplicable(0),
                 remoteUserSignaled(1),
                 localLmiError(2),
                 remoteLmiError(3),
                 localLinkDown(4),
                 remoteLinkDown(5),
                 pvcDown(6) }
   ACCESS     read-only
   STATUS     mandatory
   DESCRIPTION
     "This attribute indicates the reason for the latest inactive A-bit status 
      sent to the ATM VCC.
      The value is notApplicable when the aBitStatusToNetwork is active.
      The value is remoteUserSignaled if the FrAtm originating the A-Bit 
      status has detected that the virtual circuit is down at the remote 
      network through the LMI protocol. The FrAtm must be running 
      network site LMI protocol for this A-Bit status reason to be sent.
      The value is localLmiError if the LMI protocol is down at this Ep.
      The value is remoteLmiError if the LMI protocol is down at the 
      FrAtm originating this A-Bit status reason.
      The value is localLinkDown if the physical interface is disabled at 
      this Ep.
      The value is pvcDown if no A-Bit status has been sent to this Ep 
      (i.e., no A-Bit status has been relayed from the FrAtm).
      The value is remoteLinkDown if the physical interface is disabled 
      at the FrAtm originating this A-Bit status reason."
   DEFVAL     { notApplicable }
::= { mcsMgrFrf5EpGEpDlciOperEntry 2 }

mcsMgrFrf5EpGEpDlciABitStatusFromIf OBJECT-TYPE
   SYNTAX     INTEGER  {
                 inactive(0),
                 active(1) }
   ACCESS     read-only
   STATUS     mandatory
   DESCRIPTION
     "This attribute indicates the most recent A-bit status received from 
      the ATM VCC. If the value is inactive, the reason for the LMI 
      failure is given by the aBitReasonFromNetwork."
   DEFVAL     { inactive }
::= { mcsMgrFrf5EpGEpDlciOperEntry 3 }

mcsMgrFrf5EpGEpDlciABitReasonFromIf OBJECT-TYPE
   SYNTAX     INTEGER  {
                 notApplicable(0),
                 remoteUserSignalled(1),
                 localLmiError(2),
                 localLinkDown(4),
                 missingFromLmiReport(7) }
   ACCESS     read-only
   STATUS     mandatory
   DESCRIPTION
     "This attributes indicates the reason for the latest inactive A-bit 
      status received from the ATM VCC.
      The value is notApplicable when the aBitStatusFromNetwork is 
      active.
      The value is remoteUserSignaled if the remote FRF.5 End Point 
      originating the A-Bit status has detected that the virtual circuit is 
      down at the remote network through the LMI protocol. The remote 
      FRF.5 End Point must be running network site LMI protocol for this 
      A-Bit status reason to be sent.
      The value is localLmiError if the LMI protocol is down at this Ep.
      The value is localLinkDown if the physical interface is disabled at 
      this Ep.
      The value is missingFromLmiReport if the remote FRF.5 End Point 
      did not provide a reason along with the inactive A-Bit status."
   DEFVAL     { notApplicable }
::= { mcsMgrFrf5EpGEpDlciOperEntry 4 }

mcsMgrFrf5EpGEpDlciAccessConnectionComponent OBJECT-TYPE
   SYNTAX     AsciiString (SIZE (0..23))
   ACCESS     read-only
   STATUS     mandatory
   DESCRIPTION
     "This attribute identifies the FrAtm Dlci to which this Dlci 
      component is bound."
::= { mcsMgrFrf5EpGEpDlciOperEntry 5 }


-- An AtmConnection component is created for each ATM connection 
-- established by an application. It shows where the data traffic for this 
-- connection is directed.

mcsMgrFrf5EpGEpAtmCon OBJECT IDENTIFIER ::= { mcsMgrFrf5EpGEp 5 }



mcsMgrFrf5EpGEpAtmConRowStatusTable OBJECT-TYPE
   SYNTAX     SEQUENCE OF McsMgrFrf5EpGEpAtmConRowStatusEntry
   ACCESS     not-accessible
   STATUS     mandatory
   DESCRIPTION
     "This entry controls the addition and deletion of 
      mcsMgrFrf5EpGEpAtmCon components."
::= { mcsMgrFrf5EpGEpAtmCon 1 }

mcsMgrFrf5EpGEpAtmConRowStatusEntry OBJECT-TYPE
   SYNTAX     McsMgrFrf5EpGEpAtmConRowStatusEntry
   ACCESS     not-accessible
   STATUS     mandatory
   DESCRIPTION
     "A single entry in the table represents a single 
      mcsMgrFrf5EpGEpAtmCon component."
   INDEX {
      mcsMgrIndex,
      mcsMgrFrf5EpGIndex,
      mcsMgrFrf5EpGEpIndex,
      mcsMgrFrf5EpGEpAtmConIndex }
::= { mcsMgrFrf5EpGEpAtmConRowStatusTable 1 }

McsMgrFrf5EpGEpAtmConRowStatusEntry ::= SEQUENCE {
   mcsMgrFrf5EpGEpAtmConRowStatus
      RowStatus,
   mcsMgrFrf5EpGEpAtmConComponentName
      DisplayString,
   mcsMgrFrf5EpGEpAtmConStorageType
      StorageType,
   mcsMgrFrf5EpGEpAtmConIndex
      NonReplicated }

mcsMgrFrf5EpGEpAtmConRowStatus OBJECT-TYPE
   SYNTAX     RowStatus 
   ACCESS     read-only
   STATUS     mandatory
   DESCRIPTION
     "This variable is used as the basis for SNMP naming of
      mcsMgrFrf5EpGEpAtmCon components.
      These components cannot be added nor deleted."
::= { mcsMgrFrf5EpGEpAtmConRowStatusEntry 1 }

mcsMgrFrf5EpGEpAtmConComponentName OBJECT-TYPE
   SYNTAX     DisplayString 
   ACCESS     read-only
   STATUS     mandatory
   DESCRIPTION
     "This variable provides the component's string name for
      use with the ASCII Console Interface"
::= { mcsMgrFrf5EpGEpAtmConRowStatusEntry 2 }

mcsMgrFrf5EpGEpAtmConStorageType OBJECT-TYPE
   SYNTAX     StorageType 
   ACCESS     read-only
   STATUS     mandatory
   DESCRIPTION
     "This variable represents the storage type value for the
      mcsMgrFrf5EpGEpAtmCon tables."
::= { mcsMgrFrf5EpGEpAtmConRowStatusEntry 4 }

mcsMgrFrf5EpGEpAtmConIndex OBJECT-TYPE
   SYNTAX     NonReplicated 
   ACCESS     not-accessible
   STATUS     mandatory
   DESCRIPTION
     "This variable represents the index for the mcsMgrFrf5EpGEpAtmCon tables."
::= { mcsMgrFrf5EpGEpAtmConRowStatusEntry 10 }

mcsMgrFrf5EpGEpAtmConOperTable OBJECT-TYPE
   SYNTAX     SEQUENCE OF McsMgrFrf5EpGEpAtmConOperEntry
   ACCESS     not-accessible
   STATUS     mandatory
   DESCRIPTION
     "This attribute group contains the operational attributes for the 
      NapAtmConnection component."
::= { mcsMgrFrf5EpGEpAtmCon 10 }

mcsMgrFrf5EpGEpAtmConOperEntry OBJECT-TYPE
   SYNTAX     McsMgrFrf5EpGEpAtmConOperEntry
   ACCESS     not-accessible
   STATUS     mandatory
   DESCRIPTION
     "An entry in the mcsMgrFrf5EpGEpAtmConOperTable."
   INDEX {
      mcsMgrIndex,
      mcsMgrFrf5EpGIndex,
      mcsMgrFrf5EpGEpIndex,
      mcsMgrFrf5EpGEpAtmConIndex }
::= { mcsMgrFrf5EpGEpAtmConOperTable 1 }

McsMgrFrf5EpGEpAtmConOperEntry ::= SEQUENCE {
   mcsMgrFrf5EpGEpAtmConNextHop
      RowPointer }

mcsMgrFrf5EpGEpAtmConNextHop OBJECT-TYPE
   SYNTAX     RowPointer 
   ACCESS     read-only
   STATUS     mandatory
   DESCRIPTION
     "This attribute shows the component name of the AtmIf Vcc Ep or 
      AtmCon component to which this switched connection is 
      established."
::= { mcsMgrFrf5EpGEpAtmConOperEntry 1 }




-- 
-- Version and Compliance statements
-- 



-- Object-Group Statement:
-- A list of all current accessible leaf objects.

-- OBJECTS { mcsMgrFrf5EpGEpLmiProtocolStatus,
--           mcsMgrFrf5EpGEpSustainedCellRate01,
--           mcsMgrFrf5EpGEpLmiSequenceErrors,
--           mcsMgrFrf5EpGEpLmiAdminState,
--           mcsMgrFrf5EpGEpLmiProtocolErrors,
--           mcsMgrFrf5EpGEpLastVccCauseDiag,
--           mcsMgrFrf5EpGEpLmiFullStatusEnqToIf,
--           mcsMgrFrf5EpGEpLmiRowStatus,
--           mcsMgrFrf5EpGEpLmiKeepAliveEnqToIf,
--           mcsMgrFrf5EpGEpLmiEventCount,
--           mcsMgrFrf5EpGEpDlciABitStatusToIf,
--           mcsMgrFrf5EpGEpEpdAccessRate,
--           mcsMgrFrf5EpGEpEpdComponentName,
--           mcsMgrFrf5EpGEpEpdType,
--           mcsMgrFrf5EpGEpStandbyStatus,
--           mcsMgrFrf5EpGEpTrafficParmConversionPolicy,
--           mcsMgrFrf5EpGEpLmiUserSideEventHistory,
--           mcsMgrFrf5EpGEpAvailabilityStatus,
--           mcsMgrFrf5EpGEpPeakCellRate01,
--           mcsMgrFrf5EpGEpDlciStorageType,
--           mcsMgrFrf5EpGEpLmiUsageState,
--           mcsMgrFrf5EpGEpLmiFullStatusEnqFromInterface,
--           mcsMgrFrf5EpGEpLmiSide,
--           mcsMgrFrf5EpGEpDlciAccessConnectionComponent,
--           mcsMgrFrf5EpGEpAlarmStatus,
--           mcsMgrFrf5EpGEpLmiComponentName,
--           mcsMgrFrf5EpGEpLmiErrorEventThreshold,
--           mcsMgrFrf5EpGEpLmiNetworkSideEventHistory,
--           mcsMgrFrf5EpGEpEpdCommittedBurstSize,
--           mcsMgrFrf5EpGEpUnknownStatus,
--           mcsMgrFrf5EpGEpMaximumBurstSize0,
--           mcsMgrFrf5EpGEpLmiProcedures,
--           mcsMgrFrf5EpGEpEpdExcessInformationRate,
--           mcsMgrFrf5EpGEpEpdExcessBurstSize,
--           mcsMgrFrf5EpGEpConnectionTransferPriority,
--           mcsMgrFrf5EpGEpLmiOperationalState,
--           mcsMgrFrf5EpGEpLmiUnexpectedReports,
--           mcsMgrFrf5EpGEpControlStatus,
--           mcsMgrFrf5EpGEpEpdRowStatus,
--           mcsMgrFrf5EpGEpDlciABitReasonToIf,
--           mcsMgrFrf5EpGAddrAddrPreRowStatus,
--           mcsMgrFrf5EpGEpEpdCustomerIdentifier,
--           mcsMgrFrf5EpGAddrComponentName,
--           mcsMgrFrf5EpGEpEpdRemoteConnectionIdentifier,
--           mcsMgrFrf5EpGAddrStorageType,
--           mcsMgrFrf5EpGStorageType,
--           mcsMgrFrf5EpGEpSustainedCellRate0,
--           mcsMgrFrf5EpGEpEpdCommittedInformationRate,
--           mcsMgrFrf5EpGEpLmiAsyncStatusReport,
--           mcsMgrFrf5EpGAddrAddrPreValue,
--           mcsMgrFrf5EpGEpAdminState,
--           mcsMgrFrf5EpGEpAtmConStorageType,
--           mcsMgrFrf5EpGEpOperationalState,
--           mcsMgrFrf5EpGEpDlciABitStatusFromIf,
--           mcsMgrFrf5EpGEpStorageType,
--           mcsMgrFrf5EpGEpLmiFullStatusToInterface,
--           mcsMgrFrf5EpGEpEpdConnectionTransferPriority,
--           mcsMgrFrf5EpGEpRowStatus,
--           mcsMgrFrf5EpGEpEpdStorageType,
--           mcsMgrFrf5EpGEpAtmConNextHop,
--           mcsMgrFrf5EpGEpLmiLinkVerificationTimer,
--           mcsMgrFrf5EpGRowStatus,
--           mcsMgrFrf5EpGEpProceduralStatus,
--           mcsMgrFrf5EpGEpLmiPollingVerifTimeouts,
--           mcsMgrFrf5EpGEpAvgFrameSize,
--           mcsMgrFrf5EpGEpDlciABitReasonFromIf,
--           mcsMgrFrf5EpGAddrCommentText,
--           mcsMgrFrf5EpGEpType,
--           mcsMgrFrf5EpGAddrRowStatus,
--           mcsMgrFrf5EpGAddrRemoteAddress,
--           mcsMgrFrf5EpGEpLmiKeepAliveStatusEnqFromInterface,
--           mcsMgrFrf5EpGEpUsageState,
--           mcsMgrFrf5EpGEpDlciComponentName,
--           mcsMgrFrf5EpGEpMaximumBurstSize01,
--           mcsMgrFrf5EpGEpServiceCategory,
--           mcsMgrFrf5EpGEpComponentName,
--           mcsMgrFrf5EpGEpLmiStorageType,
--           mcsMgrFrf5EpGEpAtmConRowStatus,
--           mcsMgrFrf5EpGEpLastVccClearCause,
--           mcsMgrFrf5EpGEpLmiNoStatusReportCount,
--           mcsMgrFrf5EpGEpLmiUnexpectedIes,
--           mcsMgrFrf5EpGEpLmiStatusSequenceErrors,
--           mcsMgrFrf5EpGEpDlciRowStatus,
--           mcsMgrFrf5EpGEpLmiKeepAliveStatusToInterface,
--           mcsMgrFrf5EpGEpAtmConComponentName,
--           mcsMgrFrf5EpGEpLmiFullStatusPollingCycles,
--           mcsMgrFrf5EpGComponentName,
--           mcsMgrFrf5EpGEpLmiCheckPointTimer }
-- STATUS  mandatory
-- DESCRIPTION
--   "A list of all current accessible leaf objects."

frf5EpGroup OBJECT IDENTIFIER ::= { frf5EpMIB 1 }
frf5EpGroupBD OBJECT IDENTIFIER ::= { frf5EpGroup 4 }
frf5EpGroupBD02 OBJECT IDENTIFIER ::= { frf5EpGroupBD 3 }
frf5EpGroupBD02A OBJECT IDENTIFIER ::= { frf5EpGroupBD02 2 }



-- Agent-Capabilities Statement:

-- PRODUCT-RELEASE "Passport Release 7.0 Frf5Ep."
-- STATUS          mandatory
-- DESCRIPTION     "Frf5Ep MIB: MIB Version BD02A,
--                  Software Version BG00S4C."
-- SUPPORTS        Nortel-Magellan-Passport-Frf5EpMIB
--    INCLUDES     { frf5EpGroupBD02A }

frf5EpCapabilities OBJECT IDENTIFIER ::= { frf5EpMIB 3 }
frf5EpCapabilitiesBD OBJECT IDENTIFIER ::= { frf5EpCapabilities 4 }
frf5EpCapabilitiesBD02 OBJECT IDENTIFIER ::= { frf5EpCapabilitiesBD 3 }
frf5EpCapabilitiesBD02A OBJECT IDENTIFIER ::= { frf5EpCapabilitiesBD02 2 }





END
