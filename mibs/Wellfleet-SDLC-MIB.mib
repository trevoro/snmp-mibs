Wellfleet-SDLC-MIB DEFINITIONS ::= BEGIN

-- Created by mdl2asn version 3.1
-- Creation date: Wed Aug 30 16:47:24 EDT 1995


    IMPORTS

      Counter, TimeTicks
        FROM RFC1155-SMI
      OBJECT-TYPE
        FROM RFC-1212
      DisplayString
        FROM RFC1213-MIB
      wfSdlcGroup
        FROM Wellfleet-COMMON-MIB;


    wfSdlc		OBJECT IDENTIFIER ::= { wfSdlcGroup 1 }

    wfSdlcDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete SDLC."
        DEFVAL	{ created }
        ::= { wfSdlc 1 }

    wfSdlcDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable SDLC."
        DEFVAL	{ enabled }
        ::= { wfSdlc 2 }

    wfSdlcState OBJECT-TYPE
        SYNTAX	INTEGER {
    		    up(1),
    		    down(2),
    		    init(3),
    		    notpresent(4)
    		}
        ACCESS	read-only
        STATUS	mandatory
        DESCRIPTION
                "The current state of SDLC."
        DEFVAL	{ down }
        ::= { wfSdlc 3 }

    wfSdlcPortAdminTable OBJECT-TYPE
        SYNTAX	SEQUENCE OF WfSdlcPortAdminEntry
        ACCESS	not-accessible
        STATUS	mandatory
        DESCRIPTION
                "-- THE SDLC PORT ADMINISTRATIVE TABLE
                'This table contains objects that can be changed to manage an SDLC port.
                Changing one of these parameters  take effect in the operating port
                immediately or may wait until the interface is restarted depending on
                the object. Most of the objects in this read-write table have
                corresponding read-only objects in the wfSdlcPortOperTable that return
                the current opeating value. The operating values may be different from
                these configured values if a configured parameter was changed after the
                interface was started."
        ::= { wfSdlcGroup 2 }

    wfSdlcPortAdminEntry OBJECT-TYPE
        SYNTAX	WfSdlcPortAdminEntry
        ACCESS	not-accessible
        STATUS	mandatory
        DESCRIPTION
                "A list of configured values for an SDLC port"
        INDEX	{ wfSdlcPortAdminIndex }
        ::= { wfSdlcPortAdminTable 1 }

    WfSdlcPortAdminEntry ::= SEQUENCE {
    	    wfSdlcPortAdminDelete
    		INTEGER,
    	    wfSdlcPortAdminDisable
    		INTEGER,
    	    wfSdlcPortAdminIndex
    		INTEGER,
    	    wfSdlcPortAdminAddress4
    		DisplayString,
    	    wfSdlcPortAdminType
    		INTEGER,
    	    wfSdlcPortAdminTopology
    		INTEGER,
    	    wfSdlcPortAdminACTIVTO
    		INTEGER,
    	    wfSdlcPortAdminPAUSE
    		INTEGER,
    	    wfSdlcPortAdminCredit
    		INTEGER,
    	    wfSdlcPortAdminIdleTimer
    		INTEGER,
    	    wfSdlcPortAdminIdleRetry
    		INTEGER,
    	    wfSdlcPortAdminNPRcvTimer
    		INTEGER,
    	    wfSdlcPortAdminNPRcvRetry
    		INTEGER,
    	    wfSdlcPortAdminWriteTimer
    		INTEGER,
    	    wfSdlcPortAdminWriteRetry
    		INTEGER,
    	    wfSdlcPortAdminLinkConnTimer
    		INTEGER,
    	    wfSdlcPortAdminLinkConnRetry
    		INTEGER,
    	    wfSdlcPortAdminPriFdplx
    		INTEGER,
    	    wfSdlcPortAdminSecFdplx
    		INTEGER,
    	    wfSdlcPortAdminUseRej
    		INTEGER,
    	    wfSdlcPortAdminPortType
    		INTEGER,
    	    wfSdlcPortAdminMaxXidSize
    		INTEGER,
    	    wfSdlcPortAdminMaxRetryCount
    		INTEGER,
    	    wfSdlcPortAdminMaxFrameSize
    		INTEGER,
    	    wfSdlcPortAdminDlcName8
    		DisplayString,
    	    wfSdlcPortAdminCpType
    		INTEGER,
    	    wfSdlcPortAdminLsRole
    		INTEGER,
    	    wfSdlcPortAdminPortNumber
    		INTEGER,
    	    wfSdlcPortAdminLsAddress
    		INTEGER,
    	    wfSdlcPortAdminTotLsActLim
    		INTEGER,
    	    wfSdlcPortAdminInLsActLim
    		INTEGER,
    	    wfSdlcPortAdminOutLsActLim
    		INTEGER,
    	    wfSdlcPortAdminNegLsSupp
    		INTEGER,
    	    wfSdlcPortAdminRcvPoolSize
    		INTEGER,
    	    wfSdlcPortAdminStatsColl
    		INTEGER,
    	    wfSdlcPortAdminDebugFlg
    		INTEGER
        }

    wfSdlcPortAdminDelete OBJECT-TYPE
        SYNTAX	INTEGER {
    		    created(1),
    		    deleted(2)
    		}
        ACCESS	read-write
        STATUS	mandatory
        DESCRIPTION
                "Create/Delete Port"
        DEFVAL	{ created }
        ::= { wfSdlcPortAdminEntry 1 }

    wfSdlcPortAdminDisable OBJECT-TYPE
        SYNTAX	INTEGER {
    		    enabled(1),
    		    disabled(2)
    		}
        ACCESS	read-write
        STATUS	mandatory
        DESCRIPTION
                "Enable/Disable Port"
        DEFVAL	{ enabled }
        ::= { wfSdlcPortAdminEntry 2 }

    wfSdlcPortAdminIndex OBJECT-TYPE
        SYNTAX	INTEGER
        ACCESS	read-only
        STATUS	mandatory
        DESCRIPTION
                "The ifIndex value for the SDLC port.This is equivalent to the circuit
                number for this interface."
        ::= { wfSdlcPortAdminEntry 3 }

    wfSdlcPortAdminAddress4 OBJECT-TYPE
        SYNTAX	DisplayString
        ACCESS	read-write
        STATUS	mandatory
        DESCRIPTION
                "A string of 4 bytes that defines the physical port to which this
                interface is assigned. Its value shall be unique within the administered
                system. It must contain only ASCII printable characters.
                A write operation shall not take effect until the port is cycled
                inactive."
        ::= { wfSdlcPortAdminEntry 4 }

    wfSdlcPortAdminType OBJECT-TYPE
        SYNTAX	INTEGER {
    		    leased(1),
    		    switched(2)
    		}
        ACCESS	read-write
        STATUS	mandatory
        DESCRIPTION
                "This parameter defines whether the SDLC port is to connect to a
                leased or switched line. A write operation to this administrative
                value shall not take effect until the SDLC port has been cycled
                inactive."
        DEFVAL	{ leased }
        ::= { wfSdlcPortAdminEntry 5 }

    wfSdlcPortAdminTopology OBJECT-TYPE
        SYNTAX	INTEGER {
    		    ptop(1),
    		    multipoint(2)
    		}
        ACCESS	read-write
        STATUS	mandatory
        DESCRIPTION
                "This parameter defines whether the SDLC port is to operate in a
                point-to-point or multidropped topology. A write operation to this
                administrative value shall not take effect until the SDLC port has
                been cycled inactive."
        DEFVAL	{ ptop }
        ::= { wfSdlcPortAdminEntry 6 }

    wfSdlcPortAdminACTIVTO OBJECT-TYPE
        SYNTAX	INTEGER(0..120)
        ACCESS	read-write
        STATUS	mandatory
        DESCRIPTION
                "This parameter defines the period of time, in seconds,(0....120)
                the port will allow a switched line to remain inactive ( no I-Frames)
                before disconnecting. A value of zero indicates no timeout.
                A write operation to this administered value will not take effect until
                the port is cycled inactive."
        DEFVAL	{ 15 }
        ::= { wfSdlcPortAdminEntry 7 }

    wfSdlcPortAdminPAUSE OBJECT-TYPE
        SYNTAX	INTEGER(1..600)
        ACCESS	read-write
        STATUS	mandatory
        DESCRIPTION
                "This object defines the minimum elapsed time, (1.......600)
                in tenths of seconds, between any two traversals of the poll list
                for a primary SDLC port. This object has meaning for primary SDLC
                ports only. A write operation to this administered value will not
                take effect until the port is cycled inactive."
        DEFVAL	{ 20 }
        ::= { wfSdlcPortAdminEntry 8 }

    wfSdlcPortAdminCredit OBJECT-TYPE
        SYNTAX	INTEGER(1..50)
        ACCESS	read-write
        STATUS	mandatory
        DESCRIPTION
                "This field is used to regulate the flow of data from the DLC
                Interface to the DLC client."
        DEFVAL	{ 7 }
        ::= { wfSdlcPortAdminEntry 9 }

    wfSdlcPortAdminIdleTimer OBJECT-TYPE
        SYNTAX	INTEGER(1..65535)
        ACCESS	read-write
        STATUS	mandatory
        DESCRIPTION
                "This timer is used as a 'watch-dog' for a completely inactive line. The
                timer is specified in milliseconds."
        DEFVAL	{ 6000 }
        ::= { wfSdlcPortAdminEntry 10 }

    wfSdlcPortAdminIdleRetry OBJECT-TYPE
        SYNTAX	INTEGER(1..2147483647)
        ACCESS	read-write
        STATUS	mandatory
        DESCRIPTION
                "The number of times to rerun the idle timer before failure."
        DEFVAL	{ 20 }
        ::= { wfSdlcPortAdminEntry 11 }

    wfSdlcPortAdminNPRcvTimer OBJECT-TYPE
        SYNTAX	INTEGER(1..65535)
        ACCESS	read-write
        STATUS	mandatory
        DESCRIPTION
                "The Non-Productive receive timeout corresponds to the time allowed for
                receipt of a valid frame from the secondary. The timer is specified in
                milliseconds."
        DEFVAL	{ 2000 }
        ::= { wfSdlcPortAdminEntry 12 }

    wfSdlcPortAdminNPRcvRetry OBJECT-TYPE
        SYNTAX	INTEGER(1..2147483647)
        ACCESS	read-write
        STATUS	mandatory
        DESCRIPTION
                "The Non-Productive receive retry limit is used in conjunction with the
                timeout value to provide the overall time before an outage message is issued."
        DEFVAL	{ 15 }
        ::= { wfSdlcPortAdminEntry 13 }

    wfSdlcPortAdminWriteTimer OBJECT-TYPE
        SYNTAX	INTEGER(1..65535)
        ACCESS	read-write
        STATUS	mandatory
        DESCRIPTION
                "The maximum amount of time allowed to transmit a complete frame.
                The timer is specified in milliseconds."
        DEFVAL	{ 3000 }
        ::= { wfSdlcPortAdminEntry 14 }

    wfSdlcPortAdminWriteRetry OBJECT-TYPE
        SYNTAX	INTEGER(1..2147483647)
        ACCESS	read-write
        STATUS	mandatory
        DESCRIPTION
                "The write timer retry limit is used in conjunction with the timeout value
                to provide the overall time before an outage message is issued."
        DEFVAL	{ 10 }
        ::= { wfSdlcPortAdminEntry 15 }

    wfSdlcPortAdminLinkConnTimer OBJECT-TYPE
        SYNTAX	INTEGER(1..65535)
        ACCESS	read-write
        STATUS	mandatory
        DESCRIPTION
                "The Link connection timeout together with the retry limit corresponds to
                the time interval spent waiting. The timer is specified
                in milliseconds."
        DEFVAL	{ 3000 }
        ::= { wfSdlcPortAdminEntry 16 }

    wfSdlcPortAdminLinkConnRetry OBJECT-TYPE
        SYNTAX	INTEGER(1..2147483647)
        ACCESS	read-write
        STATUS	mandatory
        DESCRIPTION
                "The Link connection retry limit specifies the number of times the link has
                been tested for a connection before it fails the pending activate port request.'"
        DEFVAL	{ 10 }
        ::= { wfSdlcPortAdminEntry 17 }

    wfSdlcPortAdminPriFdplx OBJECT-TYPE
        SYNTAX	INTEGER {
    		    false(1),
    		    true(2)
    		}
        ACCESS	read-write
        STATUS	mandatory
        DESCRIPTION
                "Primary SDLC station is full-duplex or not"
        DEFVAL	{ false }
        ::= { wfSdlcPortAdminEntry 18 }

    wfSdlcPortAdminSecFdplx OBJECT-TYPE
        SYNTAX	INTEGER {
    		    false(1),
    		    true(2)
    		}
        ACCESS	read-write
        STATUS	mandatory
        DESCRIPTION
                "Secondary SDLC station is full-duplex or not"
        DEFVAL	{ false }
        ::= { wfSdlcPortAdminEntry 19 }

    wfSdlcPortAdminUseRej OBJECT-TYPE
        SYNTAX	INTEGER {
    		    false(1),
    		    true(2)
    		}
        ACCESS	read-write
        STATUS	mandatory
        DESCRIPTION
                "Whether REJ are in use for out of sequence I-frames"
        DEFVAL	{ true }
        ::= { wfSdlcPortAdminEntry 20 }

    wfSdlcPortAdminPortType OBJECT-TYPE
        SYNTAX	INTEGER {
    		    leased(1),
    		    dialout(2),
    		    autoanswer(3),
    		    autoanswerdialout(4),
    		    mandialout(5),
    		    mananswer(6),
    		    mananswerdialout(7)
    		}
        ACCESS	read-write
        STATUS	mandatory
        DESCRIPTION
                "Type of port
                1 - Leased Line
                2 - Switched Line with dial out capabilities
                3 - Switched Line with auto answer capabilities
                4 - Switched Line with auto answer and dial out capabilities
                5 - Switched Line with manual dial out capabilities
                6 - Switched Line with manual answer capabilities
                7 - Switched Line with manual answer and dial out capabilities "
        DEFVAL	{ leased }
        ::= { wfSdlcPortAdminEntry 21 }

    wfSdlcPortAdminMaxXidSize OBJECT-TYPE
        SYNTAX	INTEGER(0..256)
        ACCESS	read-write
        STATUS	mandatory
        DESCRIPTION
                "Maximum XID size"
        DEFVAL	{ 256 }
        ::= { wfSdlcPortAdminEntry 22 }

    wfSdlcPortAdminMaxRetryCount OBJECT-TYPE
        SYNTAX	INTEGER(1..7)
        ACCESS	read-write
        STATUS	mandatory
        DESCRIPTION
                "Maximum number of times that a frame can be retransmitted."
        DEFVAL	{ 5 }
        ::= { wfSdlcPortAdminEntry 23 }

    wfSdlcPortAdminMaxFrameSize OBJECT-TYPE
        SYNTAX	INTEGER {
    		    pdu0265(265),
    		    pdu0521(521),
    		    pdu1033(1033),
    		    pdu2057(2057),
    		    pdu4105(4105)
    		}
        ACCESS	read-write
        STATUS	mandatory
        DESCRIPTION
                "Maximum frame size supported by this DLC."
        DEFVAL	{ pdu1033 }
        ::= { wfSdlcPortAdminEntry 24 }

    wfSdlcPortAdminDlcName8 OBJECT-TYPE
        SYNTAX	DisplayString
        ACCESS	read-write
        STATUS	mandatory
        DESCRIPTION
                "A string of 8 bytes that names this DLC. Its value shall
                be unique within the administered system. It must contain only
                ASCII printable characters. A write operation shall not take effect
                until the port is cycled inactive."
        ::= { wfSdlcPortAdminEntry 25 }

    wfSdlcPortAdminCpType OBJECT-TYPE
        SYNTAX	INTEGER {
    		    learn(1),
    		    len(2),
    		    network(3),
    		    end(4),
    		    vrn(5)
    		}
        ACCESS	read-write
        STATUS	mandatory
        DESCRIPTION
                "type of CP
                1 - LEARN NODE
                2 - LEN NODE
                3 - NETWORK NODE
                2 - END NODE
                5 - VRN NODE "
        DEFVAL	{ network }
        ::= { wfSdlcPortAdminEntry 26 }

    wfSdlcPortAdminLsRole OBJECT-TYPE
        SYNTAX	INTEGER {
    		    neg(1),
    		    pri(2),
    		    sec(3)
    		}
        ACCESS	read-write
        STATUS	mandatory
        DESCRIPTION
                "Link Station Role
                1 - Negotiable
                2 - Primary
                3 - Secondary "
        DEFVAL	{ pri }
        ::= { wfSdlcPortAdminEntry 27 }

    wfSdlcPortAdminPortNumber OBJECT-TYPE
        SYNTAX	INTEGER(1..2048)
        ACCESS	read-write
        STATUS	mandatory
        DESCRIPTION
                "Port Number, unique within this system."
        DEFVAL	{ 1 }
        ::= { wfSdlcPortAdminEntry 28 }

    wfSdlcPortAdminLsAddress OBJECT-TYPE
        SYNTAX	INTEGER(1..254)
        ACCESS	read-write
        STATUS	mandatory
        DESCRIPTION
                "Link Station Address. This object has meaning if this
                link station is a secondary link station."
        DEFVAL	{ 2 }
        ::= { wfSdlcPortAdminEntry 29 }

    wfSdlcPortAdminTotLsActLim OBJECT-TYPE
        SYNTAX	INTEGER(1..254)
        ACCESS	read-write
        STATUS	mandatory
        DESCRIPTION
                "Total link station activation limit."
        DEFVAL	{ 16 }
        ::= { wfSdlcPortAdminEntry 30 }

    wfSdlcPortAdminInLsActLim OBJECT-TYPE
        SYNTAX	INTEGER(1..254)
        ACCESS	read-write
        STATUS	mandatory
        DESCRIPTION
                "Inbound link station activation limit."
        DEFVAL	{ 8 }
        ::= { wfSdlcPortAdminEntry 31 }

    wfSdlcPortAdminOutLsActLim OBJECT-TYPE
        SYNTAX	INTEGER(1..254)
        ACCESS	read-write
        STATUS	mandatory
        DESCRIPTION
                "Outbound link station activation limit."
        DEFVAL	{ 8 }
        ::= { wfSdlcPortAdminEntry 32 }

    wfSdlcPortAdminNegLsSupp OBJECT-TYPE
        SYNTAX	INTEGER {
    		    false(1),
    		    true(2)
    		}
        ACCESS	read-write
        STATUS	mandatory
        DESCRIPTION
                "Whether the DLC supports Negoatible connections"
        DEFVAL	{ false }
        ::= { wfSdlcPortAdminEntry 33 }

    wfSdlcPortAdminRcvPoolSize OBJECT-TYPE
        SYNTAX	INTEGER(1..255)
        ACCESS	read-write
        STATUS	mandatory
        DESCRIPTION
                "Receive Buffer pool size."
        DEFVAL	{ 7 }
        ::= { wfSdlcPortAdminEntry 34 }

    wfSdlcPortAdminStatsColl OBJECT-TYPE
        SYNTAX	INTEGER {
    		    false(1),
    		    true(2)
    		}
        ACCESS	read-write
        STATUS	mandatory
        DESCRIPTION
                "Whether Stats collection is turned on for this port."
        DEFVAL	{ true }
        ::= { wfSdlcPortAdminEntry 35 }

    wfSdlcPortAdminDebugFlg OBJECT-TYPE
        SYNTAX	INTEGER {
    		    enabled(1),
    		    disabled(2)
    		}
        ACCESS	read-write
        STATUS	mandatory
        DESCRIPTION
                "Debug Flag, Enables/Disables debug log messages."
        DEFVAL	{ disabled }
        ::= { wfSdlcPortAdminEntry 36 }

    wfSdlcPortOperTable OBJECT-TYPE
        SYNTAX	SEQUENCE OF WfSdlcPortOperEntry
        ACCESS	not-accessible
        STATUS	mandatory
        DESCRIPTION
                "This table contains current SDLC port parameters. Many of
                these objects have corresponding objects inthe wfSdlcPortAdmnTable."
        ::= { wfSdlcGroup 3 }

    wfSdlcPortOperEntry OBJECT-TYPE
        SYNTAX	WfSdlcPortOperEntry
        ACCESS	not-accessible
        STATUS	mandatory
        DESCRIPTION
                "Currently set parameters for a specific SDLC port"
        INDEX	{ wfSdlcPortOperIndex }
        ::= { wfSdlcPortOperTable 1 }

    WfSdlcPortOperEntry ::= SEQUENCE {
    	    wfSdlcPortOperIndex
    		INTEGER,
    	    wfSdlcPortOperAddress4
    		DisplayString,
    	    wfSdlcPortOperRole
    		INTEGER,
    	    wfSdlcPortOperType
    		INTEGER,
    	    wfSdlcPortOperTopology
    		INTEGER,
    	    wfSdlcPortOperACTIVTO
    		INTEGER,
    	    wfSdlcPortOperPAUSE
    		INTEGER,
    	    wfSdlcPortOperSlowPollMethod
    		INTEGER,
    	    wfSdlcPortOperSlowPollTimer
    		TimeTicks,
    	    wfSdlcPortOperAbmSuppInd
    		INTEGER,
    	    wfSdlcPortOperSimRimSupp
    		INTEGER,
    	    wfSdlcPortOperSecInitNonactSupp
    		INTEGER
        }

    wfSdlcPortOperIndex OBJECT-TYPE
        SYNTAX	INTEGER
        ACCESS	read-only
        STATUS	mandatory
        DESCRIPTION
                "The ifIndex value for the SDLC port. This value reflects the
                circuit number for this interface."
        ::= { wfSdlcPortOperEntry 1 }

    wfSdlcPortOperAddress4 OBJECT-TYPE
        SYNTAX	DisplayString
        ACCESS	read-only
        STATUS	mandatory
        DESCRIPTION
                "An octet string that describes the physical port to which
                this interface is currently attached."
        ::= { wfSdlcPortOperEntry 2 }

    wfSdlcPortOperRole OBJECT-TYPE
        SYNTAX	INTEGER {
    		    sec(1),
    		    pri(2),
    		    neg(4)
    		}
        ACCESS	read-only
        STATUS	mandatory
        DESCRIPTION
                "Link Station Role
                1 - Secondary
                2 - Primary
                4 - Negotiable"
        DEFVAL	{ pri }
        ::= { wfSdlcPortOperEntry 3 }

    wfSdlcPortOperType OBJECT-TYPE
        SYNTAX	INTEGER {
    		    leased(1),
    		    switched(2)
    		}
        ACCESS	read-only
        STATUS	mandatory
        DESCRIPTION
                "This parameter defines whether the SDLC port is currently
                operating as though connected to a leased or switched line."
        DEFVAL	{ leased }
        ::= { wfSdlcPortOperEntry 4 }

    wfSdlcPortOperTopology OBJECT-TYPE
        SYNTAX	INTEGER {
    		    ptop(1),
    		    multipoint(2)
    		}
        ACCESS	read-only
        STATUS	mandatory
        DESCRIPTION
                "This parameter defines whether the SDLC port is currently
                operating in a point-to-point or multi dropped topology."
        DEFVAL	{ multipoint }
        ::= { wfSdlcPortOperEntry 5 }

    wfSdlcPortOperACTIVTO OBJECT-TYPE
        SYNTAX	INTEGER
        ACCESS	read-only
        STATUS	mandatory
        DESCRIPTION
                "This parameter describes the period of time, in seconds,
                the port will allow a switched line to remain inactive
                ( no I-Frames) before disconnecting. A value of zero indicates
                no timeout."
        ::= { wfSdlcPortOperEntry 6 }

    wfSdlcPortOperPAUSE OBJECT-TYPE
        SYNTAX	INTEGER
        ACCESS	read-only
        STATUS	mandatory
        DESCRIPTION
                "This object describes the current minimum elapsed time, in
                tenths of seconds, between any two traversals of the poll list
                for a primary SDLC port. This object has meaning for primary
                SDLC ports only."
        ::= { wfSdlcPortOperEntry 7 }

    wfSdlcPortOperSlowPollMethod OBJECT-TYPE
        SYNTAX	INTEGER {
    		    servlim(1),
    		    pause(2),
    		    other(3)
    		}
        ACCESS	read-only
        STATUS	mandatory
        DESCRIPTION
                "This object defines the exact method that is in effect for
                periodically polling failed secondary link station addresses."
        DEFVAL	{ pause }
        ::= { wfSdlcPortOperEntry 8 }

    wfSdlcPortOperSlowPollTimer OBJECT-TYPE
        SYNTAX	TimeTicks
        ACCESS	read-only
        STATUS	mandatory
        DESCRIPTION
                "This object describes the elapsed time, in 1/100ths of seconds,
                between polls for failed secondary link station addresses."
        ::= { wfSdlcPortOperEntry 9 }

    wfSdlcPortOperAbmSuppInd OBJECT-TYPE
        SYNTAX	INTEGER {
    		    supported(1),
    		    notsupported(2)
    		}
        ACCESS	read-only
        STATUS	mandatory
        DESCRIPTION
                "Specifies whether Asynchronous Balanced Mode is supported."
        DEFVAL	{ notsupported }
        ::= { wfSdlcPortOperEntry 10 }

    wfSdlcPortOperSimRimSupp OBJECT-TYPE
        SYNTAX	INTEGER {
    		    supported(1),
    		    notsupported(2)
    		}
        ACCESS	read-only
        STATUS	mandatory
        DESCRIPTION
                "Specifies whether SDLC RIM or SIM initialization options
                are supported."
        DEFVAL	{ supported }
        ::= { wfSdlcPortOperEntry 11 }

    wfSdlcPortOperSecInitNonactSupp OBJECT-TYPE
        SYNTAX	INTEGER {
    		    supported(1),
    		    notsupported(2)
    		}
        ACCESS	read-only
        STATUS	mandatory
        DESCRIPTION
                "Specifies whether secondary-initiated nonactivation XID
                support is provided."
        DEFVAL	{ notsupported }
        ::= { wfSdlcPortOperEntry 12 }

    wfSdlcPortStatsTable OBJECT-TYPE
        SYNTAX	SEQUENCE OF WfSdlcPortStatsEntry
        ACCESS	not-accessible
        STATUS	mandatory
        DESCRIPTION
                "-- This table shall keep only physical statistics about a port.
                'Each entry in this table contains statistics for a specific
                SDLC port."
        ::= { wfSdlcGroup 4 }

    wfSdlcPortStatsEntry OBJECT-TYPE
        SYNTAX	WfSdlcPortStatsEntry
        ACCESS	not-accessible
        STATUS	mandatory
        DESCRIPTION
                "A list of statistics for an SDLC port"
        INDEX	{ wfSdlcPortStatsIndex }
        ::= { wfSdlcPortStatsTable 1 }

    WfSdlcPortStatsEntry ::= SEQUENCE {
    	    wfSdlcPortStatsIndex
    		INTEGER,
    	    wfSdlcPortStatsDwarfFrames
    		INTEGER
        }

    wfSdlcPortStatsIndex OBJECT-TYPE
        SYNTAX	INTEGER
        ACCESS	read-only
        STATUS	mandatory
        DESCRIPTION
                "The ifIndex value for the SDLC port."
        ::= { wfSdlcPortStatsEntry 1 }

    wfSdlcPortStatsDwarfFrames OBJECT-TYPE
        SYNTAX	INTEGER
        ACCESS	read-only
        STATUS	mandatory
        DESCRIPTION
                "This object reflects the total number of frames received by this
                port which were delivered intact by the physical layer but were too
                short to be legal."
        ::= { wfSdlcPortStatsEntry 2 }

    wfSdlcLSAdminTable OBJECT-TYPE
        SYNTAX	SEQUENCE OF WfSdlcLSAdminEntry
        ACCESS	not-accessible
        STATUS	mandatory
        DESCRIPTION
                "The following classes of information is modelled for each SDLC
                link station:
                --
                -- 1. ADMINISTRATIVE ( read/write)
                -- 2. OPERATIONAL ( read-only)
                -- 3. STATISTICS ( read-only)

                --
                -- THE SDLC LINK STATION ADMINISTRATIVE TABLE

                'This table contains objects that can be changed to manage an
                SDLC link station. These parameters are per Link Station. Changing
                one of these parameters may take effect in the operating link
                immediately or may wait until the link is restarted depending on the
                object. Most of the objects in this read-write table have
                corresponding read-only objects in the wfSdlcLSOperTable that return
                the current operating value. The operating values may be different
                from these configured values if changed by XID negotiation or if a
                configured parameter was changed after the link was started."
        ::= { wfSdlcGroup 5 }

    wfSdlcLSAdminEntry OBJECT-TYPE
        SYNTAX	WfSdlcLSAdminEntry
        ACCESS	not-accessible
        STATUS	mandatory
        DESCRIPTION
                "A list of configured values for an SDLC link"
        INDEX	{ wfSdlcLSAdminIfIndex,
    		  wfSdlcLSAdminAddress }
        ::= { wfSdlcLSAdminTable 1 }

    WfSdlcLSAdminEntry ::= SEQUENCE {
    	    wfSdlcLSAdminDelete
    		INTEGER,
    	    wfSdlcLSAdminDisable
    		INTEGER,
    	    wfSdlcLSAdminIfIndex
    		INTEGER,
    	    wfSdlcLSAdminAddress
    		INTEGER,
    	    wfSdlcLSAdminGroupAddress
    		INTEGER,
    	    wfSdlcLSAdminRole
    		INTEGER,
    	    wfSdlcLSAdminMAXDATA
    		INTEGER,
    	    wfSdlcLSAdminREPLYTO
    		INTEGER,
    	    wfSdlcLSAdminMAXIN
    		INTEGER,
    	    wfSdlcLSAdminMAXOUT
    		INTEGER,
    	    wfSdlcLSAdminMODULO
    		INTEGER,
    	    wfSdlcLSAdminRETRIESm
    		INTEGER,
    	    wfSdlcLSAdminRETRIESt
    		INTEGER,
    	    wfSdlcLSAdminRETRIESn
    		INTEGER,
    	    wfSdlcLSAdminRNRLIMIT
    		INTEGER,
    	    wfSdlcLSAdminContTimer
    		INTEGER,
    	    wfSdlcLSAdminContTimerRetry
    		INTEGER,
    	    wfSdlcLSAdminContTimer2
    		INTEGER,
    	    wfSdlcLSAdminContTimer2Retry
    		INTEGER,
    	    wfSdlcLSAdminDiscTimer
    		INTEGER,
    	    wfSdlcLSAdminDiscTimerRetry
    		INTEGER,
    	    wfSdlcLSAdminNvePollTimer
    		INTEGER,
    	    wfSdlcLSAdminNvePollTimerRetry
    		INTEGER,
    	    wfSdlcLSAdminNvePollTimer2
    		INTEGER,
    	    wfSdlcLSAdminNvePollTimer2Retry
    		INTEGER,
    	    wfSdlcLSAdminNoRespTimerRetry
    		INTEGER,
    	    wfSdlcLSAdminRemBusyTimerRetry
    		INTEGER,
    	    wfSdlcLSAdminRRTimer
    		INTEGER,
    	    wfSdlcLSAdminGpAddName
    		DisplayString,
    	    wfSdlcLSAdminPollFrame
    		INTEGER,
    	    wfSdlcLSAdminPollOnIframe
    		INTEGER,
    	    wfSdlcLSAdminLinkStationName
    		DisplayString,
    	    wfSdlcLSAdminAdjNodeType
    		INTEGER,
    	    wfSdlcLSAdminSimRim
    		INTEGER
        }

    wfSdlcLSAdminDelete OBJECT-TYPE
        SYNTAX	INTEGER {
    		    created(1),
    		    deleted(2)
    		}
        ACCESS	read-write
        STATUS	mandatory
        DESCRIPTION
                "Create/Delete Link Station"
        DEFVAL	{ created }
        ::= { wfSdlcLSAdminEntry 1 }

    wfSdlcLSAdminDisable OBJECT-TYPE
        SYNTAX	INTEGER {
    		    enabled(1),
    		    disabled(2)
    		}
        ACCESS	read-write
        STATUS	mandatory
        DESCRIPTION
                "This object controls the desired state of the SDLC station."
        DEFVAL	{ enabled }
        ::= { wfSdlcLSAdminEntry 2 }

    wfSdlcLSAdminIfIndex OBJECT-TYPE
        SYNTAX	INTEGER
        ACCESS	read-only
        STATUS	mandatory
        DESCRIPTION
                "The ifIndex value for the SDLC port which owns this link station.
                This is equivalent to the circuit number for this interface."
        ::= { wfSdlcLSAdminEntry 3 }

    wfSdlcLSAdminAddress OBJECT-TYPE
        SYNTAX	INTEGER
        ACCESS	read-only
        STATUS	mandatory
        DESCRIPTION
                "This value is the poll address of the secondary link station for
                this SDLC link. It uniquely identifies the SDLC link station within a
                single SDLC port."
        ::= { wfSdlcLSAdminEntry 4 }

    wfSdlcLSAdminGroupAddress OBJECT-TYPE
        SYNTAX	INTEGER
        ACCESS	read-write
        STATUS	mandatory
        DESCRIPTION
                "This value is the group poll address of the secondary link station for
                this SDLC link. If this link station is not part of a group, this address
                will be NULL."
        ::= { wfSdlcLSAdminEntry 5 }

    wfSdlcLSAdminRole OBJECT-TYPE
        SYNTAX	INTEGER {
    		    negot(1),
    		    primary(2),
    		    sec(3),
    		    msec(4)
    		}
        ACCESS	read-write
        STATUS	mandatory
        DESCRIPTION
                "This object describes the role that the link station shall assume
                the next time a connection is established."
        DEFVAL	{ primary }
        ::= { wfSdlcLSAdminEntry 6 }

    wfSdlcLSAdminMAXDATA OBJECT-TYPE
        SYNTAX	INTEGER {
    		    pdu0265(265),
    		    pdu0521(521),
    		    pdu1033(1033),
    		    pdu2057(2057),
    		    pdu4105(4105)
    		}
        ACCESS	read-write
        STATUS	mandatory
        DESCRIPTION
                "This object controls the maximum PDU size allowed for the logical
                link. This value includes the Transmission Header (TH) and Request
                Header (RH). A write operation to this administrative value will not
                change the operational value, wfSdlcLSOperMAXDATA, until the link
                station hasbeen cycled inactive."
        DEFVAL	{ pdu1033 }
        ::= { wfSdlcLSAdminEntry 7 }

    wfSdlcLSAdminREPLYTO OBJECT-TYPE
        SYNTAX	INTEGER(1..600)
        ACCESS	read-write
        STATUS	mandatory
        DESCRIPTION
                "This object controls the reply timeout, in tenths of seconds,
                (1....600) for an SDLC link station. If the link station does not
                receive a repsonse to a poll or message before the specified time
                expires then the appropriate error recovery shall be initiated. A
                write operation to this administered value will not change the
                operational value, wfSdlcLSOperREPLYTO, until the link station is
                cycled inactive. This object has no meaning for secondary SDLC link
                stations."
        DEFVAL	{ 30 }
        ::= { wfSdlcLSAdminEntry 8 }

    wfSdlcLSAdminMAXIN OBJECT-TYPE
        SYNTAX	INTEGER(1..127)
        ACCESS	read-write
        STATUS	mandatory
        DESCRIPTION
                "This object controls the maximum number, (1.....127) of
                unacknowledged frames which an SDLC link station may receive. This
                will range from one to modulus minus one. The modulus is controlled
                by the object: wfSdlcLSAdminModulus. A write operation to this
                administered value will not change the operational value,
                wfSdlcLSOperMAXIN, until the link station is cycled inactive."
        DEFVAL	{ 7 }
        ::= { wfSdlcLSAdminEntry 9 }

    wfSdlcLSAdminMAXOUT OBJECT-TYPE
        SYNTAX	INTEGER(1..127)
        ACCESS	read-write
        STATUS	mandatory
        DESCRIPTION
                "This object controls the maximum consequetive unacknowledged
                frames, (1.....127) which an SDLC link station shall send without
                an acknowledgement. This shall range from one to modulus minus one.
                The modulus is controlled by the object: wfSdlcLSAdminMODULO. A
                write operation to this administered value will not change the
                operational value, wfSdlcLSOperMAXOUT, until the link station is
                cycled inactive."
        DEFVAL	{ 7 }
        ::= { wfSdlcLSAdminEntry 10 }

    wfSdlcLSAdminMODULO OBJECT-TYPE
        SYNTAX	INTEGER {
    		    default(8),
    		    extended(128)
    		}
        ACCESS	read-write
        STATUS	mandatory
        DESCRIPTION
                "This object controls the modulus, (8,128) for an SDLC link
                station. This modulus determines the size of the rotating
                acknowledgement window used the SDLC link station pair A write
                operation to this administered value will not change the operational
                value, wfSdlcLSOperMAXOUT, until the link station is cycled inactive."
        DEFVAL	{ default }
        ::= { wfSdlcLSAdminEntry 11 }

    wfSdlcLSAdminRETRIESm OBJECT-TYPE
        SYNTAX	INTEGER(1..600)
        ACCESS	read-write
        STATUS	mandatory
        DESCRIPTION
                "This object controls number of retries, ( 1.....128) in a retry
                sequence for an SDLC link station. A retry sequence is a series of
                retransmitted frames ( data or control) for which no positive
                acknowledgement is received. The number of times that the retry
                sequence is to be repeated is controlled by the object:
                wfSdlcLSOperRETRIESn. The interval between retry sequences is
                controlled by the object: wfSdlcLSOperRETRIESt. A write operation to
                this administered value will not change the operational value,
                wfSdlcLSOperRETRIESm, until the link station is cycled inactive."
        DEFVAL	{ 20 }
        ::= { wfSdlcLSAdminEntry 12 }

    wfSdlcLSAdminRETRIESt OBJECT-TYPE
        SYNTAX	INTEGER(0..255)
        ACCESS	read-write
        STATUS	mandatory
        DESCRIPTION
                "This object controls the interval, in seconds, (0....255) between
                retry sequences for an SDLC link station if multiple retry sequences
                are specified . A retry sequence is a series of retransmitted frames
                ( data or control) for which no positive acknowledgement is received.
                The number of repeated retries sequences is controlled by the object:
                wfSdlcLSAdminRETRIESn. The retries per sequence is controlled by the
                object: wfSdlcLSAdminRETRIESm. A write operation to this administered
                value will not change the operational value, wfSdlcLSOperRETRIESt,
                until the link station is cycled inactive."
        DEFVAL	{ 2 }
        ::= { wfSdlcLSAdminEntry 13 }

    wfSdlcLSAdminRETRIESn OBJECT-TYPE
        SYNTAX	INTEGER(1..127)
        ACCESS	read-write
        STATUS	mandatory
        DESCRIPTION
                "This object controls the number of times, (1....127) that a retry
                sequence is repeated for an SDLC link station. A retry sequence is a
                series of retransmitted frames ( data or control) for which no positive
                acknowledgement is received. The interval between retry sequences is
                controlled by the object: wfSdlcLSAdminRETRIESn. The retries per
                sequence is controlled by the object: wfSdlcLSAdminRETRIESm. A write
                operation to this administered value will not change the operational
                value, wfSdlcLSOperRETRIESn, until the link station is cycled
                inactive."
        DEFVAL	{ 4 }
        ::= { wfSdlcLSAdminEntry 14 }

    wfSdlcLSAdminRNRLIMIT OBJECT-TYPE
        SYNTAX	INTEGER(1..90)
        ACCESS	read-write
        STATUS	mandatory
        DESCRIPTION
                "This object controls the length of time, in minutes, (1.....90)
                that an SDLC link station will allow its adjacent link station to
                remain in a busy (RNR) state before declaring it inoperative. A write
                operation to this administered value will not change the operational
                value, wfSdlcLSOperRNRLIMIT, until the link station is cycled
                inactive."
        DEFVAL	{ 3 }
        ::= { wfSdlcLSAdminEntry 15 }

    wfSdlcLSAdminContTimer OBJECT-TYPE
        SYNTAX	INTEGER(1..64000)
        ACCESS	read-write
        STATUS	mandatory
        DESCRIPTION
                "This object controls the timeout required before a SNRM or XID
                is retransmitted in the event of non-acknowledgement. Used for
                Primary SDLC only. The value must be greater then the no response
                (T1) timeout value (no_resp_timer) The timer is specified in
                milliseconds."
        DEFVAL	{ 4000 }
        ::= { wfSdlcLSAdminEntry 16 }

    wfSdlcLSAdminContTimerRetry OBJECT-TYPE
        SYNTAX	INTEGER(1..64000)
        ACCESS	read-write
        STATUS	mandatory
        DESCRIPTION
                "This object controls the number of times transmission and
                retransmission of a contact frame (e.g. SNRM) is allowed before
                switching to the slow
                poll timer."
        DEFVAL	{ 4 }
        ::= { wfSdlcLSAdminEntry 17 }

    wfSdlcLSAdminContTimer2 OBJECT-TYPE
        SYNTAX	INTEGER(1..64000)
        ACCESS	read-write
        STATUS	mandatory
        DESCRIPTION
                "This object controls the slow poll contact timer in milliseconds.
                When the contact timer retry count expires, polling will continue
                using this timer."
        DEFVAL	{ 4000 }
        ::= { wfSdlcLSAdminEntry 18 }

    wfSdlcLSAdminContTimer2Retry OBJECT-TYPE
        SYNTAX	INTEGER(1..64000)
        ACCESS	read-write
        STATUS	mandatory
        DESCRIPTION
                "This object controls the number of times transmission and
                retransmission of a contact frame (e.g. SNRM) is allowed before
                an outage message is sent to the DLC user."
        DEFVAL	{ 8 }
        ::= { wfSdlcLSAdminEntry 19 }

    wfSdlcLSAdminDiscTimer OBJECT-TYPE
        SYNTAX	INTEGER(1..64000)
        ACCESS	read-write
        STATUS	mandatory
        DESCRIPTION
                "This object controls the time in milliseconds before a DISC
                is retransmitted in the event of non-acknowledgement
                (for primary SDLC only)."
        DEFVAL	{ 4000 }
        ::= { wfSdlcLSAdminEntry 20 }

    wfSdlcLSAdminDiscTimerRetry OBJECT-TYPE
        SYNTAX	INTEGER(1..64000)
        ACCESS	read-write
        STATUS	mandatory
        DESCRIPTION
                "This object controls the number of times transmission and
                retransmission of a DISC is allowed."
        DEFVAL	{ 4 }
        ::= { wfSdlcLSAdminEntry 21 }

    wfSdlcLSAdminNvePollTimer OBJECT-TYPE
        SYNTAX	INTEGER(1..64000)
        ACCESS	read-write
        STATUS	mandatory
        DESCRIPTION
                "This object controls the timeout required before an adjacent
                secondary station is re-inserted into the polling list after
                being removed for non-response. The time is specified in
                milliseconds."
        DEFVAL	{ 400 }
        ::= { wfSdlcLSAdminEntry 22 }

    wfSdlcLSAdminNvePollTimerRetry OBJECT-TYPE
        SYNTAX	INTEGER(1..65535)
        ACCESS	read-write
        STATUS	mandatory
        DESCRIPTION
                "This object controls the number of times a station is removed
                from the polling list on the normal poll timer before switching
                to the slow poll timer."
        DEFVAL	{ 16 }
        ::= { wfSdlcLSAdminEntry 23 }

    wfSdlcLSAdminNvePollTimer2 OBJECT-TYPE
        SYNTAX	INTEGER(1..64000)
        ACCESS	read-write
        STATUS	mandatory
        DESCRIPTION
                "The slow negative poll timer in milliseconds. When the negative
                poll timer count expires, the poll will continue by using this
                timer."
        DEFVAL	{ 1000 }
        ::= { wfSdlcLSAdminEntry 24 }

    wfSdlcLSAdminNvePollTimer2Retry OBJECT-TYPE
        SYNTAX	INTEGER(1..65535)
        ACCESS	read-write
        STATUS	mandatory
        DESCRIPTION
                "This object controls the number of times a station is removed
                from the polling list before an outage message is sent to a client."
        DEFVAL	{ 65535 }
        ::= { wfSdlcLSAdminEntry 25 }

    wfSdlcLSAdminNoRespTimerRetry OBJECT-TYPE
        SYNTAX	INTEGER(1..64000)
        ACCESS	read-write
        STATUS	mandatory
        DESCRIPTION
                "This object controls the number of times an adjacent secondary
                station is seen to fail to respond before an outage message is sent
                to a client."
        DEFVAL	{ 10 }
        ::= { wfSdlcLSAdminEntry 26 }

    wfSdlcLSAdminRemBusyTimerRetry OBJECT-TYPE
        SYNTAX	INTEGER(1..64000)
        ACCESS	read-write
        STATUS	mandatory
        DESCRIPTION
                "The Remote busy retry limit value is user with the timeout
                value to provide the overall timeout before an outage message
                is sent to a client."
        DEFVAL	{ 4 }
        ::= { wfSdlcLSAdminEntry 27 }

    wfSdlcLSAdminRRTimer OBJECT-TYPE
        SYNTAX	INTEGER(0..64000)
        ACCESS	read-write
        STATUS	mandatory
        DESCRIPTION
                "The RR Turn-around timer is in milliseconds. It is the time
                that DLC waits before turning the poll bit around when it has
                no work to do."
        ::= { wfSdlcLSAdminEntry 28 }

    wfSdlcLSAdminGpAddName OBJECT-TYPE
        SYNTAX	DisplayString
        ACCESS	read-write
        STATUS	mandatory
        DESCRIPTION
                "The address of the group to which this link station belongs.
                This object is only used in association with group polling.
                It is 4 bytes of ASCII."
        ::= { wfSdlcLSAdminEntry 29 }

    wfSdlcLSAdminPollFrame OBJECT-TYPE
        SYNTAX	INTEGER {
    		    disc(83),
    		    snrm(147),
    		    xid(191),
    		    snrme(223),
    		    test(243)
    		}
        ACCESS	read-write
        STATUS	mandatory
        DESCRIPTION
                "The frame to use for pre-activation polling. This is normally
                set to XID to show that polling is in the control of the DLC user."
        DEFVAL	{ xid }
        ::= { wfSdlcLSAdminEntry 30 }

    wfSdlcLSAdminPollOnIframe OBJECT-TYPE
        SYNTAX	INTEGER {
    		    false(1),
    		    true(2)
    		}
        ACCESS	read-write
        STATUS	mandatory
        DESCRIPTION
                "Flag whether this link station is permitted to send the poll bit
                on an I-frame. Certain SDLC implementations do not handle receipt of
                I-frames carrying the poll bit."
        DEFVAL	{ true }
        ::= { wfSdlcLSAdminEntry 31 }

    wfSdlcLSAdminLinkStationName OBJECT-TYPE
        SYNTAX	DisplayString
        ACCESS	read-write
        STATUS	mandatory
        DESCRIPTION
                "The name of the adjacent link station in ASCII. Used for stats
                and Alert messages to uniquely identify the station. 8 BYTES in
                length."
        ::= { wfSdlcLSAdminEntry 32 }

    wfSdlcLSAdminAdjNodeType OBJECT-TYPE
        SYNTAX	INTEGER {
    		    learn(1),
    		    len(2),
    		    network(3),
    		    end(4),
    		    vrn(5)
    		}
        ACCESS	read-write
        STATUS	mandatory
        DESCRIPTION
                "Adjacent Node type"
        DEFVAL	{ network }
        ::= { wfSdlcLSAdminEntry 33 }

    wfSdlcLSAdminSimRim OBJECT-TYPE
        SYNTAX	INTEGER {
    		    false(1),
    		    true(2)
    		}
        ACCESS	read-write
        STATUS	mandatory
        DESCRIPTION
                "This object controls the support for transmission and receipt
                of SIM and RIM control frames for this link station."
        DEFVAL	{ false }
        ::= { wfSdlcLSAdminEntry 34 }

    wfSdlcLSOperTable OBJECT-TYPE
        SYNTAX	SEQUENCE OF WfSdlcLSOperEntry
        ACCESS	not-accessible
        STATUS	mandatory
        DESCRIPTION
                "This table contains current SDLC link parameters. Many of
                these objects have corresponding objects in the wfSdlcLSAdmnTable."
        ::= { wfSdlcGroup 6 }

    wfSdlcLSOperEntry OBJECT-TYPE
        SYNTAX	WfSdlcLSOperEntry
        ACCESS	not-accessible
        STATUS	mandatory
        DESCRIPTION
                "A list of current SDLC link parameters"
        INDEX	{ wfSdlcLSOperIfIndex,
    		  wfSdlcLSOperAddress }
        ::= { wfSdlcLSOperTable 1 }

    WfSdlcLSOperEntry ::= SEQUENCE {
    	    wfSdlcLSOperIfIndex
    		INTEGER,
    	    wfSdlcLSOperAddress
    		INTEGER,
    	    wfSdlcLSOperRole
    		INTEGER,
    	    wfSdlcLSOperState
    		INTEGER,
    	    wfSdlcLSOperMAXDATA
    		INTEGER,
    	    wfSdlcLSOperREPLYTO
    		INTEGER,
    	    wfSdlcLSOperMAXIN
    		INTEGER,
    	    wfSdlcLSOperMAXOUT
    		INTEGER,
    	    wfSdlcLSOperMODULO
    		INTEGER,
    	    wfSdlcLSOperRETRIESm
    		INTEGER,
    	    wfSdlcLSOperRETRIESt
    		INTEGER,
    	    wfSdlcLSOperRETRIESn
    		INTEGER,
    	    wfSdlcLSOperRNRLIMIT
    		INTEGER,
    	    wfSdlcLSOperDATMODE
    		INTEGER,
    	    wfSdlcLSOperCreateTime
    		TimeTicks,
    	    wfSdlcLSOperLastFailCause
    		INTEGER,
    	    wfSdlcLSOperLastFailCtrlIn2
    		OCTET STRING,
    	    wfSdlcLSOperLastFailCtrlOut2
    		OCTET STRING,
    	    wfSdlcLSOperLastFailFRMRInfo5
    		OCTET STRING,
    	    wfSdlcLSOperLastFailREPLYTOs
    		Counter,
    	    wfSdlcLSOperGroupAddress
    		INTEGER
        }

    wfSdlcLSOperIfIndex OBJECT-TYPE
        SYNTAX	INTEGER
        ACCESS	read-only
        STATUS	mandatory
        DESCRIPTION
                "The ifIndex value for the SDLC port which owns this link station."
        ::= { wfSdlcLSOperEntry 1 }

    wfSdlcLSOperAddress OBJECT-TYPE
        SYNTAX	INTEGER
        ACCESS	read-only
        STATUS	mandatory
        DESCRIPTION
                "This value is the poll address of the secondary link station
                in this SDLC link. It uniquely identifies the SDLC link station
                within a single SDLC port."
        ::= { wfSdlcLSOperEntry 2 }

    wfSdlcLSOperRole OBJECT-TYPE
        SYNTAX	INTEGER {
    		    negot(1),
    		    primary(2),
    		    sec(3),
    		    msec(4)
    		}
        ACCESS	read-only
        STATUS	mandatory
        DESCRIPTION
                "This object reflects the current role that the link station
                is assuming."
        DEFVAL	{ sec }
        ::= { wfSdlcLSOperEntry 3 }

    wfSdlcLSOperState OBJECT-TYPE
        SYNTAX	INTEGER {
    		    discont(1),
    		    conpend(2),
    		    contact(3),
    		    dispend(4)
    		}
        ACCESS	read-only
        STATUS	mandatory
        DESCRIPTION
                "This object describes the operational state of the SDLC link
                station. The managed system shall attempt to keep this value
                consistent with the administered state."
        DEFVAL	{ discont }
        ::= { wfSdlcLSOperEntry 4 }

    wfSdlcLSOperMAXDATA OBJECT-TYPE
        SYNTAX	INTEGER {
    		    pdu0265(265),
    		    pdu0521(521),
    		    pdu1033(1033),
    		    pdu2057(2057),
    		    pdu4105(4105)
    		}
        ACCESS	read-only
        STATUS	mandatory
        DESCRIPTION
                "This object reflects the current maximum PDU size allowed
                for the logical link. This value includes the Transmission Header
                (TH) and Request Header (RH). This value will controlled by the
                administered MAXDATA, wfSdlcLSAdminMAXDATA, or by the value negotiated
                in the XID exchange for link stations on a switched
                 SDLC line."
        DEFVAL	{ pdu1033 }
        ::= { wfSdlcLSOperEntry 5 }

    wfSdlcLSOperREPLYTO OBJECT-TYPE
        SYNTAX	INTEGER
        ACCESS	read-only
        STATUS	mandatory
        DESCRIPTION
                "This object reflects the current reply timeout, in tenths of
                seconds, for an SDLC link station. If the link station does not
                receive a repsonse to a poll or message before the specified time
                expires then the appropriate error recovery shall be initiated.
                This object has no meaning for secondary SDLC link stations."
        ::= { wfSdlcLSOperEntry 6 }

    wfSdlcLSOperMAXIN OBJECT-TYPE
        SYNTAX	INTEGER
        ACCESS	read-only
        STATUS	mandatory
        DESCRIPTION
                "This object reflects the current maximum number of
                unacknowledged frames which an SDLC link station may receive.
                This shall range from one to modulus minus one."
        ::= { wfSdlcLSOperEntry 7 }

    wfSdlcLSOperMAXOUT OBJECT-TYPE
        SYNTAX	INTEGER
        ACCESS	read-only
        STATUS	mandatory
        DESCRIPTION
                "This object controls the maximum consequetive unacknowledged
                frames which an SDLC link station shall send without an
                acknowledgement. This shall range from one to modulus minus one.
                The modulus is controlled by the object: wfSdlcLSAdminMODULO.
                This value will controlled by the administered MAXOUT,
                wfSdlcLSAdminMAXOUT, or by the value negotiated in the XID exchange
                for link stations on a switched SDLC line."
        ::= { wfSdlcLSOperEntry 8 }

    wfSdlcLSOperMODULO OBJECT-TYPE
        SYNTAX	INTEGER
        ACCESS	read-only
        STATUS	mandatory
        DESCRIPTION
                "This object reflects the current modulus for an SDLC link
                station. This modulus determines the size of rotating acknowledgement
                window used by the SDLC link station pair."
        ::= { wfSdlcLSOperEntry 9 }

    wfSdlcLSOperRETRIESm OBJECT-TYPE
        SYNTAX	INTEGER
        ACCESS	read-only
        STATUS	mandatory
        DESCRIPTION
                "This object controls number of retries in a retry sequence
                for an SDLC link station. A retry sequence is a series of
                retransmitted frames ( data or control) for which no positive
                acknowledgement is received. The current number of times that the
                retry sequence is to be repeated is reflected by the object:
                wfSdlcLSOperRETRIESn. The current interval between retry sequences
                is reflected by the object: wfSdlcLSOperRETRIESt."
        ::= { wfSdlcLSOperEntry 10 }

    wfSdlcLSOperRETRIESt OBJECT-TYPE
        SYNTAX	INTEGER
        ACCESS	read-only
        STATUS	mandatory
        DESCRIPTION
                "This object reflects the current interval, in seconds, between
                retry sequences for an SDLC link station if multiple retry sequences
                are specified. A retry sequence is a series of retransmitted frames
                ( data or control) for which no positive acknowledgement is received.
                The current number of repeated retries sequences is reflected by the
                object: wfSdlcLSOperRETRIESn. The current retries per sequence is
                reflected by the object: wfSdlcLSOperRETRIESm."
        ::= { wfSdlcLSOperEntry 11 }

    wfSdlcLSOperRETRIESn OBJECT-TYPE
        SYNTAX	INTEGER
        ACCESS	read-only
        STATUS	mandatory
        DESCRIPTION
                "This object reflects the current number of times that a retry
                sequence is repeated for an SDLC link station. A retry sequence is
                a series of retransmitted frames ( data or control) for which no
                positive acknowledgement is received. The current interval between
                retry sequences is reflected by the object: wfSdlcLSOperRETRIESn.
                The current retries per sequence is reflected by the
                object: wfSdlcLSOperRETRIESm."
        ::= { wfSdlcLSOperEntry 12 }

    wfSdlcLSOperRNRLIMIT OBJECT-TYPE
        SYNTAX	INTEGER
        ACCESS	read-only
        STATUS	mandatory
        DESCRIPTION
                "This object reflects the current length of time, in minutes,
                that an SDLC link station will allow its adjacent link station to
                remain in a busy (RNR) state before declaring it inoperative."
        ::= { wfSdlcLSOperEntry 13 }

    wfSdlcLSOperDATMODE OBJECT-TYPE
        SYNTAX	INTEGER {
    		    half(1),
    		    full(2)
    		}
        ACCESS	read-only
        STATUS	mandatory
        DESCRIPTION
                "This object reflects whether the current communications mode with
                the adjacent link station is two-way-alternate (half) or
                two-way-simultaneous (full)."
        DEFVAL	{ half }
        ::= { wfSdlcLSOperEntry 14 }

    wfSdlcLSOperCreateTime OBJECT-TYPE
        SYNTAX	TimeTicks
        ACCESS	read-only
        STATUS	mandatory
        DESCRIPTION
                "This object describes the time, in 1/100ths of seconds,
                of the creation of this SDLC link station."
        ::= { wfSdlcLSOperEntry 15 }

    wfSdlcLSOperLastFailCause OBJECT-TYPE
        SYNTAX	INTEGER {
    		    undefined(1),
    		    rxfrmr(2),
    		    txfrmr(3),
    		    noresp(4),
    		    protoerr(5),
    		    noactiv(6),
    		    rnrlimit(7),
    		    retriesexp(8)
    		}
        ACCESS	read-only
        STATUS	mandatory
        DESCRIPTION
                "This enumerated object reflects the cause of the last failure
                of this SDLC link station. If the link station has not failed, then
                this value has no meaning."
        ::= { wfSdlcLSOperEntry 16 }

    wfSdlcLSOperLastFailCtrlIn2 OBJECT-TYPE
        SYNTAX	OCTET STRING
        ACCESS	read-only
        STATUS	mandatory
        DESCRIPTION
                "This object reflects the last control octet or octets
                (depending on modulus) received by this SDLC link station at the
                time of the last failure. If the link station has not failed, then
                this value has no meaning."
        ::= { wfSdlcLSOperEntry 17 }

    wfSdlcLSOperLastFailCtrlOut2 OBJECT-TYPE
        SYNTAX	OCTET STRING
        ACCESS	read-only
        STATUS	mandatory
        DESCRIPTION
                "This object reflects the last control octet or octets
                (depending on modulus) sent by this SDLC link station at the time of
                the last failure. If the link station has not failed, then this
                value has no meaning."
        ::= { wfSdlcLSOperEntry 18 }

    wfSdlcLSOperLastFailFRMRInfo5 OBJECT-TYPE
        SYNTAX	OCTET STRING
        ACCESS	read-only
        STATUS	mandatory
        DESCRIPTION
                "This object reflects the information field of the FRMR frame
                if the last failure for this SDLC link station was as a result of an
                invalid frame. Otherwise, this field has no meaning."
        ::= { wfSdlcLSOperEntry 19 }

    wfSdlcLSOperLastFailREPLYTOs OBJECT-TYPE
        SYNTAX	Counter
        ACCESS	read-only
        STATUS	mandatory
        DESCRIPTION
                "This object reflects the number of times that the REPLYTO timer
                had expired for an SDLC link station at the time of the last failure.
                If the link station has not failed, then this value has no meaning."
        ::= { wfSdlcLSOperEntry 20 }

    wfSdlcLSOperGroupAddress OBJECT-TYPE
        SYNTAX	INTEGER
        ACCESS	read-only
        STATUS	mandatory
        DESCRIPTION
                "This value is the group poll address of the secondary link station for
                this SDLC link. If this link station is not part of a group, this address
                will be NULL."
        ::= { wfSdlcLSOperEntry 21 }

    wfSdlcLSStatsTable OBJECT-TYPE
        SYNTAX	SEQUENCE OF WfSdlcLSStatsEntry
        ACCESS	not-accessible
        STATUS	mandatory
        DESCRIPTION
                "Each entry in this table contains statistics for a specific
                SDLC link station."
        ::= { wfSdlcGroup 7 }

    wfSdlcLSStatsEntry OBJECT-TYPE
        SYNTAX	WfSdlcLSStatsEntry
        ACCESS	not-accessible
        STATUS	mandatory
        DESCRIPTION
                "A list of statistics for a specific SDLC link station"
        INDEX	{ wfSdlcLSStatsIfIndex,
    		  wfSdlcLSStatsAddress }
        ::= { wfSdlcLSStatsTable 1 }

    WfSdlcLSStatsEntry ::= SEQUENCE {
    	    wfSdlcLSStatsIfIndex
    		INTEGER,
    	    wfSdlcLSStatsAddress
    		INTEGER,
    	    wfSdlcLSStatsBLUsIns
    		Counter,
    	    wfSdlcLSStatsBLUsOuts
    		Counter,
    	    wfSdlcLSStatsOctetsIns
    		Counter,
    	    wfSdlcLSStatsOctetsOuts
    		Counter,
    	    wfSdlcLSStatsPollsOuts
    		Counter,
    	    wfSdlcLSStatsPollRspOuts
    		Counter,
    	    wfSdlcLSStatsLocalBusies
    		Counter,
    	    wfSdlcLSStatsRemoteBusies
    		Counter,
    	    wfSdlcLSStatsIFramesIns
    		Counter,
    	    wfSdlcLSStatsIFramesOuts
    		Counter,
    	    wfSdlcLSStatsRetransmits
    		Counter,
    	    wfSdlcLSStatsIOctetsIns
    		Counter,
    	    wfSdlcLSStatsIOctetsOuts
    		Counter,
    	    wfSdlcLSStatsUIFramesIns
    		Counter,
    	    wfSdlcLSStatsUIFramesOuts
    		Counter,
    	    wfSdlcLSStatsXIDsIns
    		Counter,
    	    wfSdlcLSStatsXIDsOuts
    		Counter,
    	    wfSdlcLSStatsTESTsIns
    		Counter,
    	    wfSdlcLSStatsTESTsOuts
    		Counter,
    	    wfSdlcLSStatsREJsIns
    		Counter,
    	    wfSdlcLSStatsREJsOuts
    		Counter,
    	    wfSdlcLSStatsFRMRsIns
    		Counter,
    	    wfSdlcLSStatsFRMRsOuts
    		Counter,
    	    wfSdlcLSStatsSimsIn
    		Counter,
    	    wfSdlcLSStatsSimsOut
    		Counter,
    	    wfSdlcLSStatsRimsIn
    		Counter,
    	    wfSdlcLSStatsRimsOut
    		Counter
        }

    wfSdlcLSStatsIfIndex OBJECT-TYPE
        SYNTAX	INTEGER
        ACCESS	read-only
        STATUS	mandatory
        DESCRIPTION
                "A list of statistics for an SDLC link station."
        ::= { wfSdlcLSStatsEntry 1 }

    wfSdlcLSStatsAddress OBJECT-TYPE
        SYNTAX	INTEGER
        ACCESS	read-only
        STATUS	mandatory
        DESCRIPTION
                "This value is the poll address of the secondary link station in
                this SDLC link. It uniquely identifies the SDLC link station within
                a single SDLC port."
        ::= { wfSdlcLSStatsEntry 2 }

    wfSdlcLSStatsBLUsIns OBJECT-TYPE
        SYNTAX	Counter
        ACCESS	read-only
        STATUS	mandatory
        DESCRIPTION
                "This object reflects the total basic link units (BLUs; frames)
                received from an adjacent SDLC link station since last reset or
                system startup."
        ::= { wfSdlcLSStatsEntry 3 }

    wfSdlcLSStatsBLUsOuts OBJECT-TYPE
        SYNTAX	Counter
        ACCESS	read-only
        STATUS	mandatory
        DESCRIPTION
                "This object reflects the total basic link units (BLUs; frames),
                transmitted to an adjacent SDLC link station since last reset or
                system startup."
        ::= { wfSdlcLSStatsEntry 4 }

    wfSdlcLSStatsOctetsIns OBJECT-TYPE
        SYNTAX	Counter
        ACCESS	read-only
        STATUS	mandatory
        DESCRIPTION
                "This object reflects the total octets received from an adjacent
                SDLC link station since last reset or system startup."
        ::= { wfSdlcLSStatsEntry 5 }

    wfSdlcLSStatsOctetsOuts OBJECT-TYPE
        SYNTAX	Counter
        ACCESS	read-only
        STATUS	mandatory
        DESCRIPTION
                "This object reflects the total octets transmitted to an adjacent
                SDLC link station since last reset or system startup."
        ::= { wfSdlcLSStatsEntry 6 }

    wfSdlcLSStatsPollsOuts OBJECT-TYPE
        SYNTAX	Counter
        ACCESS	read-only
        STATUS	mandatory
        DESCRIPTION
                "This object reflects the total polls sent to an adjacent SDLC
                link station since last reset or system startup."
        ::= { wfSdlcLSStatsEntry 7 }

    wfSdlcLSStatsPollRspOuts OBJECT-TYPE
        SYNTAX	Counter
        ACCESS	read-only
        STATUS	mandatory
        DESCRIPTION
                "This object reflects the total polls responded to by the local
                SDLC link station since last reset or system startup."
        ::= { wfSdlcLSStatsEntry 8 }

    wfSdlcLSStatsLocalBusies OBJECT-TYPE
        SYNTAX	Counter
        ACCESS	read-only
        STATUS	mandatory
        DESCRIPTION
                "This object reflects the total number of times that the local
                SDLC link station has entered a busy state (RNR) since last reset or system
                startup."
        ::= { wfSdlcLSStatsEntry 9 }

    wfSdlcLSStatsRemoteBusies OBJECT-TYPE
        SYNTAX	Counter
        ACCESS	read-only
        STATUS	mandatory
        DESCRIPTION
                "This object reflects the total number of times that an
                adjacent ( remote) SDLC link station has entered a busy state
                (RNR) since last reset or system startup."
        ::= { wfSdlcLSStatsEntry 10 }

    wfSdlcLSStatsIFramesIns OBJECT-TYPE
        SYNTAX	Counter
        ACCESS	read-only
        STATUS	mandatory
        DESCRIPTION
                "This object reflects the total I-frames received from
                an adjacent SDLC link station since last reset or system startup."
        ::= { wfSdlcLSStatsEntry 11 }

    wfSdlcLSStatsIFramesOuts OBJECT-TYPE
        SYNTAX	Counter
        ACCESS	read-only
        STATUS	mandatory
        DESCRIPTION
                "This object reflects the total I-frames transmitted to an
                adjacent SDLC link station since last reset or system startup."
        ::= { wfSdlcLSStatsEntry 12 }

    wfSdlcLSStatsRetransmits OBJECT-TYPE
        SYNTAX	Counter
        ACCESS	read-only
        STATUS	mandatory
        DESCRIPTION
                "This object reflects the total frames retransmitted to an
                adjacent SDLC link station since last reset or system startup."
        ::= { wfSdlcLSStatsEntry 13 }

    wfSdlcLSStatsIOctetsIns OBJECT-TYPE
        SYNTAX	Counter
        ACCESS	read-only
        STATUS	mandatory
        DESCRIPTION
                "This object reflects the total octets contained in I-frames
                received from an adjacent SDLC link station since last reset or
                system startup."
        ::= { wfSdlcLSStatsEntry 14 }

    wfSdlcLSStatsIOctetsOuts OBJECT-TYPE
        SYNTAX	Counter
        ACCESS	read-only
        STATUS	mandatory
        DESCRIPTION
                "This object reflects the total octets contained in I-frames
                transmitted to an adjacent SDLC link station since last reset or
                system startup."
        ::= { wfSdlcLSStatsEntry 15 }

    wfSdlcLSStatsUIFramesIns OBJECT-TYPE
        SYNTAX	Counter
        ACCESS	read-only
        STATUS	mandatory
        DESCRIPTION
                "This object reflects the total UI-frames received from an
                adjacent SDLC link station since last reset or system startup."
        ::= { wfSdlcLSStatsEntry 16 }

    wfSdlcLSStatsUIFramesOuts OBJECT-TYPE
        SYNTAX	Counter
        ACCESS	read-only
        STATUS	mandatory
        DESCRIPTION
                "This object reflects the total UI-frames transmitted to an
                adjacent SDLC link station since last reset or system startup."
        ::= { wfSdlcLSStatsEntry 17 }

    wfSdlcLSStatsXIDsIns OBJECT-TYPE
        SYNTAX	Counter
        ACCESS	read-only
        STATUS	mandatory
        DESCRIPTION
                "This object reflects the total XID frames received from an
                adjacent SDLC link station since last reset or system startup."
        ::= { wfSdlcLSStatsEntry 18 }

    wfSdlcLSStatsXIDsOuts OBJECT-TYPE
        SYNTAX	Counter
        ACCESS	read-only
        STATUS	mandatory
        DESCRIPTION
                "This object reflects the total XID frames transmitted to an
                adjacent SDLC link station since last reset or system startup."
        ::= { wfSdlcLSStatsEntry 19 }

    wfSdlcLSStatsTESTsIns OBJECT-TYPE
        SYNTAX	Counter
        ACCESS	read-only
        STATUS	mandatory
        DESCRIPTION
                "This object reflects the total TEST frames, commands or responses,
                received from an adjacent SDLC link station since last reset or
                system startup."
        ::= { wfSdlcLSStatsEntry 20 }

    wfSdlcLSStatsTESTsOuts OBJECT-TYPE
        SYNTAX	Counter
        ACCESS	read-only
        STATUS	mandatory
        DESCRIPTION
                "This object reflects the total TEST frames, commands or responses,
                transmitted to an adjacent SDLC link station since last reset or
                system startup."
        ::= { wfSdlcLSStatsEntry 21 }

    wfSdlcLSStatsREJsIns OBJECT-TYPE
        SYNTAX	Counter
        ACCESS	read-only
        STATUS	mandatory
        DESCRIPTION
                "This object reflects the total REJ frames received from an
                adjacent SDLC link station since last reset or system startup."
        ::= { wfSdlcLSStatsEntry 22 }

    wfSdlcLSStatsREJsOuts OBJECT-TYPE
        SYNTAX	Counter
        ACCESS	read-only
        STATUS	mandatory
        DESCRIPTION
                "This object reflects the total REJ frames transmitted to an
                adjacent SDLC link station since last reset or system startup."
        ::= { wfSdlcLSStatsEntry 23 }

    wfSdlcLSStatsFRMRsIns OBJECT-TYPE
        SYNTAX	Counter
        ACCESS	read-only
        STATUS	mandatory
        DESCRIPTION
                "This object reflects the total frame reject (FRMR) frames
                received from an adjacent SDLC link station since last reset or
                system startup."
        ::= { wfSdlcLSStatsEntry 24 }

    wfSdlcLSStatsFRMRsOuts OBJECT-TYPE
        SYNTAX	Counter
        ACCESS	read-only
        STATUS	mandatory
        DESCRIPTION
                "This object reflects the total frame reject (FRMR) frames
                transmitted to an adjacent SDLC link station since last reset
                or system startup."
        ::= { wfSdlcLSStatsEntry 25 }

    wfSdlcLSStatsSimsIn OBJECT-TYPE
        SYNTAX	Counter
        ACCESS	read-only
        STATUS	mandatory
        DESCRIPTION
                "This object reflects the total set initialization mode (SIM) frames
                received from an adjacent SDLC link station since last reset or
                system startup."
        ::= { wfSdlcLSStatsEntry 26 }

    wfSdlcLSStatsSimsOut OBJECT-TYPE
        SYNTAX	Counter
        ACCESS	read-only
        STATUS	mandatory
        DESCRIPTION
                "This object reflects the total set initialization mode (SIM) frames
                transmitted to an adjacent SDLC link station since last reset or
                system startup."
        ::= { wfSdlcLSStatsEntry 27 }

    wfSdlcLSStatsRimsIn OBJECT-TYPE
        SYNTAX	Counter
        ACCESS	read-only
        STATUS	mandatory
        DESCRIPTION
                "This object reflects the total request initialization mode (RIM) frames
                received from an adjacent SDLC link station since last reset or
                system startup."
        ::= { wfSdlcLSStatsEntry 28 }

    wfSdlcLSStatsRimsOut OBJECT-TYPE
        SYNTAX	Counter
        ACCESS	read-only
        STATUS	mandatory
        DESCRIPTION
                "This object reflects the total request initialization mode (RIM) frames
                transmitted to an adjacent SDLC link station since last reset or
                system startup."
        ::= { wfSdlcLSStatsEntry 29 }

    END  -- Wellfleet-SDLC-MIB
