KYOCERA-Private-MIB DEFINITIONS ::= BEGIN
--
--		Created by S.Kanemitsu
--		SE group Printer Div. KYOCERA Corp.
--
--		August 01, 1996
--		Release 1.00
--
--		Applied printer model:
--			FS-1600+, FS-3600+, FS-1550+, FS-3400+
--

--
--	Declare imports
--
	IMPORTS
		hrDeviceIndex
			FROM HOST-RESOURCES-MIB
		OBJECT-TYPE
			FROM RFC-1212
		DisplayString FROM SNMPv2-TC
		enterprises FROM RFC1155-SMI;

--
--	Object identifier definition
--
	kyocera			OBJECT IDENTIFIER ::= { enterprises 1347 }

--  !! Following definition is for SNMPv2-SMI.
--	kcPrinter		MODULE-IDENTITY
--			LAST-UPDATED "9608010000Z"
--			ORGANIZATION "KYOCERA Corporation"
--			CONTACT-INFO
--				"		S. Kanemitsu
--						SE Group, Printer Div.
--				Postal: KYOCERA Corporation
--						2-14-9 Tamagawadai
--						Setagaya-ku, Tokyo 158 Japan
--
--				   Tel: +81-3-3708-3858
--				   Fax: +81-3-3708-0423
--				E-mail: Shige@KEI-CA.Compuserve.com"
--			DESCRIPTION
--				"The private MIB module for KYOCERA printers."
-- 		::= { kyocera 43 }

--	!! Following definition is for SNMP(v1).
	kcPrinter		OBJECT IDENTIFIER ::= { kyocera 43 }
	
	kcprtGeneral		OBJECT IDENTIFIER ::= { kcPrinter 5 }
	kcprtOutput			OBJECT IDENTIFIER ::= { kcPrinter 9 }
	kcprtMarker			OBJECT IDENTIFIER ::= { kcPrinter 10 }
	kcprtChannel		OBJECT IDENTIFIER ::= { kcPrinter 14 }
	kcprtMemoryResource	OBJECT IDENTIFIER ::= { kcPrinter 20 }

--
--	General group
--
--		To view and control the sub-unit independent value.
--
	kcprtGeneralTable	OBJECT-TYPE
		SYNTAX	SEQUENCE OF KcprtGeneralEntry
		ACCESS	not-accessible
		STATUS	mandatory
		DESCRIPTION
			"This table contains the generic parameters that is applied
			to the KYOCERA network printer."
		
		::= { kcprtGeneral 1 }
	
	kcprtGeneralEntry	OBJECT-TYPE
		SYNTAX	KcprtGeneralEntry
		ACCESS	not-accessible
		STATUS	mandatory
		DESCRIPTION
			"A list of general entries for KYOCERA printer."
		INDEX	{ hrDeviceIndex }
		::= { kcprtGeneralTable 1 }
	
	KcprtGeneralEntry	::= SEQUENCE {
					kcprtGeneralModelName	DisplayString,
					kcprtOptionVersion		DisplayString,
					kcprtKpdlLevel			INTEGER,
					kcprtSystemUpTime		INTEGER,
					kcprtBinNumber			INTEGER,
					kcprtCardSlotCapacity	INTEGER,
					kcprtRomSlotCapacity	INTEGER,
					kcprtSimmSlotCapacity	INTEGER,
					kcprtSimmSlotUsed		INTEGER,
					kcprtOriginalMemorySize	INTEGER,
					kcprtTotalMemorySize	INTEGER,
					kcprtUserMemorySize		INTEGER,
					kcprtVirtualMemory		INTEGER,
					kcprtPageMemorySize		INTEGER,
					kcprtHostBufferSize		INTEGER,
					kcprtHostBuffer1stRate	INTEGER,
					kcprtHostBuffer2ndRate	INTEGER,
					kcprtHostBuffer3rdRate	INTEGER,
					kcprtHostBufferOption	INTEGER,
					kcprtBufferXoffLevel	INTEGER,
					kcprtBufferXonLevel		INTEGER,
					kcprtFFTimeout			INTEGER,
					kcprtSleepTimer			INTEGER,
					kcprtWakeupStatusPage	INTEGER,
					kcprtOnlineControl		INTEGER,
					kcprtCopyCount			INTEGER
			}

	kcprtGeneralModelName	OBJECT-TYPE
		SYNTAX	DisplayString	( SIZE(0..32) )
		ACCESS	read-only
		STATUS	mandatory
		DESCRIPTION
			"The printer's model name."
		::= { kcprtGeneralEntry 1 }
		
	kcprtOptionDescription		OBJECT-TYPE
		SYNTAX	DisplayString	( SIZE(0..10) )
		ACCESS	read-only
		STATUS	mandatory
		DESCRIPTION
			"The string used for identify the option interface."
		::= { kcprtGeneralEntry 2 }
		
	kcprtKpdlLevel			OBJECT-TYPE
		SYNTAX	INTEGER	(0..2)
		ACCESS	read-only
		STATUS	mandatory
		DESCRIPTION
			"The level of KPDL. The value (0) means KPDL is not supported or KPDL ROM is missing."
		::= { kcprtGeneralEntry 3 }
		
	kcprtSystemUpTime		OBJECT-TYPE
		SYNTAX	INTEGER	(0..4294967295)
		ACCESS	read-only
		STATUS	mandatory
		DESCRIPTION
			"The amount of time since this printer was last powered on. Unit is second."
		::= { kcprtGeneralEntry 4 }
		
	kcprtBinNumber			OBJECT-TYPE
		SYNTAX	INTEGER	(0..255)
		ACCESS	read-only
		STATUS	mandatory
		DESCRIPTION
			"The number of paper bins that is implemented within printer itself.  This number does not show all of input bin number."
		::= { kcprtGeneralEntry 5 }
		
	kcprtCardSlotCapacity	OBJECT-TYPE
		SYNTAX	INTEGER	(0..255)
		ACCESS	read-only
		STATUS	mandatory
		DESCRIPTION
			"The number of IC card slots that this printer actually has.  The value (0) means this printer has no IC card slot."
		::= { kcprtGeneralEntry 6 }
		
	kcprtRomSlotCapacity	OBJECT-TYPE
		SYNTAX	INTEGER	(0..255)
		ACCESS	read-only
		STATUS	mandatory
		DESCRIPTION
			"The number of option ROM slots.  The value (0) means this printer has no option ROM slot."
		::= { kcprtGeneralEntry 7 }
		
	kcprtSimmSlotCapacity	OBJECT-TYPE
		SYNTAX	INTEGER	(0..255)
		ACCESS	read-only
		STATUS	mandatory
		DESCRIPTION
			"The number of SIMM slots that this printer actually has."
		::= { kcprtGeneralEntry 8 }
		
	kcprtSimmSlotUsed		OBJECT-TYPE
		SYNTAX	INTEGER	(0..255)
		ACCESS	read-only
		STATUS	mandatory
		DESCRIPTION
			" The number of SIMM slots that is currently used for SIMM."
		::= { kcprtGeneralEntry 9 }
		
	kcprtOriginalMemorySize	OBJECT-TYPE
		SYNTAX	INTEGER	(0..4294967295)
		ACCESS	read-only
		STATUS	mandatory
		DESCRIPTION
			"The amount of memory that this printer has on its controller board. Note this value does not include any other optional memory. Unit is kilobytes."
		::= { kcprtGeneralEntry 10 }
		
	kcprtTotalMemorySize	OBJECT-TYPE
		SYNTAX	INTEGER	(0..4294967295)
		ACCESS	read-only
		STATUS	mandatory
		DESCRIPTION
			"The amount of memory that this printer actually has. Unit is kilobytes."
		::= { kcprtGeneralEntry 11 }
		
	kcprtUserMemorySize		OBJECT-TYPE
		SYNTAX	INTEGER	(0..4294967295)
		ACCESS	read-only
		STATUS	mandatory
		DESCRIPTION
			"The amount of memory that is available for user. Unit is kilobyte."
		::= { kcprtGeneralEntry 12 }
		
	kcprtVirtualMemory		OBJECT-TYPE
		SYNTAX	INTEGER	{
			notSupported(0),
			support(1)
		}
		ACCESS	read-only
		STATUS	mandatory
		DESCRIPTION
			"This object shows whether this printer has the virtual memory function."
		::= { kcprtGeneralEntry 13 }

	kcprtPageMemorySize		OBJECT-TYPE
		SYNTAX	INTEGER	{
			size-128KB(1),
			size-256KB(2),
			size-512KB(3),
			size-A4orLetter(4),
			size-Legal(5),
			size-doubleA4orLetter(6),
			size-doubleLegal(7)
		}
		ACCESS	read-write
		STATUS	mandatory
		DESCRIPTION
			"The page memory size corresponding to the FRPO R5 parameter. Because each model of our printer has slightly different value combination, it is recommended to verify the value after writing. Please ask to KYOCERA about the value combination for each printer. For example, our A3 type printer does not have this capability so that The value will be always 512KB(3). The value (-1) means others. Writing (-1) has no meaning."
		::= { kcprtGeneralEntry 14 }
		
	kcprtHostBufferSize		OBJECT-TYPE
		SYNTAX	INTEGER	(0..99)
		ACCESS	read-write
		STATUS	mandatory
		DESCRIPTION
			" The host buffer size in units of ten kilobytes. The value(0) means that the host buffer size is 5 Kbytes."
		::= { kcprtGeneralEntry 15 }
		
	kcprtHostBuffer1stRate	OBJECT-TYPE
		SYNTAX	INTEGER	(0..9)
		ACCESS	read-write
		STATUS	mandatory
		DESCRIPTION
			"The ratio of the main host buffer size."
		::= { kcprtGeneralEntry 16 }
		
	kcprtHostBuffer2ndRate	OBJECT-TYPE
		SYNTAX	INTEGER	(0..9)
		ACCESS	read-write
		STATUS	mandatory
		DESCRIPTION
			"The ratio of the 2nd host buffer size."
		::= { kcprtGeneralEntry 17 }
		
	kcprtHostBuffer3rdRate	OBJECT-TYPE
		SYNTAX	INTEGER	(0..9)
		ACCESS	read-write
		STATUS	mandatory
		DESCRIPTION
			"The ratio of the 3rd host buffer size. Note that this entry will be 'not accessible' if the printer has only two interfaces."
		::= { kcprtGeneralEntry 18 }
		
	kcprtHostBufferOption	OBJECT-TYPE
		SYNTAX	INTEGER	{
			automatic(0),
			fixed(1)
		} 
		ACCESS	read-write
		STATUS	mandatory
		DESCRIPTION
			"In the automatic mode, the first data arriving from the computer go into main buffer (1st buffer). In the fixed mode, each buffer is fixed on the appropriate interface. Refer to User’s manual."
		::= { kcprtGeneralEntry 19 }
		
	kcprtBufferXoffLevel	OBJECT-TYPE
		SYNTAX	INTEGER	(0..99)
		ACCESS	read-write
		STATUS	mandatory
		DESCRIPTION
			"The printer will pause for receiving data when the ratio of occupied data on the host buffer reaches this threshold level. Note that this value should be larger than kcprtBufferXonLevel. If not, the value is ignored."
		::= { kcprtGeneralEntry 20 }
		
	kcprtBufferXonLevel		OBJECT-TYPE
		SYNTAX	INTEGER	(0..99)
		ACCESS	read-write
		STATUS	mandatory
		DESCRIPTION
			"The printer will begin to receive data again when the ratio of occupied data on the host buffer becomes lower than this threshould level. Note that value should be less than kcprtBufferXoffLevel. If not, the value is ignored."
		::= { kcprtGeneralEntry 21 }
		
	kcprtFFTimeout			OBJECT-TYPE
		SYNTAX	INTEGER	(0..99)
		ACCESS	read-write
		STATUS	mandatory
		DESCRIPTION
			"The form-feed time-out timer in units of five seconds. The value (0) means the time-out timer is off."
		::= { kcprtGeneralEntry 22 }
		
	kcprtSleepTimer			OBJECT-TYPE
		SYNTAX	INTEGER	(0..24)
		ACCESS	read-write
		STATUS	mandatory
		DESCRIPTION
			"The value of sleep timer in units of five minutes. The value (0) means the sleep timer is off."
		::= { kcprtGeneralEntry 23 }
		
	kcprtWakeupStatusPage	OBJECT-TYPE
		SYNTAX	INTEGER	{
			disable(0),
			enable(1)
		}
		ACCESS	read-write
		STATUS	mandatory
		DESCRIPTION
			"If enable, a printer generates the status page each time it comes up."
		::= { kcprtGeneralEntry 24 }
		
	kcprtOnlineControl		OBJECT-TYPE
		SYNTAX	INTEGER	{
			offLine(0),
			onLine(1)
		}
		ACCESS	read-write
		STATUS	mandatory
		DESCRIPTION
			"This object controls the on/off line status. Note the writing value does not apply in some situation."
		::= { kcprtGeneralEntry 25 }
		
	kcprtCopyCount			OBJECT-TYPE
		SYNTAX	INTEGER	(1..999)
		ACCESS	read-write
		STATUS	mandatory
		DESCRIPTION
			"The default copy number."
		::= { kcprtGeneralEntry 26 }
		
--
--	General->CPU table
--
	kcprtCpuTable	OBJECT-TYPE
		SYNTAX	SEQUENCE OF KcprtCpuEntry
		ACCESS	not-accessible
		STATUS	mandatory
		DESCRIPTION
			"Information of CPU that is implemented in the printer."
		::={ kcprtGeneral 4 }

	kcprtCpuEntry		OBJECT-TYPE
		SYNTAX	KcprtCpuEntry
		ACCESS	not-accessible
		STATUS	mandatory
		DESCRIPTION
			"A list of CPU information for KYOCERA printer."
		INDEX { hrDeviceIndex, kcprtCpuIndex }
		::={ kcprtCpuTable 1 }

	KcprtCpuEntry	::= SEQUENCE {
		kcprtCpuIndex	INTEGER,
		kcprtCpuName	DisplayString,
		kcprtCpuClock	INTEGER,
		kcprtCpuRole	INTEGER,
		kcprtFirmwareVersion	DisplayString,
		kcprtFirmwareUpdate		INTEGER
	}

	kcprtCpuIndex		OBJECT-TYPE
		SYNTAX	INTEGER
		ACCESS	not-accessible
		STATUS	mandatory
		DESCRIPTION
			"A unique value used by the printer to identify CPU on the printer’s controller."
		::={ kcprtCpuEntry 1 }

	kcprtCpuName		OBJECT-TYPE
		SYNTAX	DisplayString ( SIZE(0..31) )
		ACCESS	read-only
		STATUS	mandatory
		DESCRIPTION
			"The CPU model name, such as ‘68EC040’."
 		::={ kcprtCpuEntry 2 }
		
	kcprtCpuClock		OBJECT-TYPE
		SYNTAX	INTEGER
		ACCESS	read-only
		STATUS	mandatory
		DESCRIPTION
			"The clock speed of CPU in unit of MHz."
		::={ kcprtCpuEntry 3 }

	kcprtCpuRole		OBJECT-TYPE
		SYNTAX	INTEGER	{
			engine(0),
			controller(1)
		}
		ACCESS	read-only
		STATUS	mandatory
		DESCRIPTION
			"The role of this CPU. The value (-1) means others."
		::={ kcprtCpuEntry 4 }

	kcprtFirmwareVersion	OBJECT-TYPE
		SYNTAX	DisplayString ( SIZE( 0..31 ) )
		ACCESS	read-only
		STATUS	mandatory
		DESCRIPTION
			"The version string for the firmware of this CPU."
		::={ kcprtCpuEntry 5 }

	kcprtFirmwareUpdata		OBJECT-TYPE
		SYNTAX	INTEGER	{
			enabled(3),
			disabled(4)
		}
		ACCESS	read-only
		STATUS	mandatory
		DESCRIPTION
			"Shows whether this firmware can be updated on the controller."
		::={ kcprtCpuEntry 6 }

--
--	Output group
--
--		To view and/or control the output unit, especially for SO-6.
--
	kcprtOutputTable	OBJECT-TYPE
		SYNTAX	SEQUENCE OF KcprtOutputEntry
		ACCESS	not-accessible
		STATUS	mandatory
		DESCRIPTION
			"This table contains the basic part of the output unit. The main purpose is to control SO-6."
		::={ kcprtOutput 1 }
	
	kcprtOutputEntry	OBJECT-TYPE
		SYNTAX	KcprtOutputEntry
		ACCESS	not-accessible
		STATUS	mandatory
		DESCRIPTION
			"A list of information for the output unit, especially for the SO-6."
		INDEX {hrDeviceIndex, kcprtOutputIndex}
		::={ kcprtOutputTable 1 }

	KcprtOutputEntry	::= SEQUENCE {
		kcprtOutputIndex			INTEGER,
		kcprtOutputMode				INTEGER,
		kcprtOutputMultiMode		INTEGER,
		kcprtOutputGroupNumber		INTEGER,
		kcprtOutputDefaultGroup		INTEGER,
		kcprtOutputBulkStatus		INTEGER,
		kcprtOutputTrayMaxCapacity	INTEGER
	}

	kcprtOutputIndex	OBJECT-TYPE
		SYNTAX	INTEGER
		ACCESS	not-accessible
		STATUS	mandatory
		DESCRIPTION
			"The value of the prtOutputIndex of this printer that this entry is associated with."
		::={ kcprtOutputEntry 1 }
 
	kcprtOutputMode		OBJECT-TYPE
		SYNTAX	INTEGER	{
			sorter(0),
			collator(1),
			stacker(2),
			mailbox(3)
		}
		ACCESS	read-write
		STATUS	mandatory
		DESCRIPTION
			"The operation mode of the sorter.  If this device does not support the sorter function, the reading value is (-1) and all writing are ignored.  Also, writing value (-1) does not take effect."
		::={ kcprtOutputEntry 2 }

	kcprtOutputMultiMode		OBJECT-TYPE
		SYNTAX	INTEGER {
			off(0),
			id-specific(1),
			if-specific(2)
		}
		ACCESS	read-write
		STATUS	mandatory
		DESCRIPTION
			"In the multiple mode, the sorter can simultaneously be used by different computers.  Each computer may assign its own output trays.  This value determines how the tray is selected.
			The value (-1) means others or 'not supported'."
		::={ kcprtOutputEntry 3 }
 
	kcprtOutputGroupNumber		OBJECT-TYPE
		SYNTAX	INTEGER
		ACCESS	read-only
		STATUS	mandatory
		DESCRIPTION
			"This entry shows how many groups are existing on the output device."
		::={ kcprtOutputEntry 4 }

	kcprtOutputDefaultGroup		OBJECT-TYPE
		SYNTAX	INTEGER
		ACCESS	read-write
		STATUS	mandatory
		DESCRIPTION
			"The value of the kcprtTrayGroupIndex corresponding to the current output tray group in a sorter. This value has no meaning if this output unit is not a soter. The value (0) means that the multiple mode is disabled and all of trays will be able to use. Writing value (0) indicates a selection of bulkTray . Writing is only allowed when the multiple mode is enabled."
		::={ kcprtOutputEntry 5 }
 
	kcprtOutputBulkStatus		OBJECT-TYPE
		SYNTAX	INTEGER {
			notFull(0),
			full(1)
		}
		ACCESS	read-only
		STATUS	mandatory
		DESCRIPTION
			"This entry shows current status of the bulk tray. Since the bulk tray of SO-6 has only a full sensor, this entry has only two states. In future, the state will be added."
		::={ kcprtOutputEntry 6 }

	kcprtOutputTrayMaxCapacity		OBJECT-TYPE
		SYNTAX	INTEGER
		ACCESS	read-only
		STATUS	mandatory
		DESCRIPTION
			"This entry shows how many pages the tray on this output device can hold. Unit is sheet."
		::={ kcprtOutputEntry 7 }


--
--	Output->TrayGroup table
--
--		To see the multiple tray output device, such as SO-6.
--
kcprtTrayGroupTable		OBJECT-TYPE
	SYNTAX	SEQUENCE OF KcprtTrayGroupEntry
	ACCESS	not-accessible
	STATUS	mandatory
	DESCRIPTION
		"The concept of Group is for the multiple computer environment.  These contents take effect when kcprtOutputMultiMode is enable.  For further information, refer to the sorter manual. Note in case of off (0), the access to this content is ineffective."
	::={ kcprtOutput 2 }

	kcprtTrayGroupEntry		OBJECT-TYPE
		SYNTAX	KcprtTrayGroupEntry
		ACCESS	not-accessible
		STATUS	mandatory
		DESCRIPTION
			"A list of information about the tray group on the multiple tray device."
		INDEX {hrDeviceIndex, kcprtOutputIndex, kcprtTrayGroupIndex}
		::={ kcprtTrayGroupTable 1 }

	KcprtTrayGroupEntry	::= SEQUENCE {
		kcprtTrayGroupIndex			INTEGER,
		kcprtTrayGroupBeginIndex	INTEGER,
		kcprtTrayGroupEndIndex		INTEGER
	}

	kcprtTrayGroupIndex		OBJECT-TYPE
	SYNTAX	INTEGER
	ACCESS	not-accessible
	STATUS	mandatory
	DESCRIPTION
		"The unique value used by the printer to identify each tray groups.  Note that this value will be changed while the printer power cycles if Prescribe ASTK command is issued."
	::={ kcprtTrayGroupEntry 1 }

	kcprtTrayGroupBeginIndex		OBJECT-TYPE
		SYNTAX	INTEGER
		ACCESS	read-only
		STATUS	mandatory
		DESCRIPTION
			"The value of the kcprtOutputTrayIndex corresponding to the tray that is assigned as the begining of this group."
		::={ kcprtTrayGroupEntry 2 }

	kcprtTrayGroupEndIndex		OBJECT-TYPE
		SYNTAX	INTEGER
		ACCESS	read-only
		STATUS	mandatory
		DESCRIPTION
			"The value of the kcprtOutputTrayIndex corresponding to the tray that is assigned as the end of this group.  This index is automatically assigned by the printer when the group is created. Please refer to thePrescribe manual for detailed information."
		::={ kcprtTrayGroupEntry 3 }


--
--	Output->Tray table
--
--		To see and control the individual tray.
--
	kcprtOutputTrayTable		OBJECT-TYPE
		SYNTAX	SEQUENCE OF KcprtOutputTrayEntry
		ACCESS	not-accessible
		STATUS	mandatory
		DESCRIPTION
			"Note in case of off (0), the access to this content is ineffective."
		::={ kcprtOutput 3 }

	kcprtOutputTrayEntry		OBJECT-TYPE
		SYNTAX	KcprtOutputTrayEntry
		ACCESS	not-accessible
		STATUS	mandatory
		DESCRIPTION
			"A list of information about the individual tray."
		INDEX{ hrDeviceIndex, kcprtOutputIndex, kcprtOutputTrayIndex }
		::={ kcprtOutputTrayTable 1 }
	
	KcprtOutputTrayEntry	::= SEQUENCE {
		kcprtOutputTrayIndex	INTEGER,
		kcprtOutputTrayOrder	INTEGER,
		kcprtOutputTrayGroup	INTEGER,
		kcprtOutputTrayCount	INTEGER
	}

	kcprtOutputTrayIndex		OBJECT-TYPE
		SYNTAX	INTEGER
		ACCESS	not-accessible
		STATUS	mandatory
		DESCRIPTION
			"The unique value used by a printer to identify each trays. Values are expected to remain stable across successive printer power cycle. This contents has no meaning except for a sorter device."
		::={ kcprtOutputTrayEntry 1 }

	kcprtOutputTrayOrder		OBJECT-TYPE
		SYNTAX	INTEGER
		ACCESS	read-only
		STATUS	mandatory
		DESCRIPTION
			"The output order for trays. The beginning number is (1) and the last number should be equal to the maximum tray number.
			When the multiple mode is  available, the order in the appropriate group is determined by this entry.
			The number should be unique and continuous in one group or the whole if the group function is disabled.
			The value (0) means the order has not been determined. In case all of the trays are not determined, the sorter will operate in default settings. About default settings, refer to the sorter’s manual. Currently this entry is read-only."
		::={ kcprtOutputTrayEntry 2 }

	kcprtOutputTrayGroup		OBJECT-TYPE
		SYNTAX	INTEGER
		ACCESS	read-only
		STATUS	mandatory
		DESCRIPTION
			"The value of kcprtTrayGroupIndex corresponding to the group that this tray is assigned to. The value (0) means this tray is not assigned to a group or the multiple mode is disable."
		::={ kcprtOutputTrayEntry 3 }

	kcprtOutputTrayCount		OBJECT-TYPE
		SYNTAX	INTEGER
		ACCESS	read-only
		STATUS	mandatory
		DESCRIPTION
			"The count of page that the tray may be holding. Since the tray cannot count the page that it has currently, the value is not always same as the actual page counts.
			If all of paper is removed, this value will be 0. In SO-6, there is no full sensor. So, if the application needs to know whether the tray is full or not, the application should compare this value with OutputTrayMaxCapacity.
			In some case, the printer is turned on with remaining some pages on the tray for example, this value will be same as MaxCapacity to inform that paper is remaining and demand to remove the page."
		::={ kcprtOutputTrayEntry 4 }


--
--	Marker
--
--		To see and control the marker unit specific for KYOCERA printer.
--
	kcprtMarkerTable		OBJECT-TYPE
		SYNTAX	SEQUENCE OF KcprtMarkerEntry
		ACCESS	not-accessible
		STATUS	mandatory
		DESCRIPTION
			"This table contains some useful entries to control the marker specific function."
		::={ kcprtMarker 1 }
		
	kcprtMarkerEntry		OBJECT-TYPE
		SYNTAX	KcprtMarkerEntry
		ACCESS	not-accessible
		STATUS	mandatory
		DESCRIPTION
			"A list of entries that corresponds each function of the marker."
		INDEX{hrDeviceIndex, prtMarkerIndex}
		::={ kcprtMarkerTable 1 }

	KcprtMarkerEntry	::= SEQUENCE {
		kcprtMarkerIndex							INTEGER,
		kcprtMarkerKirLevel							INTEGER,
		kcprtMarkerEcoprintLevel					INTEGER,
		kcprtMarkerAddressabilityFeedDirDeclared	INTEGER,
		kcprtMarkerAddressabilityXFeedDirDeclared	INTEGER,
		kcprtMarkerAddressabilityFeedDirChosen		INTEGER,
		kcprtMarketAddressabilityXFeedDirChosen		INTEGER
	}

	kcprtMarkerIndex		OBJECT-TYPE
		SYNTAX	INTEGER
		ACCESS	not-accessible
		STATUS	mandatory
		DESCRIPTION
			"The value of the prtMarkerIndex of the printer devices with which it is associated."
		::={ kcprtMarkerEntry 1 }
	
	kcprtMarkerKirLevel		OBJECT-TYPE
		SYNTAX	INTEGER	{
			offOrNotSupport(0),
			light(1),
			medium(2),
			dark(3)
		}
		ACCESS	read-write
		STATUS	mandatory
		DESCRIPTION
			"The value that shows current KIR level. The value (0) means off or not support (0)."
		::={ kcprtMarkerEntry 2 }

	kcprtMarkerEcoprintLevel		OBJECT-TYPE
		SYNTAX	INTEGER	{
			offOrNotSupport(0),
			light(1),
			medium(2),
			dark(3)
		}
		ACCESS	read-write
		STATUS	mandatory
		DESCRIPTION
			"The value that shows current Ecoprint level. The value (0) means off or not support."
		::={ kcprtMarkerEntry 3 }

	kcprtMarkerAddressabilityFeedDirDeclared		OBJECT-TYPE
		SYNTAX	INTEGER
		ACCESS	read-write
		STATUS	mandatory
		DESCRIPTION
			"This object provides the value of the declared addressability, in the feed direction, of this marker. This addressability is measured in prtMarkerAddressabilityUnit."
		::={ kcprtMarkerEntry 4 }

	kcprtMarkerAddressabilityXFeedDirDeclared		OBJECT-TYPE
		SYNTAX	INTEGER
		ACCESS	read-write
		STATUS	mandatory
		DESCRIPTION
			"This object provides the value of declared dimension, in the cross feed direction, of this marker device. This addressability is measured in prtMarkerAddressabilityUnit."
		::={ kcprtMarkerEntry 5 }

	kcprtMarkerAddressablilityFeedDirChosen		OBJECT-TYPE
		SYNTAX	INTEGER
		ACCESS	read-only
		STATUS	mandatory
		DESCRIPTION
			"The value of the addressability, in the feed direction,  chosen by the printer. If the printer supports the declared addressability, this addressability is the same as the declared addressability. If not, this addressability is set to the closest addressability that the printer supports when the declared dimension is set."
		::={ kcprtMarkerEntry 6 }

	kcprtMarkerAddressablilityXFeedDirChosen		OBJECT-TYPE
		SYNTAX	INTEGER
		ACCESS	read-only
		STATUS	mandatory
		DESCRIPTION
			"The value of the addressability, in the cross feed direction,  chosen by the printer. If the printer supports the declared addressability, this addressability is the same as the declared addressability. If not, this addressability is set to the closest addressability that the printer supports when the declared dimension is set."
		::={ kcprtMarkerEntry 7 }


--
--	Channel group
--
--		To control the HEX dump function
--
	kcprtChannelTable		OBJECT-TYPE
		SYNTAX	SEQUENCE OF KcprtChannelEntry
		ACCESS	not-accessible
		STATUS	mandatory
		DESCRIPTION
			"This table control's HEX dump function."
		::={ kcprtChannel 1 }
		
	kcprtChannelEntry		OBJECT-TYPE
		SYNTAX	KcprtChannelEntry
		ACCESS	not-accessible
		STATUS	mandatory
		DESCRIPTION
			""
		INDEX{hrDeviceIndex, kcprtChannelIndex}
		::={ kcprtChannelTable 1 }

	KcprtChannelEntry		::= SEQUENCE {
		kcprtChannelIndex		INTEGER,
		kcprtChannelFunction	INTEGER
	}
	
	kcprtChannelIndex		OBJECT-TYPE
		SYNTAX	INTEGER
		ACCESS	not-accessible
		STATUS	mandatory
		DESCRIPTION
			"The value of the prtChannelIndex of the printer device that this prtChannelEntry is associated with."
		::={ kcprtChannelEntry 1 }

	kcprtChannelFunction		OBJECT-TYPE
		SYNTAX	INTEGER	{
			through(0),
			hexDump(1)
		}
		ACCESS	read-write
		STATUS	mandatory
		DESCRIPTION
			"The current state of the  function of this channel. KYOCERA printer can set the hex dump mode to interface (channel). Writing affects all interface(channel).This setting is only valid for one job. After processing the job, this entry automatically returns ‘through(0)’."
		::={ kcprtChannelEntry 2 }


--
--	Memory Resource group
--
--		To see and control the resources on the memory device.
--

--
--	MemoryResource->MemoryDevice table
--
	kcprtMemoryDeviceTable		OBJECT-TYPE
		SYNTAX	SEQUENCE OF KcprtMemoryDeviceEntry
		ACCESS	not-accessible
		STATUS	mandatory
		DESCRIPTION
			"This table contains information for each memory device, such as the IC-Card."
		::={ kcprtMemoryResource 1 }
		
	kcprtMemoryDeviceEntry		OBJECT-TYPE
		SYNTAX	KcprtMemoryDeviceEntry
		ACCESS	not-accessible
		STATUS	mandatory
		DESCRIPTION
			"A list of entries that are corresponding to the each function of the memory device."
		INDEX { hrDeviceIndex, kcprtMemoryDeviceIndex }
		::={ kcprtMemoryDeviceTable 1 }

	KcprtMemoryDeviceEntry		::= SEQUENCE {
		kcprtMemoryDeviceIndex		INTEGER,
		kcprtMemoryDeviceLocation	INTEGER,
		kcprtMemoryDeviceType		INTEGER,
		kcprtMemoryDeviceTotalSize	INTEGER,
		kcprtMemoryDeviceUsedSize	INTEGER,
		kcprtMemoryDeviceStatus		INTEGER
	}

	kcprtMemoryDeviceIndex		OBJECT-TYPE
		SYNTAX	INTEGER
		ACCESS	not-accessible
		STATUS	mandatory
		DESCRIPTION
			"A unique value that is corresponding to each memory device, such as IC-Card. The value assignment will change if the IC-Card is removed or inserted."
		::={ kcprtMemoryDeviceEntry 1 }

	kcprtMemoryDeviceLocation		OBJECT-TYPE
		SYNTAX	INTEGER	{
			icCardSlot-A(0),
			icCardslot-B(1),
			optionROMsocket(2),
			residentFont(3),
			downloadArea(4),
			others(255)
		}
		ACCESS	read-only
		STATUS	mandatory
		DESCRIPTION
			"The value shows the location of this memory device. Note that if the location is download area, only the resource that has been assigned to the current interface can be managed. To see other resources, the management application have to change the current interface."
		::={ kcprtMemoryDeviceEntry 2 }

	kcprtMemoryDeviceType		OBJECT-TYPE
		SYNTAX	INTEGER	{
			rom(0),
			flash(1),
			sram(2),
			dram(3),
			others(255)
		}
		ACCESS	read-only
		STATUS	mandatory
		DESCRIPTION
			"The value shows the type of this memory device."
		::={ kcprtMemoryDeviceEntry 3 }

	kcprtMemoryDeviceTotalSize		OBJECT-TYPE
		SYNTAX	INTEGER
		ACCESS	read-only
		STATUS	mandatory
		DESCRIPTION
			"The maximum space of the memory device. Unit is bytes."
		::={ kcprtMemoryDeviceEntry 4 }

	kcprtMemoryDeviceUsedSize		OBJECT-TYPE
		SYNTAX	INTEGER
		ACCESS	read-only
		STATUS	mandatory
		DESCRIPTION
			"The amount of occupied space on the device. Unit is bytes. If the device cannot detect the amount, the value is (-1)."
		::={ kcprtMemoryDeviceEntry 5 }

	kcprtMemoryDeviceStatus		OBJECT-TYPE
		SYNTAX	INTEGER	{
			readyReadWrite(0),
			readyReadOnly(1),
			notAccessible(2),
			lowBattery(4)
		}
		ACCESS	read-only
		STATUS	mandatory
		DESCRIPTION
			"This value shows current status of this device. ‘not accessible’ means that the printer recognized the device but the access is impossible. ‘battery low’ is for a kind of battery backuped device, such as IC-card."
		::={ kcprtMemoryDeviceEntry 6 }


--
--	MemoryResource->Partition table
--
	kcprtPartitionTable		OBJECT-TYPE
		SYNTAX	SEQUENCE OF KcprtPartitionEntry
		ACCESS	not-accessible
		STATUS	mandatory
		DESCRIPTION
			"This table contains partition information for each device."
		::={ kcprtMemoryResource 2 }

	kcprtPartitionEntry		OBJECT-TYPE
		SYNTAX	KcprtPartitionEntry
		ACCESS	not-accessible
		STATUS	mandatory
		DESCRIPTION
			"A list of entries that is corresponding to the each information about the partition."
		INDEX {hrDeviceIndex, kcprtPartitionIndex }
		::={ kcprtPartitionTable 1 }

	KcprtPartitionEntry	::=	SEQUENCE {
		kcprtPartitionIndex			INTEGER,
		kcprtPartitionSize			INTEGER,
		kcprtPartitionLocation		INTEGER,
		kcprtPartitionResourceType	INTEGER,
		kcprtPartitionName			DisplayString,
		kcprtPartitionLoad			INTEGER
	}

	kcprtPartitionIndex		OBJECT-TYPE
		SYNTAX	INTEGER
		ACCESS	not-accessible
		STATUS	mandatory
		DESCRIPTION
			"A unique value corresponding to the each partition on the printer's memory device. This assigment will change in some cases."
		::={ kcprtPartitionEntry 1 }

	kcprtPartitionSize		OBJECT-TYPE
		SYNTAX	INTEGER
		ACCESS	read-only
		STATUS	mandatory
		DESCRIPTION
			"This value shows the size of this partition. Unit is byte."
		::={ kcprtPartitionEntry 2 }

	kcprtPartitionLocation		OBJECT-TYPE
		SYNTAX	INTEGER
		ACCESS	read-only
		STATUS	mandatory
		DESCRIPTION
			"This value of kcprtMemoryDeviceIndex corresponding to the device on which this partition exists. If the device is unknown, this value is (-1)."
		::={ kcprtPartitionEntry 3 }

	kcprtPartitionResourceType		OBJECT-TYPE
		SYNTAX	INTEGER	{
			void(0),
			macro(3),
			hostData(4),
			programData(5),
			messageData(6),
			fontData(7)
		}
		ACCESS	read-only
		STATUS	mandatory
		DESCRIPTION
			"The type of the resource that is using this partition."
		::={ kcprtPartitionEntry 4 }

	kcprtPartitionName		OBJECT-TYPE
		SYNTAX	DisplayString ( SIZE(1..15) )
		ACCESS	read-only
		STATUS	mandatory
		DESCRIPTION
			"The name that is assigned to this partition."
		::={ kcprtPartitionEntry 5 }

	kcprtPartitionLoad		OBJECT-TYPE
		SYNTAX	INTEGER	{
			notLoaded(0),
			loaded(1)
		}
		ACCESS	read-only
		STATUS	mandatory
		DESCRIPTION
			"This value shows whether this partition has been read by the printer. basically, the resource should be read by the printer to make it available."
		::={ kcprtPartitionEntry 6 }


--
--	MemoryResource->MacroData table
--
	kcprtMacroDataTable		OBJECT-TYPE
		SYNTAX	SEQUENCE OF KcprtMacroDataEntry
		ACCESS	not-accessible
		STATUS	mandatory
		DESCRIPTION
			"This table contains information about MACRO resource."
		::={ kcprtMemoryResource 3 }

	kcprtMacroDataEntry		OBJECT-TYPE
		SYNTAX	KcprtMacroDataEntry
		ACCESS	not-accessible
		STATUS	mandatory
		DESCRIPTION
			""
		INDEX { hrDeviceIndex, kcprtMacroDataIndex }
		::={ kcprtMacroDataTable 1 }

	KcprtMacroDataEntry	::=	SEQUENCE {
		kcprtMacroDataIndex		INTEGER,
		kcprtMacroDataName		DisplayString,
		kcprtMacroDataID		INTEGER,
		kcprtMacroDataType		INTEGER,
		kcprtMacroDataAutoLoad		INTEGER,
		kcprtMacroDataLocation		INTEGER,
		kcprtMacroDataAttribute		INTEGER
	}

	kcprtMacroDataIndex		OBJECT-TYPE
		SYNTAX	INTEGER
		ACCESS	not-accessible
		STATUS	mandatory
		DESCRIPTION
			""
		::={ kcprtMacroDataEntry 1 }

	kcprtMacroDataName		OBJECT-TYPE
		SYNTAX	DisplayString ( SIZE( 1..4 ) )
		ACCESS	read-only
		STATUS	mandatory
		DESCRIPTION
			"This value will be effective if the macro is described in Prescribe. Otherwise, this value will be NULL."
		::={ kcprtMacroDataEntry 2 }

	kcprtMacroDataID		OBJECT-TYPE
		SYNTAX	INTEGER
		ACCESS	read-only
		STATUS	mandatory
		DESCRIPTION
			"This value will be effective if the macro is described in PCL. Otherwise, the value will be unknown(-1)."
		::={ kcprtMacroDataEntry 3 }

	kcprtMacroDataType		OBJECT-TYPE
		SYNTAX	INTEGER	{
			prescribe(1),
			pcl(2),
			others(255)
		}
		ACCESS	read-only
		STATUS	mandatory
		DESCRIPTION
			"This value is corresponding to the PDL that is used for decribing this macro."
		::={ kcprtMacroDataEntry 4 }

	kcprtMacroDataAutoLoad		OBJECT-TYPE
		SYNTAX	INTEGER	{
			off(0),
			onWithInitialize(1),
			onWithoutInitialize(2)
		}
		ACCESS	read-only
		STATUS	mandatory
		DESCRIPTION
			"This value shows the state of the form overlay function that is controled by AMCR command. Only one macro can be set as ‘on’, so at most one entry will have ‘on’ value."
		::={ kcprtMacroDataEntry 5 }

	kcprtMacroDataLocation		OBJECT-TYPE
		SYNTAX	INTEGER
		ACCESS	read-only
		STATUS	mandatory
		DESCRIPTION
			"The value of kcprtMemoryDeviceIndex correspinding to the device that this macro is currently stored. unknown is (-1)."
		::={ kcprtMacroDataEntry 6 }

	kcprtMacroDataAttribute		OBJECT-TYPE
		SYNTAX	INTEGER	{
			notRegistered(0),
			registered(1)
		}
		ACCESS	read-only
		STATUS	mandatory
		DESCRIPTION
			"‘not registered’ means this resource is existing on the device but it is not available for the printer. For example, macro on the IC card that is inserted into the printer after turning on will be ‘not registered’. To turn it into ‘registered’, user must select them from the front panel menu."
		::={ kcprtMacroDataEntry 7 }


--
--	MemoryResource->HostData table
--
	kcprtHostDataTable		OBJECT-TYPE
		SYNTAX	SEQUENCE OF KcprtHostDataEntry
		ACCESS	not-accessible
		STATUS	mandatory
		DESCRIPTION
			"This table contains information about the host data. Note that 'Host data' does not mean the job itself."
		::={ kcprtMemoryResource 4 }

	kcprtHostDataEntry		OBJECT-TYPE
		SYNTAX	KcprtHostDataEntry
		ACCESS	not-accessible
		STATUS	mandatory
		DESCRIPTION
			"A list of entries that are corresponding each information of the host data."
		INDEX { hrDeviceIndex, kcprtHostDataIndex }
		::={ kcprtHostDataTable 1 }

	KcprtHostDataEntry		::= SEQUENCE {
		kcprtHostDataIndex		INTEGER,
		kcprtHostDataname		DisplayString,
		kcprtHostDataLocation	INTEGER,
		kcprtHostDataAttribute	INTEGER
	}

	kcprtHostDataIndex		OBJECT-TYPE
		SYNTAX	INTEGER
		ACCESS	not-accessible
		STATUS	mandatory
		DESCRIPTION
			"A unique value corresponding to each information of the host data. The assigment will change in some case."
		::={ kcprtHostDataEntry 1 }

	kcprtHostDataName		OBJECT-TYPE
		SYNTAX	DisplayString ( SIZE( 1..15 ) )
		ACCESS	read-only
		STATUS	mandatory
		DESCRIPTION
			"The name that is used for descriminating each host data."
		::={ kcprtHostDataEntry 2 }

	kcprtHostDataLocation		OBJECT-TYPE
		SYNTAX	INTEGER
		ACCESS	read-only
		STATUS	mandatory
		DESCRIPTION
			"The value of kcprtMemoryDeviceIndex that is corresponding to the device in which this host data is stored. If the device is unknown, the value is -1."
		::={ kcprtHostDataEntry 3 }

	kcprtHostDataAttribute		OBJECT-TYPE
		SYNTAX	INTEGER	{
			notRegistered(0),
			registered(1)
		}
		ACCESS	read-only
		STATUS	mandatory
		DESCRIPTION
			"Basically, the value is always ‘registered’."
		::={ kcprtHostDataEntry 4 }


--
--	MemoryResource->ProgramData table
--
	kcprtProgramDataTable		OBJECT-TYPE
		SYNTAX	SEQUENCE OF KcprtProgramDataEntry
		ACCESS	not-accessible
		STATUS	mandatory
		DESCRIPTION
			"This table contains information about the program data. The program data is a kind of emulation and a Prescribe command, not a macro."
		::={ kcprtMemoryResource 5 }

	kcprtProgramDataEntry		OBJECT-TYPE
		SYNTAX	KcprtProgramDataEntry
		ACCESS	not-accessible
		STATUS	mandatory
		DESCRIPTION
			"A list of entries that are corresponding to each information of the program data."
		INDEX { hrDeviceIndex, kcprtProgramDataIndex }
		::={ kcprtProgramDataTable 1 }

	KcprtProgramDataEntry	::= SEQUENCE {
		kcprtProgramDataIndex		INTEGER,
		kcprtProgramDataName		DisplayString,
		kcprtProgramDataType		INTEGER,
		kcprtProgramDataLocation	INTEGER,
		kcprtProgramDataAttribute	INTEGER
	}

	kcprtProgramDataIndex		OBJECT-TYPE
		SYNTAX	INTEGER
		ACCESS	not-accessible
		STATUS	mandatory
		DESCRIPTION
			"A unique value corresponding to each program data. This assigment may change in some case."
		::={ kcprtProgramDataEntry 1 }

	kcprtProgramDataName		OBJECT-TYPE
		SYNTAX	DisplayString( SIZE( 1..15 ) )
		ACCESS	read-only
		STATUS	mandatory
		DESCRIPTION
			""
		::={ kcprtProgramDataEntry 2 }

	kcprtProgramDataType		OBJECT-TYPE
		SYNTAX	INTEGER	{
			emulation(0),
			prescribe(1),
			others(255)
		}
		ACCESS	read-only
		STATUS	mandatory
		DESCRIPTION
			""
		::={ kcprtProgramDataEntry 3 }

	kcprtProgramDataLocation		OBJECT-TYPE
		SYNTAX	INTEGER
		ACCESS	read-only
		STATUS	mandatory
		DESCRIPTION
			"The value of kcprtMemoryDeviceIndex corresponding to the device in which this program data is stored. If the device is unknown, the value is (-1)."
		::={ kcprtProgramDataEntry 4 }

	kcprtProgramDataAttribute		OBJECT-TYPE
		SYNTAX	INTEGER	{
			notRegistered(0),
			registered(1),
			running(2)
		}
		ACCESS	read-only
		STATUS	mandatory
		DESCRIPTION
			"‘running’ means the program is running."
		::={ kcprtProgramDataEntry 5 }


--
--	MemoryResource->MessageData table
--
	kcprtMessageDataTable		OBJECT-TYPE
		SYNTAX	SEQUENCE OF KcprtMessageDataEntry
		ACCESS	not-accessible
		STATUS	mandatory
		DESCRIPTION
			"This is a bunch of message that is handled as one of the flont panel language by the printer."
		::={ kcprtMemoryResource 6 }

	kcprtMessageDataEntry		OBJECT-TYPE
		SYNTAX	KcprtMessageDataEntry
		ACCESS	not-accessible
		STATUS	mandatory
		DESCRIPTION
			"A list of entries that are corresponding to each information of the message data."
		INDEX { hrDeviceIndex, kcprtMessageDataIndex }
		::={ kcprtMessageDataTable 1 }

	KcprtMessageDataEntry		::= SEQUENCE {
		kcprtMessageDataIndex		INTEGER,		
		kcprtMessageDataName		DisplayString,
		kcprtMessageDataLocation	INTEGER,
		kcprtMessageDataAttribute	INTEGER
	}

	kcprtMessageDataIndex		OBJECT-TYPE
		SYNTAX	INTEGER
		ACCESS	not-accessible
		STATUS	mandatory
		DESCRIPTION
			"The index vaule that is assigned to each front panel language."
		::={ kcprtMessageDataEntry 1 }

	kcprtMessageDataName		OBJECT-TYPE
		SYNTAX	DisplayString ( SIZE( 1..15 ) )
		ACCESS	read-only
		STATUS	mandatory
		DESCRIPTION
			"The name of the message data block."
		::={ kcprtMessageDataEntry 2 }

	kcprtMessageDataLocation		OBJECT-TYPE
		SYNTAX	INTEGER
		ACCESS	read-only
		STATUS	mandatory
		DESCRIPTION
			"The value of kcprtMemoryDeviceIndex corresponding to the device in which this message data is stored. If the device is unknown, the value is -1."
		::={ kcprtMessageDataEntry 3 }

	kcprtMessageDataAttribute		OBJECT-TYPE
		SYNTAX	INTEGER	{
			notRegistered(0),
			registered(1)
		}
		ACCESS	read-only
		STATUS	mandatory
		DESCRIPTION
			"Always ‘registered’ in the current products."
		::={ kcprtMessageDataEntry 4 }


--
--	MemoryResource->Font table
--
	kcprtFontDataTable		OBJECT-TYPE
		SYNTAX	SEQUENCE OF KcprtFontDataEntry
		ACCESS	not-accessible
		STATUS	mandatory
		DESCRIPTION
			"This table contains font information."
		::={ kcprtMemoryResource 7 }

	kcprtFontDataEntry		OBJECT-TYPE
		SYNTAX	KcprtFontDataEntry
		ACCESS	not-accessible
		STATUS	mandatory
		DESCRIPTION
			"A list of entries that are corresponding each information of the font."
		INDEX { hrDeviceIndex, kcprtFontDataIndex }
		::={ kcprtFontDataTable 1 }

	KcprtFontDataEntry		::= SEQUENCE {
		kcprtFontDataIndex		INTEGER,
		kcprtTypeFaceName		DisplayString,
		kcprtFontID				INTEGER,
		kcprtFontType			INTEGER,
		kcprtFontLocation		INTEGER,
		kcprtFontAttribute		INTEGER
	}

	kcprtFontDataIndex		OBJECT-TYPE
		SYNTAX	INTEGER
		ACCESS	not-accessible
		STATUS	mandatory
		DESCRIPTION
			"A unique value corresponding to each font data. The assignment may change in some case."
		::={ kcprtFontDataEntry 1 }

	kcprtTypeFaceName		OBJECT-TYPE
		SYNTAX	DisplayString ( SIZE( 0..31 ) )
		ACCESS	read-only
		STATUS	mandatory
		DESCRIPTION
			"The value will be NULL if no name has been assigned."
		::={ kcprtFontDataEntry 2 }

	kcprtFontID		OBJECT-TYPE
		SYNTAX	INTEGER
		ACCESS	read-only
		STATUS	mandatory
		DESCRIPTION
			"This value will be -1 if no ID has been assigned."
		::={ kcprtFontDataEntry 3 }

	kcprtFontType	OBJECT-TYPE
		SYNTAX	INTEGER	{
			bitmap(0),
			scalable(1),
			others(255)
		}
		ACCESS	read-only
		STATUS	mandatory
		DESCRIPTION
			""
		::={ kcprtFontDataEntry 4 }

	kcprtFontLocation		OBJECT-TYPE
		SYNTAX	INTEGER
		ACCESS	read-only
		STATUS	mandatory
		DESCRIPTION
			"The value of kcprtMemoryDeviceIndex corresponding to the device on which this font is stored. If it is unknown, the value is -1."
		::={ kcprtFontDataEntry 5 }

	kcprtFontAttribute		OBJECT-TYPE
		SYNTAX	INTEGER	{
			notRegistered(0),
			registered (1)
		}
		ACCESS	read-only
		STATUS	mandatory
		DESCRIPTION
			"In the current printer, this value is always ‘registered’."
		::={ kcprtFontDataEntry 6 }


END
