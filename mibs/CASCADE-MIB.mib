-- ***************************************************************************
-- * Cascade Communications STDX/B-STDX MIB definitions 		     *
--
-- Date		Engineer	Description
-- --------------------------------------------------------------------------
-- 05/11/94	Mike Bernstein	Added new pportInterface types for E1
-- 06/10/94	Ren Yonghong	Added some SVC objects
-- 10/06/94	Ren Yonghong	Reserved trap number 36 for SVC
-- 10/06/94	Arvind Puntambekar Added SMDS modifications for 4.0 release
-- 10/20/94	Ren Yonghong	Detailed all possible values for pportDataRate
-- 11/15/94	Ren Yonghong	Clarified and enhanced several objects
-- 12/14/94	Dan Bergman	Added ISDN objects
-- 12/15/94     Chris D'Souza   Added dsx3 loopback objects
-- 12/21/94	Eric Li		Added dsx3 FEAC status object
-- 01/09/95	Mike Drozdick	Added lportLastInvalidDLCI and 
--				lportTrkProtState.
-- 01/11/95	Mike Drozdick	Added cardTrkProtState.
-- 01/16/95     Chris D'Souza   Added ds1 loopback objects
-- 01/19/95	Martin Jensen	Added version info objects to card group
-- 03/06/95	Chris D'Souza	Modified objects for short haul T1 cards
-- 03/10/95	John Moy	Added lportTrkTrafficMix.
-- 04/17/95     Jim Coronella   Added Atm pport and ckt objects.
-- 04/20/95     Jonathan West   fix diag code for hssi online diag tests
-- 04/28/95     Jim Martel	Added Atm ckt objects for cell rates
-- 05/05/95	John Moy	Added lport objects for routing QoS changes
-- 07/11/95	Martin Jensen	Add software group to support full s/w id
-- 05/25/95	Jonathan West	Added lport objects for QoS bandwidth management
-- 05/31/95	Jonathan West	Added ckt objects for ATM traffic
-- 06/07/95	Ron Parker	Added: 	cascsvc branch,
--					cascsvc.svcaddress group,
--					cascsvc.svcaddress.svcNodePrefixTable,
--					cascsvc.svcaddress.svcPrefixTable,
--					cascsvc.svcaddress.svcAddrTable,
--					cascsvc.svcaddress.svcDteUserPartTable,
--					cascsvc.svcmgt group,
--					cascsvc.svcmgt.svcFailedCallTable,
--					cascfr.ckt.cktLeafTable,
--					cascfr.lport.atmSigLportTable,
--					ATM lport entries,
--					svc ident stats upload lport entry,
--					svcFailedCall trap
-- 06/09/95	Phil Malloy	Added OAM objects to node, lport, and ckt
-- 06/09/95	Eric Li		Added Topaz IOM timing, various cell counters,
--				etc. in card and pport group.
-- 06/12/95	Ron Parker	Change indexing of SVC Failed Call Log to
--				port.inst.
--				Change diag code object to octet string. 
-- 06/19/95	Jonathan West	lport vars: lportInVAvailbw, lportbwUNIPolicy.
-- 06/20/95     Jim Coronella   Added DS3 PLCP Enable/Disable.
-- 06/23/95     Ruediger Eckhard	Added B-STDX 9000 CBR/ATM-IWU objects.
-- 06/23/95	Eric Li		Added Topaz OC3 & STM1 IOPs.
-- 06/26/95	Stephen Bortolussi	Added traps and lport objects for SMDS
--					Network trouble shooting.
-- 06/27/95	Mardy Marshall	Added:	Objects to the Node Group for B-STDX 500
--					Application/Configuration backup and
--					restoration and management.
--					Objects to the Node Group and Traps
--					for B-STDX 500 System Timing Management.
-- 06/29/95     Oliver Lin	Added:  CardCpuFgUtil for Cpu foreground
--					utilization. And move the
--					cardTrkProtState.
-- 07/07/95	Ron Parker	Added svcRemotePrefixTable to cascsvc.svcaddr.
-- 07/12/95	Mike Bernstein	Modified comment for pportDataRate
--				Added cktFailReason 29, 30
--				Updated lportErrType values through 19
-- 07/19/95     Ruediger Eckhard	Removed double defined
--					ckt{In,Out}CellsCLP[01]
--					Added pportOc3LoopConfig and
--					pportOc3LoopStatus
-- 07/25/95	Mike Drozdick	Added lportTrkProtFailureThreshold.
-- 07/31/95	Mike Drozdick	Added lportPtr.
-- 08/02/95	Eric Li 	Added cardSystemPrimaryClockModeConfig & 
--				cardSystemSecondaryClockModeConfig
-- 08/08/95	Ron Parker	Added svcConfigTable, moved atmSigLportTable
--				to svcAtmConfigTable.
-- 08/14/95	Dan Bergman	Add cardISDNSigType, cardISDNChanId,
--                              pportISDNIpBaseAddr,
--			 	lportISDNPoolUtil, lportISDNIpAddrAssignFail &
--				the trap lportISDNIpAddrRej 
--				Changed lportISDNRejCnt to lportISDNIpAddr  
-- 08/21/95	Dan Bergman     Moved cardISDNSigType and cardISDNChanId up to
--				where SWBuild and SWBuildID were located
-- 08/31/95	RonParker	Expanded Q.93B and Q.SAAL statistics in 
--				svcAtmConfigTable.  
-- 				Rename svcFailedCallTable to
--                              svcAtmFailedCallTable.
-- 09/13/95	Eric Li		Add traps for IOM timing section
-- 09/22/95	Mike Drozdick	Clarify definition of lportLastInvalidDLCI.
-- 09/25/95	Larry Palmer    Removed svcaddr, netSvcAddrNetWidth,
--				netSvcAddrPortWidth, netSvcAddrUserWidth,
--				svcAddressTable
-- 09/29/95	Eric Li		Add pportSonetSTM1Scramble & clarified
--				pportLaserStatus
-- ***************************************************************************

CASCADE-MIB DEFINITIONS ::= BEGIN

IMPORTS
	enterprises, IpAddress, Counter,
 	Gauge, TimeTicks
		FROM RFC1155-SMI
	DisplayString, ifInErrors
		FROM RFC1213-MIB
	OBJECT-TYPE
		FROM RFC-1212
	TRAP-TYPE
		FROM RFC-1215;

--  This MIB module uses the extended OBJECT-TYPE macro as defined in RFC 1212



--  Title
cascade		OBJECT IDENTIFIER ::= { enterprises 277 }
cascfr		OBJECT IDENTIFIER ::= { cascade 1 }
cascsmds	OBJECT IDENTIFIER ::= { cascade 2 } 
namebinding	OBJECT IDENTIFIER ::= { cascade 3 }
isdnaddr	OBJECT IDENTIFIER ::= { cascade 4 }
cascsvc		OBJECT IDENTIFIER ::= { cascade 5 }
software	OBJECT IDENTIFIER ::= { cascade 6 }
provserver	OBJECT IDENTIFIER ::= { cascade 9 }

--  The ranges of ifIndex

Index ::= INTEGER	--  1..ifNumber

net		OBJECT IDENTIFIER ::= { cascfr 1 }
ase		OBJECT IDENTIFIER ::= { cascfr 2 }
node		OBJECT IDENTIFIER ::= { cascfr 3 }
pport		OBJECT IDENTIFIER ::= { cascfr 4 }
lport		OBJECT IDENTIFIER ::= { cascfr 5 }
ckt		OBJECT IDENTIFIER ::= { cascfr 6 }
card		OBJECT IDENTIFIER ::= { cascfr 7 }
ds1		OBJECT IDENTIFIER ::= { cascfr 8 }
smdsaddr	OBJECT IDENTIFIER ::= { cascsmds 1 }
svcaddress	OBJECT IDENTIFIER ::= { cascsvc 1 }
svcmgt		OBJECT IDENTIFIER ::= { cascsvc 2 }


--  The Network Group
--
--  The variables that are relevant to a Cascade network
--

netMask OBJECT-TYPE
	SYNTAX	IpAddress
	ACCESS	read-write
	STATUS	mandatory
	DESCRIPTION
		"The IP subnet mask for the network.  The default is 	
	 	255.255.255.0 (class C) which allows 254 nodes."
	::= { net 1 }

netNumber OBJECT-TYPE
	SYNTAX	IpAddress
	ACCESS	read-write
	STATUS	mandatory
	DESCRIPTION
		"The IP network number for the network."
	::= { net 2 }

netDlciAddrSig OBJECT-TYPE
	SYNTAX	INTEGER {
		    globalAddr (1),
		    localAddr (2)
		}
	ACCESS	read-write
	STATUS	mandatory
	DESCRIPTION
		"This variable states the DLCI addressing significance."
	::= { net 3 }

netMaxSegsize OBJECT-TYPE
	SYNTAX	INTEGER
	ACCESS	read-write
	STATUS	mandatory
	DESCRIPTION
		"This variable states the maximum sgement size for the network."
	::= { net 4 }

 netSmdsAreaMaskStart OBJECT-TYPE 
         SYNTAX  INTEGER 
         ACCESS  read-write
         STATUS  mandatory 
         DESCRIPTION 
                 "This variable states the starting digit number for defining
		  the start of the Area Mask for SMDS Addresses."
         ::= { net 8 } 

 
 netSmdsAreaMaskDigits OBJECT-TYPE 
         SYNTAX  INTEGER 
         ACCESS  read-write
         STATUS  mandatory 
         DESCRIPTION 
                 "This variable states the number of digits used for defining
		  the Area Mask for SMDS Addresses."
         ::= { net 9 } 


--
--	OSPF Autonomous System External Device and Host Table - For NMS paths
--	(Currently an External Device is always accessible via Ethernet,
--       whereas a Host is always accessible via SLIP.)
--

aseTable OBJECT-TYPE
	SYNTAX	SEQUENCE OF AseEntry
	ACCESS	not-accessible
	STATUS	mandatory
	DESCRIPTION
		"A list of ASE entries."
	::= { ase 1 }

aseEntry OBJECT-TYPE
	SYNTAX	AseEntry
	ACCESS	not-accessible
	STATUS	mandatory
	DESCRIPTION
		"An ASE entry contains an external NMS path accessible from
		the node."
	INDEX	{ aseAddr }
	::= { aseTable 1 }

AseEntry ::= 
	SEQUENCE {
		aseAddr	
			IpAddress,
		aseMask	
			IpAddress,
		aseDefaultGwAddr
			IpAddress,
		aseMetricType
			INTEGER,
		aseAdminStatus
			INTEGER,
		aseIfIndex
			Index,
		aseDlci
			INTEGER
	}

aseAddr OBJECT-TYPE
	SYNTAX	IpAddress
	ACCESS	read-only
	STATUS	mandatory
	DESCRIPTION
		"IP Address for an external NMS."
	::= { aseEntry 1 }

aseMask OBJECT-TYPE
	SYNTAX	IpAddress
	ACCESS	read-only
	STATUS	mandatory
	DESCRIPTION
		"IP Address mask for an external NMS.  The default value
		is 255.255.255.255."
	::= { aseEntry 2 }

aseDefaultGwAddr OBJECT-TYPE
	SYNTAX	IpAddress
	ACCESS	read-write
	STATUS	mandatory
	DESCRIPTION
		"Default Gateway IP Address for reaching the external 
		NMS.  This field is not applicable to NMSs which are
		reachable via SLIP or on the same Ethernet."
	::= { aseEntry 3 }

aseMetricType OBJECT-TYPE
	SYNTAX	INTEGER
	ACCESS	read-only
	STATUS	mandatory
	DESCRIPTION
		"Type of metric (1 or 2) for each external NMS.
		The default is 1.  (This field is not applicable to SLIP-
		based hosts.)"
	::= { aseEntry 4 }

aseAdminStatus OBJECT-TYPE
 	SYNTAX  INTEGER {
 		    -- invalid (0),
		    valid (1)
 		}
 	ACCESS  read-write
 	STATUS  mandatory
 	DESCRIPTION
		"The desired state of the entry."
	::= { aseEntry 5 }

aseIfIndex OBJECT-TYPE
	SYNTAX	Index
	ACCESS	read-write
	STATUS	mandatory
	DESCRIPTION
		"The interface value of the corresponding MIB-II ifEntry."
	::= { aseEntry 6 }


aseDlci OBJECT-TYPE
	SYNTAX	INTEGER
	ACCESS	read-write
	STATUS	mandatory
	DESCRIPTION
		"The management dlci through which the NMS communicates
		 to the switch."
	::= { aseEntry 7 }

-- 	The Node Group
--
--	The variables that configure a node
--

nodeIpAddr OBJECT-TYPE
	SYNTAX	IpAddress
	ACCESS	read-write
	STATUS	mandatory
	DESCRIPTION
		"The inband IP address of the node in the Cascade internal
		trunk IP network."
	::= { node 1 }

nodeLanIpAddr OBJECT-TYPE
	SYNTAX	IpAddress
	ACCESS	read-write
	STATUS	mandatory
	DESCRIPTION
		"The inband (Ethernet) IP address of the node for a NMS 
		to access the node and the internal trunk IP network."
	::= { node 2 }

nodeNMSTable OBJECT-TYPE
	SYNTAX	SEQUENCE OF NodeNMSEntry
	ACCESS	not-accessible
	STATUS	mandatory
	DESCRIPTION
		"A list of NMS entries."
	::= { node 3 }

nodeNMSEntry OBJECT-TYPE
	SYNTAX	NodeNMSEntry
	ACCESS	not-accessible
	STATUS	mandatory
	DESCRIPTION
		"A NMS entry contains an IP address of a NMS which has
		extended privilages."
	INDEX	{ nodeNMSIndex }
	::= { nodeNMSTable 1 }

NodeNMSEntry ::= 
	SEQUENCE {
		nodeNMSIndex
			Index,
		nodeNMSIpAddr
			IpAddress
	}

nodeNMSIndex OBJECT-TYPE
	SYNTAX	Index
	ACCESS	read-only
	STATUS	mandatory
	DESCRIPTION
		"The IP address entry of a primary Network Management Station."
	::= { nodeNMSEntry 1 }

nodeNMSIpAddr OBJECT-TYPE
	SYNTAX	IpAddress
	ACCESS	read-write
	STATUS	mandatory
	DESCRIPTION
		"The IP address of the primary Network Management Station.
		It is to this address that Traps and TFTP requests
		will be directed."
	::= { nodeNMSEntry 2 }

nodeState OBJECT-TYPE
	SYNTAX	INTEGER {
		    down (1),
		    initializing (2),
		    active (3),
		    marginal (4),
		    testing (5)
		}
	ACCESS	read-write
	STATUS	mandatory
	DESCRIPTION
		"The state of the switch. The switch needs to await the 
		state to be set to active before being fully operational
		after cold boot, when the NMS is reachable."
	::= { node 4 }

nodePollStatus OBJECT-TYPE
	SYNTAX	OCTET STRING
	ACCESS	read-only
	STATUS	mandatory
	DESCRIPTION
		"The consolidated node status in response to keep-alive polls.
		It is an octet string of a proprietary format"
	::= { node 5 }

nodeModel OBJECT-TYPE
	SYNTAX	DisplayString
	ACCESS	read-only
	STATUS	mandatory
	DESCRIPTION
		"The part number of the node."
	::= { node 6 }

nodeSerial OBJECT-TYPE
	SYNTAX	OCTET STRING
	ACCESS	read-only
	STATUS	mandatory
	DESCRIPTION
		"The serial number (i.e., Ethernet Addr) of the switch."
	::= { node 7 }

nodeSwRev OBJECT-TYPE
	SYNTAX	DisplayString
	ACCESS	read-only
	STATUS	mandatory
	DESCRIPTION
		"The software revision number (major.minor)."
	::= { node 8 }

nodeHwRev OBJECT-TYPE
	SYNTAX	DisplayString
	ACCESS	read-only
	STATUS	mandatory
	DESCRIPTION
		"The hardware revision number (major.minor)."
	::= { node 9 }

nodeEpromRev OBJECT-TYPE
	SYNTAX	DisplayString
	ACCESS	read-only
	STATUS	mandatory
	DESCRIPTION
		"The EPROM firmware revision number (major.minor)."
	::= { node 10 }

nodeCpuUtil OBJECT-TYPE
	SYNTAX	Gauge
	ACCESS	read-only
	STATUS	mandatory
	DESCRIPTION
		"The CPU utilization percentage for packet processing."
	::= { node 11 }

nodePsAStatus OBJECT-TYPE
	SYNTAX	INTEGER {
		    up (1),
		    down (2),
		    marginal (4)
		}
	ACCESS	read-only
	STATUS	mandatory
	DESCRIPTION
		"The status of the power supply A.  For a detailed explanation
		 for the power supply being either in the down or marginal
		 state, refer to the nodePsADiagCode object."
	::= { node 12 }

nodePsBStatus OBJECT-TYPE
	SYNTAX	INTEGER {
		    up (1),
		    down (2),
		    marginal (4)
		}
	ACCESS	read-only
	STATUS	mandatory
	DESCRIPTION
		"The status of the power supply B.  For a detailed explanation
		 for the power supply being either in the down or marginal
		 state, refer to the nodePsBDiagCode object."
	::= { node 13 }

nodeFanTable OBJECT-TYPE
	SYNTAX	SEQUENCE OF NodeFanEntry
	ACCESS	not-accessible
	STATUS	mandatory
	DESCRIPTION
		"A list of fan entries."
	::= { node 14 }

nodeFanEntry OBJECT-TYPE
	SYNTAX	NodeFanEntry
	ACCESS	not-accessible
	STATUS	mandatory
	DESCRIPTION
		"A Fan entry contains the status of a fan."
	INDEX	{ nodeFanIndex }
	::= { nodeFanTable 1 }

NodeFanEntry ::= 
	SEQUENCE {
		nodeFanIndex	
			INTEGER,
		nodeFanStatus	
			INTEGER,
		nodeFanSpeed	
			Gauge 
	}

nodeFanIndex OBJECT-TYPE
	SYNTAX	INTEGER
	ACCESS	read-only
	STATUS	mandatory
	DESCRIPTION
		"A unique value for each fan."
	::= { nodeFanEntry 1 }

nodeFanStatus OBJECT-TYPE
	SYNTAX	INTEGER {
		    up (1),
		    down (2),
		    marginal (3)
		}
	ACCESS	read-only
	STATUS	mandatory
	DESCRIPTION
		"The status of the fan."
	::= { nodeFanEntry 2 }
	
nodeFanSpeed OBJECT-TYPE
	SYNTAX	Gauge
	ACCESS	read-only
	STATUS	mandatory
	DESCRIPTION
		"The speed in Revolutions Per. Minute (RPM) of the fan."
	::= { nodeFanEntry 3 }
	
nodeMemoryUtil OBJECT-TYPE
	SYNTAX	Gauge
	ACCESS	read-only
	STATUS	mandatory
	DESCRIPTION
		"The percentage of system memory utilization on this intelligent card."
	::= { node 15 }

nodeMemoryUsage OBJECT-TYPE
	SYNTAX	Gauge
	ACCESS	read-only
	STATUS	mandatory
	DESCRIPTION
		"The system memory utilization, in terms of free bytes, for
		this intelligent card."
	::= { node 16 }

nodeMaxFramesize OBJECT-TYPE
	SYNTAX	INTEGER
	ACCESS	read-only
	STATUS	mandatory
	DESCRIPTION
		"The maximum frame size supported by the node.
		The default is 4096."
	::= { node 17 }

nodeQOSPollTimer OBJECT-TYPE
 	SYNTAX  INTEGER
 	ACCESS  read-write
 	STATUS  mandatory
 	DESCRIPTION
		"The timer (seconds) for generating QOS polling packets."
	::= { node 18 }

nodeActivePvcs OBJECT-TYPE
	SYNTAX	Counter
	ACCESS	read-only
	STATUS	mandatory
	DESCRIPTION
		"The number of currently active PVCs on the node."
	::= { node 19 }

nodeInactivePvcs OBJECT-TYPE
	SYNTAX	Counter
	ACCESS	read-only
	STATUS	mandatory
	DESCRIPTION
		"The number of currently inactive PVCs on the node."
	::= { node 20 }

nodePendingPvcs OBJECT-TYPE
	SYNTAX	Counter
	ACCESS	read-only
	STATUS	mandatory
	DESCRIPTION
		"The number of currently call pending PVCs on the node."
	::= { node 21 }

nodeInOctets OBJECT-TYPE
	SYNTAX	Counter
	ACCESS	read-only
	STATUS	mandatory
	DESCRIPTION
		"The total number of octets received on the node, including
		framing bytes."
	::= { node 22 }

nodeInPkts OBJECT-TYPE
	SYNTAX	Counter
	ACCESS	read-only
	STATUS	mandatory
	DESCRIPTION
		"The total number of packets received on the node."
	::= { node 23 }

nodeOutOctets OBJECT-TYPE
	SYNTAX	Counter
	ACCESS	read-only
	STATUS	mandatory
	DESCRIPTION
		"The total number of octets transmitted out of the node,
		including framing bytes."
	::= { node 24 }

nodeOutPkts OBJECT-TYPE
	SYNTAX	Counter
	ACCESS	read-only
	STATUS	mandatory
	DESCRIPTION
		"The total number of packets requested to be transmitted out
		of the node, including those that were discarded or not sent."
	::= { node 25 }

nodeSwFilename OBJECT-TYPE
	SYNTAX	DisplayString
	ACCESS	read-write
	STATUS	mandatory
	DESCRIPTION
		"Name of the file to be downloaded."
	::= { node 26 }

nodeRebootAfterLoad OBJECT-TYPE
	SYNTAX	INTEGER {
		    -- no-reboot (0),
		    reboot (1)
		}
	ACCESS	read-write
	STATUS	mandatory
	DESCRIPTION
		"Instructs the device to either automatically reboot after
		the successful scheduled download or not."
	::= { node 27 }

nodeSwToLoad OBJECT-TYPE
	SYNTAX	TimeTicks
	ACCESS	read-write
	STATUS	mandatory
	DESCRIPTION
		"Instructs the device to initiate a software download
		(via tftp) request to the master management station after 
		the specified time ticks have elapsed."
	::= { node 28 }

nodeSwLoadState OBJECT-TYPE
	SYNTAX	INTEGER {
		    inactive (1),
		    pending (2),
		    active (3),
		    failed (4)
		}
	ACCESS	read-write
	STATUS	mandatory
	DESCRIPTION
		"The state of the software download request.  A download
		which is in either the PENDING, ACTIVE or FAILED state
		can be terminated by setting this object to INACTIVE."
	::= { node 29 }

nodePrFilename OBJECT-TYPE
	SYNTAX	DisplayString
	ACCESS	read-write
	STATUS	mandatory
	DESCRIPTION
		"Name of the PRAM image file to be downloaded."
	::= { node 30 }

nodePrToLoad OBJECT-TYPE
	SYNTAX	TimeTicks
	ACCESS	read-write
	STATUS	mandatory
	DESCRIPTION
		"Instructs the device to initiate a PRAM image file download
		(via tftp) request to the master management station after 
		the specified time ticks have elapsed."
	::= { node 31 }

nodePrLoadState OBJECT-TYPE
	SYNTAX	INTEGER {
		    inactive (1),
		    pending (2),
		    active (3),
		    failed (4)
		}
	ACCESS	read-write
	STATUS	mandatory
	DESCRIPTION
		"The state of the PRAM download request.  A download
		which is in either the PENDING, ACTIVE or FAILED state
		can be terminated by setting this object to INACTIVE."
	::= { node 32 }

nodeToWarmboot OBJECT-TYPE
	SYNTAX	TimeTicks
	ACCESS	read-write
	STATUS	mandatory
	DESCRIPTION
		"Instructs the switch to initiate a system warm boot after 
		the specified time ticks have elapsed. A value of 0 indicates
		cancellation of the previously scheduled re-boot request."
	::= { node 33 }

nodeToColdboot OBJECT-TYPE
	SYNTAX	TimeTicks
	ACCESS	read-write
	STATUS	mandatory
	DESCRIPTION
		"Instructs the switch to initiate a system cold boot after 
		the specified time ticks have elapsed. A value of 0 indicates
		cancellation of the previously scheduled re-boot request."
	::= { node 34 }

nodeToRedundant OBJECT-TYPE
	SYNTAX	TimeTicks
	ACCESS	read-write
	STATUS	mandatory
	DESCRIPTION
		"If redundancy is configured, instructs the node acting as Backup
		to disable the Active node and take over as the Active node.
		The disabling is initiated after the specified time ticks have
		elapsed. A value of 0 indicates cancellation of the previously
		scheduled request."
	::= { node 35 }

nodeInitiateBulkStats OBJECT-TYPE
	SYNTAX	IpAddress
	ACCESS	read-write
	STATUS	mandatory
	DESCRIPTION
		"Initiates a Bulk Statistics poll and via TFTP, transfer the data
		to the specified IP address."
	::= { node 36 }

nodeDiagNonFatalSource OBJECT-TYPE
	SYNTAX	INTEGER {
		power-on-diagnostics (1),
		background-diagnostics (2),
		fault (3),
		frame-heap (4)
	}
	ACCESS	read-only
	STATUS	mandatory
	DESCRIPTION
		"Source who reported last non-fatal error."
	::= { node 37 }

nodeDiagNonFatalTime OBJECT-TYPE
	SYNTAX	TimeTicks
	ACCESS	read-only
	STATUS	mandatory
	DESCRIPTION
		"Time the last non-fatal error was reported."
	::= { node 38 }

nodeDiagNonFatalErrMajor OBJECT-TYPE
	SYNTAX	INTEGER
	ACCESS	read-only
	STATUS	mandatory
	DESCRIPTION
		"Major error code of last non-fatal error."
	::= { node 39 }

nodeDiagNonFatalErrMinor OBJECT-TYPE
	SYNTAX	INTEGER
	ACCESS	read-only
	STATUS	mandatory
	DESCRIPTION
		"Minor error code of last non-fatal error."
	::= { node 40 }

nodeDiagNonFatalStr OBJECT-TYPE
	SYNTAX	DisplayString
	ACCESS	read-only
	STATUS	mandatory
	DESCRIPTION
		"Ascii string describing last non-fatal error."
	::= { node 41 }

nodeDiagFatalSource OBJECT-TYPE
	SYNTAX	INTEGER {
		power-on-diagnostics (1),
		background-diagnostics (2),
		fault (3),
		frame-heap (4)
	}
	ACCESS	read-only
	STATUS	mandatory
	DESCRIPTION
		"Source who reported last fatal error."
	::= { node 42 }

nodeDiagFatalTime OBJECT-TYPE
	SYNTAX	TimeTicks
	ACCESS	read-only
	STATUS	mandatory
	DESCRIPTION
		"Time the last fatal error was reported."
	::= { node 43 }

nodeDiagFatalErrMajor OBJECT-TYPE
	SYNTAX	INTEGER
	ACCESS	read-only
	STATUS	mandatory
	DESCRIPTION
		"Major error code of last fatal error."
	::= { node 44 }

nodeDiagFatalErrMinor OBJECT-TYPE
	SYNTAX	INTEGER
	ACCESS	read-only
	STATUS	mandatory
	DESCRIPTION
		"Minor error code of last fatal error."
	::= { node 45 }

nodeDiagFatalStr OBJECT-TYPE
	SYNTAX	DisplayString
	ACCESS	read-only
	STATUS	mandatory
	DESCRIPTION
		"Ascii string describing last fatal error."
	::= { node 46 }

nodeDiagFatalReboots OBJECT-TYPE
	SYNTAX	Counter
	ACCESS	read-only
	STATUS	mandatory
	DESCRIPTION
		"Number of times the switch has re-booted since last
		fatal error was reported."
	::= { node 47 }

nodeDiagFatalAddress OBJECT-TYPE
	SYNTAX	INTEGER
	ACCESS	read-only
	STATUS	mandatory
	DESCRIPTION
		"Address switch was executing when it encountered fatal error."
	::= { node 48 }

nodeDiagBackgroundPasses OBJECT-TYPE
	SYNTAX	Counter
	ACCESS	read-only
	STATUS	mandatory
	DESCRIPTION
		"Number of passes made by the background diagnostics."
	::= { node 49 }

nodeDiagBackgroundFailures OBJECT-TYPE
	SYNTAX	Counter
	ACCESS	read-only
	STATUS	mandatory
	DESCRIPTION
		"Number of failures discovered by background diagnostics."
	::= { node 50 }

nodeDiagBackgroundSuccesses OBJECT-TYPE
	SYNTAX	Counter
	ACCESS	read-only
	STATUS	mandatory
	DESCRIPTION
		"Number of successful passes by background diagnostics."
	::= { node 51 }

nodeDiagLEDReset OBJECT-TYPE
	SYNTAX	INTEGER {
		-- state-unchanged (0),
		state-to-active (1)
	}
	ACCESS	read-write
	STATUS	mandatory
	DESCRIPTION
		"Change the node state from marginal to active.  Change the
		LED from yellow to green."
	::= { node 52 }

nodeDiagPowerExtensive OBJECT-TYPE
	SYNTAX	INTEGER {
		-- fast-tests (0),
		extensive-tests (1)
	}
	ACCESS	read-write
	STATUS	mandatory
	DESCRIPTION
		"Should power on diagnostics do slower, extensive testing,
		or fast testing?"
	::= { node 53 }

nodePortPoll OBJECT-TYPE
	SYNTAX	OCTET STRING
	ACCESS	read-only
	STATUS	mandatory
	DESCRIPTION
		"The consolidated port status in response to keep-alive polls."
	::= { node 54 }

nodeMaxTelnetConsole OBJECT-TYPE
	SYNTAX	INTEGER 
	ACCESS	read-write
	STATUS	mandatory
	DESCRIPTION
		"The number of concurrent telnet consoles allowed. The default
		is 2. The maximum is 5. Set it 0 to disable telnet access."
	::= { node 55 }

nodeConsoleTimeout OBJECT-TYPE
	SYNTAX	INTEGER 
	ACCESS	read-write
	STATUS	mandatory
	DESCRIPTION
		"Idle-logoff timer in minutes. The default is 5 minutes, and the
		maximum can be set is 60 minutes. To disable idle-logout, set
		this to 0."
	::= { node 56 }

nodeConsoleTable OBJECT-TYPE
	SYNTAX	SEQUENCE OF NodeConsoleEntry
	ACCESS	not-accessible
	STATUS	mandatory
	DESCRIPTION
		"A list of active consoles on the node, logged in through telnet
		or serial port."
	::= { node 57 }

nodeConsoleEntry OBJECT-TYPE
	SYNTAX	NodeConsoleEntry
	ACCESS	not-accessible
	STATUS	mandatory
	DESCRIPTION
		"Information of a console."
	INDEX	{ nodeConsoleIndex }
	::= { nodeConsoleTable 1 }

NodeConsoleEntry ::= 
	SEQUENCE {
		nodeConsoleIndex
			INTEGER,
		nodeUserName
			OCTET STRING,
		nodeUserFrom
			IpAddress,
		nodeConsoleAccessMode
			INTEGER,
		nodeConsoleUptime
			TimeTicks
	}

nodeConsoleIndex OBJECT-TYPE
	SYNTAX	INTEGER (1..6)
	ACCESS	read-only
	STATUS	mandatory
	DESCRIPTION
		"A positive integer to identify a console"
	::= { nodeConsoleEntry 1 }

nodeUserName OBJECT-TYPE
	SYNTAX	OCTET STRING
	ACCESS	read-only
	STATUS	mandatory
	DESCRIPTION
		"The login user name up to 31 characters. There is no 
		 validation of the name, i.e., any string is acceptable."
	::= { nodeConsoleEntry 2 }

nodeUserFrom OBJECT-TYPE
	SYNTAX	IpAddress
	ACCESS	read-only
	STATUS	mandatory
	DESCRIPTION
		"The IP address from which the user logged in. 0.0.0.0 if the
		user logged in through serial port."
	::= { nodeConsoleEntry 3 }

nodeConsoleAccessMode OBJECT-TYPE
	SYNTAX	INTEGER {
		readOnly (1),
		readWrite (2)
	}
	ACCESS	read-only
	STATUS	mandatory
	DESCRIPTION
		"The access mode of the console. By default, a user is in READ ONLY
		 mode."
	::= { nodeConsoleEntry 4 }

nodeConsoleUptime OBJECT-TYPE
	SYNTAX	TimeTicks
	ACCESS	read-only
	STATUS	mandatory
	DESCRIPTION
		"How long the console has been active."
	::= { nodeConsoleEntry 5 }

nodePsADiagCode OBJECT-TYPE
	SYNTAX	INTEGER
	ACCESS	read-only
	STATUS	mandatory
	DESCRIPTION
		"The failure code of the power supply A.  A non-zero value
		 indicates one or more failures.  Refer to the hardware
		 manual for a description of the failure code."
	::= { node 58 }

nodePsBDiagCode OBJECT-TYPE
	SYNTAX	INTEGER
	ACCESS	read-only
	STATUS	mandatory
	DESCRIPTION
		"The failure code of the power supply B.  A non-zero value
		 indicates one or more failures.  Refer to the hardware
		 manual for a description of the failure code."
	::= { node 59 }
	
nodeFrameMemoryUtil OBJECT-TYPE
	SYNTAX	Gauge
	ACCESS	read-only
	STATUS	mandatory
	DESCRIPTION
		"The percentage of frame memory utilization on this intelligent card."
	::= { node 60 }

nodeFrameMemoryUsage OBJECT-TYPE
	SYNTAX	Gauge
	ACCESS	read-only
	STATUS	mandatory
	DESCRIPTION
		"The frame memory utilization, in terms of free bytes, for
		this intelligent card."
	::= { node 61 }

nodeCapability OBJECT-TYPE
	SYNTAX	INTEGER {
                        frame-relay (1),
			smds (2)
		}
	ACCESS	read-only
	STATUS	mandatory
	DESCRIPTION
		"The capability of this node."
	::= { node 62 }

nodeSvcLastCallFailure OBJECT-TYPE
        SYNTAX  OCTET STRING
        ACCESS  read-only
        STATUS  mandatory
        DESCRIPTION
                "A textual string describing the last call failure."
        ::= { node 63 }

nodeRerouteDelay OBJECT-TYPE
	SYNTAX INTEGER
	ACCESS read-write
	STATUS mandatory
	DESCRIPTION
		"The number of seconds delay between each reroute batch event."
	::= { node 64 }

nodeRerouteCount OBJECT-TYPE
	SYNTAX INTEGER
	ACCESS read-write
	STATUS mandatory
	DESCRIPTION
		"The number of virtual circuits to request a reroute for duing
		a single reroute batch event."
	::= { node 65 }

nodeFileTransferRequest OBJECT-TYPE
        SYNTAX  DisplayString
        ACCESS  read-write
        STATUS  mandatory
        DESCRIPTION
                "This object is used to initiate file transfers to and from
                 the switch. A management station can initiate a file transfer
                 by settting this object of text string in the following
                 format:
 
                      operation filename time-to-wait target-host protocol
 
                 where
                   operation  	- 	[get | put],
                   filename   	- 	configuration.[card]
                   time-to-wait	-	a number in seconds
                   target-host	-	the IP address of target host
                   protocol	-	[tftp | ftp]
		   
                 Multiple transfers can be specified by repeating above with
                 ';' between each transfer specifier.
 
                 Examples:
 
                   o  get configuration.10 5 152.148.10.100 tftp
 
                      will start a transfer of configuration information
                      on card 10 to host 152.148.10.100 in 5 seconds.

                   o  put configuration.1 2 152.148.1.1 tftp ;
                      get configuration.1 15 152.148.1.1 tftp

                      will (1) transfer configuration.1 from 152.148.1.1
                           (2) transfer configuration.2 to 152.148.1.1

               To cancel the transfer request, set this object to empty.
               " 
        ::= { node 66 }

nodeFileTransferStatus OBJECT-TYPE
        SYNTAX  INTEGER {
                    complete (1),       -- transfer complete or no outstanding
                                        -- transfer request
                    active (2),         -- transfer is in progress
                    failed (3),         -- transfer failed - generic error
                    invalid (4),        -- invalid request
		    filename (5),       -- file name error or file non-existent
                    timeout (6),        -- transfer timed out
		    canceled (7)	-- transfer is cancelled
                }
        ACCESS  read-only
        STATUS  mandatory
        DESCRIPTION
                "The status of the file tarnsfer."
        ::= { node 67 }


nodeTime OBJECT-TYPE
	SYNTAX TimeTicks
	ACCESS read-write
	STATUS mandatory
	DESCRIPTION
                "The current wall-clock time that is set on the switch in 
                Universal Coordinated Time (UCT).  The value is the number 
		of seconds since 00:00:00 UCT January 1, 1970."
	::= { node 68 }

nodeBillingAPAddress OBJECT-TYPE
	SYNTAX IpAddress
	ACCESS read-write
	STATUS mandatory
	DESCRIPTION
		"The IP Address of the Adjunct Billing Processor that is 
		servicing this switch."
	::= {node 69 }

nodeBillingAPUsername OBJECT-TYPE
	SYNTAX DisplayString
	ACCESS read-write
	STATUS mandatory
	DESCRIPTION
		"The Username of the account on the Adjunct Billing Processor 
		to which usage data will be transferred via FTP."
	::= { node 70 }

nodeBillingAPPassword OBJECT-TYPE
	SYNTAX DisplayString
	ACCESS read-write
	STATUS mandatory
	DESCRIPTION
		"The Password corresponding to the account identified by
		nodeBillingAPUsername.  A NULL string is returned when read."
	::= { node 71 }

nodeBillingSwAPCommsFailures OBJECT-TYPE
	SYNTAX Counter
	ACCESS read-write
	STATUS mandatory
	DESCRIPTION
		"The number of times that communication from the switch to the
		Adjunct Billing Processor has failed during the current 
		aggregation period.  A failure signifies failure of a file 
		transfer operation to the Adjunct Processor."
	::= { node 72 }

nodeBillingTable OBJECT-TYPE
	SYNTAX SEQUENCE OF NodeBillingEntry
	ACCESS not-accessible
	STATUS mandatory
	DESCRIPTION
		"A table of Billing System managable objects, indexed by 
		service."
	::= { node 73 }

nodeBillingEntry OBJECT-TYPE
	SYNTAX NodeBillingEntry
	ACCESS not-accessible
	STATUS mandatory
	DESCRIPTION
		"A nodeBillingEntry contains a set of statistics that 
		summarize the Billing System performance for a particular 
		service.
		"
	INDEX { nodeBillingService }
	::= {nodeBillingTable 1 }

NodeBillingEntry ::=
	SEQUENCE {
		nodeBillingService
			INTEGER,
		nodeBilling
			INTEGER,
		nodeBillingAggrPeriod
			TimeTicks,
		nodeBillingCurAggrPeriodStart
			TimeTicks,
		nodeBillingCurAggrPeriodEnd
			TimeTicks,
		nodeBillingCollection
			TimeTicks,
		nodeBillingDailyProcessing
			INTEGER,
		nodeBillingDPTime
			TimeTicks,
		nodeBillingUsageRecOvflWarnings
			Counter,
		nodeBillingTotalUsageRecOvflWarnings
			Counter,
		nodeBillingBillableUsageEvents
			Counter,
		nodeBillingNonBillableUsageEvents
			Counter,
		nodeBillingUsageRecCreated
			Counter,
		nodeBillingTotalUsageRecCreated
			Counter,
		nodeBillingUsageRecCrFailures
			Counter,
		nodeBillingTotalUsageRecCrFailures
			Counter,
		nodeBillingUsageRecSent
			Counter,
		nodeBillingTotalUsageRecSent
			Counter,
		nodeBillingUsageDataStoreFull
			Counter,
		nodeBillingTotalUsageDataStoreFull
			Counter,
		nodeBillingAdminAction
			INTEGER
	}

nodeBillingService OBJECT-TYPE
	SYNTAX INTEGER {
			smds (1)
			}
	ACCESS read-only
	STATUS mandatory
	DESCRIPTION
		"
		The service being reported.  This is the index into the table.
		Additional table rows for Frame Relay and ATM may be provided 
		in the future.
		"
	::= {nodeBillingEntry 1 }

nodeBilling OBJECT-TYPE
	SYNTAX INTEGER {
			disabled (1),
			enabled  (2)
			}
	ACCESS read-write
	STATUS mandatory
	DESCRIPTION
		"Switch to enable and disable billing on the STDX.  

		When the value of nodeBilling is 'enabled', the value of a 
		logical port's lportBilling object will take precedence.  When
		the value of nodeBilling is 'disabled', it overrides all 
		logical ports' lportBilling objects and billing is disabled 
		across the entire switch.

		The default value of this object is 'disabled'.
		"
	::= {nodeBillingEntry 2 }

nodeBillingAggrPeriod OBJECT-TYPE
	SYNTAX TimeTicks
	ACCESS read-write
	STATUS mandatory
	DESCRIPTION	
		"Defines the length of the Billing Aggregation Period in 
		 seconds.  The default value is 15 minutes.  The minimum value
		 is 10 minutes."
	::= {nodeBillingEntry 3 }

nodeBillingCurAggrPeriodStart OBJECT-TYPE
	SYNTAX TimeTicks
	ACCESS read-only
	STATUS mandatory
	DESCRIPTION	
		"The start-time of the current aggregation period, given by
		the number of seconds since 00:00:00 UCT January 1, 1970."
	::= {nodeBillingEntry 4 }

nodeBillingCurAggrPeriodEnd OBJECT-TYPE
	SYNTAX TimeTicks
	ACCESS read-only
	STATUS mandatory
	DESCRIPTION	
		"The end-time of the current aggregation period, given by
		the number of seconds since 00:00:00 UCT January 1, 1970."
	::= {nodeBillingEntry 5 }

nodeBillingCollection OBJECT-TYPE
	SYNTAX TimeTicks
	ACCESS read-write
	STATUS mandatory
	DESCRIPTION	
		"Defines how often the Data Aggregation process on the CP is 
		to poll the IOPs for usage data.  The default value is 30 
		second.  The range is unbounded, but practical use will 
		dictate a range from 30 seconds to 1 minute." 
	::= {nodeBillingEntry 6 }

nodeBillingDailyProcessing OBJECT-TYPE
	SYNTAX INTEGER {
			disabled (1),
			enabled  (2)
			}
	ACCESS read-write
	STATUS mandatory
	DESCRIPTION
		"Defines whether the Billing System is to perform a set of 
		carrier-specific actions at the time given by 
		nodeBillingDPTime.   This object can be used to schedule the 
		generation of statistics on a 24-hour basis, for example."
	::= {nodeBillingEntry 7 }

nodeBillingDPTime OBJECT-TYPE
	SYNTAX TimeTicks
	ACCESS read-write
	STATUS mandatory
	DESCRIPTION	
		"Defines the time (given by the number of seconds since 
		00:00:00 UCT) that the Billing System is to perform a set of 
		carrier-specific actions.  This object can be used to schedule
		the generation of statistics on a 24-hour basis, for example."
	::= {nodeBillingEntry 8 }

nodeBillingUsageRecOvflWarnings OBJECT-TYPE
	SYNTAX Counter
	ACCESS read-only
	STATUS mandatory
	DESCRIPTION
		"
		Count of the number of usage record counter-value overflow
		conditions that have occurred during the current aggregation 
		period.  An overflow condition exists when an attempt was made
		to update a usage record counter, but such an update would have
		overflowed the counter.  In this case, the usage record is 
		closed and a new one is opened, if there is sufficient space in
		the service's aggregated usage data store.
		"
	::= {nodeBillingEntry 9 }

nodeBillingTotalUsageRecOvflWarnings OBJECT-TYPE
	SYNTAX Counter
	ACCESS read-only
	STATUS mandatory
	DESCRIPTION
		"
		Count of the number of usage record overflow conditions that 
		have occurred during the current day.
		"
	::= {nodeBillingEntry 10}

nodeBillingBillableUsageEvents OBJECT-TYPE
	SYNTAX Counter
	ACCESS read-only
	STATUS mandatory
	DESCRIPTION
		"
		Count of the number of data units (e.g, SMDS L3 PDUs) 
		processed for billing treatment.
		"
	::= {nodeBillingEntry 11 }

nodeBillingNonBillableUsageEvents OBJECT-TYPE
	SYNTAX Counter
	ACCESS read-only
	STATUS mandatory
	DESCRIPTION
		"
		Count of the number of data units (e.g, SMDS L3 PDUs) not 
		considered for billing treatment.
		"
	::= {nodeBillingEntry 12 }

nodeBillingUsageRecCreated OBJECT-TYPE
	SYNTAX Counter
	ACCESS read-only
	STATUS mandatory
	DESCRIPTION
		"
		Count of the number of usage records created during the 
		current aggregation period.
		"
	::= {nodeBillingEntry 13 }

nodeBillingTotalUsageRecCreated OBJECT-TYPE
	SYNTAX Counter
	ACCESS read-only
	STATUS mandatory
	DESCRIPTION
		"
		Count of the total number of usage records created during 
		the current day.
		"
	::= {nodeBillingEntry 14 }

nodeBillingUsageRecCrFailures OBJECT-TYPE
	SYNTAX Counter
	ACCESS read-only
	STATUS mandatory
	DESCRIPTION
		"
		Total number of usage records that could not be created during
		the current aggregation period.  This counter is normally 
		incremented when the usage data file is at capacity and no 
		additional usage records can be added.
		"
	::= {nodeBillingEntry 15 }

nodeBillingTotalUsageRecCrFailures OBJECT-TYPE
	SYNTAX Counter
	ACCESS read-only
	STATUS mandatory
	DESCRIPTION
		"
		Total number of usage records that could not be created during 
		the current day.
		"
	::= {nodeBillingEntry 16 }

nodeBillingUsageRecSent OBJECT-TYPE
	SYNTAX Counter
	ACCESS read-only
	STATUS mandatory
	DESCRIPTION
		"
		Total number of usage records that have been transferred to 
		the Adjunct Billing Processor during the current aggregation 
		period.
		"
	::= {nodeBillingEntry 17 }

nodeBillingTotalUsageRecSent OBJECT-TYPE
	SYNTAX Counter
	ACCESS read-only
	STATUS mandatory
	DESCRIPTION
		"
		Total number of usage records that have been transferred to 
		the Adjunct Billing Processor during the current day.
		"
	::= {nodeBillingEntry 18 }

nodeBillingUsageDataStoreFull OBJECT-TYPE
	SYNTAX Counter
	ACCESS read-only
	STATUS mandatory
	DESCRIPTION
		"
		The number of times the aggregated usage data store became 
		full during the current aggregation period.
		"
	::= {nodeBillingEntry 19 }

nodeBillingTotalUsageDataStoreFull OBJECT-TYPE
	SYNTAX Counter
	ACCESS read-only
	STATUS mandatory
	DESCRIPTION
		"Total number of times the aggregated usage data store became 
		full during the current day.
		"
	::= {nodeBillingEntry 20 }

nodeBillingAdminAction OBJECT-TYPE
	SYNTAX INTEGER {
			invalid (1),
			forceUpload (2)
			}
	ACCESS read-write
	STATUS mandatory
	DESCRIPTION
		"This object defines a set of administrative actions that
		can be performed by the Billing System.

		forceUpload - Forces the current aggregation period to end
		and the service's aggregated usage data file to be uploaded
		to the Adjunct Processor.  A new aggregation period is
		then started.  This action can be requested when billing is
		enabled or disabled for the service.

		This object always returns invalid(1) when read.
		"
	::= {nodeBillingEntry 21 }

nodeRerouteAlg OBJECT-TYPE
	SYNTAX INTEGER {
		-- negpos (0),
		negneg (1),
		pospos (2),
		disable (3)
        }
	ACCESS read-write
	STATUS mandatory
	DESCRIPTION
		"The number of seconds delay between each reroute batch event."
	::= { node 74 }

nodeOamAlarmDisabled OBJECT-TYPE
	SYNTAX INTEGER {
		enabled(1),
		disabled(2)
	}
	ACCESS read-write
	STATUS mandatory
	DESCRIPTION
		"If disabled then don't generate oam alarms for circuits that are
		down on this switch."
	::= { node 76 }

nodeRefclocksrcTable OBJECT-TYPE
	SYNTAX  SEQUENCE OF NodeRefclocksrcEntry
	ACCESS  not-accessible
	STATUS  mandatory
	DESCRIPTION
	       "A list of generators (sources) for the system reference
		clock on the node. This reference clock is used by the clock
		generation unit (CGU) to create the system clock. To this
		reference clock the constant bit rate ATM interface cards
		(CBR cards) are synchronized."
	::= { node 77 }

-- The table of reference clock sources

nodeRefclocksrcEntry OBJECT-TYPE
	SYNTAX	NodeRefclocksrcEntry
	ACCESS	not-accessible
	STATUS	mandatory
	DESCRIPTION
		"Information of a single system reference clock source."
	INDEX	{ nodeRefclocksrcIndex }
	::= { nodeRefclocksrcTable 1 }

NodeRefclocksrcEntry ::= 
	SEQUENCE {
		nodeRefclocksrcIndex
			INTEGER,
		nodeRefclocksrcPriority
			INTEGER,
		nodeRefclocksrcType
			INTEGER,
		nodeRefclocksrcSlotId
			INTEGER,
		nodeRefclocksrcPportId
			INTEGER
	}

nodeRefclocksrcIndex OBJECT-TYPE
	SYNTAX	INTEGER (1..20)
	ACCESS	read-write
	STATUS	mandatory
	DESCRIPTION
		"A positive integer to identify an entry in the nodeRefclocksrcTable."
	::= { nodeRefclocksrcEntry 1 }

nodeRefclocksrcPriority OBJECT-TYPE
	SYNTAX	INTEGER (1..20)
	ACCESS	read-write
	STATUS	mandatory
	DESCRIPTION
	       "The priority of the system reference clock source.
		A source with a nodeRefclocksrcPriority=n means that this source is 
		used before a source with a higher value of nodeRefclocksrcPriority 
		as long as this source is available.
		The system choses one of the sources with the same lowest 
		available value of nodeRefclocksrcPriority."
	::= { nodeRefclocksrcEntry 2 }

nodeRefclocksrcType OBJECT-TYPE
	SYNTAX	INTEGER {
			external (1),		-- external clock source
			pport (2)		-- recovered from line interface
			}
	ACCESS	read-write
	STATUS	mandatory
	DESCRIPTION
		"The type of the reference clock source. It is either an
		 external clock source connected to a ATM-IWU or DS3 card,
		 or the reference clock is recovered from the line interface."
	::= { nodeRefclocksrcEntry 3 }
 
nodeRefclocksrcSlotId OBJECT-TYPE
	SYNTAX	INTEGER 
	ACCESS	read-write
	STATUS	mandatory
	DESCRIPTION
		"The card number of the reference clock source.
		 In case of an external clock interface this is the number of
		 the card as defined in cardLogicalSlotId.
		 In case of a clock recovered from the line interface it is
		 the number of the corresponding card as defined in 
		 cardLogicalSlotId."
	::= { nodeRefclocksrcEntry 4 }
 
nodeRefclocksrcPportId OBJECT-TYPE
	SYNTAX	INTEGER 
	ACCESS	read-write
	STATUS	mandatory
	DESCRIPTION
		"The interface number of the reference clock source.
		 In case of an external clock interface this is meaningless.
		 In case of a clock recovered from the line interface it is
		 the number of the corresponding pport as defined in pportId."
	::= { nodeRefclocksrcEntry 5 }

nodeRefclockActiveSrc OBJECT-TYPE
	SYNTAX	INTEGER 
	ACCESS	read-only
	STATUS	mandatory
	DESCRIPTION
	       "The entry number of the active reference clock source in 
		nodeRefclocksrcTable. If zero, the CGU is in free-running mode or 
		holdover mode using the last PLL parameters."
	::= { node 78 }

nodeRefclockActiveCGUSlotId OBJECT-TYPE
	SYNTAX	INTEGER 
	ACCESS	read-only
	STATUS	mandatory
	DESCRIPTION
		"The physical slot id of the current master CGU board."
	::= { node 79 }

nodeRefclockActiveCGUMode OBJECT-TYPE
	SYNTAX	INTEGER {
		free-running (1),
		sync-to-reference-clock (2),
		holdover (3),
		extended-holdover (4)
			}
	ACCESS	read-only
	STATUS	mandatory
	DESCRIPTION
		"The clock mode of the current master CGU board."
	::= { node 80 } 

nodeInitiateImageBackup	OBJECT-TYPE
	SYNTAX	INTEGER {
		proceed (1)	-- proceed with the backup
			}
	ACCESS	read-write
	STATUS	mandatory
	DESCRIPTION
		"When set, copy all of the runtime application images
		and configuration images to there corresponding backup
		locations on the hard disk."
	::= { node 81 }

nodeImageBackupState	 OBJECT-TYPE
	SYNTAX	INTEGER {
		proceeding (1),	-- Proceeding with the backup
		done       (2)	-- Done with backup operation
		}
	ACCESS	read-only
	STATUS	mandatory
	DESCRIPTION
		"Provides the current state of the images backup
		operation."
	::= { node 82 }

nodeInitiateImageRestore	OBJECT-TYPE
	SYNTAX	INTEGER {
		proceed (1)	-- Proceed with the restore
		}
	ACCESS	read-write
	STATUS	mandatory
	DESCRIPTION
		"When set, copy all of the runtime application images
		and configuration images from their BACKUP locations on
		the hard disk to there corresponding ACTIVE locations on
		the hard disk.  Once completed, reboot the entire node."
	::= { node 83 }

nodeApplicationTable		OBJECT-TYPE
	SYNTAX	SEQUENCE OF NodeApplicationEntry
	ACCESS	not-accessible
	STATUS	mandatory
	DESCRIPTION
		"A list of Application Image Descriptions."
	::= { node 84 }

nodeApplicationEntry		OBJECT-TYPE
	SYNTAX	NodeApplicationEntry
	ACCESS	not-accessible
	STATUS	mandatory
	DESCRIPTION
		"An Application Entry contains a description of the
		 application image, the version of the PRIMARY copy and
		 the version of the SECONDARY copy."
	INDEX	{ nodeApplicationIndex }
	::= { nodeApplicationTable 1 }

NodeApplicationEntry ::=
	SEQUENCE {
		nodeApplicationIndex
			Index,
		nodeApplicationDescription
			DisplayString,
		nodePrimaryVersion
			DisplayString,
		nodeSecondaryVersion
			DisplayString
	}

nodeApplicationIndex		OBJECT-TYPE
	SYNTAX	Index
	ACCESS	read-only
	STATUS	mandatory
	DESCRIPTION
		"The numeric index of application images.
			1 - SP Runtime Application
			2 - IOM Type A Runtime Application
			3 - IOM Type B Runtime Application
			4 - IOM Type C Runtime Application
			5 - IOM Type D Runtime Application"
	::= { nodeApplicationEntry 1 }

nodeApplicationDescription		OBJECT-TYPE
	SYNTAX	DisplayString
	ACCESS	read-only
	STATUS	mandatory
	DESCRIPTION
		"The description of this Application Image."
	::= { nodeApplicationEntry 2 }

nodePrimaryVersion		OBJECT-TYPE
	SYNTAX	DisplayString
	ACCESS	read-only
	STATUS	mandatory
	DESCRIPTION
		"The version of the PRIMARY Application Image."
	::= { nodeApplicationEntry 3 }

nodeSecondaryVersion	OBJECT-TYPE
	SYNTAX	DisplayString
	ACCESS	read-only
	STATUS	mandatory
	DESCRIPTION
		"The version of the SECONDARY Application Image."
	::= { nodeApplicationEntry 4 }

nodePrimarySyncRefAdminState		OBJECT-TYPE
	SYNTAX	INTEGER {
		externala (1),	-- T1 Rate External Clock A
		externalb (2),	-- T1 Rate External Clock B
		portrefa (3),	-- IOM Port Reference Clock A
		portrefb (4),	-- IOM Port Reference Clock B
		internal   (5)	-- Internal Free Running Clock
		}
	ACCESS	read-write
	STATUS	mandatory
	DESCRIPTION
		"The requested primary clock synchronization reference
		 source."
	::= { node 85 }

nodePrimarySyncRefOperationalState	OBJECT-TYPE
	SYNTAX	INTEGER {
		externala (1),	-- T1 Rate External Clock A
		externalb (2),	-- T1 Rate External Clock B
		portrefa (3),	-- IOM Port Reference Clock A
		portrefb (4),	-- IOM Port Reference Clock B
		internal   (5)	-- Internal Free Running Clock
		}
	ACCESS	read-only
	STATUS	mandatory
	DESCRIPTION
		"The actual primary clock synchronization reference source."
	::= { node 86 }

nodeSecondarySyncRefAdminState		OBJECT-TYPE
	SYNTAX	INTEGER {
		externala (1),	-- T1 Rate External Clock A
		externalb (2),	-- T1 Rate External Clock B
		portrefa (3),	-- IOM Port Reference Clock A
		portrefb (4),	-- IOM Port Reference Clock B
		internal   (5)	-- Internal Free Running Clock
		}
	ACCESS	read-write
	STATUS	mandatory
	DESCRIPTION
		"The requested secondary clock synchronization reference
		 source."
	::= { node 87 }

nodeSecondarySyncRefOperationalState	OBJECT-TYPE
	SYNTAX	INTEGER {
		externala (1),	-- T1 Rate External Clock A
		externalb (2),	-- T1 Rate External Clock B
		portrefa (3),	-- IOM Port Reference Clock A
		portrefb (4),	-- IOM Port Reference Clock B
		internal   (5)	-- Internal Free Running Clock
		}
	ACCESS	read-only
	STATUS	mandatory
	DESCRIPTION
		"The actual secondary clock synchronization reference
		 source."
	::= { node 88 }

nodePrimaryPLLOperationalState		OBJECT-TYPE
	SYNTAX	INTEGER {
		active (1),		-- Running and valid
		down   (2)		-- Not valid
		}
	ACCESS	read-only
	STATUS	mandatory
	DESCRIPTION
		"The current state of the primary synchronization PLL."
	::= { node 89 }

nodeSecondaryPLLOperationalState		OBJECT-TYPE
	SYNTAX	INTEGER {
		active (1),		-- Running and valid
		down   (2)		-- Not valid
		}
	ACCESS	read-only
	STATUS	mandatory
	DESCRIPTION
		"The current state of the secondary synchronization PLL."
	::= { node 90 }

nodeExternalClockAOperationalState	OBJECT-TYPE
	SYNTAX	INTEGER {
		active (1),		-- Valid
		ais    (2),		-- Detected AIS Alarm
		los    (3)		-- Detected Loss Of Signal
		}
	ACCESS	read-only
	STATUS	mandatory
	DESCRIPTION
		"The current state of the External Clock A reference."
	::= { node 91 }

nodeExternalClockBOperationalState	OBJECT-TYPE
	SYNTAX	INTEGER {
		active (1),		-- Valid
		ais    (2),		-- Detected AIS Alarm
		los    (3)		-- Detected Loss Of Signal
		}
	ACCESS	read-only
	STATUS	mandatory
	DESCRIPTION
		"The current state of the External Clock B reference."
	::= { node 92 }

nodePortClockAOperationalState	OBJECT-TYPE
	SYNTAX	INTEGER {
		active (1),		-- Valid
		down   (2)		-- Invalid
		}
	ACCESS	read-only
	STATUS	mandatory
	DESCRIPTION
		"The current state of the Port Clock A reference."
	::= { node 93 }

nodePortClockBOperationalState	OBJECT-TYPE
	SYNTAX	INTEGER {
		active (1),		-- Valid
		down   (2)		-- Invalid
		}
	ACCESS	read-only
	STATUS	mandatory
	DESCRIPTION
		"The current state of the Port Clock B reference."
	::= { node 94 }

nodeExternalTimingSource	OBJECT-TYPE
	SYNTAX	INTEGER {
		externala (1),	-- T1 Rate External Clock A
		externalb (2),	-- T1 Rate External Clock B
		portrefa (3),	-- IOM Port Reference Clock A
		portrefb (4),	-- IOM Port Reference Clock B
		internal   (5)	-- Internal Free Running Clock
		}
	ACCESS	read-write
	STATUS	mandatory
	DESCRIPTION
		"The reference for the external timing output."
	::= { node 95 }

nodeSyncAutoRestore	OBJECT-TYPE
	SYNTAX	INTEGER {
		enable (1),		-- Allow auto-restore
		disable(2)		-- Do not allow auto-restore
		}
	ACCESS	read-write
	STATUS	mandatory
	DESCRIPTION
		"The configuration of the Synchronization Reference Auto
		 Restoration function."
	::= { node 96 }

nodeExternalClockInterfaceType	OBJECT-TYPE
	SYNTAX	INTEGER {
		t1    (1),		-- T1 rate W/W terminals
		e1bnc (2),		-- E1 rate 75 ohm BNC
		e1ww  (3)		-- E1 rate W/W terminals
		}
	ACCESS	read-only
	STATUS	mandatory
	DESCRIPTION
		"The interface type of the External Clock references."
	::= { node 97 }

--  The Card Group
--
--  The variables that manage intelligent cards (PP's, CP's, IOP's).
--  For redundant pairs of cards, only the active card is managed.
--
--  NOTE: The card group is currently only supported in the B-STDX 9000 platform.

CardTypes ::= INTEGER {
--			invalid (0),
			v35-6 (1),		-- 6-port V.35 i/o card
			ft1-1-24 (2),		-- 1-port 24-channel Fractional T1
			fe1-1-30 (3),		-- 1-port 30-channel Fractional E1
			uio-6 (4),		-- 6-port universal i/o card
			cp1 (5),		-- Control Processor
			uio-8 (6),		-- 8-port V.35 i/o card
			ft1-4-24 (7),		-- 4-port 24-channel Fractional T1
			fe1-4-30 (8),		-- 4-port 30-channel Fractional E1
			ft3-1 (9),		-- 1-port Fractional T3 i/o card
			fe3-1 (10),		-- 1-port Fractional E3 i/o card
			hssi-2 (11),		-- HSSI i/o card
			dsx1-10 (12),		-- 10-port DSX-1 card
			rs232-18 (13),		-- 18-port X.21/V.24 I/O card, for STDX 3000/6000 only
			rs232-8 (14),		-- 8-port X.21/V.24 I/O card, for STDX 3000/6000 only
			ut1-4-24 (15),		-- 4-port 24-channel Un-Channelized T1
			ue1-4-30 (16),		-- 4-port 30-channel Un-Channelized E1
			atmds3-1 (17),		-- 1-port ATM DS3 UNI I/O card
			atme3-1 (18),		-- 1-port ATM E3 UNI I/O card
			pri-4 (19),		-- 4-port ISDN PRI I/O card
			e1-pri-4 (20),		-- 4-port E1 PRI I/O card
			sft1-4-24 (21),		-- 4-port short haul 24-channel Fractional T1 card
			sut1-4-24 (22),		-- 4-port short haul 24-channel Un-Channelized T1 card
			st1-pri-4 (23),		-- 4-port short haul PRI I/O card
			t1-atm    (24),		-- T1 ATM
			e1-atm    (25),		-- E1 ATM
			ads3-t3   (26),		-- ATM DS3 T3 (topaz)
			ads3-e3   (27),		-- ATM DS3 E3 (topaz)
			cbr-ds1-s-4 (28),	-- 4-port CBR T1 structured card
			cbr-ds1-us-4 (29),	-- 4-port CE T1 card
			cbr-e1-s-4 (30),	-- 4-port CBR E1 structured card
			cbr-e1-us-4 (31),	-- 4-port CE E1 card
			atmiwu-1 (32),		-- 1-port ATM-IWU STM-1/STS-3c card
			toc3-atm-4 (33),	-- 4-port Topaz OC3c/STM1 ATM card
			tstm1-atm-4 (34),	-- 4-port Topaz STM1 ATM card (OBSOLETE code)
			sp-4    (35),		-- 4x4 switching processor (new terminology is "sp-10")
			sp-8    (36),		-- 8x8 switching processor (new terminology is "sp-20")
			atmcs-1     (37),	-- 1-port ATM-CS card (siemens)
			toc12-atm-1 (38),	-- 1-port Topaz OC12c/STM4 ATM card
			tstm4-atm-1 (39),	-- 1-port Topaz STM4 ATM card (OBSOLETE code)
			ads1-t1 (40),		-- Topaz 8 port T1 ATM
			ads1-e1 (41),		-- Topaz 8 port E1 ATM
			ads1-j2 (42),		-- Topaz 8 port J2 ATM
			e1-12 (43),		-- 12-port E1 i/o card
			bio1-4-16 (44),		-- Garnet BIO1 4 PHY sub-cards 16 ports
			bio1-oc3-4 (45),	-- Garnet BIO1 OC3 PHY sub-card 4 ports
			bio1-oc12-1 (46),	-- Garnet BIO1 OC12 PHY sub-card 1 port
			bio1-oc12x4 (47),	-- Garnet BIO1 OC12x4 PHY sub-card 1 port 4 channels
			bio1-oc48-1 (48),	-- Garnet BIO1 OC48 PHY sub-card 1 port
			np1 (49),		-- Garnet Node Processor card
			sf1 (50),		-- Garnet Switch Fabric card
			tm1 (51),		-- Garnet Timing Module card
			tfds3-t3-6    (52),	-- 6-port Topaz DS3 T3 Ultracore card
			tfds3-e3-6    (53),	-- 6-port Topaz DS3 E3 Ultracore card
			tfast-ether-4 (54),	-- 4-port Topaz Fast Ethernet Ultracore card
			fast-ether-2  (55),	-- 2-port BSTDX Fast Ethernet Ultracore card
			ls-oc3-1     (56),	-- 1-port BSTDX OC3c/STM-1 Ultracore card
			tcfds3-t3-6   (57),	-- 6-port Topaz Cell Frame Cell DS3 T3 Ultracore card
			tcfds3-e3-6  (58),	-- 6-port Topaz Cell Frame Cell DS3 E3 Ultracore card
			toc3-cfc-2   (59),	-- 2-port Topaz Cell Frame Cell OC3c/STM-1 Ultracore card
			atmcs-e3-1   (60),	-- 1-port ATM-CS-E3 card (siemens)
						-- (61) is reserved
			be1-atm-12 (62),	-- 12-port BSTDX E1 ATM card
			bt1-atm-12 (63),	-- 12-port BSTDX T1 ATM card
			bds3-1-0 (64),		-- 1 port BSTDX Channelized 3/1/0
			gfether-4 (65),		-- Granite Topaz Fast Ethernet UC card
			gfds3-t3-6 (66),	-- Granite Topaz Frame DS3 UC card
			gfds3-e3-6 (67),	-- Granite Topaz Frame E3 UC card
			gchn-ds3-4 (68),	-- Granite Topaz Channalized  DS3 card
			g-server (69),		-- Granite Topaz Server card
			sp-30    (70),		-- 8x8 sp with new PTS
			sp-40    (71)		-- 8x8 sp with new PTS and more memory
		   }


CardStatuses ::= INTEGER {
--			invalid (0),
			up (1),
			down (2),
			testing (3),
			maintenance (6),
			overtemp (7)
		    }

cardNumber   OBJECT-TYPE
	SYNTAX	INTEGER    
	ACCESS  read-only
	STATUS  mandatory
	DESCRIPTION
		"The number of manageable cards physically present in this node. 
		Standby cards are not considered manageable."
	::= { card 1}

cardTable  OBJECT-TYPE
	SYNTAX	SEQUENCE OF CardEntry
	ACCESS	not-accessible
	STATUS	mandatory
	DESCRIPTION
		"A list of cardEntry's. The number of entries is given by the value of
		cardNumber"
	::= { card 2}

CardEntry  ::=
	SEQUENCE {
		cardLogicalSlotId
			INTEGER,
		cardPhysicalSlotId
			INTEGER,
		cardAdminType
			CardTypes,
		cardOperType
			CardTypes,
		cardState
			INTEGER,
		cardAdminStatus
			CardStatuses,
		cardOperStatus
			CardStatuses,
		cardDiagStatus
			INTEGER,
		cardRedundConfig
			INTEGER,
		cardRedundSlotMask
			INTEGER,
		cardRedundActual
			INTEGER,
		cardRedundState
			INTEGER,
		cardToRedundant
			TimeTicks,
		cardDiagNonFatalSource
			INTEGER,
		cardDiagNonFatalTime
			TimeTicks,
		cardDiagNonFatalErrMajor
			INTEGER,
		cardDiagNonFatalErrMinor
			INTEGER,
		cardDiagNonFatalStr
			DisplayString,
		cardDiagFatalSource
			INTEGER,
		cardDiagFatalTime
			TimeTicks,
		cardDiagFatalErrMajor
			INTEGER,
		cardDiagFatalErrMinor
			INTEGER,
		cardDiagFatalStr
			DisplayString,
		cardDiagFatalReboots
			Counter,
		cardDiagFatalAddress
			INTEGER,
		cardDiagBackgroundPasses
			Counter,
		cardDiagBackgroundFailures
			Counter,
		cardDiagBackgroundSuccesses
			Counter,
		cardDiagLEDReset
			INTEGER,
		cardDiagPowerExtensive
			INTEGER,
		cardCpuUtil
			Gauge,
		cardMemoryUsage
			Gauge,
		cardMaxVCs
			Gauge,
		cardInUseVCs
			Gauge,
		cardFreeVCs
			Gauge,
		cardInOctets
			Counter,
		cardInPkts
			Counter,
		cardOutOctets
			Counter,
		cardOutPkts
			Counter,
		cardToWarmboot
			TimeTicks,
		cardToColdboot
			TimeTicks,
		cardModel
			DisplayString,
		cardSerial
			DisplayString,
		cardSwRev
			DisplayString,
		cardHwRev
			DisplayString,
		cardEpromRev
			DisplayString,
		cardName
			DisplayString,
		cardCktGroupTrap
			OCTET STRING,
		cardOutBtus
			Counter,
		cardInGoodBtus
			Counter,
		cardInErrorBtus
			Counter,
		cardInNoVcBtus
			Counter,
		cardInLinkDownBtus
			Counter,
		cardInNoBufferBtus
			Counter,
		cardInForwardBitBtus
			Counter,
		cardDiagTestId
			INTEGER,
		cardDiagTestRuns
			INTEGER,
		cardDiagState
			INTEGER,
		cardDiagOptionStr
			OCTET STRING,
		cardDiagPasses
			Counter,
		cardDiagFailures
			Counter,
		cardDiagResultString
			DisplayString,
		cardFrameMemoryUtil
			Gauge,
		cardResetPram
			INTEGER,
		cardMemoryUtil
			Gauge,
		cardFrameMemoryUsage
			Gauge,
		cardUpTime
			TimeTicks,
		cardPramChecksum
			INTEGER,
		cardPhysicalIndex
			INTEGER,
		cardExternalClockRate
			INTEGER,
		cardShootState
			INTEGER,
		cardEraseAll
			INTEGER,
		cardAdminCapability
			INTEGER,
		cardOperCapability
			INTEGER,
		cardISDNswtype
			INTEGER,
		cardCpuFgUtil
			Gauge,
		cardTrkProtState
			INTEGER,
		cardISDNSigType
			INTEGER,
		cardISDNChanId
			INTEGER,
		cardTransmitClockConfig
			INTEGER,
		cardTransmitClockSwitchOver
			INTEGER,
		cardTransmitClockStatus
			INTEGER,
		cardSystemPrimaryClockPortConfig
			INTEGER,
		cardSystemPrimaryClockStatus
			INTEGER,
		cardSystemSecondaryClockPortConfig
			INTEGER,
		cardSystemSecondaryClockStatus
			INTEGER,
		cardInCells
			Counter,
		cardInErrorCells
			Counter,
		cardInErrorVPIVCI
			Counter,
		cardOutCells
			Counter,
		cardOutDiscardCells
			Counter,
		cardQOSQueueSize
			INTEGER,
		cardLastErrorPort
			INTEGER,
		cardLastErrorVPI
			INTEGER,
		cardLastErrorVCI
			INTEGER,
		cardSystemPrimaryClockModeConfig
			INTEGER,
		cardSystemSecondaryClockModeConfig
			INTEGER,
		cardNFBDEStatus
			INTEGER,
		cardProductCode
			DisplayString,
		cardMfgPN
			DisplayString,
		cardTotalUpTime
			TimeTicks,
		cardIOAType
			INTEGER,
		cardIOAHwRev
			DisplayString,
		cardIOASerial
			DisplayString,
		cardIOAProductCode
			DisplayString,
		cardIOAMfgPN
			DisplayString,
		cardDS0Support
			INTEGER,
		cardDiagParamId
			INTEGER,
		cardDiagParamValue
			INTEGER,
		cardBulkStatsPeakCapability
			INTEGER,
		cardBulkStatsTotalCapability
			INTEGER,
		cardBulkStatsPeakEnable
			INTEGER,
		cardBulkStatsTotalEnable
			INTEGER,
		cardBulkStatsBaseCollectPeriod
			INTEGER,
		cardNrtsHwRev
			INTEGER,
		cardNrtsOutCellBufSize
			INTEGER,
		cardNrtsOperState
			INTEGER,
		cardNrtsAdminState
			INTEGER,
		cardNrtsCcrmProtocolId
			INTEGER,
		cardNrtsBcmProtocolId
			INTEGER,
		cardNrtsRmGenInterval
			INTEGER,
		cardNrtsIdleCktThresh
			INTEGER,
		cardNrtsVbrNrtManage
			INTEGER,
		cardNrtsIcrFact
			INTEGER,
		cardNrtsMcastDiscardThresh
			INTEGER,
		cardNrtsMcastDiscardCount
			Counter,
		cardAdminIOAType
			INTEGER,
		cardNrtsMcastRate
			INTEGER,
		cardMonStatus
			INTEGER,
		cardImageSetA
			DisplayString,
		cardImageSetB
			DisplayString,
		cardMacAddress
			DisplayString,
		cardFlashRev
			DisplayString,
		cardRequiredCapabilityBitmask
			INTEGER,
		cardOperCapabilityBitmask
			INTEGER,
		cardDslModule
			OCTET STRING,
		cardIPTableSize
			INTEGER,
		cardIPTableState
			INTEGER,
		cardATMTcaInBufOverflowAlertPeriod
			INTEGER,
		cardATMTcaInBufOverflowThresh
			INTEGER,
		cardATMTcaInInvalidVpiVciAlertPeriod
			INTEGER,
		cardATMTcaInInvalidVpiVciThresh
			INTEGER,
                cardATMTcaInATMDCFullAlertPeriod
                        INTEGER,
                cardATMTcaInATMDCFullThresh
                        INTEGER,
		cardATMTcaEnable
			INTEGER,
		cardATMTcaId
			INTEGER,
		cardATMTcaECidLookupFailureAlertPeriod
			INTEGER,
		cardATMTcaECidLookupThresh
			INTEGER,
		cardATMTcaSPPearlOCbrFailureAlertPeriod
			INTEGER,
		cardATMTcaSPPearlOCbrThresh
			INTEGER,
		cardATMTcaSPPearlOAbrFailureAlertPeriod
			INTEGER,
		cardATMTcaSPPearlOAbrThresh
			INTEGER,
		cardATMTcaSPPearlOVbr1FailureAlertPeriod
			INTEGER,
		cardATMTcaSPPearlOVbr1Thresh
			INTEGER,
		cardATMTcaSPPearlOVbr2FailureAlertPeriod
			INTEGER,
		cardATMTcaSPPearlOVbr2Thresh
			INTEGER,
                cardATMTcaSPPearlGCbrFailureAlertPeriod
                        INTEGER,
                cardATMTcaSPPearlGCbrThresh
                        INTEGER,
                cardATMTcaSPPearlGAbrFailureAlertPeriod
                        INTEGER,
                cardATMTcaSPPearlGAbrThresh
                        INTEGER,
                cardATMTcaSPPearlGVbr1FailureAlertPeriod
                        INTEGER,
                cardATMTcaSPPearlGVbr1Thresh
                        INTEGER,
                cardATMTcaSPPearlGVbr2FailureAlertPeriod
                        INTEGER,
                cardATMTcaSPPearlGVbr2Thresh
                        INTEGER,
                cardATMTcaSPEnable
                        INTEGER,
                cardSPEFCIEnable
                        INTEGER,
                cardSPClpEnable
                        INTEGER,
		spATMTcaId
			INTEGER,
                cardSubcardToRedundant
			CardTypes,
		cardMemory5Usage
        		Gauge,
		cardSF1OperStatus
			CardStatuses,
		cardSF2OperStatus
			CardStatuses,
		cardTM1OperStatus
			CardStatuses,
		cardTM2OperStatus
			CardStatuses,
		cardMemStartLog
			INTEGER,
		cardMemLogLevel
			INTEGER,
		cardMemClrLog
			INTEGER,
		cardValidSubcards
			INTEGER,
		cardClp0CbrThreshold
			INTEGER,
		cardClp01CbrThreshold
			INTEGER,
		cardClp0VbrRtThreshold
			INTEGER,
		cardClp01VbrRtThreshold
			INTEGER,
		cardClp0VbrNrtThreshold
			INTEGER,
		cardClp01VbrNrtThreshold
			INTEGER,
		cardClp0UAbrThreshold
			INTEGER,
		cardClp01UAbrThreshold
			INTEGER,
		cardControlMessagesFromBus
			Counter,
		cardControlMessagesToBus
			Counter,
		cardBTUsFromBus
			Counter,
		cardBTUsToBus
			Counter,
		cardInvalidPvcBTUs
			Counter,
		cardIncompleteFramesFromBus
			Counter,
		cardBTUsBusErrors
			Counter,
		cardBTUsNoResource
			Counter,
		cardInvalidPvcBTUsThreshold
			INTEGER,
		cardIncompleteFramesFromBusThreshold
			INTEGER,
		cardBTUsBusErrorThreshold
			INTEGER,
		cardBTUsNoResourceThreshold
			INTEGER,
		cardFrameMemoryThreshold
			INTEGER,
		cardHoldQFrameMemory
			Counter,
		cardTotalAAL5RxErrorCount
			Counter,
		cardOperMemSize
			INTEGER
	}

cardEntry  OBJECT-TYPE
	SYNTAX	CardEntry
	ACCESS	not-accessible
	STATUS	mandatory
	DESCRIPTION
		"The card entry contains objects relevant to managing intelligent
		cards."
	INDEX	    { cardLogicalSlotId, cardRedundState }
	::= { cardTable 1}

cardLogicalSlotId OBJECT-TYPE
	SYNTAX	INTEGER
	ACCESS	read-only
	STATUS	mandatory
	DESCRIPTION
		"The logical slot number of this card. This is used as an index for
		the cardTable. In redundant configurations, this can be the physical
		slot number of either redundant card. In non redundant
		configurations, this is the same as cardPhysicalSlotId."
	::= { cardEntry 1}

cardPhysicalSlotId OBJECT-TYPE
	SYNTAX	INTEGER
	ACCESS	read-only
	STATUS	mandatory
	DESCRIPTION
		"The physical slot number of this card. This can be different from
		cardLogicalSlotId in redundant configurations."
	::= { cardEntry 2}

cardAdminType OBJECT-TYPE
	SYNTAX	CardTypes
	ACCESS	read-write
	STATUS	mandatory
	DESCRIPTION
		"The desired card type."
	::= { cardEntry 3}

cardOperType OBJECT-TYPE
	SYNTAX	CardTypes
	ACCESS	read-only
	STATUS	mandatory
	DESCRIPTION
		"The actual card type."
	::= { cardEntry 4}

cardState OBJECT-TYPE
	SYNTAX	INTEGER {
--			unknown (0),
			present (1),
			loading (2),
			start (3),
			init (4),
			sync (5),
			syncdone (6),
			ready (7),
			active (8),
			stopped (9),
			down (10),
			debug (11),
			offlinediag (12)
		    }
	ACCESS	read-only
	STATUS	 mandatory
	DESCRIPTION
		"The state of this card."
	::= { cardEntry 5}

cardAdminStatus OBJECT-TYPE
	SYNTAX	CardStatuses
	ACCESS	read-write
	STATUS	 mandatory
	DESCRIPTION
		"The desired status of this card."
	::= { cardEntry 6}

cardOperStatus OBJECT-TYPE
	SYNTAX	 CardStatuses
	ACCESS	read-only
	STATUS	mandatory
	DESCRIPTION
		"The current status of this card."
	::= { cardEntry 7}

cardDiagStatus OBJECT-TYPE
	SYNTAX  INTEGER {
--			unknown (0),
			ok (1),
			marginal (2)
		    }
	ACCESS	read-only
	STATUS	mandatory
	DESCRIPTION
		"The current diagnostics status of this card, as determined by
		background diagnostics."
	::= { cardEntry 8}

cardRedundConfig OBJECT-TYPE
	SYNTAX	INTEGER {
--			none (0),
			configured (1)
		    }
	ACCESS	read-only
	STATUS	mandatory
	DESCRIPTION
		"Is the card configured for redundancy?"
	::= { cardEntry 9}

cardRedundSlotMask OBJECT-TYPE
	SYNTAX	INTEGER
	ACCESS	read-write
	STATUS	mandatory
	DESCRIPTION
		"A 32-bit mask indicating the slot position of this card and its
		redundant partner. The low bit is slot 1 and the high bit is slot
		32."
	::= { cardEntry 10}

cardRedundActual OBJECT-TYPE
	SYNTAX	INTEGER {
			connected (1),
			not-connected (2)
		    }
	ACCESS	read-only
	STATUS	mandatory
	DESCRIPTION
		"Is the card currently connected to a redundant card?"
	::= { cardEntry 11}

cardRedundState OBJECT-TYPE
	SYNTAX	INTEGER {
			active (1),
			standby (2)
		    }
	ACCESS	read-only
	STATUS	mandatory
	DESCRIPTION
		"The current redundancy state of this card.  Exception: when
		used as an index for the following objects: cardAdminType,
		cardAdminCapability, and cardAdminStatus, the value 1 indicates
		the card of the redundant pair in the lower-numbered slot, and
		the value 2 indicates the card in the higher-numbered slot."
	::= { cardEntry 12}

cardToRedundant OBJECT-TYPE
	SYNTAX	TimeTicks
	ACCESS	read-write
	STATUS	mandatory
	DESCRIPTION
		"Instructs the standby card to reset the active card and take over
		as new active card. The reset takes place after specified time ticks
		have elapsed. A value of 0 indicates cancellation of the previously
		scheduled request."
	::= { cardEntry 13}

cardDiagNonFatalSource OBJECT-TYPE
	SYNTAX	INTEGER {
		power-on-diagnostics (1),
		background-diagnostics (2),
		fault (3),
		frame-heap (4),
		redundancy (5),
		system-level (6),
		card-level (7),
		i960-data-structures (8),
		general (9),
		data-alignment (10),
		device-driver-level (11)
	}
	ACCESS	read-only
	STATUS	mandatory
	DESCRIPTION
		"Source who reported last non-fatal error."
	::= { cardEntry 14 }

cardDiagNonFatalTime OBJECT-TYPE
	SYNTAX	TimeTicks
	ACCESS	read-only
	STATUS	mandatory
	DESCRIPTION
		"Time the last non-fatal error was reported."
	::= { cardEntry 15 }

cardDiagNonFatalErrMajor OBJECT-TYPE
	SYNTAX	INTEGER
	ACCESS	read-only
	STATUS	mandatory
	DESCRIPTION
		"Major error code of last non-fatal error."
	::= { cardEntry 16 }

cardDiagNonFatalErrMinor OBJECT-TYPE
	SYNTAX	INTEGER
	ACCESS	read-only
	STATUS	mandatory
	DESCRIPTION
		"Minor error code of last non-fatal error."
	::= { cardEntry 17 }

cardDiagNonFatalStr OBJECT-TYPE
	SYNTAX	DisplayString
	ACCESS	read-only
	STATUS	mandatory
	DESCRIPTION
		"Ascii string describing last non-fatal error."
	::= { cardEntry 18 }

cardDiagFatalSource OBJECT-TYPE
	SYNTAX	INTEGER {
		power-on-diagnostics (1),
		background-diagnostics (2),
		fault (3),
		frame-heap (4),
		redundancy (5),
		system-level (6),
		card-level (7),
		i960-data-structures (8),
		general (9),
		data-alignment (10),
		device-driver-level (11)
	}
	ACCESS	read-only
	STATUS	mandatory
	DESCRIPTION
		"Source who reported last fatal error."
	::= { cardEntry 19 }

cardDiagFatalTime OBJECT-TYPE
	SYNTAX	TimeTicks
	ACCESS	read-only
	STATUS	mandatory
	DESCRIPTION
		"Time the last fatal error was reported."
	::= { cardEntry 20 }

cardDiagFatalErrMajor OBJECT-TYPE
	SYNTAX	INTEGER
	ACCESS	read-only
	STATUS	mandatory
	DESCRIPTION
		"Major error code of last fatal error."
	::= { cardEntry 21 }

cardDiagFatalErrMinor OBJECT-TYPE
	SYNTAX	INTEGER
	ACCESS	read-only
	STATUS	mandatory
	DESCRIPTION
		"Minor error code of last fatal error."
	::= { cardEntry 22 }

cardDiagFatalStr OBJECT-TYPE
	SYNTAX	DisplayString
	ACCESS	read-only
	STATUS	mandatory
	DESCRIPTION
		"Ascii string describing last fatal error."
	::= { cardEntry 23 }

cardDiagFatalReboots OBJECT-TYPE
	SYNTAX	Counter
	ACCESS	read-only
	STATUS	mandatory
	DESCRIPTION
		"Number of times the switch has re-booted since last
		fatal error was reported."
	::= { cardEntry 24 }

cardDiagFatalAddress OBJECT-TYPE
	SYNTAX	INTEGER
	ACCESS	read-only
	STATUS	mandatory
	DESCRIPTION
		"Address switch was executing when it encountered fatal error."
	::= { cardEntry 25 }

cardDiagBackgroundPasses OBJECT-TYPE
	SYNTAX	Counter
	ACCESS	read-only
	STATUS	mandatory
	DESCRIPTION
		"Number of passes made by the background diagnostics."
	::= { cardEntry 26 }

cardDiagBackgroundFailures OBJECT-TYPE
	SYNTAX	Counter
	ACCESS	read-only
	STATUS	mandatory
	DESCRIPTION
		"Number of failures discovered by background diagnostics."
	::= { cardEntry 27 }

cardDiagBackgroundSuccesses OBJECT-TYPE
	SYNTAX	Counter
	ACCESS	read-only
	STATUS	mandatory
	DESCRIPTION
		"Number of successful passes by background diagnostics."
	::= { cardEntry 28 }

cardDiagLEDReset OBJECT-TYPE
	SYNTAX	INTEGER {
--		state-unchanged (0),
		state-to-active (1)
	}
	ACCESS	read-write
	STATUS	mandatory
	DESCRIPTION
		"Change the card state from marginal to active.  Change the
		LED from yellow to green."
	::= { cardEntry 29 }

cardDiagPowerExtensive OBJECT-TYPE
	SYNTAX	INTEGER {
--		fast-tests (0),
		extensive-tests (1)
	}
	ACCESS	read-write
	STATUS	mandatory
	DESCRIPTION
		"Should power on diagnostics do slower, extensive testing,
		or fast testing?"
	::= { cardEntry 30 }

cardCpuUtil OBJECT-TYPE
	SYNTAX	Gauge
	ACCESS	read-only
	STATUS	mandatory
	DESCRIPTION
		"The CPU utilization percentage for packet processing on this
		 intelligent card."
	::= { cardEntry 31 }

cardMemoryUsage OBJECT-TYPE
	SYNTAX	Gauge
	ACCESS	read-only
	STATUS	mandatory
	DESCRIPTION
		"The memory utilization, in terms of free bytes, for
		this intelligent card."
	::= { cardEntry 32 }

cardMaxVCs OBJECT-TYPE
	SYNTAX	Gauge
	ACCESS	read-only
	STATUS	mandatory
	DESCRIPTION
		"The number of available VC entries on this card."
	::= { cardEntry 33 }

cardInUseVCs OBJECT-TYPE
	SYNTAX	Gauge
	ACCESS	read-only
	STATUS	mandatory
	DESCRIPTION
		"The number of currently in use VC entries on this card."
	::= { cardEntry 34 }

cardFreeVCs OBJECT-TYPE
	SYNTAX	Gauge
	ACCESS	read-only
	STATUS	mandatory
	DESCRIPTION
		"The number of currently free VC entries on this card."
	::= { cardEntry 35 }

cardInOctets OBJECT-TYPE
	SYNTAX	Counter
	ACCESS	read-only
	STATUS	mandatory
	DESCRIPTION
		"The total number of octets received on this card, including
		framing bytes."
	::= { cardEntry 36 }

cardInPkts OBJECT-TYPE
	SYNTAX	Counter
	ACCESS	read-only
	STATUS	mandatory
	DESCRIPTION
		"The total number of packets received on this card."
	::= { cardEntry 37 }

cardOutOctets OBJECT-TYPE
	SYNTAX	Counter
	ACCESS	read-only
	STATUS	mandatory
	DESCRIPTION
		"The total number of octets transmitted out of this card,
		including framing bytes."
	::= { cardEntry 38 }

cardOutPkts OBJECT-TYPE
	SYNTAX	Counter
	ACCESS	read-only
	STATUS	mandatory
	DESCRIPTION
		"The total number of packets requested to be transmitted out
		of this card, including those that were discarded or not sent."
	::= { cardEntry 39 }

cardToWarmboot OBJECT-TYPE
	SYNTAX	TimeTicks
	ACCESS	read-write
	STATUS	mandatory
	DESCRIPTION
		"Warm boots the card after the specified time ticks have
		elapsed. A value of 0 indicates cancellation of the previously
		scheduled re-boot request."
	::= { cardEntry 40 }

cardToColdboot OBJECT-TYPE
	SYNTAX	TimeTicks
	ACCESS	read-write
	STATUS	mandatory
	DESCRIPTION
		"Cold boots the card after the specified time ticks have
		elapsed. A value of 0 indicates cancellation of the previously
		scheduled re-boot request."
	::= { cardEntry 41 }

cardModel OBJECT-TYPE
	SYNTAX	DisplayString
	ACCESS	read-only
	STATUS	mandatory
	DESCRIPTION
		"The part number of the card."
	::= { cardEntry 42 }

cardSerial OBJECT-TYPE
	SYNTAX	DisplayString
	ACCESS	read-only
	STATUS	mandatory
	DESCRIPTION
		"The serial number of the card."
	::= { cardEntry 43 }

cardSwRev OBJECT-TYPE
	SYNTAX	DisplayString
	ACCESS	read-only
	STATUS	mandatory
	DESCRIPTION
		"The software rev number (major.minor)."
	::= { cardEntry 44 }

cardHwRev OBJECT-TYPE
	SYNTAX	DisplayString
	ACCESS	read-only
	STATUS	mandatory
	DESCRIPTION
		"The hardware rev number (major.minor)."
	::= { cardEntry 45 }

cardEpromRev OBJECT-TYPE
	SYNTAX	DisplayString
	ACCESS	read-only
	STATUS	mandatory
	DESCRIPTION
		"The EPROM firmware rev number (major.minor)."
	::= { cardEntry 46 }

cardName OBJECT-TYPE
	SYNTAX	DisplayString
	ACCESS	read-write
	STATUS	mandatory
	DESCRIPTION
		"The name of this card"
	::= { cardEntry 47 }

cardCktGroupTrap OBJECT-TYPE
	SYNTAX	OCTET STRING
	ACCESS	read-only
	STATUS	mandatory
	DESCRIPTION
		"This is a ( 4 + n*134 ) byte octet string where n => 1.
		 The first and second byte is the interface/slot id of the
		 link/IOP going down or link goes up.
		 The third byte is the reason why circuits go down:
		 1 is a user link goes down,
		 2 is a trunk link goes down,
		 3 is an IOP goes down and
		 4 is an user link goes up
		 The fourth byte is the count of entries in the following
		 circuit bit map array.
		 Each circuit bit map entry is 134 bytes.
		 The first 2 bytes is the IOP slot on which dlci's are defined.
		 The second 2 bytes is the Physical port ID on which dlci's
		 are defined.
		 The third 2 bytes is the interface id on which dlci's are
		 defined.
		 The following 128 bytes (1024 bits) is a bit map for dlci's
		 defined on the interface. The left-most bit of the first byte
		 represent dlci 0 and the right-most bit of the 128th byte
		 represent dlci 1023. If a bit is set, it means the
		 corresponding dlci on that interface is up/down."
	::= { cardEntry 48 }


cardOutBtus OBJECT-TYPE
	SYNTAX	Counter
	ACCESS	read-only
	STATUS	mandatory
	DESCRIPTION
		"The number of bus transfer units sent by this card."
	::= { cardEntry 49 }

cardInGoodBtus OBJECT-TYPE
	SYNTAX	Counter
	ACCESS	read-only
	STATUS	mandatory
	DESCRIPTION
		"The number of good bus transfer units received by this card."
	::= { cardEntry 50 }

cardInErrorBtus OBJECT-TYPE
	SYNTAX	Counter
	ACCESS	read-only
	STATUS	mandatory
	DESCRIPTION
		"The number of bus transfer units received with errors."
	::= { cardEntry 51 }

cardInNoVcBtus OBJECT-TYPE
	SYNTAX	Counter
	ACCESS	read-only
	STATUS	mandatory
	DESCRIPTION
		"The number of bus transfer units discarded because no circuit
		was found."
	::= { cardEntry 52 }

cardInLinkDownBtus OBJECT-TYPE
	SYNTAX	Counter
	ACCESS	read-only
	STATUS	mandatory
	DESCRIPTION
		"The number of bus transfer units discarded because the outgoing
		link was inactive."
	::= { cardEntry 53 }

cardInNoBufferBtus OBJECT-TYPE
	SYNTAX	Counter
	ACCESS	read-only
	STATUS	mandatory
	DESCRIPTION
		"The number of bus transfer units discarded because no buffer
		was available."
	::= { cardEntry 54 }

cardInForwardBitBtus OBJECT-TYPE
	SYNTAX	Counter
	ACCESS	read-only
	STATUS	mandatory
	DESCRIPTION
		"The number of bus transfer units discarded because the circuit
		forward bit was off."
	::= { cardEntry 55 }

cardDiagTestId OBJECT-TYPE
	SYNTAX	INTEGER
	ACCESS	read-write
	STATUS	mandatory
	DESCRIPTION
		"Identification of the diagnostics tests to be run."
	::= { cardEntry 56 }

cardDiagTestRuns OBJECT-TYPE
	SYNTAX	INTEGER
	ACCESS	read-write
	STATUS	mandatory
	DESCRIPTION
		"The number of passes of the diagnostics tests to be run.
		The default value is 1."
	::= { cardEntry 57 }


cardDiagState OBJECT-TYPE
	SYNTAX	INTEGER {
--		inactive (0),
		active(1)
	}
	ACCESS	read-write
	STATUS	mandatory
	DESCRIPTION
		"The current state of the foreground diagnostics on this card."
	::= { cardEntry 58 }

cardDiagOptionStr OBJECT-TYPE
	SYNTAX	OCTET STRING
	ACCESS	read-write
	STATUS	mandatory
	DESCRIPTION
		"Optional parameters to the diagnostic."
	::= { cardEntry 59 }

cardDiagPasses OBJECT-TYPE
	SYNTAX	Counter
	ACCESS	read-only
	STATUS	mandatory
	DESCRIPTION
		"Number of successful diagnostic passes."
	::= { cardEntry 60 }

cardDiagFailures OBJECT-TYPE
	SYNTAX	Counter
	ACCESS	read-only
	STATUS	mandatory
	DESCRIPTION
		"Number of failed diagnostic passes."
	::= { cardEntry 61 }

cardDiagResultString OBJECT-TYPE
	SYNTAX	DisplayString
	ACCESS	read-only
	STATUS	mandatory
	DESCRIPTION
		"Description of last diagnostic failure."
	::= { cardEntry 62 }

cardFrameMemoryUtil OBJECT-TYPE
	SYNTAX	Gauge
	ACCESS	read-only
	STATUS	mandatory
	DESCRIPTION
		"The percentage of frame memory utilization on this intelligent card."
	::= { cardEntry 63 }

cardResetPram OBJECT-TYPE
	SYNTAX	INTEGER {
		reset-pram (1)
	}
	ACCESS	read-write
	STATUS	mandatory
	DESCRIPTION
		"Setting this to 1 causes a reset of PRAM on the corresponding
		card."
	::= { cardEntry 64 }

cardMemoryUtil OBJECT-TYPE
	SYNTAX	Gauge
	ACCESS	read-only
	STATUS	mandatory
	DESCRIPTION
		"The percentage of system memory utilization on this intelligent card."
	::= { cardEntry 65 }

cardFrameMemoryUsage OBJECT-TYPE
	SYNTAX	Gauge
	ACCESS	read-only
	STATUS	mandatory
	DESCRIPTION
		"The frame memory utilization, in terms of free bytes, for
		this intelligent card."
	::= { cardEntry 66 }

cardUpTime OBJECT-TYPE
	SYNTAX	TimeTicks
	ACCESS	read-only
	STATUS	mandatory
	DESCRIPTION
		"The time (in hundredths of a second) since this card was last
		booted."
	::= { cardEntry 67 }

cardPramChecksum OBJECT-TYPE
	SYNTAX	INTEGER
	ACCESS	read-only
	STATUS	mandatory
	DESCRIPTION
		" The PRAM checksum for this card."
	::= { cardEntry 68 }

cardPhysicalIndex OBJECT-TYPE
	SYNTAX	INTEGER
	ACCESS	read-only
	STATUS	mandatory
	DESCRIPTION
		" The physical slot id of this card."
	::= { cardEntry 69 }

cardExternalClockRate OBJECT-TYPE
	SYNTAX	INTEGER
	ACCESS	read-only
	STATUS	mandatory
	DESCRIPTION
		"The external clock rate for DSX1, T1 and E1 cards.  The
		value is specified in units of 8KHz and can range from 1 to 255."
	::= { cardEntry 70 }

cardShootState OBJECT-TYPE
	SYNTAX	INTEGER {
--		shoot-disabled (0),
		shoot-enabled  (1)
	}
	ACCESS	read-write
	STATUS	mandatory
	DESCRIPTION
		"Specifies whether the system monitor on the CP should shoot
		this card if it's unreachable. The default is enabled. The
		card index used in the binding refers to a physical card."
	::= { cardEntry 71 }


cardEraseAll OBJECT-TYPE
	SYNTAX	INTEGER {
		erase-all (1)
	}
	ACCESS	read-write
	STATUS	mandatory
	DESCRIPTION
		"When set to 1, erases program flash and PRAM on specified card."
	::= { cardEntry 72 }

cardAdminCapability OBJECT-TYPE
	SYNTAX	INTEGER {
		iop-frame-relay (1),
		iop-multi-service (2),
		iop-16meg-service (3),
		cp-basic (4),
		cp-30 (5),
		cp-plus (8),
		cp-40 (9),
		cp-50 (10),
		iom-fcp (11)
	}
	ACCESS	read-write
	STATUS	mandatory
	DESCRIPTION
		"The desired capability of the card"
	::= { cardEntry 73 }

cardOperCapability OBJECT-TYPE
	SYNTAX	INTEGER {
		iop-frame-relay (1),
		iop-multi-service (2),
		iop-16meg-service (3),
		cp-basic (4),
		cp-30 (5),
		cp-plus (8),
		cp-40 (9),
		cp-50 (10),
		iom-fcp (11)
	}
	ACCESS	read-only
	STATUS	mandatory
	DESCRIPTION
		"The actual capability of the card"
	::= { cardEntry 74 }

cardISDNswtype OBJECT-TYPE
	SYNTAX	INTEGER {
		att-4ess (1),
		att-5ess (2),
		dms100	(3)
	}
	ACCESS	read-write
	STATUS	mandatory
	DESCRIPTION
		"Specifies the ISDN central office switch type for the card."
	::= { cardEntry 75 }

cardCpuFgUtil OBJECT-TYPE
	SYNTAX	Gauge
	ACCESS	read-only
	STATUS	mandatory
	DESCRIPTION
		"The CPU foreground utilization percentage for packet
		processing on this intelligent card."
	::= { cardEntry 76 }

cardTrkProtState OBJECT-TYPE
	SYNTAX	INTEGER {
		enabled (1),
		disabled (2)
	}
	ACCESS	read-write
	STATUS	mandatory
	DESCRIPTION
		"Control for issue of Link Trunk Protocol request frames.  If
		set to disabled, the issue of trunk protocol requests is
		blocked for all trunks on this card."
	::= { cardEntry 77 }

cardISDNSigType OBJECT-TYPE
	SYNTAX	INTEGER {
		no-nfas (1),
		nfas (2)
	}
	ACCESS	read-write
	STATUS	mandatory
	DESCRIPTION
		"Specifies whether the ISDN Signalling type is Associated or
		Non-Facility Associated Signalling"
	::= { cardEntry 78 }

cardISDNChanId OBJECT-TYPE
	SYNTAX	INTEGER {
		exclusive (1),
		preferred (2)
	}
	ACCESS	read-write
	STATUS	mandatory
	DESCRIPTION
		"Specifies whether Channel ID assignment is performed by the
		central office switch or the 9000 - Exclusive (central office)
		Preferred (9000)"
	::= { cardEntry 79 }

cardTransmitClockConfig OBJECT-TYPE
	SYNTAX	INTEGER {
		system-primary-clock (1),
		system-secondary-clock (2),
		system-primary-secondary-clock (3),
		free-running-clock (4),
                e1-G703sec10-clock (5),
                e1-network-clock (6)
 	}
	ACCESS	read-write
	STATUS	mandatory
	DESCRIPTION
		"The transmit clock source for timing section of the card"
	::= { cardEntry 80 }

cardTransmitClockSwitchOver OBJECT-TYPE
	SYNTAX	INTEGER {
		enable (1),
		disable (2)
	}
	ACCESS	read-write
	STATUS	mandatory
	DESCRIPTION
		"Enable/disable automatic transmit clock source switch-over
		 once a failed clock reference has recovered."
	::= { cardEntry 81 }

cardTransmitClockStatus OBJECT-TYPE
	SYNTAX	INTEGER {
		in-synchronization (1),
		loss-of-synchronization (2)
	}
	ACCESS	read-only
	STATUS	mandatory
	DESCRIPTION
		"The transmit clock PLL synchronization status of the card"
	::= { cardEntry 82 }

cardSystemPrimaryClockPortConfig OBJECT-TYPE
	SYNTAX	INTEGER
	ACCESS	read-write
	STATUS	mandatory
	DESCRIPTION
		"The port number (1-x) on the card that specifies the system
		 primary clock source. A zero specifies no port"
	::= { cardEntry 83 }

cardSystemPrimaryClockStatus OBJECT-TYPE
	SYNTAX	INTEGER {
		normal	(1),
		failure (2)
	}
	ACCESS	read-only
	STATUS	mandatory
	DESCRIPTION
		"The system primary clock status as detected on the card.
		 On the BIO, this refers to the Timing Module 1 clock
		 status as detected by the BIO."
	::= { cardEntry 84 }

cardSystemSecondaryClockPortConfig OBJECT-TYPE
	SYNTAX	INTEGER
	ACCESS	read-write
	STATUS	mandatory
	DESCRIPTION
		"The port number (1 to x) on the card that specifies the system
		 secondary clock source.  A zero specifies no port"
	::= { cardEntry 85 }

cardSystemSecondaryClockStatus OBJECT-TYPE
	SYNTAX	INTEGER {
		normal	(1),
		failure (2)
	}
	ACCESS	read-only
	STATUS	mandatory
	DESCRIPTION
		"The system secondary clock status as detected on the card.
		 On the BIO, this refers to the Timing Module 2 clock
		 status as detected by the BIO."
	::= { cardEntry 86}

cardInCells OBJECT-TYPE
	SYNTAX	Counter
	ACCESS	read-only
	STATUS	mandatory
	DESCRIPTION
		"The total number of cells received on this card."
	::= { cardEntry 87 }

cardInErrorCells OBJECT-TYPE
	SYNTAX	Counter
	ACCESS	read-only
	STATUS	mandatory
	DESCRIPTION
		"The total number of cells received on this card with HEC error."
	::= { cardEntry 88 }

cardInErrorVPIVCI OBJECT-TYPE
	SYNTAX	Counter
	ACCESS	read-only
	STATUS	mandatory
	DESCRIPTION
		"The total number of cells received with HEC invalid VPI, VCI."
	::= { cardEntry 89 }

cardOutCells OBJECT-TYPE
	SYNTAX	Counter
	ACCESS	read-only
	STATUS	mandatory
	DESCRIPTION
		"The total number of cells transmitted out of this card"
	::= { cardEntry 90 }

cardOutDiscardCells OBJECT-TYPE
	SYNTAX	Counter
	ACCESS	read-only
	STATUS	mandatory
	DESCRIPTION
		"The total number of cells discarded due to congestion on
		 this card"
	::= { cardEntry 91 }

cardQOSQueueSize OBJECT-TYPE
	SYNTAX	INTEGER {
		cell-8K (1),
		cell-24K (2)
	}
	ACCESS	read-only
	STATUS	mandatory
	DESCRIPTION
		"The ATM QOS queue size (per cell) of each port on the card"
	::= { cardEntry 92 }

cardLastErrorPort OBJECT-TYPE
	SYNTAX	INTEGER
	ACCESS	read-only
	STATUS	mandatory
	DESCRIPTION
		"The port number (1 to x) of the last cell with invalid cell
		 header on the card"
	::= { cardEntry 93 }

cardLastErrorVPI OBJECT-TYPE
	SYNTAX	INTEGER
	ACCESS	read-only
	STATUS	mandatory
	DESCRIPTION
		"The VPI of the last cell with invalid cell header on the card"
	::= { cardEntry 94 }

cardLastErrorVCI OBJECT-TYPE
	SYNTAX	INTEGER
	ACCESS	read-only
	STATUS	mandatory
	DESCRIPTION
		"The VCI of the last cell with invalid cell header on the card"
	::= { cardEntry 95 }

cardSystemPrimaryClockModeConfig OBJECT-TYPE
	SYNTAX	INTEGER {
		line-rate (1),
		plcp-mode (2)
	}
	ACCESS	read-write
	STATUS	mandatory
	DESCRIPTION
		"The system primary clock mode. PLCP is for DS3 port only"
	::= { cardEntry 96 }

cardSystemSecondaryClockModeConfig OBJECT-TYPE
	SYNTAX	INTEGER {
		line-rate (1),
		plcp-mode (2)
	}
	ACCESS	read-write
	STATUS	mandatory
	DESCRIPTION
		"The system secondary clock mode. PLCP is for DS3 port only"
	::= { cardEntry 97 }

cardNFBDEStatus OBJECT-TYPE
	SYNTAX	INTEGER {
		cleared (1),
		not-cleared (2)
	}
	ACCESS	read-write
	STATUS	mandatory
	DESCRIPTION
		"Non Fatal Background Diagnostic Error Status"
	::= { cardEntry 98 }

cardProductCode OBJECT-TYPE
	SYNTAX	DisplayString
	ACCESS	read-only
	STATUS	mandatory
	DESCRIPTION
		"This card's product code."
	::= { cardEntry 99 }

cardMfgPN OBJECT-TYPE
	SYNTAX	DisplayString
	ACCESS	read-only
	STATUS	mandatory
	DESCRIPTION
		"This card's manufacturing part number."
	::= { cardEntry 100 }

cardTotalUpTime OBJECT-TYPE
	SYNTAX	TimeTicks
	ACCESS	read-only
	STATUS	mandatory
	DESCRIPTION
		"This card's total accumulated up time, in hours."
	::= { cardEntry 101 }

cardIOAType OBJECT-TYPE
	SYNTAX	INTEGER {
	      spa (1),			-- Topaz SPA, redundant
	      toc3-4 (2),		-- Topaz OC3/STM1 MM 4-port SC, non-redundant
	      tstm1-4 (3),		-- Topaz STM-1 MM 4-port SC, non-redundant OBSOLETE, use (2)
	      tds3-8 (4),		-- Topaz DS3 8-port, non-redundant
	      te3-8 (5),		-- Topaz E3 8-port, non-redundant
	      toc3-smfir-n-4 (6),	-- Topaz OC3/STM1 SMF, intermediate reach, 4-port SC, non-redundant
	      toc3-smfir-r-4 (7),	-- Topaz OC3/STM1 SMF, intermediate reach, 4-port SC, redundant
	      toc3-mm-r-4 (8),		-- Topaz OC3/STM1 MM, 4-port SC, redundant
	      toc3-smflr-n-4 (9),	-- Topaz OC3/STM1 SMF, long reach, 4-port SC, non-redundant
	      toc3-smflr-r-4 (10),	-- Topaz OC3/STM1 SMF, long reach, 4-port SC, redundant
	      tstm1-smfir-n-4 (11),	-- Topaz STM-1 SMF, intermediate reach, 4-port SC, non-redundant OBSOLETE, use (6)
	      tstm1-smfir-r-4 (12),	-- Topaz STM-1 SMF, intermediate reach, 4-port SC, redundant OBSOLETE, use (7)
	      tstm1-mm-r-4 (13),	-- Topaz STM-1 MM, 4-port SC, redundant OBSOLETE, use (8)
	      tstm1-smflr-n-4 (14),	-- Topaz STM-1 SMF, long reach, 4-port SC, non-redundant OBSOLETE, use (9)
	      tstm1-smflr-r-4 (15),	-- Topaz STM-1 SMF, long reach, 4-port SC, redundant OBSOLETE, use (10)
	      tds3-r-8 (16),		-- Topaz DS3 8-port, redundant
	      te3-r-8 (17),		-- Topaz E3 8-port, redundant
	      hssi-n (18),		-- BSTDX HSSI non-redundant IOA
	      hssi-r (19),		-- BSTDX HSSI redundant IOA
	      toc12-smf-n-1(21),	-- Topaz OC12/STM4 SMF non-redundant IOA
              tads1-t1-n-8 (22),        -- Topaz T1 ATM - T1 non-redundant IOA
              tads1-t1-r-8 (23),        -- Topaz T1 ATM - T1 redundant IOA
              tads1-e1-75-n-8 (24),     -- Topaz T1 ATM - E1 75 ohm non-redund IOA
              tads1-e1-75-r-8 (25),     -- Topaz T1 ATM - E1 75 ohm redundant IOA
              tads1-e1-120-n-8 (26),    -- Topaz T1 ATM - E1 120 ohm non-red IOA
              tads1-e1-120-r-8 (27),    -- Topaz T1 ATM - E1 120 ohm redundant IOA
              tads1-j2-75-n-8 (28),     -- Topaz T1 ATM - J2 75 ohm non-red IOA
              tads1-j2-75-r-8 (29),     -- Topaz T1 ATM - J2 75 ohm redundant IOA
              tads1-j2-120-n-8 (30),    -- Topaz T1 ATM - J2 120 ohm non-red IOA
              tads1-j2-120-r-8 (31),    -- Topaz T1 ATM - J2 120 ohm redundant IOA
	      bCS-DS3-n-1 (35),		-- BSTDX DS3 (CS) non redundant IOA
	      bCS-DS3-r-1 (36),		-- BSTDX DS3 (CS) redundant IOA
	      bIWU-OC3-mm-n-1 (37),	-- BSTDX OC3 (IWU) multimode non redundant IOA
	      bIWU-OC3-smfir-n-1 (38),	-- BSTDX OC3 (IWU) single mode intermediate reach non-redundant IOA
	      toc3-stm1copper-n-4 (39),	-- Topaz OC3/STM1 Copper, 4-port SC, non-redundant
	      toc3-stm1copper-r-4 (40),	-- Topaz OC3/STM1 Copper, 4-port SC, redundant
	      spa-universal (32),	-- Topaz Universal SPA (E1/T1)
              nplus1-chassis (41),       -- N+1 Chassis Indicator
	      toc12-smflr-n-1(42),	-- Topaz OC12/STM4 SMF long reach non-redundant IOA
	      npa-universal (43),	-- Garnet Universal NPA
	      bIWU-OC3-bumm-1 (44),	-- BSTDX OC3 (IWU) base unit multimode redundant IOA
	      bIWU-OC3-bumm-smfir-1 (45),	-- BSTDX OC3 (IWU) base unit single mode intermediate reach redundant IOA
	      bIWU-OC3-trm-mm-1 (46),	-- BSTDX OC3 (IWU) tranceiver module multimode redundant IOA
	      bIWU-OC3-trm-smfir-1 (47),	-- BSTDX OC3 (IWU) tranceiver module single mode intermediate reach redundant IOA
	      uio-v35 (48), 		-- BSTDX UIO-V35 IOA
	      uio-x21 (49),		-- BSTDX UIO-X21 IOA
              bds1-e1-bnc-n-12 (50),    -- BSTDX 12 port - E1 75 ohm non-redund IOA
              bds1-e1-bnc-r-12 (51),    -- BSTDX 12 port - E1 75 ohm redundant IOA
              bds1-e1-db15-n-12 (52),   -- BSTDX 12 port - E1 120 ohm non-red IOA
              bds1-e1-db15-r-12 (53),   -- BSTDX 12 port - E1 120 ohm redundant IOA
	      bCS-E3-n-1 (54),		-- BSTDX E3 (CS) non redundant IOA
	      bCS-E3-r-1 (55),		-- BSTDX E3 (CS) redundant IOA
	      bCP-1-m (56), 		-- BSTDX CP redundant IOA with MIM
	      bCP-1-o (57), 		-- BSTDX CP redundant IOA before MIM
	      be1-atm-75-n-12 (58),	-- BSTDX E1 ATM 75 ohm non-redundant
	      be1-atm-75-r-12 (59),	-- BSTDX E1 ATM 75 ohm redundant
	      be1-atm-120-n-12 (60),	-- BSTDX E1 ATM 120 ohm non-redundant
	      be1-atm-120-r-12 (61),	-- BSTDX E1 ATM 120 ohm redundant
	      bt1-atm-100-n-12 (62),	-- BSTDX T1 ATM 100 ohm non-redundant
	      bt1-atm-100-r-12 (63),	-- BSTDX T1 ATM 100 ohm redundant
              bds1-e1-rj48h-n-12 (64),  -- BSTDX 12 port - E1 120 ohm RJ48 non-red IOA
              bds1-e1-rj48h-r-12 (65),   -- BSTDX 12 port - E1 120 ohm RJ48 red IOA
	      gx550-backplane (66),	 -- Garnet backplane MIM id
	      cbx500-ether-n-4 (67),    -- CBX500 4 port ethernet IOA, non-redund
	      cbx500-ds3-n-6 (68),      -- CBX500 6 port DS3 IOA, non-redund
	      bstdx9000-ether-n-2 (69), -- BSTDX9000 2 port ethernet IOA, non-redund
	      bio550-oc3-smfir (70),    -- Garnet OC3 SMF IR
	      bio550-oc3-smflr (71),    -- Garnet OC3 SMF LR
	      bio550-oc3-mmf (72),      -- Garnet OC3 MMF
	      bio550-oc12-smfir (73),   -- Garnet OC12 SMF IR
	      bio550-oc12-smflr (74),   -- Garnet OC12 SMF LR
	      bio550-oc12-mmf (75)      -- Garnet OC12 MMF
			}
	ACCESS	read-only
	STATUS	mandatory
	DESCRIPTION
		"The type of IOA attached to this card."
	::= { cardEntry 102 }

cardIOAHwRev OBJECT-TYPE
	SYNTAX	DisplayString
	ACCESS	read-only
	STATUS	mandatory
	DESCRIPTION
		"The attached IOA's hardware revision."
	::= { cardEntry 103 }

cardIOASerial OBJECT-TYPE
	SYNTAX	DisplayString
	ACCESS	read-only
	STATUS	mandatory
	DESCRIPTION
		"The attached IOA's serial number."
	::= { cardEntry 104 }

cardIOAProductCode OBJECT-TYPE
	SYNTAX	DisplayString
	ACCESS	read-only
	STATUS	mandatory
	DESCRIPTION
		"The attached IOA's product code."
	::= { cardEntry 105 }

cardIOAMfgPN OBJECT-TYPE
	SYNTAX	DisplayString
	ACCESS	read-only
	STATUS	mandatory
	DESCRIPTION
		"The attached IOA's manufacturing part number."
	::= { cardEntry 106 }

cardDS0Support OBJECT-TYPE
	SYNTAX	INTEGER {
		ds0-lpbk-not-supported	   (1),
		ds0-lpbk-supported	   (2)
	}
	ACCESS	read-only
	STATUS	mandatory
	DESCRIPTION
		"Some B-Stdx T1 boards do not support lpbk."
	::= { cardEntry 107 }


cardDiagParamId OBJECT-TYPE
	SYNTAX	INTEGER
	ACCESS	read-write
	STATUS	mandatory
	DESCRIPTION
		"Parameter identifier for internal diagnostics."
	::= { cardEntry 108 }


cardDiagParamValue OBJECT-TYPE
	SYNTAX	INTEGER
	ACCESS	read-write
	STATUS	mandatory
	DESCRIPTION
		"Value assigned to parameter specified by cardDiagParamId."
	::= { cardEntry 109 }

cardBulkStatsPeakCapability OBJECT-TYPE
	SYNTAX INTEGER {
		disabled (1),
		enabled (2)
	}
	ACCESS read-write
	STATUS mandatory
	DESCRIPTION
		"Configures capability to collect peak 5-minute statistics.
		 Capability change takes effect upon IOM reboot."
	::= { cardEntry 110 }

cardBulkStatsTotalCapability OBJECT-TYPE
	SYNTAX INTEGER {
		disabled (1),
		enabled (2)
	}
	ACCESS read-write
	STATUS mandatory
	DESCRIPTION
		"Configures capability to collect total statistics.
		 Capability change takes effect upon IOM reboot."
	::= { cardEntry 111 }

cardBulkStatsPeakEnable OBJECT-TYPE
	SYNTAX INTEGER {
		disabled (1),
		enabled (2)
	}
	ACCESS read-write
	STATUS mandatory
	DESCRIPTION
		"Reflects the operational state of the peak 5-minute
		 statistic collection on an IOM. For this setting to be
		 enabled, the respective capability must be enabled."
	::= { cardEntry 112 }

cardBulkStatsTotalEnable OBJECT-TYPE
	SYNTAX INTEGER {
		disabled (1),
		enabled (2)
	}
	ACCESS read-write
	STATUS mandatory
	DESCRIPTION
		"Reflects the operational state of the total statistic
		 collection on an IOM. For this setting to be enabled,
		 the respective capability must be enabled."
	::= { cardEntry 113 }

cardBulkStatsBaseCollectPeriod OBJECT-TYPE
	SYNTAX INTEGER (15..1440)
	ACCESS read-write
	STATUS mandatory
	DESCRIPTION
		"Configures base collection period for bulk statistics
		 on an IOM in minutes. Only the following values are
		 allowed: 15, 20, 30, 60, 120, 180, 240, 360, 720, 1440.
		 The default value is 60."
	::= { cardEntry 114 }

cardNrtsHwRev OBJECT-TYPE
	SYNTAX	INTEGER
	ACCESS	read-only
	STATUS	mandatory
	DESCRIPTION
		"Hardware revision of the NRTS processor."
	::= { cardEntry 115 }

cardNrtsOutCellBufSize OBJECT-TYPE
	SYNTAX	INTEGER
	ACCESS	read-only
	STATUS	mandatory
	DESCRIPTION
		"The size of the NRTS output cell buffer."
	::= { cardEntry 116 }

cardNrtsOperState OBJECT-TYPE
	SYNTAX	INTEGER {
		absent (1),
		down (2),
		up (3)
	}
	ACCESS	read-only
	STATUS	mandatory
	DESCRIPTION
		"The operational status of the NRTS processor."
	::= { cardEntry 117 }

cardNrtsAdminState OBJECT-TYPE
	SYNTAX	INTEGER {
		disabled (1),
		enabled (2)
	}
	ACCESS	read-write
	STATUS	mandatory
	DESCRIPTION
		"The admin status of the NRTS processor."
	::= { cardEntry 118 }

cardNrtsCcrmProtocolId OBJECT-TYPE
	SYNTAX	INTEGER
	ACCESS	read-write
	STATUS	mandatory
	DESCRIPTION
		"The protocol ID field for the CCRM cells. Must be different
		 from the BCM protocol ID. Default is 6."
	::= { cardEntry 119 }

cardNrtsBcmProtocolId OBJECT-TYPE
	SYNTAX	INTEGER
	ACCESS	read-write
	STATUS	mandatory
	DESCRIPTION
		"The protocol ID field for the BCM cells. Must be different
		 from the CCRM protocol ID. Default is 5."
	::= { cardEntry 120 }

cardNrtsRmGenInterval OBJECT-TYPE
	SYNTAX	INTEGER
	ACCESS	read-write
	STATUS	mandatory
	DESCRIPTION
		"The RM cell generation interval in ms. Minimum is 30,
		 maximum is 250, default is 100."
	::= { cardEntry 121 }

cardNrtsIdleCktThresh OBJECT-TYPE
	SYNTAX	INTEGER
	ACCESS	read-write
	STATUS	mandatory
	DESCRIPTION
		"The number of RM cell generation intervals with no cell
		 reception upon which the circuit is declared idle.
		 Minimum is 1, maximum is 8, default is 8."
	::= { cardEntry 122 }

cardNrtsVbrNrtManage OBJECT-TYPE
	SYNTAX	INTEGER {
		no (1),
		yes (2)
	}
	ACCESS	read-write
	STATUS	mandatory
	DESCRIPTION
		"Indicates whether VBR NRT traffic should be managed by
		 the NRTS processor."
	::= { cardEntry 123 }

cardNrtsIcrFact OBJECT-TYPE
	SYNTAX	INTEGER
	ACCESS	read-write
	STATUS	mandatory
	DESCRIPTION
		"A factor used to calculate the Initial Cell Rate for a circuit
		 from its MCR and PCR."
	::= { cardEntry 124 }

cardNrtsMcastDiscardThresh OBJECT-TYPE
	SYNTAX	INTEGER
	ACCESS	read-write
	STATUS	mandatory
	DESCRIPTION
		"A NRTS discard threshold for the multicast circuits."
	::= { cardEntry 125 }

cardNrtsMcastDiscardCount OBJECT-TYPE
	SYNTAX	Counter
	ACCESS	read-only
	STATUS	mandatory
	DESCRIPTION
		"A NRTS discard counter for the multicast circuits."
	::= { cardEntry 126 }

cardAdminIOAType OBJECT-TYPE
	SYNTAX	INTEGER {
	      spa (1),			-- Topaz SPA, redundant
	      toc3-4 (2),		-- Topaz OC3/STM1 MM 4-port SC, non-redundant
	      tstm1-4 (3),		-- Topaz STM-1 MM 4-port SC, non-redundant OBSOLETE, use (2)
	      tds3-8 (4),		-- Topaz DS3 8-port, non-redundant
	      te3-8 (5),		-- Topaz E3 8-port, non-redundant
	      toc3-smfir-n-4 (6),	-- Topaz OC3/STM1 SMF, intermediate reach, 4-port SC, non-redundant
	      toc3-smfir-r-4 (7),	-- Topaz OC3/STM1 SMF, intermediate reach, 4-port SC, redundant
	      toc3-mm-r-4 (8),		-- Topaz OC3/STM1 MM, 4-port SC, redundant
	      toc3-smflr-n-4 (9),	-- Topaz OC3/STM1 SMF, long reach, 4-port SC, non-redundant
	      toc3-smflr-r-4 (10),	-- Topaz OC3/STM1 SMF, long reach, 4-port SC, redundant
	      tstm1-smfir-n-4 (11),	-- Topaz STM-1 SMF, intermediate reach, 4-port SC, non-redundant OBSOLETE, use (6)
	      tstm1-smfir-r-4 (12),	-- Topaz STM-1 SMF, intermediate reach, 4-port SC, redundant OBSOLETE, use (7)
	      tstm1-mm-r-4 (13),	-- Topaz STM-1 MM, 4-port SC, redundant OBSOLETE, use (8)
	      tstm1-smflr-n-4 (14),	-- Topaz STM-1 SMF, long reach, 4-port SC, non-redundant OBSOLETE, use (9)
	      tstm1-smflr-r-4 (15),	-- Topaz STM-1 SMF, long reach, 4-port SC, redundant OBSOLETE, use (10)
	      tds3-r-8 (16),		-- Topaz DS3 8-port, redundant
	      te3-r-8 (17),		-- Topaz E3 8-port, redundant
	      hssi-n (18),		-- BSTDX HSSI non-redundant IOA
	      hssi-r (19),		-- BSTDX HSSI redundant IOA
	      toc12-smf-n-1(21),	-- Topaz OC12/STM4 SMF non-redundant IOA
              tads1-t1-n-8 (22),        -- Topaz T1 ATM - T1 non-redundant IOA
              tads1-t1-r-8 (23),        -- Topaz T1 ATM - T1 redundant IOA
              tads1-e1-75-n-8 (24),     -- Topaz T1 ATM - E1 75 ohm non-redund IOA
              tads1-e1-75-r-8 (25),     -- Topaz T1 ATM - E1 75 ohm redundant IOA
              tads1-e1-120-n-8 (26),    -- Topaz T1 ATM - E1 120 ohm non-red IOA
              tads1-e1-120-r-8 (27),    -- Topaz T1 ATM - E1 120 ohm redundant IOA
              tads1-j2-75-n-8 (28),     -- Topaz T1 ATM - J2 75 ohm non-red IOA
              tads1-j2-75-r-8 (29),     -- Topaz T1 ATM - J2 75 ohm redundant IOA
              tads1-j2-120-n-8 (30),    -- Topaz T1 ATM - J2 120 ohm non-red IOA
              tads1-j2-120-r-8 (31),    -- Topaz T1 ATM - J2 120 ohm redundant IOA
	      bCS-DS3-n-1 (35),		-- BSTDX DS3 (CS) non redundant IOA
	      bCS-DS3-r-1 (36),		-- BSTDX DS3 (CS) redundant IOA
	      bIWU-OC3-mm-n-1 (37),	-- BSTDX OC3 (IWU) multimode non redundant IOA
	      bIWU-OC3-smfir-n-1 (38),	-- BSTDX OC3 (IWU) single mode intermediate reach non-redundant IOA
	      toc3-stm1copper-n-4 (39),	-- Topaz OC3/STM1 Copper, 4-port SC, non-redundant
	      toc3-stm1copper-r-4 (40),	-- Topaz OC3/STM1 Copper, 4-port SC, redundant
	      spa-universal (32),	-- Topaz Universal SPA (E1/T1)
              nplus1-chassis (41),       -- N+1 Chassis Indicator
	      toc12-smflr-n-1(42),	-- Topaz OC12/STM4 SMF long reach non-redundant IOA
	      npa-universal (43),	-- Garnet Universal NPA
	      bIWU-OC3-bumm-1 (44),	-- BSTDX OC3 (IWU) base unit multimode redundant IOA
	      bIWU-OC3-bumm-smfir-1 (45),	-- BSTDX OC3 (IWU) base unit single mode intermediate reach redundant IOA
	      bIWU-OC3-trm-mm-1 (46),	-- BSTDX OC3 (IWU) tranceiver module multimode redundant IOA
	      bIWU-OC3-trm-smfir-1 (47),	-- BSTDX OC3 (IWU) tranceiver module single mode intermediate reach redundant IOA
	      uio-v35 (48), 		-- BSTDX UIO-V35 IOA
	      uio-x21 (49),		-- BSTDX UIO-X21 IOA
              bds1-e1-bnc-n-12 (50),     -- BSTDX 12 port - E1 75 ohm non-redund IOA
              bds1-e1-bnc-r-12 (51),     -- BSTDX 12 port - E1 75 ohm redundant IOA
              bds1-e1-db15-n-12 (52),    -- BSTDX 12 port - E1 120 ohm non-red IOA
              bds1-e1-db15-r-12 (53),    -- BSTDX 12 port - E1 120 ohm redundant IOA
	      bCS-E3-n-1 (54),		-- BSTDX E3 (CS) non redundant IOA
	      bCS-E3-r-1 (55),		-- BSTDX E3 (CS) redundant IOA
	      bCP-1-m (56), 		-- BSTDX CP redundant IOA with MIM
	      bCP-1-o (57), 		-- BSTDX CP redundant IOA before MIM
	      be1-atm-75-n-12 (58),	-- BSTDX E1 ATM 75 ohm non-redundant
	      be1-atm-75-r-12 (59),	-- BSTDX E1 ATM 75 ohm redundant
	      be1-atm-120-n-12 (60),	-- BSTDX E1 ATM 120 ohm non-redundant
	      be1-atm-120-r-12 (61),	-- BSTDX E1 ATM 120 ohm redundant
	      bt1-atm-100-n-12 (62),	-- BSTDX T1 ATM 100 ohm non-redundant
	      bt1-atm-100-r-12 (63),	-- BSTDX T1 ATM 100 ohm redundant
              bds1-e1-rj48h-n-12 (64),  -- BSTDX 12 port - E1 120 ohm RJ48 non-red IOA
              bds1-e1-rj48h-r-12 (65),   -- BSTDX 12 port - E1 120 ohm RJ48 red IOA
	      cbx500-ether-n-4 (67),    -- CBX500 4 port ethernet IOA, non-redund
	      cbx500-ds3-n-6 (68),      -- CBX500 6 port DS3 IOA, non-redund
	      bstdx9000-ether-n-2 (69), -- BSTDX9000 2 port ethernet IOA, non-redund
	      bio550-oc3-smfir (70),    -- Garnet OC3 SMF IR
              bio550-oc3-smflr (71),    -- Garnet OC3 SMF LR
              bio550-oc3-mmf (72),      -- Garnet OC3 MMF
              bio550-oc12-smfir (73),   -- Garnet OC12 SMF IR
              bio550-oc12-smflr (74),   -- Garnet OC12 SMF LR
              bio550-oc12-mmf (75)      -- Garnet OC12 MMF
	}
	ACCESS	read-write
	STATUS	mandatory
	DESCRIPTION
		"The type of IOA attached to this card viewed from NMS."
	::= { cardEntry 127 }

cardNrtsMcastRate OBJECT-TYPE
	SYNTAX	INTEGER
	ACCESS	read-write
	STATUS	mandatory
	DESCRIPTION
		"The NRTS shaping rate for multicast circuits as a fraction of
		the line rate."
	::= { cardEntry 128 }

cardMonStatus OBJECT-TYPE
        SYNTAX  INTEGER {
                enable (1),             -- enable mon960
                disable(2)              -- disable mon960
                }
	ACCESS	read-write
	STATUS	mandatory
	DESCRIPTION
		"Set MON960 status, default(1) -- enable, 2 -- disable."
	::= { cardEntry 129 }

cardImageSetA OBJECT-TYPE
	SYNTAX DisplayString
	ACCESS read-only
	STATUS  mandatory
	DESCRIPTION
		"The details of Image Set A. The elements of each
		image are space delimited and include Part Number,
		Revision, Size and Description. The details of each
		image are linefeed delimited."
	::= { cardEntry 130 }

cardImageSetB OBJECT-TYPE
        SYNTAX DisplayString
        ACCESS read-only
        STATUS  mandatory
        DESCRIPTION
		"The details of Image Set B. The elements of each
		image are space delimited and include Part Number,
		Revision, Size and Description. The details of each
		image are linefeed delimited."	::= { cardEntry 131 }

cardMacAddress OBJECT-TYPE
	SYNTAX DisplayString
	ACCESS read-only
	STATUS mandatory
	DESCRIPTION
		"ethernet MAC address of the card if there is an ethernet
		interface. Currently only CP cards may have ethernet.
		Cards without ethernet return 0 length octet string."
	::= { cardEntry 132 }

cardFlashRev OBJECT-TYPE
	SYNTAX	DisplayString
	ACCESS	read-only
	STATUS	mandatory
	DESCRIPTION
		"The boot flash rev number."
	::= { cardEntry 133 }

cardRequiredCapabilityBitmask OBJECT-TYPE
	SYNTAX  INTEGER {
		aps-one-plus-one-support (1),
		holdover-support (2),
		vp-shaping (4),
		fe-capability (8)
	}
	ACCESS	read-only
	STATUS	mandatory
	DESCRIPTION
		"Bitmask indicating this cards' required capabilities based on
		configured features.  A bit is set to one if the corresponding
		capability is required.  This variable is a bitmask so only
		power-of-2 values can be assigned (1,2,4,8,16,etc.) ."
	::= { cardEntry 134 }

cardOperCapabilityBitmask OBJECT-TYPE
	SYNTAX  INTEGER {
		aps-one-plus-one-supported (1),
		holdover-supported (2),
		vp-shaping (4),
		fe-capability (8)
	}
	ACCESS	read-only
	STATUS	mandatory
	DESCRIPTION
		"Bitmask indicating this cards' actual capabilities. A bit is
		set to one if the corresponding capability is supported.
		This variable is a bitmask so only power-of-2 values can be
		assigned (1,2,4,8,16,etc.)."
	::= { cardEntry 135 }

cardDslModule OBJECT-TYPE
	SYNTAX  OCTET STRING
        ACCESS  read-write
        STATUS  mandatory
        DESCRIPTION
		"This is for Dynamic Software Loadl
		 You can type: ModuleName Version, ModuleName Version, ...
		 to load modules."
	::= { cardEntry 136 }


cardIPTableSize OBJECT-TYPE
	SYNTAX  INTEGER
        ACCESS  read-write
        STATUS  mandatory
        DESCRIPTION
		"The maximum number of IP routing table entries
		 supported by the card. If set to 0, routing table
		 size is assumed unlimited."
	::= { cardEntry 137 }


cardIPTableState OBJECT-TYPE
	SYNTAX	INTEGER {
		    normal (1),
		    marginal (2)
		}
        ACCESS  read-only
        STATUS  mandatory
        DESCRIPTION
		"State of the card's IP routing table. If set to
		 marginal, the routing table maximum size has
		 been exceeded. and all routes except management
		 prefixes have been discarded."
	::= { cardEntry 138 }

cardATMTcaInBufOverflowAlertPeriod OBJECT-TYPE
	SYNTAX  INTEGER
        ACCESS  read-write
        STATUS  mandatory
        DESCRIPTION
		"The atm tca ingress buffer overflow alert
		 period (in min)."
	DEFVAL { 15 }
	::= { cardEntry 139 }

cardATMTcaInBufOverflowThresh OBJECT-TYPE
	SYNTAX  INTEGER
        ACCESS  read-write
        STATUS  mandatory
        DESCRIPTION
		"The atm tca ingress buffer overflow threshold."
	DEFVAL { 1 }
	::= { cardEntry 140 }

cardATMTcaInInvalidVpiVciAlertPeriod OBJECT-TYPE
	SYNTAX  INTEGER
        ACCESS  read-write
        STATUS  mandatory
        DESCRIPTION
		"The atm tca ingress invalid vpi/vci alert
		 period (in min)."
	DEFVAL { 15 }
	::= { cardEntry 141 }

cardATMTcaInInvalidVpiVciThresh OBJECT-TYPE
	SYNTAX  INTEGER
        ACCESS  read-write
        STATUS  mandatory
        DESCRIPTION
		"The atm tca ingress invalid vpi/vci threshold."
	DEFVAL { 1 }
	::= { cardEntry 142 }

cardATMTcaInATMDCFullAlertPeriod OBJECT-TYPE
        SYNTAX  INTEGER
        ACCESS  read-write
        STATUS  mandatory
        DESCRIPTION
                "The atm tca ingress ATM DC full alert period (in min)."
        DEFVAL { 15 }
        ::= { cardEntry 143 }

cardATMTcaInATMDCFullThresh OBJECT-TYPE
        SYNTAX  INTEGER
        ACCESS  read-write
        STATUS  mandatory
        DESCRIPTION
                "The atm tca ingress ATM DC full threshold."
        DEFVAL { 1 }
        ::= { cardEntry 144 }

cardATMTcaEnable OBJECT-TYPE
	SYNTAX	INTEGER {
		    enable (1),
		    disable (2)
		}
        ACCESS  read-write
        STATUS  mandatory
        DESCRIPTION
		"The atm tca enable/disable."
	::= { cardEntry 145 }

cardATMTcaId OBJECT-TYPE
	SYNTAX  INTEGER {
		ingressBufferOverfloeC       	(1),
		ingressInvalidVpiVciC          	(2),
		ingressATMDCFullC        	(3),
		ingressBufferMsbPaeC		(4),
		ingressBufferHalfC		(5),
		ingressBufferMsbPafC		(6),
		egressCidLookupFailureC		(7)
		}
	ACCESS 	read-only
	STATUS  mandatory
	DESCRIPTION
		"This object identifies the the most recently declared card
                 ATM threshold crossing alert"
	::= { cardEntry 146 }

cardATMTcaECidLookupFailureAlertPeriod OBJECT-TYPE
	SYNTAX  INTEGER
        ACCESS  read-write
        STATUS  mandatory
        DESCRIPTION
		"The atm tca ingress buffer overflow alert
		 period (in min)."
	DEFVAL { 15 }
	::= { cardEntry 147 }

cardATMTcaECidLookupThresh OBJECT-TYPE
	SYNTAX  INTEGER
        ACCESS  read-write
        STATUS  mandatory
        DESCRIPTION
		"The atm tca ingress buffer overflow threshold."
	DEFVAL { 1 }
	::= { cardEntry 148 }

cardATMTcaSPPearlOCbrFailureAlertPeriod OBJECT-TYPE
        SYNTAX  INTEGER
        ACCESS  read-write
        STATUS  mandatory
        DESCRIPTION
                "The atm tca sp pearl overflow CBR alert
                 period (in min)."
        DEFVAL { 15 }
        ::= { cardEntry 149 }

cardATMTcaSPPearlOCbrThresh OBJECT-TYPE
        SYNTAX  INTEGER
        ACCESS  read-write
        STATUS  mandatory
        DESCRIPTION
                "The atm tca sp pearl overflow CBR threshold."
        DEFVAL { 1 }
        ::= { cardEntry 150 }

cardATMTcaSPPearlOAbrFailureAlertPeriod OBJECT-TYPE
        SYNTAX  INTEGER
        ACCESS  read-write
        STATUS  mandatory
        DESCRIPTION
                "The atm tca sp pearl overflow ABR alert
                 period (in min)."
        DEFVAL { 15 }
        ::= { cardEntry 151 }

cardATMTcaSPPearlOAbrThresh OBJECT-TYPE
        SYNTAX  INTEGER
        ACCESS  read-write
        STATUS  mandatory
        DESCRIPTION
                "The atm tca sp pearl overflow ABR threshold."
        DEFVAL { 1 }
        ::= { cardEntry 152 }

cardATMTcaSPPearlOVbr1FailureAlertPeriod OBJECT-TYPE
        SYNTAX  INTEGER
        ACCESS  read-write
        STATUS  mandatory
        DESCRIPTION
                "The atm tca sp pearl overflow VBR1 alert
                 period (in min)."
        DEFVAL { 15 }
        ::= { cardEntry 153 }

cardATMTcaSPPearlOVbr1Thresh OBJECT-TYPE
        SYNTAX  INTEGER
        ACCESS  read-write
        STATUS  mandatory
        DESCRIPTION
                "The atm tca sp pearl overflow VBR1 threshold."
        DEFVAL { 1 }
        ::= { cardEntry 154 }

cardATMTcaSPPearlOVbr2FailureAlertPeriod OBJECT-TYPE
        SYNTAX  INTEGER
        ACCESS  read-write
        STATUS  mandatory
        DESCRIPTION
                "The atm tca sp pearl overflow VBR2 alert
                 period (in min)."
        DEFVAL { 15 }
        ::= { cardEntry 155 }

cardATMTcaSPPearlOVbr2Thresh OBJECT-TYPE
        SYNTAX  INTEGER
        ACCESS  read-write
        STATUS  mandatory
        DESCRIPTION
                "The atm tca sp pearl overflow VBR2 threshold."
        DEFVAL { 1 }
        ::= { cardEntry 156 }

cardATMTcaSPPearlGCbrFailureAlertPeriod OBJECT-TYPE
        SYNTAX  INTEGER
        ACCESS  read-write
        STATUS  mandatory
        DESCRIPTION
                "The atm tca sp pearl congestion CBR alert
                 period (in min)."
        DEFVAL { 15 }
        ::= { cardEntry 157 }

cardATMTcaSPPearlGCbrThresh OBJECT-TYPE
        SYNTAX  INTEGER
        ACCESS  read-write
        STATUS  mandatory
        DESCRIPTION
                "The atm tca sp pearl congestion CBR threshold."
        DEFVAL { 1 }
        ::= { cardEntry 158 }

cardATMTcaSPPearlGAbrFailureAlertPeriod OBJECT-TYPE
        SYNTAX  INTEGER
        ACCESS  read-write
        STATUS  mandatory
        DESCRIPTION
                "The atm tca sp pearl congestion ABR alert
                 period (in min)."
        DEFVAL { 15 }
        ::= { cardEntry 159 }

cardATMTcaSPPearlGAbrThresh OBJECT-TYPE
        SYNTAX  INTEGER
        ACCESS  read-write
        STATUS  mandatory
        DESCRIPTION
                "The atm tca sp pearl congestion ABR threshold."
        DEFVAL { 1 }
        ::= { cardEntry 160 }

cardATMTcaSPPearlGVbr1FailureAlertPeriod OBJECT-TYPE
        SYNTAX  INTEGER
        ACCESS  read-write
        STATUS  mandatory
        DESCRIPTION
                "The atm tca sp pearl congestion VBR1 alert
                 period (in min)."
        DEFVAL { 15 }
        ::= { cardEntry 161 }

cardATMTcaSPPearlGVbr1Thresh OBJECT-TYPE
        SYNTAX  INTEGER
        ACCESS  read-write
        STATUS  mandatory
        DESCRIPTION
                "The atm tca sp pearl congestion VBR1 threshold."
        DEFVAL { 1 }
        ::= { cardEntry 162 }

cardATMTcaSPPearlGVbr2FailureAlertPeriod OBJECT-TYPE
        SYNTAX  INTEGER
        ACCESS  read-write
        STATUS  mandatory
        DESCRIPTION
                "The atm tca sp pearl congestion VBR2 alert
                 period (in min)."
        DEFVAL { 15 }
        ::= { cardEntry 163 }

cardATMTcaSPPearlGVbr2Thresh OBJECT-TYPE
        SYNTAX  INTEGER
        ACCESS  read-write
        STATUS  mandatory
        DESCRIPTION
                "The atm tca sp pearl congestion VBR2 threshold."
        DEFVAL { 1 }
        ::= { cardEntry 164 }

cardATMTcaSPEnable OBJECT-TYPE
        SYNTAX  INTEGER {
                    enable (1),
                    disable (2)
                }
        ACCESS  read-write
        STATUS  mandatory
        DESCRIPTION
                "The atm tca SP enable/disable."
        ::= { cardEntry 165 }

cardSPEFCIEnable OBJECT-TYPE
        SYNTAX  INTEGER {
                    enable (1),
                    disable (2)
                }
        ACCESS  read-write
        STATUS  mandatory
        DESCRIPTION
                "The atm EFCI marking enable/disable."
        ::= { cardEntry 166 }

cardSPClpEnable OBJECT-TYPE
        SYNTAX  INTEGER {
                    enable (1),
                    disable (2)
                }
        ACCESS  read-write
        STATUS  mandatory
        DESCRIPTION
                "The atm CLP-1 enable/disable."
        ::= { cardEntry 167 }

spATMTcaId OBJECT-TYPE
        SYNTAX  INTEGER {
                spBufferOverflowC1               (1),
                spBufferOverflowC2               (2),
                spBufferOverflowA1               (3),
                spBufferOverflowA2               (4),
                spBufferOverflowV11              (5),
                spBufferOverflowV12              (6),
                spBufferOverflowV21              (7),
                spBufferOverflowV22              (8),
                spBufferCongestionC1             (9),
                spBufferCongestionC2             (10),
                spBufferCongestionA1             (11),
                spBufferCongestionA2             (12),
                spBufferCongestionV11            (13),
                spBufferCongestionV12            (14),
                spBufferCongestionV21            (15),
                spBufferCongestionV22            (16)
                }
        ACCESS  read-only
        STATUS  mandatory
        DESCRIPTION
                "This object identifies the the most recently declared sp
                 ATM threshold crossing alert and first byte is used to indicate
		 the switching port number. i.e. sp 1 has spBufferOverflowC, then
		 the value is 0x1001"
        ::= { cardEntry 168 }

cardSubcardToRedundant OBJECT-TYPE
	SYNTAX	CardTypes
	ACCESS	read-write
	STATUS	mandatory
	DESCRIPTION
		"Commands the card to initiate an immediate protection
                 switch on the identified subcard that it controls. This
                 causes control to be switched from the active card to the
                 standby card."
	::= { cardEntry 169}

cardMemory5Usage OBJECT-TYPE
        SYNTAX  Gauge
        ACCESS  read-only
        STATUS  mandatory
        DESCRIPTION
                "The bank5 memory utilization, in terms of free bytes, for
                CP Oynx card only."
        ::= { cardEntry 170 }

cardSF1OperStatus OBJECT-TYPE
	SYNTAX	 CardStatuses
	ACCESS	read-only
	STATUS	mandatory
	DESCRIPTION
		"The current status of Switch Fabric 1 (GX550)."
	::= { cardEntry 171}

cardSF2OperStatus OBJECT-TYPE
	SYNTAX	 CardStatuses
	ACCESS	read-only
	STATUS	mandatory
	DESCRIPTION
		"The current status of Switch Fabric 2 (GX550)."
	::= { cardEntry 172}

cardTM1OperStatus OBJECT-TYPE
	SYNTAX	 CardStatuses
	ACCESS	read-only
	STATUS	mandatory
	DESCRIPTION
		"The current status of Timing Module 1 (GX550)."
	::= { cardEntry 173}

cardTM2OperStatus OBJECT-TYPE
	SYNTAX	 CardStatuses
	ACCESS	read-only
	STATUS	mandatory
	DESCRIPTION
		"The current status of Timing Module 2 (GX550)."
	::= { cardEntry 174}

cardMemStartLog OBJECT-TYPE
	SYNTAX  INTEGER {
-- disable
--		disable(0),	
-- enable
		enable(1)	
                }
        ACCESS  read-write
        STATUS  mandatory
        DESCRIPTION
                "Enable/Disable Memory log record, 1 -- enable, 0 -- disable."
	::= { cardEntry 175}

cardMemLogLevel OBJECT-TYPE
	SYNTAX  INTEGER
        ACCESS  read-write
        STATUS  mandatory
        DESCRIPTION
                "Set the Memory log level. Default 6 "
	::= { cardEntry 176}

cardMemClrLog OBJECT-TYPE
	SYNTAX  INTEGER {
-- disable
--		disable(0),	
-- clear Memory Log
		enable(1)	
                }
        ACCESS  read-write
        STATUS  mandatory
        DESCRIPTION
                "Enable/Disable Clear Memory log, 1 -- clear, 0 (default) --  not clear."
	::= { cardEntry 177}

cardValidSubcards OBJECT-TYPE
	SYNTAX INTEGER
	ACCESS read-only
	STATUS mandatory
	DESCRIPTION
		"The number of manageable subcards physically present in this card."
	::= { cardEntry 178}

cardClp0CbrThreshold OBJECT-TYPE
	SYNTAX INTEGER
	ACCESS read-write
	STATUS mandatory
	DESCRIPTION
		"The CLP 0 threshold for CBR queues in the card. Once queue
                 length reaches this threshold, all CLP 1 cells are discarded
		 until queue length falls below the threshold. "
	::= { cardEntry 179 }

cardClp01CbrThreshold OBJECT-TYPE
	SYNTAX INTEGER
	ACCESS read-write
	STATUS mandatory
	DESCRIPTION
		"The maximum length of CBR queues in the card. Once queue
		 length reaches this threshold, all cells are discarded
		 until queue length falls below this threshold."
	::= { cardEntry 180 }

cardClp0VbrRtThreshold OBJECT-TYPE
	SYNTAX INTEGER
	ACCESS read-write
	STATUS mandatory
	DESCRIPTION
		"The CLP 0 threshold for VBR RT queues in the card. Once queue
                 length reaches this threshold, all CLP 1 cells are discarded
		 until queue length falls below the threshold. "
	::= { cardEntry 181 }

cardClp01VbrRtThreshold OBJECT-TYPE
	SYNTAX INTEGER
	ACCESS read-write
	STATUS mandatory
	DESCRIPTION
		"The maximum length of VBR-RT queues in the card. Once queue
		 length reaches this threshold, all cells are discarded
		 until queue length falls below this threshold."
	::= { cardEntry 182 }

cardClp0VbrNrtThreshold OBJECT-TYPE
	SYNTAX INTEGER
	ACCESS read-write
	STATUS mandatory
	DESCRIPTION
		"The CLP 0 threshold for VBR NRT queues in the card. Once queue
                 length reaches this threshold, all CLP 1 cells are discarded
		 until queue length falls below the threshold. "
	::= { cardEntry 183 }

cardClp01VbrNrtThreshold OBJECT-TYPE
	SYNTAX INTEGER
	ACCESS read-write
	STATUS mandatory
	DESCRIPTION
		"The maximum length of VBR-NRT queues in the card. Once queue
		 length reaches this threshold, all cells are discarded
		 until queue length falls below this threshold."
	::= { cardEntry 184 }

cardClp0UAbrThreshold OBJECT-TYPE
	SYNTAX INTEGER
	ACCESS read-write
	STATUS mandatory
	DESCRIPTION
		"The CLP 0 threshold for ABR/UBR queues in the card. Once queue
                 length reaches this threshold, all CLP 1 cells are discarded
		 until queue length falls below the threshold. "
	::= { cardEntry 185 }

cardClp01UAbrThreshold OBJECT-TYPE
	SYNTAX INTEGER
	ACCESS read-write
	STATUS mandatory
	DESCRIPTION
		"The maximum length of UBR/ABR queues in the card. Once queue
		 length reaches this threshold, all cells are discarded
		 until queue length falls below this threshold."
	::= { cardEntry 186 }

cardControlMessagesFromBus OBJECT-TYPE
	SYNTAX Counter
	ACCESS read-write
	STATUS mandatory
	DESCRIPTION
		"The number of complete control Messages received over
		 the Cell Bus for this card. "
	::= { cardEntry 187 }

cardControlMessagesToBus OBJECT-TYPE
	SYNTAX Counter
	ACCESS read-write
	STATUS mandatory
	DESCRIPTION
		"The number of complete control Messages transmitted by this
		 card over the Cell Bus. "
	::= { cardEntry 188 }

cardBTUsFromBus OBJECT-TYPE
	SYNTAX Counter
	ACCESS read-write
	STATUS mandatory
	DESCRIPTION
		"The number of BTUs received by this card over the Cell Bus. "
	::= { cardEntry 189 }

cardBTUsToBus OBJECT-TYPE
	SYNTAX Counter
	ACCESS read-write
	STATUS mandatory
	DESCRIPTION
		"The number of BTUs transmitted by this card over the Cell
		 Bus. "
	::= { cardEntry 190 }

cardInvalidPvcBTUs OBJECT-TYPE
	SYNTAX Counter
	ACCESS read-write
	STATUS mandatory
	DESCRIPTION
		"The number of BTUs received by this card over the Cell Bus
		 with an invalid PVC identifier. "
	::= { cardEntry 191 }

cardIncompleteFramesFromBus OBJECT-TYPE
	SYNTAX Counter
	ACCESS read-write
	STATUS mandatory
	DESCRIPTION
		"The number of partial frames received by this card over the
		 Cell Bus which were discarded due to missing BTUs. "
	::= { cardEntry 192 }

cardBTUsBusErrors OBJECT-TYPE
	SYNTAX Counter
	ACCESS read-write
	STATUS mandatory
	DESCRIPTION
		"The number of BTUs received by this card over the
		 Cell Bus which were discarded due to errors. "
	::= { cardEntry 193 }

cardBTUsNoResource OBJECT-TYPE
	SYNTAX Counter
	ACCESS read-write
	STATUS mandatory
	DESCRIPTION
		"The number of BTUs received by this card over the
		 Cell Bus which were discarded due to no free BTUs available
		 to replace it. "
	::= { cardEntry 194 }

cardInvalidPvcBTUsThreshold OBJECT-TYPE
	SYNTAX INTEGER
	ACCESS read-write
	STATUS mandatory
	DESCRIPTION
		"Send trap if the number of BTUs received by this card over
		 the Cell Bus with an invalid PVC identifier exceeds this
		 in a one minute interval. Zero value implies no check. "
	::= { cardEntry 195 }

cardIncompleteFramesFromBusThreshold OBJECT-TYPE
	SYNTAX INTEGER
	ACCESS read-write
	STATUS mandatory
	DESCRIPTION
		"Send trap if the number of partial frames received by this
		 card over the Cell Bus which were discarded due to missing
		 BTUs exceeds this in a one minute interval. Zero value
		 implies no check. "
	::= { cardEntry 196 }

cardBTUsBusErrorThreshold OBJECT-TYPE
	SYNTAX INTEGER
	ACCESS read-write
	STATUS mandatory
	DESCRIPTION
		"Send trap if the number of BTUs received by this card over
		 the Cell Bus which were discarded due to errors exceeds
		 this in a one minute interval. Zero value implies no check. "
	::= { cardEntry 197 }

cardBTUsNoResourceThreshold OBJECT-TYPE
	SYNTAX INTEGER
	ACCESS read-write
	STATUS mandatory
	DESCRIPTION
		"Send trap if the number of BTUs received by this card over
		 the Cell Bus which were discarded due to no free BTUs
		 available to replace it exceeds this in a one minute
		 interval. Zero value implies no check. "
	::= { cardEntry 198 }

cardFrameMemoryThreshold OBJECT-TYPE
	SYNTAX INTEGER
	ACCESS read-write
	STATUS mandatory
	DESCRIPTION
		"The percentage of frame memory utilization on this card which
		will generate a trap. Zero value implies no check. "
	::= { cardEntry 199 }

cardHoldQFrameMemory OBJECT-TYPE
	SYNTAX	Counter
	ACCESS	read-only
	STATUS	mandatory
	DESCRIPTION
		"The frame memory utilization, in terms of bytes, currently
		on the Hold Queues for this card. "
	::= { cardEntry 200 }

cardTotalAAL5RxErrorCount OBJECT-TYPE
	SYNTAX  Counter
	ACCESS  read-only
	STATUS  mandatory
	DESCRIPTION
		"The total number of Rx errors detected by the AAL5 processor
		 on this card. "
	::= { cardEntry 201 }

cardOperMemSize OBJECT-TYPE
        SYNTAX  INTEGER
        ACCESS  read-only
        STATUS  mandatory
        DESCRIPTION
                "The total memory size on this card, in MB (1024 Kbytes)."
        ::= { cardEntry 202 }

-- 	The Physical Port Group
--
--	The variables that configure physical ports at a node
--

pportNumber OBJECT-TYPE
	SYNTAX	INTEGER
	ACCESS	read-only
	STATUS	mandatory
	DESCRIPTION
		"The number of physical ports (regardless of their current
		state) present at this node."
	::= { pport 1 }

pportTable OBJECT-TYPE
	SYNTAX	SEQUENCE OF PportEntry
	ACCESS	not-accessible
	STATUS	mandatory
	DESCRIPTION
		"A list of physical port entries.  The number of entries is
		given by the value of pportNumber."
	::= { pport 2 }

pportEntry OBJECT-TYPE
	SYNTAX	PportEntry
	ACCESS	not-accessible
	STATUS	mandatory
	DESCRIPTION
		"The physical port entry contains objects relevant to a 
		physical port."
	INDEX	{ pportSlotId, 
		  pportId }
	::= { pportTable 1 }

PportEntry ::=
	SEQUENCE {
		pportSlotId	
			INTEGER,
		pportId		
			INTEGER,
		pportAdminType
			INTEGER,
		pportNumLport	
			INTEGER,
		pportDataRate	
			INTEGER,
		pportType
			INTEGER,
		pportRecvClock
			INTEGER,
		pportXmitClock
			INTEGER,
		pportAdminStatus
			INTEGER,
		pportOperStatus
			INTEGER,
		pportDs1LineType
			INTEGER,
		pportDs1ZeroCoding
			INTEGER,
		pportDs1LineBuildout
			INTEGER,
		pportDiagTestId
			INTEGER,
		pportDiagTestRuns
			INTEGER,
		pportInOctets
			Counter,
 		pportInFrames
			Counter,
 		pportInDiscards
			Counter,
		pportInErrors
			Counter,
		pportOutOctets
			Counter,
 		pportOutFrames
			Counter,
 		pportOutDiscards
			Counter,
		pportOutErrors
			Counter,
		pportDiagState
			INTEGER,
		pportDiagOptionStr
			OCTET STRING,
		pportDiagPassCount
			INTEGER,
		pportDiagFailCount
			INTEGER,
		pportDiagResultStr
			DisplayString,
		pportLinkDownReason
			INTEGER,
		pportInterface
			INTEGER,
		pportAdminInterface
			INTEGER,
		pportCellScramble
			INTEGER,
		pportCbitParity
			INTEGER,
		pportMaxBufferSize
			INTEGER,
		pportPeakCellRate0
			INTEGER,
		pportPeakCellRate1
			INTEGER,
		pportPeakCellRate2
			INTEGER,
		pportPeakCellRate3
			INTEGER,
		pportPeakCellRate4
			INTEGER,
		pportPeakCellRate5
			INTEGER,
		pportPeakCellRate6
			INTEGER,
		pportPeakCellRate7
			INTEGER,
		pportInCells
			INTEGER,
		pportInErrorCells
			INTEGER,
		pportOutCells
			INTEGER,
		pportDs3LineBuildout
			INTEGER,
		pportSetDS0LoopUp
			INTEGER,
		pportSetDS0LoopDown
			INTEGER,
		pportDS0LoopUpStatus
			INTEGER,
		pportDS0LoopDownStatus
			INTEGER,
		pportDS0LoopStatus
			INTEGER,
		pportISDN
			INTEGER,
                pportdsx3LoopbackConfig
                        INTEGER,
                pportdsx3SendCode
                        INTEGER,
                pportdsx3LoopStatus
                        INTEGER,
                pportdsx3FEACStatus
                        INTEGER,
                pportds1LoopbackConfig
                        INTEGER,
                pportds1SendCode
                        INTEGER,
                pportds1LoopStatus
                        INTEGER,
                pportSetClkBkup
                        INTEGER,
                pportAtmIdleWord
                        INTEGER,
                pportAtmDisCardMode
                        INTEGER,
		pportAtmLastUnconfiguredVpi
			INTEGER,
		pportAtmLastUnconfiguredVci
                        INTEGER,
                pportAtmUnconfiguredCells
			Counter,
                pportAtmNumBitsVCI
			INTEGER,
                pportAtmNumBitsVPI
                        INTEGER,
		pportAtmInterfaceType
			INTEGER,
		pportSonetSDHLoopbackConfig
			INTEGER,
		pportSonetSDHLoopStatus
			INTEGER,
 		pportOutDiscardsCell
			Counter,
               pportAtmPlcp
                        INTEGER,
		pportCbrTargetClockMode
			INTEGER,
		pportCbrCurrentClockMode
			INTEGER,
		pportClockMasterChannel
			INTEGER,
		pportFibreType
			INTEGER,
		pportLaserStatus
			INTEGER,
		pportMaxActiveVpiBits
			INTEGER,
		pportBipErrorsThresh
			INTEGER,
		pportBipSectionErrors
			Counter,
		pportBipLineErrors
			Counter,
		pportBipPathErrors
			Counter,
		pportFebeErrors
			Counter,
		pportHcsErrors
			Counter,
		pportHcsSevereErrors
			Counter,
		pportCongestedReceivedCells
			Counter,
		pportCongestedTransmittedCells
			Counter,
		pportAtmLayerErroredReceivedCells
			Counter,
		pportAtmLayerErroredTransmittedCells
			Counter,
		pportDS0BitStuff 
			INTEGER,
		pportDS0BitErrorCount 
			INTEGER,
		pportDS0BitErrorFreeSeconds 
			INTEGER,
		pportDS0BitErroredSeconds 
			INTEGER,
		pportDS0MidspanRepeaters 
			INTEGER,
		pportDS0TestPatternSync 
			INTEGER,
		pportDS0InjectBitError 
			INTEGER,
		pportDS0FarendLpbkType 
			INTEGER,
		pportDS0LpbkMode 
			INTEGER,
		pportDS0SwitchLpbkStart 
			INTEGER,	
		pportDS0SwitchLpbkEnd 
			INTEGER,
		pportDS0FarendDS0InLpbk 	
			INTEGER,
		pportDS0SendTestTraffic 
			INTEGER,
		pportOc3LoopConfig
			INTEGER,
		pportOc3LoopStatus
			INTEGER,
		pportISDNIpBaseAddr
		 	IpAddress,	
		pportSonetSTM1Scramble
			INTEGER,
		pportEFCIMarking
			INTEGER,
		pportAtmQOSTransmitMode
			INTEGER,
		pportHECMode
			INTEGER,
		pportISDNChannelStatus
			OCTET STRING,
                pportds1FarEndLoopStatus
			INTEGER,
                pportds1FDLControl
			INTEGER,
                pportds1FDLPrmXmit
			INTEGER,
                pportds1FDLPidXmit
			INTEGER,
                pportds1FDLXmitPid
			OCTET STRING,
                pportds1FDLRcvPid
			OCTET STRING,
                pportds1FDLRcvTsid
			OCTET STRING,
		pportSonetSDHFramingMode
			INTEGER,
                pportds1InbandLoopType
			INTEGER,
                pportESFDataLinkStatus
			INTEGER,
                pportPMTcaId
			INTEGER,
                pportBchanTimerValue
                        INTEGER,
		pportAAL5CRC32Error
			Counter,
		pportAAL5CPIError
			Counter,
		pportAAL5LengthError
			Counter,
		pportAAL5ReassemblyTimerError
			Counter,
		pportAAL5MaxNrSegError
			Counter,
                pportRedundancyArch
                        INTEGER,
                pportAPSadminDir
                        INTEGER,
                pportAPSlineType
                        INTEGER,
                pportAPSrevertiveMode
                        INTEGER,
                pportAPSpairedSlotId
                        INTEGER,
                pportAPSpairedPportId
                        INTEGER,
                pportAPSsfBerThresh
                        INTEGER,
                pportAPSsdBerThresh
                        INTEGER,
                pportAPSwtrPeriod
                        INTEGER,
                pportAPSprotectionLineState
                        INTEGER,
                pportAPSxCommand
                        INTEGER,
                pportAPSconfigStatus
                        INTEGER,
                pportAPSOperRxStatus
                        INTEGER,
                pportBertPattern
                       INTEGER,
               pportBertUserBytes
                       INTEGER,
               pportBertErrorRate
                       INTEGER,
               pportBertCommand
                       INTEGER,
               pportBertStatus
                       INTEGER,
               pportBertBitCount
                       Gauge,
               pportBertErrorCount
                       Gauge,
               pportds1FELoopbackControl
			INTEGER,
	       pportFT1DS0s
			DisplayString,
	       pportIMUXCnt
			INTEGER,
               pportds1PMConfigThresh
			INTEGER,
	       pportIdleCellType
			INTEGER,
	       	pportATMTcaInHECErrorUAlertPeriod
			INTEGER,
		pportATMTcaInHECErrorUThresh
			INTEGER,
		pportATMTcaEBufOverflowCBRAlertPeriod
			INTEGER,
		pportATMTcaEBufOverflowCBRThresh
			INTEGER,
		pportATMTcaEBufOverflowABRAlertPeriod
			INTEGER,
		pportATMTcaEBufOverflowABRThresh
			INTEGER,
		pportATMTcaEBufOverflowVBR1AlertPeriod
			INTEGER,
		pportATMTcaEBufOverflowVBR1Thresh
			INTEGER,
		pportATMTcaEBufOverflowVBR2AlertPeriod
			INTEGER,
		pportATMTcaEBufOverflowVBR2Thresh
			INTEGER,
		pportATMTcaInFramerFIFOOverflowAlertPeriod
			INTEGER,
		pportATMTcaInFramerFIFOOverflowThresh
			INTEGER,
		pportATMTcaELookupFailureAlertPeriod
			INTEGER,
		pportATMTcaELookupFailureThresh
			INTEGER,
		pportATMTcaEnable
			INTEGER,
		pportATMTcaId
			INTEGER,
		pportFethAdminMacAddr
			OCTET STRING,
		pportFethOperMacAddr
			OCTET STRING,
		pportConfigAlarmSoakTime
			INTEGER,
		pportConfigAlarmClearTime
			INTEGER,
		pportFethPortCapability
			INTEGER,
		pportVpshapingDiscardCellCount
			INTEGER


	}

pportSlotId OBJECT-TYPE
	SYNTAX	INTEGER
	ACCESS	read-only
	STATUS	mandatory
	DESCRIPTION
		"The slot number of the corresponding physical port."
	::= { pportEntry 1 }
	
pportId OBJECT-TYPE
	SYNTAX	INTEGER
	ACCESS	read-only
	STATUS	mandatory
	DESCRIPTION
		"The port number of the corresponding physical port
		on the board."
	::= { pportEntry 2 }
		
pportAdminType OBJECT-TYPE
	SYNTAX	INTEGER {
                        v35-6 (1),              -- 6-port V.35 i/o card
                        ft1-1-24 (2),           -- 1-port 24-channel Fractional T1
                        fe1-1-30 (3),           -- 1-port 30-channel Fractional E1
                        uio-6 (4),              -- 6-port universal i/o card
                        cp1 (5),                -- Control Processor
                        uio-8 (6),              -- 8-port V.35 i/o card
                        ft1-4-24 (7),           -- 4-port 24-channel Fractional T1
                        fe1-4-30 (8),           -- 4-port 30-channel Fractional E1
                        ft3-1 (9),              -- 1-port Fractional T3 i/o card
                        fe3-1 (10),             -- 1-port Fractional E3 i/o card
                        hssi-1 (11),            -- HSSI i/o card
                        dsx1-10 (12),           -- 10-port DSX-1 card
			rs232-18 (13),		-- 18-port X.21/V.24 I/O card, for STDX 3000/6000 only
			rs232-8 (14),		-- 8-port X.21/V.24 I/O card, for STDX 3000/6000 only
			ut1-4-24 (15),		-- 4-port 24-channel Un-Channelized T1
			ue1-4-30 (16),		-- 4-port 30-channel Un-Channelized E1
			atmds3-1 (17),		-- 1-port ATM DS3 UNI I/O card
			atme3-1 (18),		-- 1-port ATM E3 UNI I/O card
			pri-4 (19),		-- 4-port ISDN PRI I/O card
			e1-pri-4 (20),		-- 4-port E1 PRI I/O card
			sft1-4-24 (21),		-- 4-port short haul 24-channel Fractional T1 card
			sut1-4-24 (22),		-- 4-port short haul 24-channel Un-Channelized T1 card
			st1-pri-4 (23),		-- 4-port short haul PRI I/O card
                        t1-atm    (24),         -- T1 ATM  
                        e1-atm    (25),         -- E1 ATM
                        ads3-t3   (26),         -- ATM DS3 T3 (topaz)  
                        ads3-e3   (27),         -- ATM DS3 E3 (topaz)  
			cbr-ds1-s-4 (28),	-- 4-port CBR DS1 structured card
			cbr-ds1-us-4 (29),	-- 4-port CBR DS1 unstructured card
			cbr-e1-s-4 (30),	-- 4-port CBR E1 structured card
			cbr-e1-us-4 (31),	-- 4-port CBR E1 unstructured card
			cbr-atmiwu-1 (32),	-- 1-port ATM-IWU STM-1/STS-3c card
			toc3-atm-4 (33),	-- 4-port Topaz OC3c ATM card
			tstm1-atm-4 (34),	-- 4-port Topaz STM1 ATM card
			atmcs-1     (35)        -- 1-port ATM-CS card (siemens)
                        }   
	ACCESS	read-write
	STATUS	mandatory
	DESCRIPTION
		"The defined type of the board which the physical port is on."
	::= { pportEntry 3 }

pportNumLport OBJECT-TYPE
	SYNTAX	INTEGER
	ACCESS	read-only
	STATUS	mandatory
	DESCRIPTION
		"The number of logical ports on the physical port."
	::= { pportEntry 4 }
			
pportDataRate OBJECT-TYPE
	SYNTAX	INTEGER
	ACCESS	read-write
	STATUS	mandatory
	DESCRIPTION
		"An estimate of the physical port's data rate in bits
		per second. The data rate can't be an arbitrary value. The
		legal values are list below. Note that the T1/E1 class of 
		cards don't support this variable and return a 0

		For UIO, DSX1:
        		9600,	19200,	38400,	48000, 	56000,	64000,	
			128000,	192000, 256000, 320000, 384000, 448000, 
			512000, 576000, 640000, 704000, 768000, 832000, 
			896000, 960000, 1024000, 1088000, 1152000, 1216000, 
			1280000, 1344000, 1408000, 1472000, 1536000, 1600000, 
			1664000, 1728000, 1792000, 1856000, 1920000, 1984000, 
			2048000, 4096000, 6144000, 8192000
		For HSSI:
		        1579000, 3158000, 4737000, 6316000, 7895000, 9474000,
		        11053000, 12632000, 14211000, 15790000, 17369000,
		        18948000, 20527000, 22106000, 23685000, 25264000,
		        26843000, 28422000, 30001000, 31580000, 33159000,
		        34738000, 36317000, 37896000, 39475000, 41054000,
		        42633000, 44212000, 45791000, 47370000, 48949000,
		        50528000
		For ATM-IWU, TOPAZ OC3c:
			155520000

		For T1, E1, UT1, UE1, PRI, SH-T1:
			0
		"
	::= { pportEntry 5 }
			
pportType OBJECT-TYPE
	SYNTAX	INTEGER {
                        v35-6 (1),              -- 6-port V.35 i/o card
                        ft1-1-24 (2),           -- 1-port 24-channel Fractional T1
                        fe1-1-30 (3),           -- 1-port 30-channel Fractional E1
                        uio-6 (4),              -- 6-port universal i/o card
                        cp1 (5),                -- Control Processor
                        uio-8 (6),              -- 8-port V.35 i/o card
                        ft1-4-24 (7),           -- 4-port 24-channel Fractional T1
                        fe1-4-30 (8),           -- 4-port 30-channel Fractional E1
                        ft3-1 (9),              -- 1-port Fractional T3 i/o card
                        fe3-1 (10),             -- 1-port Fractional E3 i/o card
                        hssi-1 (11),            -- HSSI i/o card
                        dsx1-10 (12),           -- 10-port DSX-1 card
                        rs232-18 (13),          -- 18-port X.21/V.24 I/O module, for STDX 3000/6000 only
			rs232-8 (14),		-- 8-port X.21/V.24 I/O card, for STDX 3000/6000 only
			ut1-4-24 (15),		-- 4-port 24-channel Un-Channelized T1
			ue1-4-30 (16),		-- 4-port 30-channel Un-Channelized E1
			atm-1 (17),		-- 1-port ATM DS3 UNI I/O card
			atme3-1 (18),		-- 1-port ATM E3 UNI I/O card
			pri-4 (19),		-- 4-port ISDN PRI I/O card
			e1-pri-4 (20),		-- 4-port E1 PRI I/O card
			sft1-4-24 (21),		-- 4-port short haul 24-channel Fractional T1 card
			sut1-4-24 (22),		-- 4-port short haul 24-channel Un-Channelized T1 card
			st1-pri-4 (23),		-- 4-port short haul PRI I/O card
                        t1-atm    (24),         -- T1 ATM  
                        e1-atm    (25),         -- E1 ATM
                        ads3-t3   (26),         -- ATM DS3 T3 (topaz)  
                        ads3-e3   (27),         -- ATM DS3 E3 (topaz)  
			cbr-ds1-s-4 (28),	-- 4-port CBR DS1 structured card
			cbr-ds1-us-4 (29),	-- 4-port CBR DS1 unstructured card
			cbr-e1-s-4 (30),	-- 4-port CBR E1 structured card
			cbr-e1-us-4 (31),	-- 4-port CBR E1 unstructured card
			cbr-atmiwu-1 (32),	-- 1-port ATM-IWU STM-1/STS-3c card
			toc3-atm-4 (33),	-- 4-port Topaz OC3c ATM card
			tstm1-atm-4 (34),	-- 4-port Topaz STM1 ATM card
			atmcs-1     (35)        -- 1-port ATM-CS card (siemens)
		}
	ACCESS	read-only
	STATUS	mandatory
	DESCRIPTION
		"The actual type of the physical port."
	::= { pportEntry 6 }
		
pportRecvClock OBJECT-TYPE
	SYNTAX	INTEGER
	ACCESS	read-only
	STATUS	mandatory
	DESCRIPTION
		"The receive clock source. This object works in cooperation with
		 pportXmitClock.

		 The following are the various values for different clock 
        		source types:

			Type     Clock Source     pportRevClock      pportXmitClock
		                  { pportEntry 7 }   { pportEntry 8 }
	
			V.35     DCE ............ 0    		      0
			or UIO	 LoopTime DCE ... 3                   0
	     	  		 DTE ............ 1                   2
		 		 Direct Trunk ... 1                   0
				 
			T1 or	 Loop Timed ..... 1                   1
        		E1       Internal ....... 2                   2
				 External ....... don't care	      3
		"
	::= { pportEntry 7 }
		
pportXmitClock OBJECT-TYPE
	SYNTAX	INTEGER
	ACCESS	read-only
	STATUS	mandatory
	DESCRIPTION
                "The transmit clock source. This object works in cooperation with
                 pportXmitClock.
 
                 The following are the various values for different clock  
                        source types: 
 
                        Type     Clock Source     pportRevClock      pportXmitClock
                                  { pportEntry 7 }   { pportEntry 8 } 
         
                        V.35     DCE ............ 0                   0 
                        or UIO   LoopTime DCE ... 3                   0 
                                 DTE ............ 1                   2 
                                 Direct Trunk ... 1                   0 
                                  
                        T1 or    Loop Timed ..... 1                   1 
                        E1       Internal ....... 2                   2 
				 External ....... don't care	      3
                "
	::= { pportEntry 8 }

pportAdminStatus OBJECT-TYPE
	SYNTAX	INTEGER {
		    -- invalid (0),
		    up (1),	
		    down (2),
		    testing (3)
		}
	ACCESS	read-write
	STATUS	mandatory
	DESCRIPTION
		"The desired state of the physical port."
	::= { pportEntry 9 }

pportOperStatus OBJECT-TYPE
	SYNTAX	INTEGER {
		    up (1),	
		    down (2),
		    testing (3)
		}
	ACCESS	read-only
	STATUS	mandatory
	DESCRIPTION
		"The current state of the physical port."
	::= { pportEntry 10 }

pportDs1LineType OBJECT-TYPE
	SYNTAX	INTEGER {
		    d4 (1),	
		    esf-ansi (2),
		    esf-att-address-a (3),
		    esf-none (4),
		    e1-cas-crc4	(5),
		    e1-cas-no-crc4 (6),
		    e1-no-cas-crc4 (7),
		    e1-no-cas-no-crc4 (8),
		    esf-att-address-b (9)
		}
	ACCESS	read-write
	STATUS	mandatory
	DESCRIPTION
		"The line type of the T1 or FT1-24B port. ANSI ESF is 
		equivalent to Bellcore ESF."
	::= { pportEntry 11 }

pportDs1ZeroCoding OBJECT-TYPE
	SYNTAX	INTEGER {
		    ami (1),	
		    b8zs (2),
		    hdb3 (3),
		    jammed-bit (4)
		}
	ACCESS	read-write
	STATUS	mandatory
	DESCRIPTION
		"The variety of zero code suppression used on the T1 
		or FT1-24B link.  Jammed bit is equivalent to dsx1JBZS
		where the DS0s will run at 56K bps."
	::= { pportEntry 12 }

pportDs1LineBuildout OBJECT-TYPE
	SYNTAX	INTEGER
	ACCESS	read-write
	STATUS	mandatory
	DESCRIPTION
		"The line build out or line length specification for
		the DS1 or DSX-1 transmitter. These values are card
		specific:

		10 port DSX-1 card
		------------------
		The accepted values are:

		1  -   0 to 110 feet
		2  - 110 to 220 feet
		3  - 220 to 330 feet
		4  - 330 to 440 feet
		5  - 440 to 550 feet
		6  - 550 to 660 feet
		7  - over 655 feet

		1-port and 4-port T1 cards
		--------------------------
		The accepted values are:

		 96  -   0 to 133 feet
		128  - 133 to 266 feet
		160  - 266 to 399 feet
		192  - 399 to 533 feet
		224  - 533 to 655 feet
		96   -  0 db
		32   - -7.5 db
		64   - -15 db

		4-port CBR card
		---------------
		The accepted values are:
			
		96   -  0 db
		32   - -7.5 db
		64   - -15 db

		4-port Short Haul T1 cards
		--------------------------
		The accepted values are:
		 96  -   0 to 133 feet
		128  - 133 to 266 feet
		160  - 266 to 399 feet
		192  - 399 to 533 feet
		224  - 533 to 655 feet"

	::= { pportEntry 13 }

pportDiagTestId OBJECT-TYPE
	SYNTAX	INTEGER {
		    v35-sca-local-loopback (1),
		    v35-sca-remote-loopback (2),
		    v35-csu-loopback (3),
		    hssi-local-dte-loopback (5),
		    hssi-local-line (6),
		    hssi-remote-line-loopback (7),
		    ds1-framer-local-loopback (11),
		    ds1-line-local-loopback (12),
		    ds1-framer-remote-loopback (13),
		    ds1-line-remote-loopback (14)
		}
	ACCESS	read-write
	STATUS	mandatory
	DESCRIPTION
		"Identification for the diagnostics tests to be run."
	::= { pportEntry 14 }

pportDiagTestRuns OBJECT-TYPE
	SYNTAX	INTEGER 
	ACCESS	read-write
	STATUS	mandatory
	DESCRIPTION
		"The number of passes of the diagnostics tests to be run.
		The default value is 1."
	::= { pportEntry 15 }

pportInOctets OBJECT-TYPE
	SYNTAX	Counter 
	ACCESS	read-only
	STATUS	mandatory
	DESCRIPTION
		"The total number of octets received on the physical port,
		including framing characters." 
	::= { pportEntry 16 }

pportInFrames OBJECT-TYPE
	SYNTAX	Counter 
	ACCESS	read-only
	STATUS	mandatory
	DESCRIPTION
		"The total number of frames received on the physical port." 
	::= { pportEntry 17 }

pportInDiscards OBJECT-TYPE
	SYNTAX	Counter 
	ACCESS	read-only
	STATUS	mandatory
	DESCRIPTION
		"The total number of inbound frames discarded." 
	::= { pportEntry 18 }

pportInErrors OBJECT-TYPE
	SYNTAX	Counter 
	ACCESS	read-only
	STATUS	mandatory
	DESCRIPTION
		"The total number of inbound frames that contained erroneous
		headers (e.g., illegal or unknown DLCIs)." 
	::= { pportEntry 19 }

pportOutOctets OBJECT-TYPE
	SYNTAX	Counter 
	ACCESS	read-only
	STATUS	mandatory
	DESCRIPTION
		"The total number of octets transmitted out of the physical
		port, including framing characters." 
	::= { pportEntry 20 }

pportOutFrames OBJECT-TYPE
	SYNTAX	Counter 
	ACCESS	read-only
	STATUS	mandatory
	DESCRIPTION
		"The total number of frames transmitted out of the physical
		port." 
	::= { pportEntry 21 }

pportOutDiscards OBJECT-TYPE
	SYNTAX	Counter 
	ACCESS	read-only
	STATUS	mandatory
	DESCRIPTION
		"The total number of outbound frames discarded due to 
		severe congestion." 
	::= { pportEntry 22 }

pportOutErrors OBJECT-TYPE
	SYNTAX	Counter 
	ACCESS	read-only
	STATUS	mandatory
	DESCRIPTION
		"The total number of outbound frames that causes xmit errors." 
	::= { pportEntry 23 }

pportDiagState OBJECT-TYPE
	SYNTAX	INTEGER {
		-- inactive (0),
		active(1)
	}
	ACCESS	read-write
	STATUS	mandatory
	DESCRIPTION
		"The current state of the diagnostic on this physical port."
	::= { pportEntry 24 }

pportDiagOptionStr OBJECT-TYPE
	SYNTAX	OCTET STRING
	ACCESS	read-write
	STATUS	mandatory
	DESCRIPTION
		"Optional parameters to the diagnostic."
	::= { pportEntry 25 }

pportDiagPassCount OBJECT-TYPE
	SYNTAX	INTEGER
	ACCESS	read-only
	STATUS	mandatory
	DESCRIPTION
		"Number of successful diagnostic passes."
	::= { pportEntry 26 }

pportDiagFailCount OBJECT-TYPE
	SYNTAX	INTEGER
	ACCESS	read-only
	STATUS	mandatory
	DESCRIPTION
		"Number of failed diagnostic passes."
	::= { pportEntry 27 }

pportDiagResultStr OBJECT-TYPE
	SYNTAX	DisplayString
	ACCESS	read-only
	STATUS	mandatory
	DESCRIPTION
		"Description of last diagnostic failure."
	::= { pportEntry 28 }

pportLinkDownReason OBJECT-TYPE
	SYNTAX	INTEGER {
		-- none		(0),
		red-alarm	(1),
		yellow-alarm	(2),
		blue-alarm	(4),
		carrier-loss	(8),
		looped-back	(16),
		ber-threshold   (64),
		signal-label-mismatch   (128),
		loss-of-signal	(256),
		loss-of-frame	(512),
		loss-of-cell-delination	(1024),
		line-AIS	(2048),
		path-AIS	(4096),
		loss-of-pointer	(8192),
		line-RFI	(16384),
		path-RFI	(32768),
		signal-label-undefined	(65536)
		}
	ACCESS	read-only
	STATUS	mandatory
	DESCRIPTION
		"Reason why the link is down.  The blue-alarm is equivalent
		to the Alarm Indication Signal (AIS) failure."
	::= { pportEntry 29 }

pportInterface OBJECT-TYPE
	SYNTAX	INTEGER {
		eia449		(1),
		x21		(2),
		eia530		(3),
		eia530A		(4),
		v35		(5),
		e1-coax		(6),
		e1-db		(7),
		none		(8),
		v24		(9),
		sonet		(10), 
		sdh		(11),
		multi-mode	(12),	-- optical interface for topaz only
		single-mode	(13)	-- optical interface for topaz only
		}
	ACCESS	read-only
	STATUS	mandatory
	DESCRIPTION
		"Actual interface connected to Multi-Interface Port or ATM-IWU."
	::= { pportEntry 30 }

pportAdminInterface OBJECT-TYPE
	SYNTAX	INTEGER {
		eia449		(1),
		x21		(2),
		eia530		(3),
		eia530A		(4),
		v35		(5),
		e1-coax		(6),
		e1-db		(7),
		none		(8),
		v24		(9),
		sonet           (10),
		sdh             (11),
		multi-mode	(12),	-- optical interface for topaz only
		single-mode	(13)	-- optical interface for topaz only
		}
	ACCESS	read-write
	STATUS	mandatory
	DESCRIPTION
		"Configured interface connected to Multi-Interface Port or ATM-IWU."
	::= { pportEntry 31 }

pportCellScramble OBJECT-TYPE
	SYNTAX	INTEGER {
		disabled (1),
		enabled(2)
		}
	ACCESS	read-write
	STATUS	mandatory
	DESCRIPTION
		"Configured ATM cell payload scrambling."
	::= { pportEntry 32 }

pportCbitParity OBJECT-TYPE
	SYNTAX	INTEGER {
		disabled (1),
		enabled (2)
		}
	ACCESS	read-write
	STATUS	mandatory
	DESCRIPTION
		"Configured ATM DS3 C-bit Parity."
	::= { pportEntry 33 }

pportMaxBufferSize OBJECT-TYPE
	SYNTAX	INTEGER
	ACCESS	read-write
	STATUS	mandatory
	DESCRIPTION
		"Maximum receive/transmit buffer size for the ATM UNI DS3 IOP"
	::= { pportEntry 34 }

pportPeakCellRate0 OBJECT-TYPE
	SYNTAX	INTEGER
	ACCESS	read-write
	STATUS	mandatory
	DESCRIPTION
		"Peak Cell Rate (cell/sec.) for rate queue #0.
		 rate queues 0 - 3 are high priority"
	::= { pportEntry 35 }

pportPeakCellRate1 OBJECT-TYPE
	SYNTAX	INTEGER
	ACCESS	read-write
	STATUS	mandatory
	DESCRIPTION
		"Peak Cell Rate (cell/sec.) for rate queue #1.
		 rate queues 0 - 3 are high priority"
	::= { pportEntry 36 }

pportPeakCellRate2 OBJECT-TYPE
	SYNTAX	INTEGER
	ACCESS	read-write
	STATUS	mandatory
	DESCRIPTION
		"Peak Cell Rate (cell/sec.) for rate queue #2.
		 rate queues 0 - 3 are high priority"
	::= { pportEntry 37 }

pportPeakCellRate3 OBJECT-TYPE
	SYNTAX	INTEGER
	ACCESS	read-write
	STATUS	mandatory
	DESCRIPTION
		"Peak Cell Rate (cell/sec.) for rate queue #3.
		 rate queues 0 - 3 are high priority"
	::= { pportEntry 38 }

pportPeakCellRate4 OBJECT-TYPE
	SYNTAX	INTEGER
	ACCESS	read-write
	STATUS	mandatory
	DESCRIPTION
		"Peak Cell Rate (cell/sec.) for rate queue #4.
		 rate queues 4 - 7 are low priority"
	::= { pportEntry 39 }

pportPeakCellRate5 OBJECT-TYPE
	SYNTAX	INTEGER
	ACCESS	read-write
	STATUS	mandatory
	DESCRIPTION
		"Peak Cell Rate (cell/sec.) for rate queue #5.
		 rate queues 4 - 7 are low priority"
	::= { pportEntry 40 }

pportPeakCellRate6 OBJECT-TYPE
	SYNTAX	INTEGER
	ACCESS	read-write
	STATUS	mandatory
	DESCRIPTION
		"Peak Cell Rate (cell/sec.) for rate queue #6.
		 rate queues 4 - 7 are low priority"
	::= { pportEntry 41 }


pportPeakCellRate7 OBJECT-TYPE
	SYNTAX	INTEGER
	ACCESS	read-write
	STATUS	mandatory
	DESCRIPTION
		"Peak Cell Rate (cell/sec.) for rate queue #7.
		 rate queues 4 - 7 are low priority"
	::= { pportEntry 42 }

pportInCells OBJECT-TYPE
	SYNTAX	INTEGER
	ACCESS	read-only
	STATUS	mandatory
	DESCRIPTION
		"The total number of cells received"
	::= { pportEntry 43 }

pportInErrorCells OBJECT-TYPE
	SYNTAX	INTEGER
	ACCESS	read-only
	STATUS	mandatory
	DESCRIPTION
		"The total number of cells received with error"
	::= { pportEntry 44 }

pportOutCells OBJECT-TYPE
	SYNTAX	INTEGER
	ACCESS	read-only
	STATUS	mandatory
	DESCRIPTION
		"The total number of cells transmitted"
	::= { pportEntry 45 }

pportDs3LineBuildout OBJECT-TYPE
	SYNTAX	INTEGER
	ACCESS	read-write
	STATUS	mandatory
	DESCRIPTION
		"The line build out or line length specification for
		the DS3 transmitter.

		1-port ATM-UNI DS3 card
		--------------------------
		The accepted values are:

		1 - 0 to 225 feet
		2 - 226 to 450 feet"
	::= { pportEntry 46 }


pportSetDS0LoopUp OBJECT-TYPE
	SYNTAX	INTEGER
	ACCESS	read-write
	STATUS	mandatory
	DESCRIPTION
		"Bit map used to set one or more DS0's into loopback. Low bit
    corresponds to DS0 1. If a bit is set that DS0 is put into loopback."
  ::= { pportEntry 47 }

pportSetDS0LoopDown OBJECT-TYPE
	SYNTAX	INTEGER
	ACCESS	read-write
	STATUS	mandatory
	DESCRIPTION
		"Bit map used to set one or more DS0's out of loopback. Low bit
    corresponds to DS0 1. If a bit is set that DS0 is put out of loopback."
  ::= { pportEntry 48 }

pportDS0LoopUpStatus OBJECT-TYPE
	SYNTAX	INTEGER
	ACCESS	read-only
	STATUS	mandatory
	DESCRIPTION
		"Bit map reporting which DS0's have gone into loopback since the
    last time this variable was read"
  ::= { pportEntry 49 }

pportDS0LoopDownStatus OBJECT-TYPE
	SYNTAX	INTEGER
	ACCESS	read-only
	STATUS	mandatory
	DESCRIPTION
		"Bit map reporting which DS0's have gone out of loopback since the
    last time this variable was read"
  ::= { pportEntry 50 }

pportDS0LoopStatus OBJECT-TYPE
	SYNTAX	INTEGER
	ACCESS	read-only
	STATUS	mandatory
	DESCRIPTION
		"Bit map reporting which DS0's are currently in loopback. Low bit 
    corresponds to DS0 1"
  ::= { pportEntry 51 }

pportISDN OBJECT-TYPE
	SYNTAX INTEGER {
		disabled (1),
		enabled  (2)
		}
	ACCESS read-write
	STATUS mandatory
	DESCRIPTION
		"Specifies whether ISDN PRI is enabled for this physical port"
	::= { pportEntry 52 }

pportdsx3LoopbackConfig OBJECT-TYPE
        SYNTAX INTEGER {
                dsx3NoLoop      (1),
                dsx3PayloadLoop (2),
                dsx3LineLoop    (3)
                }
        ACCESS read-write
        STATUS mandatory
        DESCRIPTION
                "Integer used to set the loopback state of the DS3 or E3"
        ::= { pportEntry 53 }

pportdsx3SendCode OBJECT-TYPE
        SYNTAX INTEGER {
                dsx3SendNoCode    (1),
                dsx3SendLineCode  (2),
                dsx3SendResetCode (4)
                }
        ACCESS read-write
        STATUS mandatory
        DESCRIPTION
                "Integer used to send loopback code to far-end DS3"
        ::= { pportEntry 54 }

pportdsx3LoopStatus OBJECT-TYPE
        SYNTAX INTEGER {
                noloop     (1),
                payloadloop (2),
                lineloop    (3)
      }
        ACCESS read-only
        STATUS mandatory
        DESCRIPTION
                "Integer indicating the current loopback status of the DS3 or E3"
        ::= { pportEntry 55 }

pportdsx3FEACStatus OBJECT-TYPE
        SYNTAX INTEGER
        ACCESS read-only
        STATUS mandatory
        DESCRIPTION
                "Integer indicating the current DS3 FAEC status:
		-- none				(0),
                DS3 Equipment Failure		(1),
		DS3 LOS				(2),
		DS3 Out of Frame		(4),
		DS3 AIS received		(8),
		DS3 IDLE received		(16),
		DS3 Equipment-Failure (NSA)	(32),
		DS3 Common Equipment Failure	(64),
		DS3 Loopback received		(128) "
        ::= { pportEntry 56 }

pportds1LoopbackConfig OBJECT-TYPE
 SYNTAX INTEGER {
                ds1NoLoop      (1),
                ds1PayloadLoop (2),
                ds1LineLoop    (3)
                }
        ACCESS read-write
        STATUS mandatory
        DESCRIPTION
                "Integer used to set the loopback state of the DS1"
        ::= { pportEntry 57 }

pportds1SendCode OBJECT-TYPE
        SYNTAX INTEGER {
                ds1SendNoCode                        (1),
                ds1SendFramedInbandLineActuateLoop   (2),
                ds1SendFramedInbandLineReleaseLoop   (3),
                ds1SendUnframedInbandLineActuateLoop (4),
                ds1SendUnframedInbandLineReleaseLoop (5),
                ds1SendFdlESFAnsiLineActuateLoop     (6),
                ds1SendFdlESFAnsiLineReleaseLoop     (7),
                ds1SendFdlESFAnsiPayloadActuateLoop  (8),
                ds1SendFdlESFAnsiPayloadReleaseLoop  (9)
                }
        ACCESS read-write
        STATUS mandatory
        DESCRIPTION
                "Integer used to send loopback code to far-end DS1"
        ::= { pportEntry 58 }

pportds1LoopStatus OBJECT-TYPE
        SYNTAX INTEGER {
                noloop     (1),
                payloadloop (2),
                lineloop    (3)
      }
        ACCESS read-only
        STATUS mandatory
        DESCRIPTION
                "Integer indicating the current loopback status of the DS1"
        ::= { pportEntry 59 }


pportSetClkBkup OBJECT-TYPE
        SYNTAX INTEGER {
                internalClkBkup     (1),
                looptimedClkBkup    (2)            
      }
        ACCESS read-only
        STATUS mandatory
        DESCRIPTION
                "The desired clock source backup if the card is set in 
        external clock source mode"
        ::= { pportEntry 60 }


pportAtmIdleWord  OBJECT-TYPE
        SYNTAX INTEGER 
        ACCESS read-write
        STATUS mandatory
        DESCRIPTION
                " The word used to stuff the payload of the ATM idle cell"
        ::= { pportEntry 61 }

pportAtmDisCardMode  OBJECT-TYPE
        SYNTAX INTEGER {
               ansiInval                (1),
               ansiUnassignedInval      (2),
               atmFInvalid              (3),
               atmFUnassignedInval      (4),
               ccittIdle                (5),
               ccittUnassignedIdle      (6)            
      }
        ACCESS read-write
        STATUS mandatory
        DESCRIPTION
                "The desired clock source backup if the card is set in 
        external clock source mode"
        ::= { pportEntry 62 }

pportAtmLastUnconfiguredVpi OBJECT-TYPE
	SYNTAX	INTEGER
	ACCESS	read-only
	STATUS	mandatory
	DESCRIPTION "This entry holds the Vpi read from the last Unconfigured
		atm cell received.  This entry applies to ATM pports
		only."
	::={ pportEntry 63 }


pportAtmLastUnconfiguredVci OBJECT-TYPE
	SYNTAX	INTEGER
	ACCESS	read-only
	STATUS	mandatory
	DESCRIPTION "This entry holds the Vci read from the last Unconfigured
		atm cell received.  This entry applies to ATM pports
		only."
	::={ pportEntry 64 }


pportAtmUnconfiguredCells OBJECT-TYPE
	SYNTAX	Counter
	ACCESS	read-only
	STATUS	mandatory
	DESCRIPTION "This entry holds a count of the number of Unconfigured
                     ATM cells received.  This entry applies to ATM pports
		only."
	::={ pportEntry 65 }

pportAtmNumBitsVCI OBJECT-TYPE
	SYNTAX	INTEGER
	ACCESS	read-only
	STATUS	mandatory
	DESCRIPTION "This entry holds a count of the VCI bits supppoted my this
                     ATM card."
	::={ pportEntry 66 }

pportAtmNumBitsVPI OBJECT-TYPE
	SYNTAX	INTEGER
	ACCESS	read-only
	STATUS	mandatory
	DESCRIPTION "This entry holds a count of the VPI bits supppoted my this
                     ATM card."
	::={ pportEntry 67 }

pportAtmInterfaceType OBJECT-TYPE
        SYNTAX INTEGER {
                uni	        (1),
                nni		(2)
                }
        ACCESS read-write
        STATUS mandatory
        DESCRIPTION
                "Integer used to set ATM UNI or NNI type"
        ::= { pportEntry 68 }

pportSonetSDHLoopbackConfig OBJECT-TYPE
        SYNTAX INTEGER {
                noLoop		(1),
                lineLoop 	(2),
                diagnosticsLoop	(3)
                }
        ACCESS read-write
        STATUS mandatory
        DESCRIPTION
                "Integer used to set the loopback state of the Sonet/SDH port "
        ::= { pportEntry 69 }

pportSonetSDHLoopStatus OBJECT-TYPE
        SYNTAX INTEGER {
                noLoop		(1),
                lineLoop 	(2),
                diagnosticsLoop	(3)
      		}
        ACCESS read-only
        STATUS mandatory
        DESCRIPTION
                "Integer indicating the current loopback status of the Sonet/SDH port"
        ::= { pportEntry 70 }

pportOutDiscardsCell OBJECT-TYPE
	SYNTAX	Counter 
	ACCESS	read-only
	STATUS	mandatory
	DESCRIPTION
		"The total number of outbound cell discarded due to 
		 congestion." 
	::= { pportEntry 71 }

pportAtmPlcp OBJECT-TYPE
	SYNTAX	INTEGER {
               enable                (1),
               disable               (2)
      }
	ACCESS	read-write
	STATUS	mandatory
	DESCRIPTION " The PLCP maintains the state of the ATM Physical Layer 
                      Convergence Protocol. When the protocol is 
                      disabled atm direct mapping is used with hec cell 
                      delineation."
	::={ pportEntry 72 }

pportCbrTargetClockMode OBJECT-TYPE
	SYNTAX  INTEGER
	ACCESS  read-write
	STATUS  mandatory
	DESCRIPTION
	       "The clocking method to be used by the CBR card.

		4-port CBR card
		-----------------------------------------------

		1 - synchronous (external) clocking
		2 - SRTS clocking
		3 - adaptive clock method"
	::= { pportEntry 73 }

pportCbrCurrentClockMode OBJECT-TYPE
	SYNTAX  INTEGER
	ACCESS  read-only
	STATUS  mandatory
	DESCRIPTION
	       "The clocking method currently used by the CBR card.

		4-port CBR card
		-----------------------------------------------

		1 - synchronous (external) clocking
		2 - SRTS clocking
		3 - adaptive clock method"
	::= { pportEntry 74 }

pportClockMasterChannel OBJECT-TYPE
	SYNTAX  INTEGER
	ACCESS  read-write
	STATUS  mandatory
	DESCRIPTION
	       "The number of the channel (lport) on this pport that is used as
		ACM/SRTS master for this line interface:

		4-port CBR E1/DS1 card (structured mode): 1..4"
	::= { pportEntry 75 }

pportFibreType OBJECT-TYPE
	SYNTAX  INTEGER {
		sonetMultiMode(4),
		sonetShortSingleMode(2)
		}
	ACCESS  read-only
	STATUS  mandatory
	DESCRIPTION     
	       "The type of fibre connected to the ATM-IWU. Its type determines the
		maximum transmission distance.

		1-port ATM-IWU STM-1/STS-3c card
		--------------------------------

		4 - multimode fibre        (maximum transmission distance approx. 2 km)
		2 - single mode fibre short haul       (maximum transmission distance approx. 20 km)"
	::= { pportEntry 76 }

pportLaserStatus OBJECT-TYPE
	SYNTAX  INTEGER {
		off (1),
		on (2)
		}
	ACCESS  read-write 
	STATUS  mandatory
	DESCRIPTION
	       "The configured state of the laser:

		1-port ATM-IWU STM-1/STS-3c card & Topaz 4-port OC3 & STM-1 card
		----------------------------------------------------------------

		1 - off
		2 - on"
	::= { pportEntry 77 }

pportMaxActiveVpiBits OBJECT-TYPE
	SYNTAX  INTEGER (0..12)
	ACCESS  read-write
	STATUS  mandatory
	DESCRIPTION
	       "The maximum number of active VPI bits configured for use at the ATM
		interface. At the ATM UNI, the maximum number of active VPI bits
		configured for use ranges from 0 to 8 only."
	::= { pportEntry 78 }

pportBipErrorsThresh OBJECT-TYPE
	SYNTAX  INTEGER  
	ACCESS  read-write
	STATUS  mandatory
	DESCRIPTION
	       "The threshold of BIP errors. If the number of line BIP-24/8
		rrors persists to exceed this value, the pport will be taken down
		and a trap will be issued:

		1-port ATM-IWU STM-1/STS-3c card:
		--------------------------------

		1 - ignore BIP errors
		4 - 10^-4 errors
		5 - 10^-5 errors
		6 - 10^-6 errors"
	::= { pportEntry 79 } 

pportBipSectionErrors OBJECT-TYPE
	SYNTAX  Counter 
	ACCESS  read-only
	STATUS  mandatory
	DESCRIPTION
	       "The number of B1 section BIP-8 errors since the last reset."
	::= { pportEntry 80 }

pportBipLineErrors OBJECT-TYPE
	SYNTAX  Counter
	ACCESS  read-only
	STATUS  mandatory
	DESCRIPTION
	       "The number of line BIP-24/8 errors since the last reset."
	::= { pportEntry 81 }

pportBipPathErrors OBJECT-TYPE
	SYNTAX  Counter
	ACCESS  read-only
	STATUS  mandatory
	DESCRIPTION
	       "The number of B3 path BIP-8 errors since the last reset."
	::= { pportEntry 82 }

pportFebeErrors OBJECT-TYPE
	SYNTAX  Counter
	ACCESS  read-only
	STATUS  mandatory
	DESCRIPTION 
	       "The number of line Far End Block Errors since the last reset."
	::= { pportEntry 83 }

pportHcsErrors OBJECT-TYPE
	SYNTAX  Counter
	ACCESS  read-only
	STATUS  mandatory
	DESCRIPTION 
	       "The number of correctable HCS errors since the last reset."
	::= { pportEntry 84 }

pportHcsSevereErrors OBJECT-TYPE
	SYNTAX  Counter 
	ACCESS  read-only 
	STATUS  mandatory
	DESCRIPTION
	       "The number of uncorrectable HCS errors since the last reset."
	::= { pportEntry 85 } 

pportCongestedReceivedCells OBJECT-TYPE
	SYNTAX  Counter
	ACCESS  read-only
	STATUS  mandatory
	DESCRIPTION
	       "The number of received cells that were discarded due to congestion of
		the ATM-IWU, since the last reset."
	::= { pportEntry 86 }

pportCongestedTransmittedCells OBJECT-TYPE
	SYNTAX  Counter
	ACCESS  read-only
	STATUS  mandatory
	DESCRIPTION
	       "The number of cells to be transmitted, that were discarded due to
		congestion of the ATM-IWU, since the last reset."
	::= { pportEntry 87 }

pportAtmLayerErroredReceivedCells OBJECT-TYPE
	SYNTAX  Counter 
	ACCESS  read-only
	STATUS  mandatory
	DESCRIPTION 
	       "The number of received cells that were discarded due to ATM layer
		errors, since the last reset."
	::= { pportEntry 88 }

pportAtmLayerErroredTransmittedCells OBJECT-TYPE
	SYNTAX  Counter
	ACCESS  read-only 
	STATUS  mandatory
	DESCRIPTION
	       "The number of cells to be transmitted, that were discarded due to ATM
		layer errors, since the last reset."
	::= { pportEntry 89 }

pportDS0BitStuff OBJECT-TYPE
	SYNTAX  INTEGER
	ACCESS  read-write 
	STATUS  mandatory
	DESCRIPTION
	       "Bit stuffing on or off for 2047 bit pattern in DS0 far end testing."
	::= { pportEntry 90 }

pportDS0BitErrorCount OBJECT-TYPE
	SYNTAX  INTEGER
	ACCESS  read-only 
	STATUS  mandatory
	DESCRIPTION
	       "Total number of errors in 2047 DS0 far end testing."
	::= { pportEntry 91 }

pportDS0BitErrorFreeSeconds OBJECT-TYPE
	SYNTAX  INTEGER
	ACCESS  read-only 
	STATUS  mandatory
	DESCRIPTION
	       "Total number of error free seconds in 2047 DS0 far end testing."
	::= { pportEntry 92 }

pportDS0BitErroredSeconds OBJECT-TYPE
	SYNTAX  INTEGER
	ACCESS  read-only 
	STATUS  mandatory
	DESCRIPTION
	       "Total number of errored seconds in 2047 DS0 far end testing."
	::= { pportEntry 93 }

pportDS0MidspanRepeaters OBJECT-TYPE
	SYNTAX  INTEGER
	ACCESS  read-write 
	STATUS  mandatory
	DESCRIPTION
	       "Number of Midspan repeaters in a link to be punched thru
	for DS0 far end testing."
	::= { pportEntry 94 }

pportDS0TestPatternSync OBJECT-TYPE
	SYNTAX  INTEGER
	ACCESS  read-only 
	STATUS  mandatory
	DESCRIPTION
	       "While DS0 far end testing, the DS0 pattern has detected the
	pattern four consecutive times.  If the pattern is lost, this variable
	will be equal to one."
	::= { pportEntry 95 }

pportDS0InjectBitError OBJECT-TYPE
	SYNTAX  INTEGER
	ACCESS  read-write
	STATUS  mandatory
	DESCRIPTION
	       "While testing DS0 far end lpbk, setting this variable will
	inject a bit error into the test pattern."
	::= { pportEntry 96 }

pportDS0FarendLpbkType OBJECT-TYPE
	SYNTAX  INTEGER
	ACCESS  read-write
	STATUS  mandatory
	DESCRIPTION
	       "The type of DS0 equipment to be looped back at the far end 
	during DS0 far end testing.
	1 - OCU
	2 - DSU
	3 - CSU."
	::= { pportEntry 97 }

pportDS0LpbkMode OBJECT-TYPE
	SYNTAX  INTEGER
	ACCESS  read-write 
	STATUS  mandatory
	DESCRIPTION
	       "This determines what mode the DS0 Processor will be set to.
	1 - no lpbk
	2 - switch lpbk
	3 - far end lpbk."
	::= { pportEntry 98 }

pportDS0SwitchLpbkStart OBJECT-TYPE
	SYNTAX  INTEGER
	ACCESS  read-write 
	STATUS  mandatory
	DESCRIPTION
	       "This is the first DS0 in a sting of consecutive DS0's to
	be looped back at the switch if the DS0 processor is set to switch
	loopback. If it's set to far end loopback, this determines which
	singleton DS0 will be monitored at the receive end."
	::= { pportEntry 99 }

pportDS0SwitchLpbkEnd OBJECT-TYPE
	SYNTAX  INTEGER
	ACCESS  read-write 
	STATUS  mandatory
	DESCRIPTION
	       "This is the Last DS0, +1, in a sting of consecutive DS0's to
	be looped back at the switch if the DS0 processor is set to switch
	loopback. If the DS0 processor is set to far end loopback, this value
	will equal pportDS0SwitchLpbkStart + 1.."
	::= { pportEntry 100 }

pportDS0FarendDS0InLpbk OBJECT-TYPE
	SYNTAX  INTEGER
	ACCESS  read-only 
	STATUS  mandatory
	DESCRIPTION
	       "This indicates the DS0 in far end loopback."
	::= { pportEntry 101 }


pportDS0SendTestTraffic OBJECT-TYPE
	SYNTAX  INTEGER
	ACCESS  read-write
	STATUS  mandatory
	DESCRIPTION
	       "Enable or Disable sending DS0 2047 test pattern for DS0 
	far end testing."
	::= { pportEntry 102 }


pportOc3LoopConfig OBJECT-TYPE
	SYNTAX INTEGER {
		oc3NoLoop     (1),
		oc3AtmLoop    (2),
		oc3SerPhyLoop (3),
		oc3ParPhyLoop (4)
	}
	ACCESS  read-write
	STATUS  mandatory
	DESCRIPTION
		"The loopback state of the ATM IWU OC3"
	::= { pportEntry 103 }


pportOc3LoopStatus OBJECT-TYPE
	SYNTAX INTEGER {
		oc3NoLoop     (1),
		oc3AtmLoop    (2),
		oc3SerPhyLoop (3),
		oc3ParPhyLoop (4)
	}
	ACCESS  read-only
	STATUS  mandatory
	DESCRIPTION
		"The current loopback status of the ATM IWU OC3"
	::= { pportEntry 104 }

pportISDNIpBaseAddr OBJECT-TYPE
	SYNTAX	IpAddress
	ACCESS	read-write
	STATUS	mandatory
	DESCRIPTION
		"Specifies the base address used for IP Dynamic Address Assignment"
	::= { pportEntry 105 }

pportSonetSTM1Scramble OBJECT-TYPE
	SYNTAX	INTEGER {
		disabled (1),
		enabled(2)
		}
	ACCESS	read-write
	STATUS	mandatory
	DESCRIPTION
		"Configured SONET/STM-1 scrambling."
	::= { pportEntry 106 }

pportEFCIMarking OBJECT-TYPE
	SYNTAX	INTEGER {
		disabled (1),
		enabled(2)
		}
	ACCESS	read-write
	STATUS	mandatory
	DESCRIPTION
		"Configured EFCI marking for cell traffic in Topaz IOMs"
	::= { pportEntry 107 }

pportAtmQOSTransmitMode OBJECT-TYPE
	SYNTAX	INTEGER {
		fix-priority (1),
		weighted-round-robin (2)
		}
	ACCESS	read-write
	STATUS	mandatory
	DESCRIPTION
		"Select fix priority or weighted round-robin for cell transmission in different ATM QOS classes."
	::= { pportEntry 108 }
pportHECMode OBJECT-TYPE
	SYNTAX	INTEGER {
		disabled (1),
		enabled(2)
		}
	ACCESS	read-write
	STATUS	mandatory
	DESCRIPTION
		"Configured ATM HEC single bit error correction routine."
	::= { pportEntry 109 }

pportISDNChannelStatus    OBJECT-TYPE
	SYNTAX	OCTET STRING
	ACCESS	read-only
	STATUS	mandatory
	DESCRIPTION
		"The ISDN call status of all the B-Channels on the pport are
	encoded into this 24 character, (for T1 ISDN PRI card...23B+D) or 31 character,
	(for E1 ISDN PRI card...30B+D ) ASCII string. The respective call state for
	each B-Channel is represented in its corresponding bit position. The D-Channel
	status is similarly encoded into the appropriate bit position (24th for T1) or
	(16th for E1). The encoding legend is as follows...

		I	B-Channel is in Idle state
		R	B-Channel is in Dialing (Ringing) state
		C	B-Channel is in Connected (Active) state
		H	B-Channel is in Releasing (Hanging-up) state
		U	D-Channel is Up
		D	D-Channel is Down"

	::= { pportEntry 110 }

pportds1FarEndLoopStatus OBJECT-TYPE
	SYNTAX INTEGER {
		fe-noloop        (1),
		fe-line-loop     (2),
                fe-payload-loop  (3)
		}
	ACCESS read-write
	STATUS mandatory
	DESCRIPTION
		"DS1 Far End Loopback Status as commanded by the switch"
	::= { pportEntry 111 }


pportds1FDLControl OBJECT-TYPE
	SYNTAX INTEGER {
		disabled (1),
		enabled  (2)
		}
	ACCESS read-write
	STATUS mandatory
	DESCRIPTION
		"Enables or Disables FDL Function for DS1 ESF pport"
	::= { pportEntry 112 }


pportds1FDLPrmXmit OBJECT-TYPE
	SYNTAX INTEGER {
		disabled (1),
		enabled  (2)
		}
	ACCESS read-write
	STATUS mandatory
	DESCRIPTION
		"Enables or Disables transmission of Performance Monitoring Report
                 (PRM) messages on the DS1 ESF FDL"
	::= { pportEntry 113 }

pportds1FDLPidXmit OBJECT-TYPE
	SYNTAX INTEGER {
		disabled (1),
		enabled  (2)
		}
	ACCESS read-write
	STATUS mandatory
	DESCRIPTION
		"Enables or Disables transmission of Path ID (PID) messages on
                 the DS1 ESF FDL"
	::= { pportEntry 114 }


pportds1FDLXmitPid OBJECT-TYPE
	SYNTAX	OCTET STRING
	ACCESS	read-write
	STATUS	mandatory
	DESCRIPTION
		"Transmit Path Id to be sent on the DS1 ESF FDL.  (76 bytes)"
	::= { pportEntry 115 }

pportds1FDLRcvPid OBJECT-TYPE
	SYNTAX	OCTET STRING
	ACCESS	read-only
	STATUS	mandatory
	DESCRIPTION
		"The last path id message received on the DS1 ESF FDL.  (76 bytes)"
	::= { pportEntry 116 }

pportds1FDLRcvTsid OBJECT-TYPE
	SYNTAX	OCTET STRING
	ACCESS	read-write
	STATUS	mandatory
	DESCRIPTION
		"The last test id message received on the DS1 ESF FDL.  (76 bytes)"
	::= { pportEntry 117 }

pportSonetSDHFramingMode OBJECT-TYPE
	SYNTAX  INTEGER {
		sonet	(1),
		sdh	(2)
		}
	ACCESS 	read-write
	STATUS  mandatory
	DESCRIPTION
		"The Framing mode for SONET/SDH port interface types."
	::= { pportEntry 118 }

pportds1InbandLoopType OBJECT-TYPE
	SYNTAX INTEGER {
		ds1CSU (1),
		ds1NI (2)
		}
	ACCESS read-write
	STATUS mandatory
	DESCRIPTION
		"Integer used to distinguish Inband Line loopback code sent
		 from the switch when commanding inband line loopbacks, and
                 reckognized by the switch when responding to remote
                 loopback commands"
	::= { pportEntry 119 }

pportESFDataLinkStatus OBJECT-TYPE
        SYNTAX  INTEGER {
		inService    (1),
		outOfService (2)
		}
	ACCESS 	read-only
	STATUS  mandatory
	DESCRIPTION
		"The current status of the DS1 ESF (FDL) data link."
	::= { pportEntry 120 }

pportPMTcaId OBJECT-TYPE
	SYNTAX  INTEGER {
		currentThresholdCVL   (1),
		currentThresholdESL   (2),
		currentThresholdSESL  (3),
		currentThresholdUASL  (4),
		currentThresholdCVP   (5),
		currentThresholdESP   (6),
		currentThresholdSESP  (7),
		currentThresholdSASP  (8),
		currentThresholdCSSP  (9),
		currentThresholdUASP  (10),
		currentThresholdCVS   (11),
		currentThresholdESS   (12),
		currentThresholdSESS  (13),
                currentThresholdESx   (14),
		dayThresholdCVL       (15),
		dayThresholdESL       (16),
		dayThresholdSESL      (17),
		dayThresholdUASL      (18),
		dayThresholdCVP       (19),
		dayThresholdESP       (20),
		dayThresholdSESP      (21),
		dayThresholdSASP      (22),
		dayThresholdCSSP      (23),
		dayThresholdUASP      (24),
		dayThresholdCVS       (25),
		dayThresholdESS       (26),
		dayThresholdSESS      (27),
                dayThresholdESx       (28),
		currentThresholdCVCPP (29),
		currentThresholdESCPP (30),
		currentThresholdSESCPP(31),
		currentThresholdSASCPP(32),
		currentThresholdUASCPP(33),
		dayThresholdCVCPP     (34),
		dayThresholdESCPP     (35),
		dayThresholdSESCPP    (36),
		dayThresholdSASCPP    (37),
		dayThresholdUASCPP    (38),
		currentThresholdCVCPPFE (39),
		currentThresholdESCPPFE (40),
		currentThresholdSESCPPFE(41),
		currentThresholdSASCPPFE(42),
		currentThresholdUASCPPFE(43),
		dayThresholdCVCPPFE     (44),
		dayThresholdESCPPFE     (45),
		dayThresholdSESCPPFE    (46),
		dayThresholdSASCPPFE    (47),
		dayThresholdUASCPPFE    (48)
		}
	ACCESS 	read-write
	STATUS  mandatory
	DESCRIPTION
		"This object identifies the the most recently declared pport
                 threshold crossing alert"
	::= { pportEntry 121 }

pportBchanTimerValue OBJECT-TYPE
	SYNTAX  INTEGER
	ACCESS 	read-write
	STATUS  mandatory
	DESCRIPTION
                 "This value is used on a per port basis to add a delay to
                  answering a ISDN call of the initial Disconnect from the
                  network.  This due to the ARP cache not updating quick
                  enough on the routers"
        ::= { pportEntry 122 }

pportAAL5CRC32Error OBJECT-TYPE
	SYNTAX  Counter
	ACCESS 	read-only
	STATUS  mandatory
	DESCRIPTION
		"Number of received AAL5 packets with CRC32 errors."
	::= { pportEntry 123 }

pportAAL5CPIError OBJECT-TYPE
	SYNTAX  Counter
	ACCESS 	read-only
	STATUS  mandatory
	DESCRIPTION
		"Number of received AAL5 packets with CPI errors
		The only valid value currently defined for the CPI
		field is all zeros"
	::= { pportEntry 124 }

pportAAL5LengthError OBJECT-TYPE
	SYNTAX  Counter
	ACCESS 	read-only
	STATUS  mandatory
	DESCRIPTION
		"Number of received AAL5 packets which satisfied one of the following
		error conditions:
		1. number of received cells * 48 bytes - length value in trailer > 55 bytes
		2. number of received cells * 48 bytes - length value in trailer < 8 bytes"
	::= { pportEntry 125 }

pportAAL5ReassemblyTimerError OBJECT-TYPE
	SYNTAX  Counter
	ACCESS 	read-only
	STATUS  mandatory
	DESCRIPTION
		"Number of expired reassembly timers"
	::= { pportEntry 126 }

pportAAL5MaxNrSegError OBJECT-TYPE
	SYNTAX  Counter
	ACCESS 	read-only
	STATUS  mandatory
	DESCRIPTION
		"Number of received AAL5 packets which exceeds the maximum allowed length"
	::= { pportEntry 127 }

pportRedundancyArch OBJECT-TYPE
	SYNTAX INTEGER {
		disabled (1),
		aps-intracard (2),
		aps-with-resilient-uni (3),
		aps-with-trunk-backup (4)
	}
	ACCESS 	read-write
	STATUS  mandatory
	DESCRIPTION
                 "Pport redundancy architecture.  Default is disabled.
		aps-intracard   -- ports are both on same card.
		aps-with-resilient-uni -- ports may be on different
   			cards, resilient UNI is used to reroute traffic.
		aps-intercard-trunk-backup -- ports may be on different
			cards, aps keeps phy layer in sync w/trunk backup."
        ::= { pportEntry 128 }

pportAPSadminDir OBJECT-TYPE
	SYNTAX INTEGER {
		uni-directional (1),
		bi-directional (2)
	}
	ACCESS 	read-write
	STATUS  mandatory
	DESCRIPTION
                 "Provisioned APS switch-direction-mode. Default is uni-
		directional."
        ::= { pportEntry 129 }

pportAPSlineType OBJECT-TYPE
	SYNTAX INTEGER {
		working-line (1),
		protection-line (2)
	}
	ACCESS 	read-write
	STATUS  mandatory
	DESCRIPTION
                 "APS line type for the pport.  Writable only when
		pportRedundancyArch is disabled."
        ::= { pportEntry 130 }

pportAPSrevertiveMode OBJECT-TYPE
	SYNTAX INTEGER {
		revertive (1),
		nonrevertive (2)
	}
	ACCESS 	read-write
	STATUS  mandatory
	DESCRIPTION
                 "APS revertive mode.  When revertive, after the condition
		for an automatic switchover clears, user traffic will be
		switched back to the working line after the pportAPSwtrPeriod
		expires.   Default is revertive."
        ::= { pportEntry 131 }

pportAPSpairedSlotId OBJECT-TYPE
	SYNTAX INTEGER (1..16)
	ACCESS 	read-write
	STATUS  mandatory
	DESCRIPTION
                 "Slot ID of the paired-with APS pport.  Writable only when
		pportRedundancyArch is disabled."
        ::= { pportEntry 132 }

pportAPSpairedPportId OBJECT-TYPE
	SYNTAX INTEGER
	ACCESS 	read-write
	STATUS  mandatory
	DESCRIPTION
                 "Pport ID of the paired-with APS pport.  Writable only when
		pportRedundancyARch is disabled."
        ::= { pportEntry 133 }

pportAPSsfBerThresh OBJECT-TYPE
	SYNTAX INTEGER (3..5)
	ACCESS 	read-write
	STATUS  mandatory
	DESCRIPTION
                 "Exponent N for APS Signal Failure based on BER.  A line
		bit-error-rate above 10^-N causes an SF BER failure to be
		asserted.  SF BER is cleared when the line BER returns to
		less than 10^-7."
        ::= { pportEntry 134 }

pportAPSsdBerThresh OBJECT-TYPE
	SYNTAX INTEGER (6..9)
	ACCESS 	read-write
	STATUS  mandatory
	DESCRIPTION
                 "Exponent N for APS Signal Degrade based on BER.  A line
		bit-error-rate above 10^-N causes an SD BER failure to be
		asserted.  SD BER is cleared when the line BER returns to
		less than 10^-(N+1)."
        ::= { pportEntry 135 }

pportAPSwtrPeriod OBJECT-TYPE
	SYNTAX INTEGER (5..12)
	ACCESS 	read-write
	STATUS  mandatory
	DESCRIPTION
                 "APS wait-to-restore period.  The number of minutes to
		wait after an automatic switch condition clears before
		switching back to the working line."
        ::= { pportEntry 136 }

pportAPSprotectionLineState OBJECT-TYPE
	SYNTAX INTEGER {
		released (1),
		selected (2)
	}
	ACCESS 	read-only
	STATUS  mandatory
	DESCRIPTION
                 "Indicates the state of the protection line selector. 
		When selected, a protection switchover has taken place
		and user traffic is being selected from the protection
		line."
        ::= { pportEntry 137 }

pportAPSxCommand OBJECT-TYPE
	SYNTAX INTEGER {
		clear (1),
		lockout-protection (2),
		forced-switch-w-to-p (3),
		forced-switch-p-to-w (4),
		manual-switch-w-to-p (5),
		manual-switch-p-to-w (6),
		exercise (7)
	}
	ACCESS 	read-write
	STATUS  mandatory
	DESCRIPTION
                 "External switch commands.  The clear command clears
		any previously activated external command.  Manual
		switch is preemptable by auto-switch-requests (line
		failures) while forced switch is not preemptable (except
		if the protection line fails).  Manual and forced switch
		from protection to working, is valid only for 1+1 mode.
		Exercise simulates a switchover using APS signalling
		without actually performing a switch to protection line."
        ::= { pportEntry 138 }

pportAPSconfigStatus OBJECT-TYPE
	SYNTAX INTEGER {
		not-configured (1),
		valid (2),
		invalid (3)
	}
	ACCESS 	read-only
	STATUS  mandatory
	DESCRIPTION
                 "Status of APS pport configuration.  The not-configured
		status indicates the pport APS feature is not configured
		or it is a non-APS pport.  The valid state indicates the
		pport APS function is configured and has been validated
		by the APS manager.  The invalid state indicates that the
		APS manager has detected a conflict between the working
		line and protection line pport configurations.  The user
		must clear the invalid state by changing the configuration
		of the misconfigured pport as soon as possible.  Check
		pportAPSadminDir, pportAPSlineType, pportAPSrevertiveMode,
		and pportAPSwtrPeriod for any misconfigurations."
        ::= { pportEntry 139 }

pportAPSOperRxStatus OBJECT-TYPE
	SYNTAX	INTEGER {
		    up (1),
		    down (2),
		    testing (3)
		}
	ACCESS	read-only
	STATUS	mandatory
	DESCRIPTION
		"The current state of the pair of APS pports with respect
		 to the ability of the pair to Receive user traffic.  When
		 indicated as up, user traffic may be received on at least
		 one of the ports in the APS pair."
	::= { pportEntry 140 }

pportBertPattern OBJECT-TYPE
	SYNTAX	INTEGER {
		allZeros	(1),
		allOnes 	(2),
		oneZero 	(3),
		oneOneZeroZero	(4),
		oneOf8		(5),
		threeOf24	(6),
		qRSS		(7),
		user1Byte	(8),
		user2Byte	(9),
		user3Byte	(10),
		user4Byte	(11)
		}
	ACCESS	read-write
	STATUS	mandatory
	DESCRIPTION
		"Pattern generated by the XBERT"
	::= { pportEntry 141 }

pportBertUserBytes OBJECT-TYPE
	SYNTAX	INTEGER
	ACCESS	read-write
	STATUS	mandatory
	DESCRIPTION
		"Definition of 1,2,3 or 4 byte pattern if UserNByte selected."
	::= { pportEntry 142 }

pportBertErrorRate OBJECT-TYPE
	SYNTAX	INTEGER {
		none		(1),
		tenMinusThree	(2),
		tenMinusSix	(3)
		}
	ACCESS	read-write
	STATUS	mandatory
	DESCRIPTION
		"Error rate to insert in generated pattern."
	::= { pportEntry 143 }

pportBertCommand OBJECT-TYPE
	SYNTAX	INTEGER {
		start		(1),
		stop		(2),
		clearCounters	(3),
		injectError	(4)
		}
	ACCESS	read-write
	STATUS	mandatory
	DESCRIPTION
		"Single shot commands to the BERT."
	::= { pportEntry 144 }

pportBertStatus OBJECT-TYPE
	SYNTAX	INTEGER {
		unused		 (1),
		unavailable	 (2),
		outOfFrame	 (3),
		inFrame 	 (4)
		}
	ACCESS	read-only
	STATUS	mandatory
	DESCRIPTION
		"Current status of the BERT for this channel."
	::= { pportEntry 145 }

pportBertBitCount OBJECT-TYPE
	SYNTAX	Gauge
	ACCESS	read-only
	STATUS	mandatory
	DESCRIPTION
		"The number of bits received - stops counting at 0xFFFFFFFF"
	::= { pportEntry 146 }

pportBertErrorCount OBJECT-TYPE
	SYNTAX	Gauge
	ACCESS	read-only
	STATUS	mandatory
	DESCRIPTION
		"The number of bits received in error- stops counting
		 at 0xFFFFFFFF"
	::= { pportEntry 147 }


pportds1FELoopbackControl OBJECT-TYPE
	SYNTAX INTEGER {
		disabled (1),
		enabled  (2)
		}
	ACCESS read-write
	STATUS mandatory
	DESCRIPTION
		"Enables or Disables Far end loopback control of the
                 switch. Enabled (2) = Loop up and down commands from far
                 end equipment will be processed.  Disabled (1) - loop up
                 and down commands from far end equipment shall be ignored.
                 This control does not affect the switch's transmission of
                 loopback commands to the far end"
	::= { pportEntry 148 }

pportFT1DS0s OBJECT-TYPE
	SYNTAX	DisplayString
	ACCESS	read-write
	STATUS	mandatory
	DESCRIPTION
		"DS0 usage bitmask for Fractional T1/E1 data rates."
	::= { pportEntry 149 }

pportIMUXCnt OBJECT-TYPE
	SYNTAX	INTEGER
	ACCESS	read-write
	STATUS	mandatory
	DESCRIPTION
		"DS3 Inverse Multiplexer counter value - specifies number of idle
                 cells to insert by the outbound process Hardware."
	::= { pportEntry 150 }

pportds1PMConfigThresh OBJECT-TYPE
	SYNTAX INTEGER {
		rfc1406 (1),
	        itu-g826  (2)
		}
	ACCESS	read-write
	STATUS	mandatory
	DESCRIPTION
		"The setting determines which standard is used for performance monitoring
		configuration thresholds"
	::= { pportEntry 151 }

pportIdleCellType OBJECT-TYPE
	SYNTAX INTEGER {
		atmforum (1),
	        itu  (2)
		}
	ACCESS	read-write
	STATUS	mandatory
	DESCRIPTION
		"The setting determines the type of Idle/unassigned cell
		transmitted by the pport.
                            1 -- ATM Forum   CLP=0, payload=6A
                            2 -- ITU         CLP=1, payload=6A"
	::= { pportEntry 152 }

pportATMTcaInHECErrorUAlertPeriod OBJECT-TYPE
        SYNTAX  INTEGER
        ACCESS  read-write
        STATUS  mandatory
        DESCRIPTION
                "ATM tca ingress HEC error uncorrectable alert
                 period (in min.)."
	DEFVAL { 15 }
        ::= { pportEntry 153 }

pportATMTcaInHECErrorUThresh OBJECT-TYPE
        SYNTAX  INTEGER
        ACCESS  read-write
        STATUS  mandatory
        DESCRIPTION
                "ATM tca ingress HEC error uncorrectable threshold."
	DEFVAL { 1 }
        ::= { pportEntry 154 }

pportATMTcaEBufOverflowCBRAlertPeriod OBJECT-TYPE
        SYNTAX  INTEGER
        ACCESS  read-write
        STATUS  mandatory
        DESCRIPTION
                "ATM tca egress buffer overflow CBR Alert period (in min)"
	DEFVAL { 15 }
        ::= { pportEntry 155 }

pportATMTcaEBufOverflowCBRThresh OBJECT-TYPE
        SYNTAX  INTEGER
        ACCESS  read-write
        STATUS  mandatory
        DESCRIPTION
                "ATM tca egress buffer overflow CBR  threshold."
	DEFVAL { 1 }
        ::= { pportEntry 156 }

pportATMTcaEBufOverflowABRAlertPeriod OBJECT-TYPE
        SYNTAX  INTEGER
        ACCESS  read-write
        STATUS  mandatory
        DESCRIPTION
                "ATM tca egress buffer overflow ABR alert
                 period (in min)"
	DEFVAL { 15 }
        ::= { pportEntry 157 }

pportATMTcaEBufOverflowABRThresh OBJECT-TYPE
        SYNTAX  INTEGER
        ACCESS  read-write
        STATUS  mandatory
        DESCRIPTION
                "ATM tca egress buffer overflow ABR  threshold."
	DEFVAL { 1 }
        ::= { pportEntry 158 }

pportATMTcaEBufOverflowVBR1AlertPeriod OBJECT-TYPE
        SYNTAX  INTEGER
        ACCESS  read-write
        STATUS  mandatory
        DESCRIPTION
                "ATM tca egress buffer overflow VBR1 alert
                 period (in min)"
	DEFVAL { 15 }
        ::= { pportEntry 159 }

pportATMTcaEBufOverflowVBR1Thresh OBJECT-TYPE
        SYNTAX  INTEGER
        ACCESS  read-write
        STATUS  mandatory
        DESCRIPTION
                "ATM tca egress buffer overflow VBR1  threshold."
	DEFVAL { 1 }
        ::= { pportEntry 160 }

pportATMTcaEBufOverflowVBR2AlertPeriod OBJECT-TYPE
        SYNTAX  INTEGER
        ACCESS  read-write
        STATUS  mandatory
        DESCRIPTION
                "ATM tca egress buffer overflow VBR2 alert
		 period (in min)"
	DEFVAL { 15 }
        ::= { pportEntry 161 }

pportATMTcaEBufOverflowVBR2Thresh OBJECT-TYPE
        SYNTAX  INTEGER
        ACCESS  read-write
        STATUS  mandatory
        DESCRIPTION
                "ATM tca egress buffer overflow VBR2  threshold."
	DEFVAL { 1 }
        ::= { pportEntry 162 }

pportATMTcaInFramerFIFOOverflowAlertPeriod OBJECT-TYPE
        SYNTAX  INTEGER
        ACCESS  read-write
        STATUS  mandatory
        DESCRIPTION
                "ATM tca ingress framer FIFO overflow alert
                 period (in min)"
	DEFVAL { 15 }
        ::= { pportEntry 163 }

pportATMTcaInFramerFIFOOverflowThresh OBJECT-TYPE
        SYNTAX  INTEGER
        ACCESS  read-write
        STATUS  mandatory
        DESCRIPTION
                "ATM tca ingress framer FIFO overflow  threshold."
	DEFVAL { 1 }
        ::= { pportEntry 164 }

pportATMTcaELookupFailureAlertPeriod OBJECT-TYPE
        SYNTAX  INTEGER
        ACCESS  read-write
        STATUS  mandatory
        DESCRIPTION
                "ATM tca egress lookup failure alert
                 period (in min)"
	DEFVAL { 15 }
        ::= { pportEntry 165 }

pportATMTcaELookupFailureThresh OBJECT-TYPE
        SYNTAX  INTEGER
        ACCESS  read-write
        STATUS  mandatory
        DESCRIPTION
                "ATM tca egress lookup failure  threshold."
	DEFVAL { 1 }
        ::= { pportEntry 166 }

pportATMTcaEnable OBJECT-TYPE
        SYNTAX  INTEGER
        ACCESS  read-write
        STATUS  mandatory
        DESCRIPTION
                "ATM tca port enable."
        ::= { pportEntry 167 }

pportATMTcaId OBJECT-TYPE
	SYNTAX  INTEGER {
		ingressHECErrorUThresholdC   	(1),
		egressCBRBufferOverflowC      	(2),
		egressABRBufferOverflowC	(3),
		egressVBR1BufferOverflowC	(4),
		egressVBR2BufferOverflowC	(5),
		ingressFramerFIFOOverflowC	(6),
		egressLookupFailureC		(7)
		}
	ACCESS 	read-write
	STATUS  mandatory
	DESCRIPTION
		"This object identifies the the most recently declared pport
                 ATM threshold crossing alert"
	::= { pportEntry 168 }

pportFethAdminMacAddr OBJECT-TYPE
	SYNTAX  OCTET STRING (SIZE(6))
	ACCESS  read-write
	STATUS  mandatory
	DESCRIPTION
		"The configured MAC address to use for this Fast Ethernet
		 port. Setting this to all zeros will force the port to use
		 the burned in MAC address."
	::= { pportEntry 169 }

pportFethOperMacAddr OBJECT-TYPE
	SYNTAX  OCTET STRING (SIZE(6))
	ACCESS	read-only
	STATUS  mandatory
	DESCRIPTION
		"The actual MAC address in use for this Fast Ethernet port."
	::= { pportEntry 170 }

pportConfigAlarmSoakTime OBJECT-TYPE
        SYNTAX	INTEGER (0..65535)
        ACCESS  read-write
        STATUS  mandatory
        DESCRIPTION
                "This is the soak time for configurable alarms. An alarm
                 of this type must persist for this period before it is
                 declared.   The time is specified in millseconds units."
        ::= { pportEntry 171 }

pportConfigAlarmClearTime OBJECT-TYPE
        SYNTAX 	INTEGER (0..65535)
        ACCESS  read-write
        STATUS  mandatory
        DESCRIPTION
                "This is the soak time for configurable alarms. An alarm
                 of this type must remain clear for this period before it is
                 declared to be cleared.   The time is specified in
                 millseconds units."
        ::= { pportEntry 172 }

pportFethPortCapability OBJECT-TYPE
	SYNTAX  INTEGER {
		fullDuplex100Mbps       (1),
		halfDuplex100Mbps       (2),
		fullDuplex10Mbps        (3),
		halfDuplex10Mbps        (4)
		}
	ACCESS  read-write
	STATUS  mandatory
	DESCRIPTION
		"Selection for the speed (10/100) and mode (half/full duplex) of operation
		for Fast Ethernet ports."
	::= { pportEntry 173 }

pportVpshapingDiscardCellCount OBJECT-TYPE
	SYNTAX	INTEGER
	ACCESS 	read-only
	STATUS 	mandatory
	DESCRIPTION
		"Cells discarded due to buffer overflow on this pport because
		of traffic shaping."
	::= { pportEntry 174 }


--	The traffic Shaper parameter table

pportTrafficShaperTable OBJECT-TYPE
	SYNTAX  SEQUENCE OF PportTrafficShaperEntry
	ACCESS  not-accessible
	STATUS  mandatory
	DESCRIPTION
	       "A list of Parameters assigned to the 16 traffic shaper parameter
		conbinations of each pport of the ATM-IWU."
	::= { pport 3 }

pportTrafficShaperEntry OBJECT-TYPE
	SYNTAX  PportTrafficShaperEntry
	ACCESS  not-accessible
	STATUS  mandatory
	DESCRIPTION 
	       "Information of a single system reference clock source."
	INDEX   { pportSlotId, pportId, pportTrafficShaperIndex }
	::= { pportTrafficShaperTable 1 }

PportTrafficShaperEntry ::=
	SEQUENCE {
		pportTrafficShaperIndex
			INTEGER,
		pportTrafficShaperPriority
			INTEGER,
		pportTrafficShaperCellRatioDividend
			INTEGER,
		pportTrafficShaperCellRatioDivisor
			INTEGER,
		pportTrafficShaperPeak
			INTEGER,
		pportTrafficShaperCredit
			INTEGER
		}

pportTrafficShaperIndex OBJECT-TYPE
	SYNTAX  INTEGER (1..16)
	ACCESS  read-write
	STATUS  mandatory
	DESCRIPTION
	       "A positive integer to identify an entry in the pportTrafficShaperTable.
		The ATM-IWU and CS cards support exactly 16 shapers."
	::= { pportTrafficShaperEntry 1 }

pportTrafficShaperPriority OBJECT-TYPE
	SYNTAX  INTEGER (0..15)
	ACCESS  read-write
	STATUS  mandatory
	DESCRIPTION
	       "The priority of the Shaper.
		Channels tied to a Shaper are served only if no higher priority Shapers
		await service. 0 ist the highest, 15 the lowest priority."
	::= { pportTrafficShaperEntry 2 }

pportTrafficShaperCellRatioDividend OBJECT-TYPE
	SYNTAX  INTEGER (0..255)
	ACCESS  read-write
	STATUS  mandatory
	DESCRIPTION
	       "The quotient of pportTrafficShaperCellRatioDividend and
		pportTrafficShaperCellRatioDivisor determines the average rate allocated
		to the shaper. The shaper serves portTrafficShaperCellRatioDividend cells
		in pportTrafficShaperCellRatioDivisor cell times."
	::= { pportTrafficShaperEntry 3 }

pportTrafficShaperCellRatioDivisor OBJECT-TYPE
	SYNTAX  INTEGER (1.. 16777215)
	ACCESS  read-write
	STATUS  mandatory
	DESCRIPTION
	       "See pportTrafficShaperCellRatioDividend"
	::= { pportTrafficShaperEntry 4 }

pportTrafficShaperPeak OBJECT-TYPE
	SYNTAX  INTEGER (0..255)
	ACCESS  read-write
	STATUS  mandatory
	DESCRIPTION
	       "The peak cell rate.
		It defines the minimum gap (in cell units) between emission of any
		consecutive cells in this channel."
	::= { pportTrafficShaperEntry 5 }

pportTrafficShaperCredit OBJECT-TYPE
	SYNTAX  INTEGER (0..255)
	ACCESS  read-write
	STATUS  mandatory
	DESCRIPTION
	       "Defines the maximum number of credits that can be accumulated by a
		shaper. This is equivalent to the maximum burst allowed at the peak rate."
	::= { pportTrafficShaperEntry 6 }


-- 	The Logical Port Group
--
--	The variables that configure logical ports at a node
--

lportTable OBJECT-TYPE
	SYNTAX	SEQUENCE OF LportEntry
	ACCESS	not-accessible
	STATUS	mandatory
	DESCRIPTION
		"A list of logical port entries.  The number of entries is
		given by the value of ifNumber in MIB-II."
	::= { lport 1 }

lportEntry OBJECT-TYPE
	SYNTAX	LportEntry
	ACCESS	not-accessible
	STATUS	mandatory
	DESCRIPTION
		"The logical port entry contains objects relevant to a 
		logical port."
	INDEX	{ lportIfIndex }
	::= { lportTable 1 }

LportEntry ::=
	SEQUENCE {		
		lportIfIndex
			Index,
		lportSlotId
			INTEGER,
		lportPportId
			INTEGER,
		lportId
			INTEGER,
		lportLink
			INTEGER,
		lportProtocol
			INTEGER,
		lportSignal
			INTEGER,
		lportFt1Ds0s
			OCTET STRING,
		lportGlobalDlci
			INTEGER,
		lportDlcmiStd
			INTEGER,
		lportDlciAddrFmt
			INTEGER,
		lportDlciAddrLen
			INTEGER,
		lportMaxFramesize
			INTEGER,
		lportDceVerifTimer
			INTEGER,
		lportDceErrorThresh
			INTEGER,
		lportDceEventCount
			INTEGER,
		lportDteErrorThresh
			INTEGER,
		lportDteEventCount
			INTEGER,
		lportDtePollTimer
			INTEGER,
		lportDteFullCounter
			INTEGER,
		lportDteMulticast
			INTEGER,
		lportTrkRnode
			IpAddress,
		lportTrkRlport
			INTEGER,
		lportCongestState
			INTEGER,
		lportQP1Len
			INTEGER,
		lportQP2Len
			INTEGER,
		lportQP3Len
			INTEGER,
		lportQP4Len
			INTEGER,
		lportErrTime
			TimeTicks,
		lportErrType
			INTEGER,
		lportErrData
			OCTET STRING,
		lportDiagTestId
			INTEGER,
		lportDiagTestRuns
			INTEGER,
		lportDataRate
			INTEGER,
		lportTrkStatus
			INTEGER,
		lportSevCongests
			INTEGER,
		lportAbsCongests
			INTEGER,
		lportTrkOverhead
			INTEGER,
		lportTrkUtil
			INTEGER,
		lportVAvailbw
			INTEGER,
		lportTrkLastTimeChange
			TimeTicks,
		lportCongestRate
			INTEGER,
		lportCongestRateThresh
			INTEGER,
		lportDiagState
			INTEGER,
		lportDiagOptionStr
			OCTET STRING,
		lportDiagPassCount
			INTEGER,
		lportDiagFailCount
			INTEGER,
		lportDiagResultStr
			DisplayString,
		lportDs0BitStuff
			INTEGER,
		lportErrorThreshold
			INTEGER,
		lportUnsyncBandwidth
			INTEGER,
		lportDTEInStatusFrames
			Counter,
		lportDTEInFullStatusFrames 
			Counter,
		lportDTEInAsyncStatusFrames 
			Counter,
		lportDTEInErrorFrames
			Counter,
		lportDTEOutPollFrames 
			Counter,
		lportDTEPollErrorCounts 
			Counter,
		lportDTEFailCounts
			Counter,
		lportDTEFailReason 
			INTEGER,
		lportDTEOperStatus 
			INTEGER,
		lportDCEInPollFrames 
			Counter,
		lportDCEInErrorFrames
			Counter,
		lportDCEOutStatusFrames 
			Counter,
		lportDCEOutFullStatusFrames 
			Counter,
		lportDCEOutAsyncStatusFrames
			Counter,
		lportDCEPollErrorCounts 
			Counter,
		lportDCEFailCounts
			Counter,
		lportDCEFailReason 
			INTEGER,
		lportDCEOperStatus 
			INTEGER,
		lportDCEOperDlcmiStd 
			INTEGER,
		lportLMIInErrorFrames
			Counter,
		lportDCEnN4
			INTEGER,
		lportDCEnT3
			INTEGER,
		lportXmitLatencyThreshold
			INTEGER,
		lportXmitRefillPriority0Percentage
			INTEGER,
		lportXmitRefillPriority1Percentage
			INTEGER,
		lportXmitRefillPriority2Percentage
			INTEGER,
		lportXmitRefillPriority3Percentage
			INTEGER,
		lportXmitDiscardLow
			INTEGER,
		lportSevereThreshold
			INTEGER,
		lportMildThreshold
			INTEGER,
		-- 82, 83, 84, 85 are deprecated
		-- These OID will be reused.
		lportTrkKeepAliveTimer
			INTEGER,
		lportTrkKeepAliveErrorThreshold
			INTEGER,
		lportIgCutThruStatus
			INTEGER,
		lportEgCutThruStatus
			INTEGER,
		lportEgCutThruThresh
			INTEGER,
		lportFrameRelayTrkEnable
			INTEGER,
		lportSmdsSsiIf
			INTEGER,
		lportSmdsSsiSlot
			INTEGER,
		lportSmdsScrnId
			INTEGER,
		lportSmdsIaScrnOp
			INTEGER,
		lportSmdsGaScrnOp
			INTEGER,
		lportSmdsIaScrnMap
			OCTET STRING,
		lportSmdsGaScrnMap
			OCTET STRING,
		lportSmdsTrkAddr
			OCTET STRING,
		lportSmdsCrc
			INTEGER,
		lportSmdsCpePoll
			INTEGER,
		lportSmdsPduCheck
			INTEGER,
		lportSmdsCntOutFrDxi2HbPolls 
			Counter,
		lportSmdsCntOutByteDxi2HbPolls 
			Counter,
		lportSmdsCntInFrDxi2HbPolls 
			Counter,
		lportSmdsCntInByteDxi2HbPolls 
			Counter,
		lportSmdsCntOutFrSip3s 
			Counter,
		lportSmdsCntOutByteSip3s 
			Counter,
		lportSmdsCntInFrSip3s 
			Counter,
		lportSmdsCntInByteSip3s 
			Counter,
		lportSmdsCntDxi2LinkIdInvalids 
			Counter,
		lportSmdsCntDxi2StationIdInvalids 
			Counter,
		lportSmdsCntDxi2CrInvalids 
			Counter,
		lportSmdsCntDxi2AeInvalids 
			Counter,
		lportSmdsCntDxi2CtrlInvalids 
			Counter,
		lportSmdsCntDxi2FrameSizeErrors 
			Counter,
		lportSmdsCntSip3RsvdInvalids 
			Counter,
		lportSmdsCntSip3BetagMismatchs 
			Counter,
		lportSmdsCntSip3BasizeIncorrects 
			Counter,
		lportSmdsCntSip3BasizeInvalids 
			Counter,
		lportSmdsCntSip3DaTypeInvalids 
			Counter,
		lportSmdsCntSip3DaInvalids 
			Counter,
		lportSmdsCntSip3SaTypeInvalids 
			Counter,
		lportSmdsCntSip3SaInvalids 
			Counter,
		lportSmdsCntSip3BasizeMismatchs 
			Counter,
		lportSmdsCntSip3HeLenInvalids 
			Counter,
		lportSmdsCntSip3HeVersionInvalids 
			Counter,
		lportSmdsCntSip3HeCarrierInvalids 
			Counter,
		lportSmdsCntSip3Crc32Errors 
			Counter,
		lportSmdsCntSip3TRsvdInvalids 
			Counter,
		lportSmdsCntSaNotFounds 
			Counter,
		lportSmdsCntSaValidationFails 
			Counter,
		lportSmdsCntSaDaOnSamePorts 
			Counter,
		lportSmdsCntDaSsiMismacths 
			Counter,
		lportSmdsCntSsiProvisionErrors 
			Counter,
		lportSmdsCntDstIaNotFounds 
			Counter,
		lportSmdsCntDstGaNotFounds 
			Counter,
		lportSmdsCntSrcIaScrnFails 
			Counter,
		lportSmdsCntDstIaScrnFails 
			Counter,
		lportSmdsCntDstGaScrnFails 
			Counter,
		lportSmdsTotalDiscards 
			Counter,
		lportSmdsSsiNode 
			INTEGER,
		lportBilling
			INTEGER,
		lportSmdsReserved144
			INTEGER,
		lportLinkStatus 
			INTEGER,
		lportLMIDelay
			INTEGER,
		lportCRC
			INTEGER,
		lportSmdsMulticastGa
			OCTET STRING,
		lportSmdsMulticastIpAddr
			IpAddress,
		lportAtmVPI
			INTEGER,
		lportAtmVCI
			INTEGER,
		lportPeakCellRateindex
			INTEGER,
		lportSustCellRate
			INTEGER,
		lportBurstTolerance
			INTEGER,
		lportBuTrkOnFailure
			INTEGER,
		lportTrkFailureThrsh
			INTEGER,
		lportTrkRestThrsh
			INTEGER,
		lportBuTrkRetryInt
			INTEGER,
		lportBuTrkRetryNum
			INTEGER,
		lportBuTrkCycleInt
			INTEGER,
		lportTrkManualBu
			INTEGER,
		lportPrimTrk
			Index,
		lportInitCallSetup
			INTEGER,
		lportBuFailReason
			INTEGER,
		lportQ922Enable
			INTEGER,
		lportQ922State
			INTEGER,
		lportTrkPduRevision
			INTEGER,
		lportPVCMgrPduRevision
			INTEGER,
		lportDS0LoopStatus
			INTEGER,
		lportISDNDuration 
			INTEGER,
		lportISDNSourceAddr
			OCTET STRING,
		lportISDNDestAddr 
			OCTET STRING,
		lportISDNIpAddr 
			IpAddress,
		lportISDNCallRejCause
			INTEGER,
		lportLastInvalidDLCI
			INTEGER,
		lportTrkProtState
			INTEGER,
		lportTrkTrafficMix 
			INTEGER,
		lportNumVC
			INTEGER,
		lportTrkAdminCost 
			INTEGER,
		lportPrivateNet
			INTEGER,
		lportTrkStaticDelay
			INTEGER,
		lportTrkDynamicDelay
			INTEGER,
		lportAtmDataRateQoS1
			INTEGER,
		lportAtmDataRateQoS2
			INTEGER,
		lportAtmDataRateQoS3
			INTEGER,
		lportAtmDataRateQoS4
			INTEGER,
		lportOutVAvailbwQoS1
			INTEGER,
		lportOutVAvailbwQoS2
			INTEGER,
		lportOutVAvailbwQoS3
			INTEGER,
		lportOutVAvailbwQoS4
			INTEGER,
		lportInVAvailbwQoS1
			INTEGER,
		lportInVAvailbwQoS2
			INTEGER,
		lportInVAvailbwQoS3
			INTEGER,
		lportInVAvailbwQoS4
			INTEGER,
		lportOutAllocbwQoS1
			INTEGER,
		lportOutAllocbwQoS2
			INTEGER,
		lportOutAllocbwQoS3
			INTEGER,
		lportOutAllocbwQoS4
			INTEGER,
		lportInAllocbwQoS1
			INTEGER,
		lportInAllocbwQoS2
			INTEGER,
		lportInAllocbwQoS3
			INTEGER,
		lportInAllocbwQoS4
			INTEGER,
		lportDynamicQoSbw
			INTEGER,
		lportSVCRetryTimer
			INTEGER,
		lportAtmNetworkType
			INTEGER,
		lportAtmRouteMetricQoS1
			INTEGER,
		lportAtmRouteMetricQoS2
			INTEGER,
		lportAtmRouteMetricQoS3
			INTEGER,
		lportAtmRouteMetricQoS4
			INTEGER,
		lportIlmiPollTimeout
			INTEGER,
		lportAtmProtocol
			INTEGER,
		lportIlmiAdminStatus
			INTEGER,
		lportIlmiOperStatus
			INTEGER,
		lportIlmiPollRetry
			Counter,
		lportAtmVpiBits
			INTEGER,
		lportAtmVciBits
			INTEGER,
		lportAtmOamAlarmEnable
			INTEGER,
		lportInVAvailbw
			INTEGER,
		lportbwUNIPolicy
			INTEGER,
		lportStarvation
			INTEGER,
		lportRecOverflow
			INTEGER,
		lportLossOfCellSequence
			INTEGER,
		lportLossOfStructurePointer
			INTEGER,
		lportCbrInsDummyCells
			Counter,
		lportRecFifoUnderflowCnt
			Counter,
		lportRecFifoOverflowCnt
			Counter,
		lportCbrLossOfStructurePointerCnt
			Counter,
		lportCbrLossOfCellSequenceCnt
			Counter,
		lportShaperId
			INTEGER,
		lportIlmiPrefixScreenMode
			INTEGER,
		lportSmdsPduViolTca
			INTEGER,
		lportSmdsPduViolThresh
			INTEGER,
		lportSmdsPduHdrSip3SaNotFound
			OCTET STRING,
		lportSmdsPduHdrSip3SaDaOnSamePort
			OCTET STRING,
		lportSmdsPduHdrSip3DstGaNotFound
			OCTET STRING,
		lportSmdsPduHdrSip3DstIaScrnFail
			OCTET STRING,
		lportSmdsPduHdrSip3SaValFail
			OCTET STRING,
		lportSmdsPduHdrSip3DstIaNotFound
			OCTET STRING,
		lportSmdsPduHdrSip3SrcIaScrnFail
			OCTET STRING,
		lportSmdsPduHdrSip3DstGaScrnFail
			OCTET STRING,
		lportSmdsPduHdrSip3SaTypeInvalid
			OCTET STRING,
		lportSmdsPduHdrSip3DaTypeInvalid
			OCTET STRING,
		lportSmdsPduHdrDxi2LinkIdInvalid
			OCTET STRING,
		lportSmdsPduHdrDxi2CrInvalid
			OCTET STRING,
		lportSmdsPduHdrDxi2CtrlInvalid
			OCTET STRING,
		lportSmdsPduHdrDxi2StationIdInvalid
			OCTET STRING,
		lportSmdsPduHdrDxi2AeInvalid
			OCTET STRING,
		lportDS0FarendLpbkEnabled
			INTEGER,
		lportDS0FarendLpbkDisabled
			INTEGER,
		lportTrkProtFailureThreshold
			INTEGER,
		lportPtr
			OCTET STRING,
		lportISDNPoolUtil 
			INTEGER,
		lportISDNIpAddrAssignFail
			INTEGER,
		lportTrkUtilQoS1
			INTEGER,
		lportTrkUtilQoS2
			INTEGER,
		lportTrkUtilQoS3
			INTEGER,
		lportTrkUtilQoS4
			INTEGER,
		lportInCells
			Counter,
		lportOutCells
			Counter
	}

lportIfIndex OBJECT-TYPE
	SYNTAX	Index
	ACCESS	read-only
	STATUS	mandatory
	DESCRIPTION
		"The ifIndex value of the  corresponding ifEntry."
	::= { lportEntry 1 }

lportSlotId OBJECT-TYPE
	SYNTAX	INTEGER
	ACCESS	read-only
	STATUS	mandatory
	DESCRIPTION
		"The slot number of the board the port is on."
	::= { lportEntry 2 }

lportPportId OBJECT-TYPE
	SYNTAX	INTEGER
	ACCESS	read-only
	STATUS	mandatory
	DESCRIPTION
		"The physical port number of the interface on the board."
	::= { lportEntry 3 }

lportId OBJECT-TYPE
	SYNTAX	INTEGER
	ACCESS	read-only
	STATUS	mandatory
	DESCRIPTION
		"The logical port number of the interface on the physical
		port.  A logical port can be uniquely identified in a 
		Cascade network as { NodeId.lportSlotId.lportPportId.lportId }.
		lportId is defaulted to 1 (i.e., one-to-one mapping between the 
		physical port and the logical port such as local V.35 or
 		carrier) except the following cases:
		- For ufr, nfr and trk logical port, it indicates the bundle
		  number for fractional T1 or 24-bundle T1.
		- For pdntrk logical port, it indicates the dlci over the PDN.
		Note that pdntrk is not allowed on fractional T1 or 24-bundle 
		T1 physical port."
	::= { lportEntry 4 }

lportLink OBJECT-TYPE
	SYNTAX	INTEGER {
-- user link: connecting to non-casc 
		    -- user (0),		
-- trunk: connecting to casc switch
		    trk (1),		
-- transport: connecting 2 FR networks using one circuit
		    transport (2)	
		}
	ACCESS	read-write
	STATUS	mandatory
	DESCRIPTION
		"The equipment type of the peer to which the logical port
		is connected."
	::= { lportEntry 5 }

lportProtocol OBJECT-TYPE
	SYNTAX	INTEGER {
-- frame relay protocol
		    -- fr (0),		
-- non-frame relay protocol
		    nfr (1),		
-- (direct frad usr port or casc trunk)
-- xlation frad, PPP-to-1294
		    fradPPPto1294 (2),	
		    smds(3),		-- SMDS	
		    atm (4),		-- ATM user-network 
		    isdndchan (5),	-- ISDN pri d-channel
		    dirmgmttrk(7),	-- Direct management trunk for SMDS
		    smdsoptmgmt(8),	-- SMDS OPT management trunk
		    atmAAL1(10)		-- ATM AAL1 (CBR) connections
		}
	ACCESS	read-write
	STATUS	mandatory
	DESCRIPTION
		"The data link protocol running on the logical port."
	::= { lportEntry 6 }

lportSignal OBJECT-TYPE
	SYNTAX	INTEGER {
		    dce (1),		-- network side 
		    dte (2),		-- user side 
		    nni (3)		-- bi-directional, both network & user
		}
	ACCESS	read-write
	STATUS	mandatory
	DESCRIPTION
		"The user-network signalling capability for SVC and DLCMI 
		of the logical port.
		Note that this only applies to fr protocol port."
	::= { lportEntry 7 }

lportFt1Ds0s OBJECT-TYPE
	SYNTAX	OCTET STRING
	ACCESS	read-only
	STATUS	mandatory
	DESCRIPTION
		"The bit mask indicating the DS0s for the fractional T1/E1 
		logical port which must be a subset of the corresponding
		pportDs1Ds0s. It's represented by a 32-bit hex char string."
	::= { lportEntry 8 }

lportGlobalDlci OBJECT-TYPE
	SYNTAX	INTEGER
	ACCESS	read-write
	STATUS	mandatory
	DESCRIPTION
		"The global DLCI correspondent to the interface if the DLCI is
		globally significant in the network. Note that this object is
		read-write only during creation, and read-only after creation."
	::= { lportEntry 9 }

lportDlcmiStd OBJECT-TYPE
	SYNTAX INTEGER {
-- Not applicable, for example, on a trunk
		   -- not-applicable (0),	
                   disabled     (1),
                   lmiRev1      (2),
                   ansiT1-617-D (3),  -- ANSI T1.617 Annex D
                   ccittQ-933-A (4),  -- CCITT Q.933 Annex A
                   autodetect   (5),  -- Auto Detection
                   ansiT1-617-B (6)   -- ANSI T1.617 Annex B
             }
        ACCESS   read-write
        STATUS   mandatory
        DESCRIPTION
                "This variable states which Data  Link  Connection Management
                scheme is active (and by implication, what DLCI it uses) on 
                the Frame Relay interface."
	::= { lportEntry 10 }


lportDlciAddrFmt OBJECT-TYPE
	SYNTAX INTEGER {
                   q922           (1)   -- 10-bit (CCITT Standard) 
             	}
        ACCESS  read-only
        STATUS  mandatory
        DESCRIPTION
                "This variable states which address format is in use on the
                Frame Relay interface."
	::= { lportEntry 11 }

lportDlciAddrLen OBJECT-TYPE
	SYNTAX INTEGER {
                   two-octets-10-bits (1),    -- Current Standard
                   three-octets-10-bits (2),
                   three-octets-16-bits (3),
		   four-octets-17-bits (4),
		   four-octets-23-bits (5)
             	}
        ACCESS  read-only
        STATUS  mandatory
        DESCRIPTION
                "This variable states which address length in octets. In the
                case of Q922 format, the length indicates the entire length 
                of the address including the control portion."
	::= { lportEntry 12 }

lportMaxFramesize OBJECT-TYPE
	SYNTAX	INTEGER
	ACCESS	read-only
	STATUS	mandatory
	DESCRIPTION
		"The maximum frame size supported on the interface. Currently
		 it's not used."
	::= { lportEntry 13 }

lportDceVerifTimer OBJECT-TYPE
	SYNTAX	INTEGER
	ACCESS	read-write
	STATUS	mandatory
	DESCRIPTION
		"The polling verification timer (secs) on the DCE interface.
		 If the port is configured as a DXI/SNI, then this MIB object
		 defines the heartbeat poll timer setting."
	::= { lportEntry 14 }

lportDceErrorThresh OBJECT-TYPE
	SYNTAX	INTEGER
	ACCESS	read-write
	STATUS	mandatory
	DESCRIPTION
		"The error threshold on the DCE interface.
		 If the port is configured as a DXI/SNI, then this MIB object
		 defines the heartbeat poll No Ack threshold setting."
	::= { lportEntry 15 }

lportDceEventCount OBJECT-TYPE
	SYNTAX	INTEGER
	ACCESS	read-write
	STATUS	mandatory
	DESCRIPTION
		"The monitored events count on the DCE interface."
	::= { lportEntry 16 }

lportDteErrorThresh OBJECT-TYPE
	SYNTAX	INTEGER
	ACCESS	read-write
	STATUS	mandatory
	DESCRIPTION
		"The error threshold on the DTE interface."
	::= { lportEntry 17 }

lportDteEventCount OBJECT-TYPE
	SYNTAX	INTEGER
	ACCESS	read-write
	STATUS	mandatory
	DESCRIPTION
		"The monitored events count on the DTE interface."
	::= { lportEntry 18 }

lportDtePollTimer OBJECT-TYPE
	SYNTAX	INTEGER
	ACCESS	read-write
	STATUS	mandatory
	DESCRIPTION
		"The link status polling timer (secs) on the DTE interface."
	::= { lportEntry 19 }

lportDteFullCounter OBJECT-TYPE
	SYNTAX	INTEGER
	ACCESS	read-write
	STATUS	mandatory
	DESCRIPTION
		"The full status polling counter on the DTE interface."
	::= { lportEntry 20 }

lportDteMulticast OBJECT-TYPE
	SYNTAX	INTEGER {
		    one-way (1),
		    two-way (2),
		    m-way (3)
		}
	ACCESS	read-only
	STATUS	mandatory
	DESCRIPTION
		"The multicast capability of the interface."
	::= { lportEntry 21 }

lportTrkRnode OBJECT-TYPE
	SYNTAX	IpAddress
	ACCESS	read-write
	STATUS	mandatory
	DESCRIPTION
		"Node at the other end of the trunk. This object is read-write
		only during lport creation, and read-only thereafter."
	::= { lportEntry 22 }

lportTrkRlport OBJECT-TYPE
	SYNTAX	INTEGER
	ACCESS	read-write
	STATUS	mandatory
	DESCRIPTION
		"Logical port (IfIndex) at the other end of the trunk. This 
"
	::= { lportEntry 23 }

lportCongestState OBJECT-TYPE
	SYNTAX	INTEGER {
		    normal (1),		-- below "knee" point
		    mild (2),		-- between "knee" & "cliff" points
		    severe (3),		-- above "cliff" point
		    critical (4)        -- xmit queue is full
		}
	ACCESS	read-only
	STATUS	mandatory
	DESCRIPTION
		"Congestion State for the logical port."
	::= { lportEntry 24 }

lportQP1Len OBJECT-TYPE
	SYNTAX	INTEGER
	ACCESS	read-only
	STATUS	mandatory
	DESCRIPTION
		"Priority-1 queue length (number of packets) in xmit buffer."
	::= { lportEntry 25 }

lportQP2Len OBJECT-TYPE
	SYNTAX	INTEGER
	ACCESS	read-only
	STATUS	mandatory
	DESCRIPTION
		"Priority-2 queue length (number of packets) in xmit buffer."
	::= { lportEntry 26 }

lportQP3Len OBJECT-TYPE
	SYNTAX	INTEGER
	ACCESS	read-only
	STATUS	mandatory
	DESCRIPTION
		"Priority-3 queue length (number of packets) in xmit buffer."
	::= { lportEntry 27 }

lportQP4Len OBJECT-TYPE
	SYNTAX	INTEGER
	ACCESS	read-only
	STATUS	mandatory
	DESCRIPTION
		"Priority-4 queue length (number of packets) in xmit buffer."
	::= { lportEntry 28 }

lportErrTime OBJECT-TYPE
	SYNTAX	TimeTicks
	ACCESS	read-only
	STATUS	mandatory
	DESCRIPTION
		"The value of sysUpTime at which the last error was detected."
	::= { lportEntry 29 }

lportErrType OBJECT-TYPE
        SYNTAX  INTEGER {
  		    short-frame	(1),
		    hdlc-abort	(2),
		    residual-bit (3),
		    crc-Error	(4),
		    rcv-Long	(5),
		    rcv-overrun	(6),
		    tx-underrun	(7),
                    unknownError (8),
                    illegalDLCI (9),
                    unknownDLCI (10),
                    dlcmiProtoErr (11),
                    dlcmiUnknownIE (12),
                    dlcmiSequenceErr (13),
                    dlcmiUnknownRpt (14),
		    unknownProt (15),
		    discardFW (16),
		    discardRange (17),
		    discardPortMismatch (18),
		    discardIllegalLen (19)
		}
	ACCESS  read-only
	STATUS  mandatory
	DESCRIPTION
                "The type of error that was last seen on this interface."
        ::= { lportEntry 30 }

lportErrData OBJECT-TYPE
	SYNTAX  OCTET STRING
	ACCESS  read-only
	STATUS  mandatory
	DESCRIPTION
                "An octet string containing as much of the error packet as
		possible.  As a minimum, it must contain the Q.922 Address
		or as much as was delivered.  It is desirable to include 
		all information up to the PDU."
        ::= { lportEntry 31 }

lportDiagTestId OBJECT-TYPE
	SYNTAX	INTEGER
	ACCESS	read-write
	STATUS	mandatory
	DESCRIPTION
		"Identification for the diagnostics tests to be run."
	::= { lportEntry 32 }

lportDiagTestRuns OBJECT-TYPE
	SYNTAX	INTEGER 
	ACCESS	read-write
	STATUS	mandatory
	DESCRIPTION
		"Number of passes of the diagnostics tests to be run.
		The default value is 1."
	::= { lportEntry 33 }

lportDataRate OBJECT-TYPE
	SYNTAX	INTEGER 
	ACCESS	read-write
	STATUS	mandatory
	DESCRIPTION
		"An estimate of the logical port's data rate in bits per
		second."
	::= { lportEntry 34 }

lportTrkStatus OBJECT-TYPE
	SYNTAX	INTEGER {
		    -- ndown (0),
		    nattempt (1),	
		    ninit (2),
		    n2way (3),
		    nexstart (4),
		    nexchange (5),
		    nloading (6),
		    nfull (7),
		    btdefined (9)
		}
	ACCESS	read-only
	STATUS	mandatory
	DESCRIPTION
		"The current state of the trunk.  The btdefined state only
		 applies to backup trunks."
	::= { lportEntry 35 }

lportSevCongests OBJECT-TYPE
	SYNTAX	INTEGER 
	ACCESS	read-only
	STATUS	mandatory
	DESCRIPTION
		"The cumulative number of times that the lport's congestion
		state has changed from mildly-congested to severely-congested
		since the last reset."
	::= { lportEntry 36 }

lportAbsCongests OBJECT-TYPE
	SYNTAX	INTEGER 
	ACCESS	read-only
	STATUS	mandatory
	DESCRIPTION
		"The cumulative number of times that the lport's congestion
		state has changed from severely-congested to absolutely-
		congested since the last reset."
	::= { lportEntry 37 }

lportTrkOverhead OBJECT-TYPE
	SYNTAX	INTEGER 
	ACCESS	read-write
	STATUS	mandatory
	DESCRIPTION
		"An estimate of the overhead (headers and internal control
		messages) in trunking user data in terms of a percentage of 
		the configured trunk bandwidth."
	::= { lportEntry 38 }

lportTrkUtil OBJECT-TYPE
	SYNTAX	INTEGER 
	ACCESS	read-write
	STATUS	mandatory
	DESCRIPTION
		"An estimate of the real utilization of the trunk bandwidth
		in terms of a percentage of the configured trunk bandwidth."
	::= { lportEntry 39 }

lportVAvailbw OBJECT-TYPE
	SYNTAX	INTEGER 
	ACCESS	read-only
	STATUS	mandatory
	DESCRIPTION
		"Currently available virtual trunk bandwidth."
	::= { lportEntry 40 }
		
lportTrkLastTimeChange OBJECT-TYPE
	SYNTAX	TimeTicks 
	ACCESS	read-only
	STATUS	mandatory
	DESCRIPTION
		"The sysUpTime value when the trunk was last changed to 
		the current status."
	::= { lportEntry 41 }

lportCongestRate OBJECT-TYPE
	SYNTAX	INTEGER 
	ACCESS	read-only
	STATUS	mandatory
	DESCRIPTION
		"The rate (%) of entering severely or absolutely congested 
		states in the last one minute interval."
	::= { lportEntry 42 }
	
lportCongestRateThresh OBJECT-TYPE
	SYNTAX	INTEGER 
	ACCESS	read-write
	STATUS	mandatory
	DESCRIPTION
		"The alert threshold (%) for the CongestRate; trap will be sent
		when exceeded."
	::= { lportEntry 43 }
	
lportDiagState OBJECT-TYPE
	SYNTAX	INTEGER {
		-- inactive (0),
		active(1)
	}
	ACCESS	read-write
	STATUS	mandatory
	DESCRIPTION
		"The current state of the diagnostic on this logical port."
	::= { lportEntry 44 }

lportDiagOptionStr OBJECT-TYPE
	SYNTAX	OCTET STRING
	ACCESS	read-write
	STATUS	mandatory
	DESCRIPTION
		"Optional parameters to the diagnostic."
	::= { lportEntry 45 }

lportDiagPassCount OBJECT-TYPE
	SYNTAX	INTEGER
	ACCESS	read-only
	STATUS	mandatory
	DESCRIPTION
		"Number of successful diagnostic passes."
	::= { lportEntry 46 }

lportDiagFailCount OBJECT-TYPE
	SYNTAX	INTEGER
	ACCESS	read-only
	STATUS	mandatory
	DESCRIPTION
		"Number of failed diagnostic passes."
	::= { lportEntry 47 }

lportDiagResultStr OBJECT-TYPE
	SYNTAX	DisplayString
	ACCESS	read-only
	STATUS	mandatory
	DESCRIPTION
		"Description of last diagnostic failure."
	::= { lportEntry 48 }

lportDs0BitStuff OBJECT-TYPE
	SYNTAX	INTEGER {
		-- no-bit-stuffing (0),
		bit-stuffing (1)
		}
	ACCESS	read-write
	STATUS	mandatory
	DESCRIPTION
		"Is bit stuffing enabled on this lport?"
	::= { lportEntry 49 }

lportErrorThreshold OBJECT-TYPE
	SYNTAX	INTEGER 
	ACCESS	read-write
	STATUS	mandatory
	DESCRIPTION
		"The per minute error threshold before a link error 
		trap is sent."
	::= { lportEntry 50 }

lportUnsyncBandwidth OBJECT-TYPE
	SYNTAX	INTEGER 
	ACCESS	read-only
	STATUS	mandatory
	DESCRIPTION
		"The accumulated allocated/deallocated bandwidth which
                has not been propagated by OSPF yet."
	::= { lportEntry 51 }

lportDTEInStatusFrames OBJECT-TYPE
	SYNTAX	Counter 
	ACCESS	read-only
	STATUS	mandatory
	DESCRIPTION
		"The number of LMI STATUS frames received from the DCE since the
		last system reset. The count includes link integrity 
		verification frames only."
	::= { lportEntry 52 }

lportDTEInFullStatusFrames OBJECT-TYPE
	SYNTAX	Counter 
	ACCESS	read-only
	STATUS	mandatory
	DESCRIPTION
		"The number of LMI Full STATUS frames received from the DTE since
		the last system reset."
	::= { lportEntry 53 }

lportDTEInAsyncStatusFrames OBJECT-TYPE
	SYNTAX	Counter 
	ACCESS	read-only
	STATUS	mandatory
	DESCRIPTION
		"The number of asynchronous LMI Status frames received from the 
		DTE since the last system reset. For LMI Rev 1, these are Update
		STATUS frames. For ANSI Annex D and CCITT Annex A these are 
		Asynchronous STATUS frames."
	::= { lportEntry 54 }

lportDTEInErrorFrames OBJECT-TYPE
	SYNTAX	Counter 
	ACCESS	read-only
	STATUS	mandatory
	DESCRIPTION
		"The number of LMI frames received containing protocol errors."
	::= { lportEntry 55 }

lportDTEOutPollFrames OBJECT-TYPE
	SYNTAX	Counter 
	ACCESS	read-only
	STATUS	mandatory
	DESCRIPTION
		"The number of LMI Status Enquiry frames transmitted since the last system 
		reset."
	::= { lportEntry 56 }

lportDTEPollErrorCounts OBJECT-TYPE
	SYNTAX	Counter 
	ACCESS	read-only
	STATUS	mandatory
	DESCRIPTION
		"The number of DTE in-channel signaling link reliability errors (i.e. 
		 LMI Status Enquiry frames that were not responded to, sequence number 
		 errors) since the last system reset."
	::= { lportEntry 57 }

lportDTEFailCounts OBJECT-TYPE
	SYNTAX  Counter 
	ACCESS	read-only
	STATUS	mandatory
	DESCRIPTION
                "The number of times since the last system reset
		LMI has declared the DTE side of the link down due to excessive 
		errors."
	::= { lportEntry 58 }

lportDTEFailReason OBJECT-TYPE
	SYNTAX INTEGER {
-- no failure
		   -- ok	   	(0), 
                   dte-bad-Nr   (1), -- received Nr != Ns
		   dte-timeout 	(2), -- timeout waiting for STATUS message
 		   prot-error   (3)  -- protocol error
            }
	ACCESS	read-only
	STATUS	mandatory
	DESCRIPTION
                "The LMI failure reason. If the rate of LMI detected errors 
		exceeds the threshold, this contains the cause of the most
		recent error."
	::= { lportEntry 59 }

lportDTEOperStatus OBJECT-TYPE
	SYNTAX INTEGER {
		   -- invalid (0),
                   up      (1),
		   down    (2)
             }
	ACCESS	read-only
	STATUS	mandatory
	DESCRIPTION
                "The operational status of the DTE side of LMI on this link."
	::= { lportEntry 60 }

lportDCEInPollFrames OBJECT-TYPE
	SYNTAX	Counter 
	ACCESS	read-only
	STATUS	mandatory
	DESCRIPTION
		"The number of LMI poll frames received from the DTE since the
		last system reset."
	::= { lportEntry 61 }

lportDCEInErrorFrames OBJECT-TYPE
	SYNTAX	Counter 
	ACCESS	read-only
	STATUS	mandatory
	DESCRIPTION
		"The number of LMI frames received containing protocol errors."
	::= { lportEntry 62 }

lportDCEOutStatusFrames OBJECT-TYPE
	SYNTAX	Counter 
	ACCESS	read-only
	STATUS	mandatory
	DESCRIPTION
		"The number of LMI STATUS frames transmitted since the last 
		system reset. The count includes link integrity verification 
		frames only."
	::= { lportEntry 63 }

lportDCEOutFullStatusFrames OBJECT-TYPE
	SYNTAX	Counter 
	ACCESS	read-only
	STATUS	mandatory
	DESCRIPTION
		"The number of LMI Full STATUS frames transmitted since the 
		last system reset."
	::= { lportEntry 64 }

lportDCEOutAsyncStatusFrames OBJECT-TYPE
	SYNTAX	Counter 
	ACCESS	read-only
	STATUS	mandatory
	DESCRIPTION
		"The number of asynchronous LMI Status frames transmitted since 
		the last system reset. For LMI Rev 1, these are Update STATUS
		frames. For ANSI Annex D and CCITT Annex A these are
		Asynchronous STATUS frames."
	::= { lportEntry 65 }

lportDCEPollErrorCounts OBJECT-TYPE
	SYNTAX	Counter 
	ACCESS	read-only
	STATUS	mandatory
	DESCRIPTION
		"The number of DCE in-channel signaling link reliability errors (i.e. 
		 timeouts waiting for LMI Status Enquiry frames, sequence number errors)
		 since the last system reset."
	::= { lportEntry 66 }

lportDCEFailCounts OBJECT-TYPE
	SYNTAX  Counter 
	ACCESS	read-only
	STATUS	mandatory
	DESCRIPTION
                "The number of times since the last system reset
		LMI has declared the DCE side of the link down due to excessive 
		errors."
	::= { lportEntry 67 }

lportDCEFailReason OBJECT-TYPE
	SYNTAX INTEGER {
-- no failure
		   -- ok	   	(0), 
                   dce-bad-Nr   (1), -- received Nr != Ns
		   dce-timeout  (2), -- timeout waiting for Status Enquiry
				     -- message
		   prot-error   (3)  -- protocol error
             }
	ACCESS	read-only
	STATUS	mandatory
	DESCRIPTION
                "The LMI failure reason. If the rate of LMI detected errors
		exceeds the threshold, this contains the cause of the most 
		recent error." 
	::= { lportEntry 68 }

lportDCEOperStatus OBJECT-TYPE
	SYNTAX INTEGER {
		   -- invalid (0),
                   up      (1),
		   down    (2)
             }
	ACCESS	read-only
	STATUS	mandatory
	DESCRIPTION
                "The operational status of the DCE side of LMI on this link."
	::= { lportEntry 69 }

lportDCEOperDlcmiStd OBJECT-TYPE
	SYNTAX INTEGER {
                   unknown      (1),
                   lmiRev1      (2),
                   ansiT1-617-D (3),  -- ANSI T1.617 Annex D
                   ccittQ-933-A (4),  -- CCITT Q.933 Annex A
                   reserved     (5),  
                   ansiT1-617-B (6)   -- ANSI T1.617 Annex B
             }
	ACCESS	read-only
	STATUS	mandatory
	DESCRIPTION
                "This variable states which Data Link Connection Management
                scheme is actually being run on this link. This is used for DCE
		links configured for AutoDetect and indicates the LMI standard 
		used in the last poll received from the DTE."
	::= { lportEntry 70 }

lportLMIInErrorFrames OBJECT-TYPE
	SYNTAX  Counter 
	ACCESS	read-only
	STATUS	mandatory
	DESCRIPTION
                "The number of total frames received with an error. 
		For NNI links this is the sum of lportDTEInErrorFrames and 
		lportDCEInErrorFrames."
	::= { lportEntry 71 }

lportDCEnN4 OBJECT-TYPE
	SYNTAX  INTEGER 
	ACCESS	read-write
	STATUS	mandatory
	DESCRIPTION
                "This variable specifies the maximum number of LMI Status Enquiry
		frames that can be received from a DTE within time interval
		lportDCEnT3. This is only valid on lports using LMIREV1."
	::= { lportEntry 72 }

lportDCEnT3 OBJECT-TYPE
	SYNTAX  INTEGER 
	ACCESS	read-write
	STATUS	mandatory
	DESCRIPTION
                "This variable specifies the time interval (secs) used to determine
		if lportDCEnN4 an excess number (lportDCEnN4) of Status Enquiry 
		messages are received. This is only valid on lports using LMIREV1."
	::= { lportEntry 73 }

lportXmitLatencyThreshold OBJECT-TYPE
	SYNTAX  INTEGER 
	ACCESS	read-write
	STATUS	mandatory
	DESCRIPTION
		"Outbound frames are allowed on the transmit commit queue when 
		the commit queue falls below this threshold (in microseconds)."
	::= { lportEntry 74 }

lportXmitRefillPriority0Percentage OBJECT-TYPE
	SYNTAX  INTEGER 
	ACCESS	read-write
	STATUS	mandatory
	DESCRIPTION
	"Percentage of time the transmit queue is refilled in priority order
	0, 1, 2, 3."
	::= { lportEntry 75 }

lportXmitRefillPriority1Percentage OBJECT-TYPE
	SYNTAX  INTEGER 
	ACCESS	read-write
	STATUS	mandatory
	DESCRIPTION
	"Percentage of time the transmit queue is refilled in priority order
	1, 2, 3, 0."
	::= { lportEntry 76 }

lportXmitRefillPriority2Percentage OBJECT-TYPE
	SYNTAX  INTEGER 
	ACCESS	read-write
	STATUS	mandatory
	DESCRIPTION
	"Percentage of time the transmit queue is refilled in priority order
	2, 3, 0, 1."
	::= { lportEntry 77 }

lportXmitRefillPriority3Percentage OBJECT-TYPE
	SYNTAX  INTEGER 
	ACCESS	read-write
	STATUS	mandatory
	DESCRIPTION
	"Percentage of time the transmit queue is refilled in priority order
	3, 0, 1, 2."
	::= { lportEntry 78 }

lportXmitDiscardLow  OBJECT-TYPE
	SYNTAX  INTEGER 
	ACCESS	read-write
	STATUS	mandatory
	DESCRIPTION
	"Priority holding queue low water discard threshold.  Discarding stops
	when holding queue hits this level."
	::= { lportEntry 79 }

lportSevereThreshold  OBJECT-TYPE
	SYNTAX  INTEGER 
	ACCESS	read-write
	STATUS	mandatory
	DESCRIPTION
	"Severe congestion level.  Outbound red and amber packets are discarded
	when the transmit queue hits this threshold."
	::= { lportEntry 80 }

lportMildThreshold  OBJECT-TYPE
	SYNTAX  INTEGER 
	ACCESS	read-write
	STATUS	mandatory
	DESCRIPTION
	"Mild congestion level.  Outbound red packets are discarded
	when the transmit queue hits this threshold."
	::= { lportEntry 81 }

lportTrkKeepAliveTimer OBJECT-TYPE
	SYNTAX	INTEGER
	ACCESS	read-write
	STATUS	mandatory
	DESCRIPTION
		"Send a keep-alive packet after this many seconds.  These packets are
		sent on trunk links only.  The range is 0 thru 15, with zero meaning the 
		keep-alive protocol is disabled.  The default is one."
	::= { lportEntry 86 }


lportTrkKeepAliveErrorThreshold OBJECT-TYPE
	SYNTAX	INTEGER
	ACCESS	read-write
	STATUS	mandatory
	DESCRIPTION
		"Declare the interface down after this many keep-alive packets in a
		row are missed.  The default is five."
	::= { lportEntry 87 }


lportIgCutThruStatus OBJECT-TYPE
	SYNTAX	INTEGER	{
		disabled	(1),
		enabled		(2)
	}
	ACCESS	read-write
	STATUS	mandatory
	DESCRIPTION
		"Enable ingress cut-thru on this user lport.  Default is disabled."
	::= { lportEntry 88 }


lportEgCutThruStatus OBJECT-TYPE
	SYNTAX	INTEGER	{
		disabled	(1),
		enabled		(2)
	}
	ACCESS	read-write
	STATUS	mandatory
	DESCRIPTION
		"Enable egress cut-thru on this user lport.  Default is disabled."
	::= { lportEntry 89 }


lportEgCutThruThresh OBJECT-TYPE
	SYNTAX	INTEGER
	ACCESS	read-write
	STATUS	mandatory
	DESCRIPTION
		"Egress cut thru threshold - start transmitting a frame on a
		user port after this many segments have arrived."
	::= { lportEntry 90 }


lportFrameRelayTrkEnable OBJECT-TYPE
	SYNTAX	INTEGER {
		allowed	(1),
		not-allowed (2)
	}
	ACCESS	read-write
	STATUS	mandatory
	DESCRIPTION
		"Allow Frame Relay Trunks on the user link."
	::= { lportEntry 91 }


lportSmdsSsiIf OBJECT-TYPE
	SYNTAX	INTEGER
	ACCESS	read-write
	STATUS	mandatory
	DESCRIPTION
		"The interface number of the SSI which this DXI/SNI is
                 multiplexed to."
	::= { lportEntry 92 }

lportSmdsSsiSlot OBJECT-TYPE
	SYNTAX	INTEGER
	ACCESS	read-write
	STATUS	mandatory
	DESCRIPTION
		"The slot of the SSI which this DXI/SNI is multiplexed
                 to."
	::= { lportEntry 93 }

lportSmdsScrnId OBJECT-TYPE
	SYNTAX	INTEGER
	ACCESS	read-write
	STATUS	mandatory
	DESCRIPTION
		"The ID of address screen for this interface."
	::= { lportEntry 94 }

lportSmdsIaScrnOp OBJECT-TYPE
	SYNTAX	INTEGER {
           	allow(1),
		disallow(2)
                }
	ACCESS	read-write
	STATUS	mandatory
	DESCRIPTION
		"Individual address screen operation."
	::= { lportEntry 95 }

lportSmdsGaScrnOp OBJECT-TYPE
	SYNTAX	INTEGER {
           	allow(1),
		disallow(2)
                }
	ACCESS	read-write
	STATUS	mandatory
	DESCRIPTION
		"Group address screen operation."
	::= { lportEntry 96 }

lportSmdsIaScrnMap OBJECT-TYPE
	SYNTAX	OCTET STRING
	ACCESS	read-write
	STATUS	mandatory
	DESCRIPTION
		"The individual address screen member bit map. For set request, 
                 the first byte is the operation : 1 for deleting, 2 for
                 adding. The following bytes are the bit map. The bit
                 position of each bit in this bit map represent a screen
                 member ID. The most significant bit is corresponding to
                 group address ID 1. For get response, The whole 
                 string is the bit map. " 
	::= { lportEntry 97 }


lportSmdsGaScrnMap OBJECT-TYPE
	SYNTAX	OCTET STRING
	ACCESS	read-write
	STATUS	mandatory
	DESCRIPTION
		"The group address screen member bit map. For set request, 
                 the first byte is the operation : 1 for deleting, 2 for
                 adding. The following bytes are the bit map. The bit
                 position of each bit in this bit map represent a screen
                 member ID. The most significant bit is corresponding to
                 group address ID 1. For get response, The whole 
                 string is the bit map. " 
	::= { lportEntry 98 }

lportSmdsTrkAddr OBJECT-TYPE
	SYNTAX	OCTET STRING
	ACCESS	read-write
	STATUS	mandatory
	DESCRIPTION
		"SMDS address. For SSI feeder port, this address is the 
                 local address of all SMDS optimim paths associated with this 
                 SSI feeder port. For SSI Optimum path port, this address is
                 the remote address of this SSI optimum path.
                 The 4 most significant bits are 1100. The following 4 bits are
                 0001. The following 5 bytes are the 10 digits number in BCD
                 format. The following 16 bits are padded with 1's"
	::= { lportEntry 99 }


lportSmdsCrc OBJECT-TYPE
	SYNTAX	INTEGER {
           	crc16(1),
		crc32(2)
                }
	ACCESS	read-write
	STATUS	mandatory
	DESCRIPTION
		"CRC which CPE generates."
	::= { lportEntry 100 }

lportSmdsCpePoll OBJECT-TYPE
	SYNTAX	INTEGER {
           	nopoll(1),
		poll(2)
                }
	ACCESS	read-write
	STATUS	mandatory
	DESCRIPTION
		"Whether CPE supports heart beat poll or not."
	::= { lportEntry 101 }

lportSmdsPduCheck OBJECT-TYPE
	SYNTAX	INTEGER {
			-- off (0),
			on (1)
		}
	ACCESS	read-write
	STATUS	mandatory
	DESCRIPTION
		"turn of/off the detailed SIP3 PDU error checking."
	::= { lportEntry 102 }

lportSmdsCntOutFrDxi2HbPolls OBJECT-TYPE
	SYNTAX	Counter
	ACCESS	read-write
	STATUS	mandatory
	DESCRIPTION
		"Number of DXI2 heart beat poll frames transmitted."
	::= { lportEntry 103 }

lportSmdsCntOutByteDxi2HbPolls OBJECT-TYPE
	SYNTAX	Counter
	ACCESS	read-write
	STATUS	mandatory
	DESCRIPTION
		"Total number of octets in DXI2 heart beat poll frames transmitted."
	::= { lportEntry 104 }

lportSmdsCntInFrDxi2HbPolls OBJECT-TYPE
	SYNTAX	Counter
	ACCESS	read-write
	STATUS	mandatory
	DESCRIPTION
		"Number of DXI2 heart beat poll frames received."
	::= { lportEntry 105 }

lportSmdsCntInByteDxi2HbPolls OBJECT-TYPE
	SYNTAX	Counter
	ACCESS	read-write
	STATUS	mandatory
	DESCRIPTION
		"Total number of octets in DXI2 heart beat poll frames received."
	::= { lportEntry 106 }

lportSmdsCntOutFrSip3s OBJECT-TYPE
	SYNTAX	Counter
	ACCESS	read-write
	STATUS	mandatory
	DESCRIPTION
		"Number of SIP3 frames transmitted."
	::= { lportEntry 107 }

lportSmdsCntOutByteSip3s OBJECT-TYPE
	SYNTAX	Counter
	ACCESS	read-write
	STATUS	mandatory
	DESCRIPTION
		"Total number of octets in SIP3 frames transmitted."
	::= { lportEntry 108 }

lportSmdsCntInFrSip3s OBJECT-TYPE
	SYNTAX	Counter
	ACCESS	read-write
	STATUS	mandatory
	DESCRIPTION
		"Number of SIP3 frames received."
	::= { lportEntry 109 }

lportSmdsCntInByteSip3s OBJECT-TYPE
	SYNTAX	Counter
	ACCESS	read-write
	STATUS	mandatory
	DESCRIPTION
		"Total number of octets in SIP3 frames received."
	::= { lportEntry 110 }

lportSmdsCntDxi2LinkIdInvalids OBJECT-TYPE
	SYNTAX	Counter
	ACCESS	read-write
	STATUS	mandatory
	DESCRIPTION
		"Number of instances that DXI2 link ID is invalid."
	::= { lportEntry 111 }

lportSmdsCntDxi2StationIdInvalids OBJECT-TYPE
	SYNTAX	Counter
	ACCESS	read-write
	STATUS	mandatory
	DESCRIPTION
		"Number of instances that DXI2 station ID is invalid."
	::= { lportEntry 112 }

lportSmdsCntDxi2CrInvalids OBJECT-TYPE
	SYNTAX	Counter
	ACCESS	read-write
	STATUS	mandatory
	DESCRIPTION
		"Number of instances that DXI2 command/response field is invalid."
	::= { lportEntry 113 }

lportSmdsCntDxi2AeInvalids OBJECT-TYPE
	SYNTAX	Counter
	ACCESS	read-write
	STATUS	mandatory
	DESCRIPTION
		"Number of instances that DXI2 address extension field is invalid."
	::= { lportEntry 114 }

lportSmdsCntDxi2CtrlInvalids OBJECT-TYPE
	SYNTAX	Counter
	ACCESS	read-write
	STATUS	mandatory
	DESCRIPTION
		"Number of instances that DXI2 control field is invalid."
	::= { lportEntry 115 }

lportSmdsCntDxi2FrameSizeErrors OBJECT-TYPE
	SYNTAX	Counter
	ACCESS	read-write
	STATUS	mandatory
	DESCRIPTION
		"Number of instances there is a DXI2 frame size error."
	::= { lportEntry 116 }

lportSmdsCntSip3RsvdInvalids OBJECT-TYPE
	SYNTAX	Counter
	ACCESS	read-write
	STATUS	mandatory
	DESCRIPTION
		"Number of instances that SIP3 reserved field in header is invalid."
	::= { lportEntry 117 }

lportSmdsCntSip3BetagMismatchs OBJECT-TYPE
	SYNTAX	Counter
	ACCESS	read-write
	STATUS	mandatory
	DESCRIPTION
		"Number of instances that SIP3 BE tag is not macthed."
	::= { lportEntry 118 }

lportSmdsCntSip3BasizeIncorrects OBJECT-TYPE
	SYNTAX	Counter
	ACCESS	read-write
	STATUS	mandatory
	DESCRIPTION
		"Number of instances that SIP3 BA size is incorrect."
	::= { lportEntry 119 }

lportSmdsCntSip3BasizeInvalids OBJECT-TYPE
	SYNTAX	Counter
	ACCESS	read-write
	STATUS	mandatory
	DESCRIPTION
		"Number of instances that SIP3 BA size is invalid."
	::= { lportEntry 120 }

lportSmdsCntSip3DaTypeInvalids OBJECT-TYPE
	SYNTAX	Counter
	ACCESS	read-write
	STATUS	mandatory
	DESCRIPTION
		"Number of instances that SIP3 destination address type is invalid."
	::= { lportEntry 121 }

lportSmdsCntSip3DaInvalids OBJECT-TYPE
	SYNTAX	Counter
	ACCESS	read-write
	STATUS	mandatory
	DESCRIPTION
		"Number of instances that SIP3 destination address is invalid."
	::= { lportEntry 122 }

lportSmdsCntSip3SaTypeInvalids OBJECT-TYPE
	SYNTAX	Counter
	ACCESS	read-write
	STATUS	mandatory
	DESCRIPTION
		"Number of instances that SIP3 source address type is invalid."
	::= { lportEntry 123 }

lportSmdsCntSip3SaInvalids OBJECT-TYPE
	SYNTAX	Counter
	ACCESS	read-write
	STATUS	mandatory
	DESCRIPTION
		"Number of instances that SIP3 source address is invalid."
	::= { lportEntry 124 }

lportSmdsCntSip3BasizeMismatchs OBJECT-TYPE
	SYNTAX	Counter
	ACCESS	read-write
	STATUS	mandatory
	DESCRIPTION
		"Number of instances that SIP3 BA sizes in the header and
		 trailer are not matched."
	::= { lportEntry 125 }

lportSmdsCntSip3HeLenInvalids OBJECT-TYPE
	SYNTAX	Counter
	ACCESS	read-write
	STATUS	mandatory
	DESCRIPTION
		"Number of instances that SIP3 header extension length is invalid."
	::= { lportEntry 126 }

lportSmdsCntSip3HeVersionInvalids OBJECT-TYPE
	SYNTAX	Counter
	ACCESS	read-write
	STATUS	mandatory
	DESCRIPTION
		"Number of instances that SIP3 header extension version is invalid."
	::= { lportEntry 127 }

lportSmdsCntSip3HeCarrierInvalids OBJECT-TYPE
	SYNTAX	Counter
	ACCESS	read-write
	STATUS	mandatory
	DESCRIPTION
		"Number of instances that SIP3 header extension carrier is invalid."
	::= { lportEntry 128 }

lportSmdsCntSip3Crc32Errors OBJECT-TYPE
	SYNTAX	Counter
	ACCESS	read-write
	STATUS	mandatory
	DESCRIPTION
		"Number of SIP3 CRC errors."
	::= { lportEntry 129 }

lportSmdsCntSip3TRsvdInvalids OBJECT-TYPE
	SYNTAX	Counter
	ACCESS	read-write
	STATUS	mandatory
	DESCRIPTION
		"Number of instances that SIP3 reserved field in trailer is invalid."
	::= { lportEntry 130 }

lportSmdsCntSaNotFounds OBJECT-TYPE
	SYNTAX	Counter
	ACCESS	read-write
	STATUS	mandatory
	DESCRIPTION
		"Number of instances that source address not found."
	::= { lportEntry 131 }

lportSmdsCntSaValidationFails OBJECT-TYPE
	SYNTAX	Counter
	ACCESS	read-write
	STATUS	mandatory
	DESCRIPTION
		"Number of instances that source address validation failed."
	::= { lportEntry 132 }

lportSmdsCntSaDaOnSamePorts OBJECT-TYPE
	SYNTAX	Counter
	ACCESS	read-write
	STATUS	mandatory
	DESCRIPTION
		"Number of instances that source address and destination addresses
		 are on the same port."
	::= { lportEntry 133 }

lportSmdsCntDaSsiMismacths OBJECT-TYPE
	SYNTAX	Counter
	ACCESS	read-write
	STATUS	mandatory
	DESCRIPTION
		"Obsolete."
	::= { lportEntry 134 }

lportSmdsCntSsiProvisionErrors OBJECT-TYPE
	SYNTAX	Counter
	ACCESS	read-write
	STATUS	mandatory
	DESCRIPTION
		"Obsolete."
	::= { lportEntry 135 }

lportSmdsCntDstIaNotFounds OBJECT-TYPE
	SYNTAX	Counter
	ACCESS	read-write
	STATUS	mandatory
	DESCRIPTION
		"Number of instances that destination individual address not found."
	::= { lportEntry 136 }

lportSmdsCntDstGaNotFounds OBJECT-TYPE
	SYNTAX	Counter
	ACCESS	read-write
	STATUS	mandatory
	DESCRIPTION
		"Number of instances that destination group address not found."
	::= { lportEntry 137 }

lportSmdsCntSrcIaScrnFails OBJECT-TYPE
	SYNTAX	Counter
	ACCESS	read-write
	STATUS	mandatory
	DESCRIPTION
		"Number of instances that source individual address screening failed."
	::= { lportEntry 138 }

lportSmdsCntDstIaScrnFails OBJECT-TYPE
	SYNTAX	Counter
	ACCESS	read-write
	STATUS	mandatory
	DESCRIPTION
		"Number of instances that destination individual address screening failed."
	::= { lportEntry 139 }

lportSmdsCntDstGaScrnFails OBJECT-TYPE
	SYNTAX	Counter
	ACCESS	read-write
	STATUS	mandatory
	DESCRIPTION
		"Number of instances that destination group address screening failed."
	::= { lportEntry 140 }

lportSmdsTotalDiscards OBJECT-TYPE
	SYNTAX	Counter
	ACCESS	read-write
	STATUS	mandatory
	DESCRIPTION
		"total number of discards."
	::= { lportEntry 141 }

lportSmdsSsiNode OBJECT-TYPE
	SYNTAX	INTEGER
	ACCESS	read-write
	STATUS	mandatory
	DESCRIPTION
		"The Node of the SSI which this DXI/SNI is multiplexed
                 to."
	::= { lportEntry 142 }

lportBilling OBJECT-TYPE
	SYNTAX INTEGER {
			disabled (1),
			enabled  (2)
			}
	ACCESS read-write
	STATUS mandatory
	DESCRIPTION
		"This object defines the ability to enable and disable billing 
		on this logical port (for SMDS this must be a DXI).  When the
		 value of nodeBilling is 'enabled', the value of this object 
		will take precedence.  When the value of nodeBilling is 
		'disabled', the value of this object will be overridden and 
		billing will be disabled.

		The default value of this object is 'disabled'.
		"
	::= {lportEntry 143 }

lportSmdsReserved144 OBJECT-TYPE
	SYNTAX	INTEGER
	ACCESS	read-write
	STATUS	mandatory
	DESCRIPTION
		"reserved! ignore!"
	::= { lportEntry 144 }

lportLinkStatus OBJECT-TYPE
	SYNTAX	INTEGER {
		up (1),
		down (2)
		}	
	ACCESS	read-write
	STATUS	mandatory
	DESCRIPTION
		"Link protocol status. The Link protocol may be frame relay 
		 LMI, DXI heart beat poll, PPP LCP, etc, depends on the lport
		 type."
	::= { lportEntry 145 }

lportLMIDelay OBJECT-TYPE
	SYNTAX INTEGER
	ACCESS read-write
	STATUS mandatory
	DESCRIPTION
		"The number of seconds 1-9 to buffer (or initiate) a FR LMI async  
                 update (or ATM OAM alarms) to allow filtering of LMI async events. 
                 Zero (0) indicates that no buffering is done (all updates are immediate) 
                 and 255 indicates that no updates are sent."
	::= { lportEntry 146 }

lportCRC	OBJECT-TYPE
	SYNTAX	INTEGER 
	ACCESS	read-write
	STATUS	mandatory
	DESCRIPTION
		"Lport CRC selection:
		 0 - 16 bit CRC
		 1 - 32 bit CRC"
	::= { lportEntry 147 }

lportSmdsMulticastGa	OBJECT-TYPE
		SYNTAX	OCTET STRING
		ACCESS	read-write
		STATUS	mandatory
		DESCRIPTION
			" The Multicast Group Address is the smds broadcast address
			which is used to get smds address from its IP address."
		::= { lportEntry 148 }

lportSmdsMulticastIpAddr	OBJECT-TYPE
 			SYNTAX	IpAddress 
			ACCESS	read-write
			STATUS	mandatory
			DESCRIPTION
				" This IP address is this logical port's IP address. "
		::= { lportEntry 149 }

lportAtmVPI OBJECT-TYPE
	SYNTAX	INTEGER
	ACCESS	read-write
	STATUS	mandatory
	DESCRIPTION
		"VPI value in the ATM cell header:
		 ATM DXI with HSSI IOP VPI (4 lsb bit) range: 0 - 15
		 ATM UNI DS3/E3 IOP    VPI (4 lsb bit) range: 0 - 15"
	::= { lportEntry 150 }

lportAtmVCI OBJECT-TYPE
	SYNTAX	INTEGER
	ACCESS	read-write
	STATUS	mandatory
	DESCRIPTION
		"VCI value in the ATM cell header:
		 ATM DXI with HSSI IOP VCI (6 lsb bit) range: 0 - 63
		 ATM UNI DS3/E3 IOP    VCI (8 lsb bit) range: 0 - 255"
	::= { lportEntry 151 }


lportPeakCellRateindex OBJECT-TYPE
	SYNTAX	INTEGER
	ACCESS	read-write
	STATUS	mandatory
	DESCRIPTION
		"Peak cell rate queue index"
	::= { lportEntry 152 }

lportSustCellRate OBJECT-TYPE
	SYNTAX	INTEGER
	ACCESS	read-write
	STATUS	mandatory
	DESCRIPTION
		"Sustainable cell rate in cell/second"
	::= { lportEntry 153 }

lportBurstTolerance OBJECT-TYPE
	SYNTAX	INTEGER
	ACCESS	read-write
	STATUS	mandatory
	DESCRIPTION
		"Burst Tolerance in multiple of 32 cells"
	::= { lportEntry 154 }

lportBuTrkOnFailure OBJECT-TYPE
	SYNTAX	INTEGER {
		  -- disabled	(0),
                  enabled	(1)
       		}
	ACCESS	read-write
	STATUS	mandatory
	DESCRIPTION
		"Enables or disables trunk backup due to link down."
	::= { lportEntry 155 }

lportTrkFailureThrsh OBJECT-TYPE
	SYNTAX	INTEGER
	ACCESS	read-write
	STATUS	mandatory
	DESCRIPTION
		"The number of seconds a primary trunk must remain down for 
		 trunk backup to be initiated."
	::= { lportEntry 156 }

lportTrkRestThrsh OBJECT-TYPE
	SYNTAX	INTEGER
	ACCESS	read-write
	STATUS	mandatory
	DESCRIPTION
		"The number of seconds a primary trunk must remain up for trunk 
		 backup to be terminated"
	::= { lportEntry 157 }

lportBuTrkRetryInt OBJECT-TYPE
	SYNTAX	INTEGER
	ACCESS	read-write
	STATUS	mandatory
	DESCRIPTION
		"The number of seconds between backup trunk call setup retries."
	::= { lportEntry 158 }

lportBuTrkRetryNum OBJECT-TYPE
	SYNTAX	INTEGER
	ACCESS	read-write
	STATUS	mandatory
	DESCRIPTION
		"The number of backup trunk call setup tries per call setup 
		 cycle."
	::= { lportEntry 159 }

lportBuTrkCycleInt OBJECT-TYPE
	SYNTAX	INTEGER
	ACCESS	read-write
	STATUS	mandatory
	DESCRIPTION
		"The number of seconds between backup trunk call setup cycles."
	::= { lportEntry 160 }

lportTrkManualBu OBJECT-TYPE
	SYNTAX	INTEGER {
                  -- none		(0),
		  initCmd	(1),
		  termCmd	(2),
		  initSched	(3),
		  termSched	(4)
       		}
	ACCESS	read-write
	STATUS	mandatory
	DESCRIPTION
		"Initiate or terminate manual backup for a primary trunk.
		   none		neither initiate or terminate
		   initCmd	initiate operator commanded backup
		   termCmd	terminate operator commanded backup
		   initSched	initiate scheduled backup
		   termSched	terminate scheduled backup"
	::= { lportEntry 161 }

lportPrimTrk OBJECT-TYPE
	SYNTAX	Index
	ACCESS	read-write
	STATUS	mandatory
	DESCRIPTION
		"Indicates the primary trunk lportIfIndex for which a backup 
		 trunk is serving as a backup.  This value is also used to 
		 determine trunk type by the following convention:
		   Value				Trunk Type
		     0				  	  Normal
		     lportIfIndex of this trunk	  	  Primary
		     other lportIfIndex			  Backup"
	::= { lportEntry 162 }

lportInitCallSetup OBJECT-TYPE
	SYNTAX	INTEGER {
		  -- false	(0),
                  true	(1)
       		}
	ACCESS	read-write
	STATUS	mandatory
	DESCRIPTION
		"TRUE if node must initiate backup trunk call setup for this 
		 primary trunk.  Otherwise FALSE."
	::= { lportEntry 163 }

lportBuFailReason OBJECT-TYPE
	SYNTAX	INTEGER {
		  -- none			(0),
		  buTrkNotDef   	(1),
		  buTrkNotEstab		(2)
        	}
	ACCESS	read-only
	STATUS	mandatory
	DESCRIPTION
		"Indicates the reason for the failure to perform trunk backup."
	::= { lportEntry 164 }

lportQ922Enable OBJECT-TYPE
        SYNTAX  INTEGER {
			enable (1),
			disable (2)
		}
        ACCESS  read-write
        STATUS  mandatory
        DESCRIPTION
                "Set 1 to eanble Q.922 on this port. Q.922 must be enabled
		 if the port is used for SVC."
        ::= { lportEntry 165 }

lportQ922State OBJECT-TYPE
        SYNTAX  INTEGER {
		-- uninitialized (0),
		tei-unassigned (1),
		assign-awaiting (2),
		establish-awaiting (3),
		tei-assigned (4),
		awaiting-establishment (5),
		awaiting-release (6),
		multiple-frame-established (7),
		timer-recovery (8)
                }
        ACCESS  read-only
        STATUS  mandatory
        DESCRIPTION
                "Q.922 state. This object only makes sense when Q.922 is
		 enabled."
        ::= { lportEntry 166 }


lportTrkPduRevision OBJECT-TYPE
        SYNTAX  INTEGER
        ACCESS  read-only
        STATUS  mandatory
        DESCRIPTION
		"The Trunk PDU Revision number being used over this trunk."
        ::= { lportEntry 167 }

lportPVCMgrPduRevision OBJECT-TYPE
        SYNTAX  INTEGER
        ACCESS  read-only
        STATUS  mandatory
        DESCRIPTION
		"The PVC Manager PDU Revision number being used over this
		 trunk."
        ::= { lportEntry 168 }

lportDS0LoopStatus OBJECT-TYPE
        SYNTAX  INTEGER
        ACCESS  read-only
        STATUS  mandatory
        DESCRIPTION
		      "Indicates whether this logical port has one or more DS0's in 
            loopback"
        ::= { lportEntry 169 }

lportISDNDuration OBJECT-TYPE
	SYNTAX  INTEGER
	ACCESS	read-only
	STATUS  mandatory
	DESCRIPTION
		"The number of seconds that the ISDN call has been established."
	::= { lportEntry 170 }

lportISDNSourceAddr OBJECT-TYPE
	SYNTAX  OCTET STRING 
	ACCESS  read-only
	STATUS  mandatory
	DESCRIPTION "The E.164 address of the source of this ISDN connection."
	::= { lportEntry 171 }

lportISDNDestAddr OBJECT-TYPE
	SYNTAX  OCTET STRING 
	ACCESS  read-only
	STATUS  mandatory
	DESCRIPTION "The E.164 address of the destination of this ISDN 	
		     connection."
	::= { lportEntry 172 }

lportISDNIpAddr OBJECT-TYPE
	SYNTAX	IpAddress	
	ACCESS	read-only
	STATUS  mandatory
	DESCRIPTION "The Ip Address of the client connected to this B-Channel"
	::= { lportEntry 173 } 

lportISDNCallRejCause OBJECT-TYPE
	SYNTAX	INTEGER
	ACCESS	read-only
	STATUS  mandatory
	DESCRIPTION "The cause of the call rejection - inability to 
		authenticate or pool is busy."
	::= { lportEntry 174 } 

lportLastInvalidDLCI OBJECT-TYPE
	SYNTAX	INTEGER
	ACCESS	read-only
	STATUS	mandatory
	DESCRIPTION
		"This item pertains to user frame relay lports only.  The frame
		relay header of the received frame contains a dlci, which
		uniquely identifies a specific pvc on this lport.  When no pvc
		has been configured, on the lport, that corresponds to the
		dlci specified in the frame header, the frame is said to have
		an invalid dlci.  This lport entry holds the value of the
		most recent invalid dlci received on this lport, to be used in
		troubleshooting faulty configurations."
	::={ lportEntry 175 }

lportTrkProtState OBJECT-TYPE
	SYNTAX	INTEGER {
			enabled (1),
			disabled (2),
			none (3)
		}
	ACCESS	read-only
	STATUS	mandatory
	DESCRIPTION "The current operational state of the link trunk protocol
		on this link."
	::={ lportEntry 176 }

lportTrkTrafficMix OBJECT-TYPE
	SYNTAX	INTEGER {
		    normal (1),
		    management-only (2),
		    management-and-PVCs (3),
		    private (4)
		}
	ACCESS	read-write
	STATUS	mandatory
	DESCRIPTION "The types of traffic allowed over a Cascade trunk."
	::= { lportEntry 177 }

lportNumVC OBJECT-TYPE
	SYNTAX INTEGER
	ACCESS read-only
	STATUS mandatory
	DESCRIPTION "The number of VCs going to or through a particular 
                 port."
	::={ lportEntry 178 }

lportTrkAdminCost OBJECT-TYPE
	SYNTAX	INTEGER
	ACCESS	read-write
	STATUS	mandatory
	DESCRIPTION "The administrative cost of the trunk. Used when
		routing circuits. Trunks with lower costs are preferred.
		Value ranges from 1 to 65,535."
	::= { lportEntry 179 }

lportPrivateNet OBJECT-TYPE
	SYNTAX	INTEGER
	ACCESS	read-write
	STATUS	mandatory
	DESCRIPTION "If non-zero, indicates the private network that the
		lport belongs to. If 0, the lport is publicly shared."
	::= { lportEntry 180 }

lportTrkStaticDelay OBJECT-TYPE
	SYNTAX	INTEGER
	ACCESS	read-write
	STATUS	mandatory
	DESCRIPTION "The measured round-trip delay of the trunk, in
		milliseconds. Measured when the trunk last became
		operational."
	::= { lportEntry 181 }

lportTrkDynamicDelay OBJECT-TYPE
	SYNTAX	INTEGER
	ACCESS	read-write
	STATUS	mandatory
	DESCRIPTION "The recently measured round-tip delay of the
		trunk. May vary from lportTrkStaticDelay due to
		congestion, or reprovisioning of the underlying media."
	::= { lportEntry 182 }

lportAtmDataRateQoS1 OBJECT-TYPE
	SYNTAX	INTEGER
	ACCESS	read-write
	STATUS	mandatory
	DESCRIPTION "An estimate of the logical port's data rate in bits per
                second reserved for QoS class 1."
	::= { lportEntry 183 }

lportAtmDataRateQoS2 OBJECT-TYPE
	SYNTAX	INTEGER
	ACCESS	read-write
	STATUS	mandatory
	DESCRIPTION "An estimate of the logical port's data rate in bits per
                second reserved for QoS class 2."
	::= { lportEntry 184 }

lportAtmDataRateQoS3 OBJECT-TYPE
	SYNTAX	INTEGER
	ACCESS	read-write
	STATUS	mandatory
	DESCRIPTION "An estimate of the logical port's data rate in bits per
                second reserved for QoS class 3."
	::= { lportEntry 185 }

lportAtmDataRateQoS4 OBJECT-TYPE
	SYNTAX	INTEGER
	ACCESS	read-write
	STATUS	mandatory
	DESCRIPTION "An estimate of the logical port's data rate in bits per
                second reserved for QoS class 4."
	::= { lportEntry 186 }

lportOutVAvailbwQoS1 OBJECT-TYPE
	SYNTAX	INTEGER 
	ACCESS	read-only
	STATUS	mandatory
	DESCRIPTION
		"Current outgoing available virtual bandwidth reserved for QoS class 1."
	::= { lportEntry 187 }
		
lportOutVAvailbwQoS2 OBJECT-TYPE
	SYNTAX	INTEGER 
	ACCESS	read-only
	STATUS	mandatory
	DESCRIPTION
		"Current outgoing available virtual bandwidth reserved for QoS class 2."
	::= { lportEntry 188 }
		
lportOutVAvailbwQoS3 OBJECT-TYPE
	SYNTAX	INTEGER 
	ACCESS	read-only
	STATUS	mandatory
	DESCRIPTION
		"Current outgoing available virtual bandwidth reserved for QoS class 3."
	::= { lportEntry 189 }
		
lportOutVAvailbwQoS4 OBJECT-TYPE
	SYNTAX	INTEGER 
	ACCESS	read-only
	STATUS	mandatory
	DESCRIPTION
		"Current outgoing available virtual bandwidth reserved for QoS class 4."
	::= { lportEntry 190 }

lportInVAvailbwQoS1 OBJECT-TYPE
	SYNTAX	INTEGER 
	ACCESS	read-only
	STATUS	mandatory
	DESCRIPTION
		"Current incoming available virtual bandwidth reserved for QoS class 1."
	::= { lportEntry 191 }
		
lportInVAvailbwQoS2 OBJECT-TYPE
	SYNTAX	INTEGER 
	ACCESS	read-only
	STATUS	mandatory
	DESCRIPTION
		"Current incoming available virtual bandwidth reserved for QoS class 2."
	::= { lportEntry 192 }
		
lportInVAvailbwQoS3 OBJECT-TYPE
	SYNTAX	INTEGER 
	ACCESS	read-only
	STATUS	mandatory
	DESCRIPTION
		"Current incoming available virtual bandwidth reserved for QoS class 3."
	::= { lportEntry 193 }
		
lportInVAvailbwQoS4 OBJECT-TYPE
	SYNTAX	INTEGER 
	ACCESS	read-only
	STATUS	mandatory
	DESCRIPTION
		"Currently incoming available virtual bandwidth reserved for QoS class 4."
	::= { lportEntry 194 }

lportOutAllocbwQoS1 OBJECT-TYPE
	SYNTAX	INTEGER 
	ACCESS	read-only
	STATUS	mandatory
	DESCRIPTION
		"Current outgoing allocated bandwidth for QoS Class 1."
	::= { lportEntry 195 }
		
lportOutAllocbwQoS2 OBJECT-TYPE
	SYNTAX	INTEGER 
	ACCESS	read-only
	STATUS	mandatory
	DESCRIPTION
		"Current outgoing allocated bandwidth for QoS Class 2."
	::= { lportEntry 196 }
		
lportOutAllocbwQoS3 OBJECT-TYPE
	SYNTAX	INTEGER 
	ACCESS	read-only
	STATUS	mandatory
	DESCRIPTION
		"Current outgoing allocated bandwidth for QoS Class 3."
	::= { lportEntry 197 }
		
lportOutAllocbwQoS4 OBJECT-TYPE
	SYNTAX	INTEGER 
	ACCESS	read-only
	STATUS	mandatory
	DESCRIPTION
		"Current outgoing allocated bandwidth for QoS Class 4."
	::= { lportEntry 198 }
		
lportInAllocbwQoS1 OBJECT-TYPE
	SYNTAX	INTEGER 
	ACCESS	read-only
	STATUS	mandatory
	DESCRIPTION
		"Current incoming allocated bandwidth for QoS Class 1."
	::= { lportEntry 199 }
		
lportInAllocbwQoS2 OBJECT-TYPE
	SYNTAX	INTEGER 
	ACCESS	read-only
	STATUS	mandatory
	DESCRIPTION
		"Current incoming allocated bandwidth for QoS Class 2."
	::= { lportEntry 200 }
		
lportInAllocbwQoS3 OBJECT-TYPE
	SYNTAX	INTEGER 
	ACCESS	read-only
	STATUS	mandatory
	DESCRIPTION
		"Current incoming allocated bandwidth for QoS Class 3."
	::= { lportEntry 201 }
		
lportInAllocbwQoS4 OBJECT-TYPE
	SYNTAX	INTEGER 
	ACCESS	read-only
	STATUS	mandatory
	DESCRIPTION
		"Current incoming allocated bandwidth for QoS Class 4."
	::= { lportEntry 202 }

lportDynamicQoSbw OBJECT-TYPE
	SYNTAX  INTEGER {
		qos-class-1(1),
		qos-class-2(2),
		qos-class-3(4),
		qos-class-4(8)
	}
	ACCESS  read-write
	STATUS	mandatory
	DESCRIPTION
		"Bitmap defining which QoS Classes should have bandwidth
		 allocated dynamically from lportDataRate instead of reserving
 		 a percentage up-front."
	::= { lportEntry 203 }

lportSVCRetryTimer OBJECT-TYPE
	SYNTAX	INTEGER
	ACCESS	read-write
	STATUS	mandatory
	DESCRIPTION "The duration in seconds (1..255) the network is allowed
          	to re-establish a SVC after network failure before clearing the SVC.
                A value of (0) indicates continuous retries by the network until
                the user clears the SVC."
	::= { lportEntry 204 }

lportAtmNetworkType OBJECT-TYPE
	SYNTAX	INTEGER {
		private (1),
		public (2)
	}
	ACCESS	read-write
	STATUS	mandatory
	DESCRIPTION "Whether this lport is supporting a private or public network."
	::= { lportEntry 205 }	

lportAtmRouteMetricQoS1 OBJECT-TYPE
	SYNTAX  INTEGER {
		    administrative-cost (1),
		    end-to-end-delay (2),
		    cell-delay-variation (3)
                }
 	ACCESS	read-write
 	STATUS	mandatory
 	DESCRIPTION "Routing metric associated with QoS Class 1."
	::= { lportEntry 206 }

lportAtmRouteMetricQoS2 OBJECT-TYPE
	SYNTAX  INTEGER {
		    administrative-cost (1),
		    end-to-end-delay (2),
		    cell-delay-variation (3)
                }
 	ACCESS	read-write
 	STATUS	mandatory
 	DESCRIPTION "Routing metric associated with QoS Class 2."
	::= { lportEntry 207 }

lportAtmRouteMetricQoS3 OBJECT-TYPE
	SYNTAX  INTEGER {
		    administrative-cost (1),
		    end-to-end-delay (2),
		    cell-delay-variation (3)
                }
 	ACCESS	read-write
 	STATUS	mandatory
 	DESCRIPTION "Routing metric associated with QoS Class 3."
	::= { lportEntry 208 }

lportAtmRouteMetricQoS4 OBJECT-TYPE
	SYNTAX  INTEGER {
		    administrative-cost (1),
		    end-to-end-delay (2),
		    cell-delay-variation (3)
                }
 	ACCESS	read-write
 	STATUS	mandatory
 	DESCRIPTION "Routing metric associated with QoS Class 4."
	::= { lportEntry 209 }

lportIlmiPollTimeout OBJECT-TYPE
        SYNTAX  INTEGER
        ACCESS  read-write
        STATUS  mandatory
        DESCRIPTION "The duration in seconds (1..255) the ILMI poll is generated
                by the network-side UME. A value of 0 set to default polling period
                of 5 seconds."
        ::= { lportEntry 210 }

lportAtmProtocol OBJECT-TYPE
	SYNTAX  INTEGER {
		    	uni-30 (1),
		    	uni-31 (2),
			iisp (3)
                }
 	ACCESS	read-write
 	STATUS	mandatory
 	DESCRIPTION 
		"UNI protocol version for this port."
	::= { lportEntry 211 }

lportIlmiAdminStatus OBJECT-TYPE
	SYNTAX  INTEGER {
			enabled (1),
			disabled (2)
                }
 	ACCESS	read-write
 	STATUS	mandatory
 	DESCRIPTION 
		"Administrative state for ILMI function on this port."
	::= { lportEntry 212 }

lportIlmiOperStatus OBJECT-TYPE
	SYNTAX  INTEGER {
			down (1),
			registering (2),
			up (3)
                }
 	ACCESS	read-only
 	STATUS	mandatory
 	DESCRIPTION 
		"Operational status for ILMI function on this port."
	::= { lportEntry 213 }

lportIlmiPollRetry OBJECT-TYPE
        SYNTAX  Counter
        ACCESS  read-write
        STATUS  mandatory
        DESCRIPTION "The number of retries of ILMI poll request will be generated
                when network-side UME detects loss of ILMI connectivity. A value of
                0 sets to default value of 4 times"
        ::= { lportEntry 214 }

lportAtmVpiBits OBJECT-TYPE
	SYNTAX	INTEGER
	ACCESS	read-write
	STATUS	mandatory
	DESCRIPTION
		"Number of bits of VPI supported."
	::= { lportEntry 215 }

lportAtmVciBits OBJECT-TYPE
	SYNTAX	INTEGER
	ACCESS	read-write
	STATUS	mandatory
	DESCRIPTION
		"Number of bits of VCI supported."
	::= { lportEntry 216 }

lportAtmOamAlarmEnable OBJECT-TYPE
	SYNTAX	INTEGER {
		enabled(1),
		disabled(2)
	}
	ACCESS	read-write
	STATUS	mandatory
	DESCRIPTION
		"If disabled then OAM alarms are not generated for circuits that
		are down on this lport."
	::= { lportEntry 217 }

lportInVAvailbw OBJECT-TYPE
	SYNTAX	INTEGER 
	ACCESS	read-only
	STATUS	mandatory
	DESCRIPTION
		"Currently available Incoming virtual bandwidth."
	::= { lportEntry 218 }
		
lportbwUNIPolicy OBJECT-TYPE
	SYNTAX  INTEGER {
			enable-uni-bw-policing(1),
			disable-uni-bw-policing(2)
                }
 	ACCESS	read-write
 	STATUS	mandatory
 	DESCRIPTION 
		"The network policy towards requiring sufficient bandwidth at the UNI
                 interface prior to allowing a circuit to be established."
	::= { lportEntry 219 }

lportStarvation OBJECT-TYPE
	SYNTAX  INTEGER {
		ok(1),
		error(2)
		}
	ACCESS  read-only 
	STATUS  mandatory
	DESCRIPTION
	       "The CBR card detected a starvation condition on this lport for
		the extended period defined in Bellcore TA-NWT-001248"
	::= { lportEntry 220 }

lportRecOverflow OBJECT-TYPE
	SYNTAX  INTEGER {
		ok(1),
		error(2)
		}
	ACCESS  read-only 
	STATUS  mandatory
	DESCRIPTION
	       "The CBR card detected a receive overflow condition on this lport for the extended
	       period defined in Bellcore TA-NWT-001248"
	::= { lportEntry 221 }

lportLossOfCellSequence OBJECT-TYPE
	SYNTAX  INTEGER {
		ok(1),
		error(2)
		}
	ACCESS  read-only 
	STATUS  mandatory
	DESCRIPTION
	       "The CBR card detected a LOS condition on this lport for the extended
		period defined in Bellcore TA-NWT-001248"
	::= { lportEntry 222 }

lportLossOfStructurePointer OBJECT-TYPE
	SYNTAX  INTEGER {
		ok(1),
		error(2)
		}
	ACCESS  read-only 
	STATUS  mandatory
	DESCRIPTION
	       "The CBR card detected a loss of structure pointer condition on this lport
		for the extended period defined in Bellcore TA-NWT-001248"
	::= { lportEntry 223 }

lportCbrInsDummyCells OBJECT-TYPE
	SYNTAX  Counter
	ACCESS  read-only
	STATUS  mandatory
	DESCRIPTION
	       "The number of dummy cells inserted due to cell loss on a constant bit rate (AAL1) interface."
	::= { lportEntry 224 }

lportRecFifoUnderflowCnt OBJECT-TYPE
	SYNTAX  Counter
	ACCESS  read-only
	STATUS  mandatory 
	DESCRIPTION
	       "The number of receive FIFO underflows since the last reset.
		If this condition persists, a lportCBRLineDataError trap is issued
		indicating the lportStarvation."
	::= { lportEntry 225 }

lportRecFifoOverflowCnt OBJECT-TYPE
	SYNTAX  Counter
	ACCESS  read-only 
	STATUS  mandatory
	DESCRIPTION
	       "The number of receive FIFO overflows since the last reset.
		If this condition persists, a lportCBRLineDataError trap is issued
		indicating the receive FIFO overflow." 
	::= { lportEntry 226 }

lportCbrLossOfStructurePointerCnt OBJECT-TYPE
	SYNTAX  Counter  
	ACCESS  read-only
	STATUS  mandatory
	DESCRIPTION
	       "The object counts how often the structured CBR card detected a loss of the
		structure pointer since the last reset."
	::= { lportEntry 227 }

lportCbrLossOfCellSequenceCnt OBJECT-TYPE 
	SYNTAX  Counter
	ACCESS  read-only 
	STATUS  mandatory
	DESCRIPTION
	       "The number of loss of cell sequence since the last reset."
	::= { lportEntry 228 }

lportShaperId OBJECT-TYPE
	SYNTAX  INTEGER
	ACCESS  read-write
	STATUS  mandatory
	DESCRIPTION
	       "The shaper to be used for this ATM trunk interworking with frame relay:
		1-port ATM-IWU STM-1/STS-3c card
		--------------------------------

		Values: 1..16"
	::= { lportEntry 229 }

lportIlmiPrefixScreenMode OBJECT-TYPE
	SYNTAX	INTEGER {
			node-prefix (1),
			port-prefix (2),
			node-prefix-or-port-prefix (3),
			reject-all (127),
			accept-all (255)
	}
	ACCESS	read-write
	STATUS	mandatory
	DESCRIPTION
		"The type of screening to apply against dynamic prefixes 
		 received from the peer ILMI entity at this DTE port."
	::= { lportEntry 230 }

lportSmdsPduViolTca OBJECT-TYPE
	SYNTAX INTEGER {
			disabled (1),
			enabled  (2)
			}
	ACCESS read-write
	STATUS mandatory
	DESCRIPTION
		"This object defines the ability to enable and disable SMDS
		pdu violation traps on this logical port. This functionality
		applies to the following logical port types: 
		SMDS DXI/SNI DCE
		SMDS DXI/SNI DTE
		SMDS SSI DTE
		SMDS Optimum Trunk
		Direct Line Trunk 
		The default value of this object is 'disabled'.
		"
	::= {lportEntry 231 }

lportSmdsPduViolThresh OBJECT-TYPE
	SYNTAX	INTEGER
	ACCESS	read-write
	STATUS	mandatory
	DESCRIPTION
		"This object defines the Smds pdu violation threshold for this
		logical port. The allowable range of threshold values is 1-255.
		The default value of this object is '10'.
		"
	::= { lportEntry 232 }

lportSmdsPduHdrSip3SaNotFound	OBJECT-TYPE
	SYNTAX	OCTET STRING
	ACCESS	read-only
	STATUS	mandatory
	DESCRIPTION
		"This object provides the Smds destination address and Smds
		source address of the last Smds pdu to cause the violation
		Smds Sa Not Found. The first 8 bytes of the octet string
		(i.e.; 16 digits in BCD format) correspond to the destination
		address. The second 8 bytes correspond to the source address.  
		"	
	::= { lportEntry 233 }

lportSmdsPduHdrSip3SaDaOnSamePort	OBJECT-TYPE
	SYNTAX	OCTET STRING
	ACCESS	read-only
	STATUS	mandatory
	DESCRIPTION
		"This object provides the Smds destination address and Smds
		source address of the last Smds pdu to cause the violation
		Smds Sa Da On Same Port. The first 8 bytes of the octet string
		(i.e.; 16 digits in BCD format) correspond to the destination
		address. The second 8 bytes correspond to the source address.  
		"	
	::= { lportEntry 234 }

lportSmdsPduHdrSip3DstGaNotFound	OBJECT-TYPE
	SYNTAX	OCTET STRING
	ACCESS	read-only
	STATUS	mandatory
	DESCRIPTION
		"This object provides the Smds destination address and Smds
		source address of the last Smds pdu to cause the violation
		Smds Dst Ga Not Found. The first 8 bytes of the octet string
		(i.e.; 16 digits in BCD format) correspond to the destination
		address. The second 8 bytes correspond to the source address.  
		"	
	::= { lportEntry 235 }

lportSmdsPduHdrSip3DstIaScrnFail	OBJECT-TYPE
	SYNTAX	OCTET STRING
	ACCESS	read-only
	STATUS	mandatory
	DESCRIPTION
		"This object provides the Smds destination address and Smds
		source address of the last Smds pdu to cause the violation
		Smds Dst Ia Scrn Fail. The first 8 bytes of the octet string
		(i.e.; 16 digits in BCD format) correspond to the destination
		address. The second 8 bytes correspond to the source address.  
		"	
	::= { lportEntry 236 }

lportSmdsPduHdrSip3SaValFail	OBJECT-TYPE
	SYNTAX	OCTET STRING
	ACCESS	read-only
	STATUS	mandatory
	DESCRIPTION
		"This object provides the Smds destination address and Smds
		source address of the last Smds pdu to cause the violation
		Smds Sa Val Fail. The first 8 bytes of the octet string
		(i.e.; 16 digits in BCD format) correspond to the destination
		address. The second 8 bytes correspond to the source address.  
		"	
	::= { lportEntry 237 }

lportSmdsPduHdrSip3DstIaNotFound	OBJECT-TYPE
	SYNTAX	OCTET STRING
	ACCESS	read-only
	STATUS	mandatory
	DESCRIPTION
		"This object provides the Smds destination address and Smds
		source address of the last Smds pdu to cause the violation
		Smds Dst Ia Not Found. The first 8 bytes of the octet string
		(i.e.; 16 digits in BCD format) correspond to the destination
		address. The second 8 bytes correspond to the source address.  
		"	
	::= { lportEntry 238 }

lportSmdsPduHdrSip3SrcIaScrnFail	OBJECT-TYPE
	SYNTAX	OCTET STRING
	ACCESS	read-only
	STATUS	mandatory
	DESCRIPTION
		"This object provides the Smds destination address and Smds
		source address of the last Smds pdu to cause the violation
		Smds Src Ia Scrn Fail. The first 8 bytes of the octet string
		(i.e.; 16 digits in BCD format) correspond to the destination
		address. The second 8 bytes correspond to the source address.  
		"	
	::= { lportEntry 239 }

lportSmdsPduHdrSip3DstGaScrnFail	OBJECT-TYPE
	SYNTAX	OCTET STRING
	ACCESS	read-only
	STATUS	mandatory
	DESCRIPTION
		"This object provides the Smds destination address and Smds
		source address of the last Smds pdu to cause the violation
		Smds Dst Ga Scrn Fail. The first 8 bytes of the octet string
		(i.e.; 16 digits in BCD format) correspond to the destination
		address. The second 8 bytes correspond to the source address.  
		"	
	::= { lportEntry 240 }

lportSmdsPduHdrSip3SaTypeInvalid	OBJECT-TYPE
	SYNTAX	OCTET STRING
	ACCESS	read-only
	STATUS	mandatory
	DESCRIPTION
		"This object provides the Smds destination address and Smds
		source address of the last Smds pdu to cause the violation
		Smds Sa Type Invalid. The first 8 bytes of the octet string
		(i.e.; 16 digits in BCD format) correspond to the destination
		address. The second 8 bytes correspond to the source address.  
		"	
	::= { lportEntry 241 }

lportSmdsPduHdrSip3DaTypeInvalid	OBJECT-TYPE
	SYNTAX	OCTET STRING
	ACCESS	read-only
	STATUS	mandatory
	DESCRIPTION
		"This object provides the Smds destination address and Smds
		source address of the last Smds pdu to cause the violation
		Smds Da Type Invalid. The first 8 bytes of the octet string
		(i.e.; 16 digits in BCD format) correspond to the destination
		address. The second 8 bytes correspond to the source address.  
		"	
	::= { lportEntry 242 }

lportSmdsPduHdrDxi2LinkIdInvalid	OBJECT-TYPE
	SYNTAX	OCTET STRING
	ACCESS	read-only
	STATUS	mandatory
	DESCRIPTION
		"This object provides the dxi2 header of the last Smds pdu to
		cause the violation Dxi2 Link Id Invalid. The length of this 
                object is 4 bytes.
		"	
	::= { lportEntry 243 }

lportSmdsPduHdrDxi2CrInvalid	OBJECT-TYPE
	SYNTAX	OCTET STRING
	ACCESS	read-only
	STATUS	mandatory
	DESCRIPTION
		"This object provides the dxi2 header of the last Smds pdu to
		cause the violation Dxi2 Cr Invalid. The length of this 
		object is 4 bytes.
		"	
	::= { lportEntry 244 }

lportSmdsPduHdrDxi2CtrlInvalid	OBJECT-TYPE
	SYNTAX	OCTET STRING
	ACCESS	read-only
	STATUS	mandatory
	DESCRIPTION
		"This object provides the dxi2 header of the last Smds pdu to
		cause the violation Dxi2 Ctrl Invalid. The length of this 
		object is 4 bytes.
		"	
	::= { lportEntry 245 }

lportSmdsPduHdrDxi2StationIdInvalid	OBJECT-TYPE
	SYNTAX	OCTET STRING
	ACCESS	read-only
	STATUS	mandatory
	DESCRIPTION
		"This object provides the dxi2 header of the last Smds pdu to
		cause the violation Dxi2 Station Id Invalid. The length of this 
		object is 4 bytes.
		"	
	::= { lportEntry 246 }

lportSmdsPduHdrDxi2AeInvalid	OBJECT-TYPE
	SYNTAX	OCTET STRING
	ACCESS	read-only
	STATUS	mandatory
	DESCRIPTION
		"This object provides the dxi2 header of the last Smds pdu to
		cause the violation Dxi2 Ae Invalid. The length of this 
		object is 4 bytes.
		"	
	::= { lportEntry 247 }

lportDS0FarendLpbkEnabled	OBJECT-TYPE
	SYNTAX	INTEGER
	ACCESS	read-write
	STATUS	mandatory
	DESCRIPTION
		"Set a single DS0 into farend loopback 1-24."	
	::= { lportEntry 248 }


lportDS0FarendLpbkDisabled	OBJECT-TYPE
	SYNTAX	INTEGER
	ACCESS	read-write
	STATUS	mandatory
	DESCRIPTION
		"Set a single DS0 out farend loopback 1-24."	
	::= { lportEntry 249 }

lportTrkProtFailureThreshold	OBJECT-TYPE
	SYNTAX	INTEGER
	ACCESS	read-write
	STATUS	mandatory
	DESCRIPTION
		"The time, measured in seconds, that Trunk Protocol waits before
		transitioning the state of an unresponsive trunk from UP to
		DOWN.  Trunk protocol keepalive requests are issued on the
		trunk lport once per second.  This value defines the failure
		threshold, that is, the number of consecutive requests that
		must go unanswered before the Trunk Protocol application will
		declare the trunk lport DOWN."
	::= { lportEntry 250 }

lportPtr	OBJECT-TYPE
	SYNTAX	OCTET STRING
	ACCESS	read-only
	STATUS	mandatory
	DESCRIPTION
		"An octet string indicating the lport pointer."
	::= { lportEntry 251 }

lportISDNPoolUtil OBJECT-TYPE
	SYNTAX	INTEGER
	ACCESS	read-only
	STATUS  mandatory
	DESCRIPTION "The percent utilization of the B-channel pool that 
		this b-channel belongs to."
	::= { lportEntry 252 } 

lportISDNIpAddrAssignFail OBJECT-TYPE
	SYNTAX	INTEGER
	ACCESS	read-only
	STATUS  mandatory
	DESCRIPTION "The cause value for why Ip Address assignment 
		has failed."
	::= { lportEntry 253 } 

lportTrkUtilQoS1 OBJECT-TYPE
	SYNTAX	INTEGER 
	ACCESS	read-write
	STATUS	mandatory
	DESCRIPTION
		"An estimate of the real QoS1 utilization of the trunk bandwidth
		in terms of a percentage of the configured trunk bandwidth."
	::= { lportEntry 254 }

lportTrkUtilQoS2 OBJECT-TYPE
	SYNTAX	INTEGER 
	ACCESS	read-write
	STATUS	mandatory
	DESCRIPTION
		"An estimate of the real QoS2 utilization of the trunk bandwidth
		in terms of a percentage of the configured trunk bandwidth."
	::= { lportEntry 255 }

lportTrkUtilQoS3 OBJECT-TYPE
	SYNTAX	INTEGER 
	ACCESS	read-write
	STATUS	mandatory
	DESCRIPTION
		"An estimate of the real QoS3 utilization of the trunk bandwidth
		in terms of a percentage of the configured trunk bandwidth."
	::= { lportEntry 256 }

lportTrkUtilQoS4 OBJECT-TYPE
	SYNTAX	INTEGER 
	ACCESS	read-write
	STATUS	mandatory
	DESCRIPTION
		"An estimate of the real QoS4 utilization of the trunk bandwidth
		in terms of a percentage of the configured trunk bandwidth."
	::= { lportEntry 257 }

lportInCells OBJECT-TYPE
	SYNTAX	Counter
	ACCESS	read-only
	STATUS	mandatory
	DESCRIPTION
		"The total number of cells received"
	::= { lportEntry 267 }

lportOutCells OBJECT-TYPE
	SYNTAX	Counter
	ACCESS	read-only
	STATUS	mandatory
	DESCRIPTION
		"The total number of cells transmitted"
	::= { lportEntry 268 }


--	The Circuit Group
--
--	The variables that configure and monitor circuits on a port.
--

cktTable OBJECT-TYPE
	SYNTAX	SEQUENCE OF CktEntry
	ACCESS	not-accessible
	STATUS	mandatory
	DESCRIPTION
		"A table containing information about specific DLCIs, channels
		and corresponding circuits."
	::= { ckt 1 }

cktEntry OBJECT-TYPE
 	SYNTAX	CktEntry
 	ACCESS	not-accessible
 	STATUS	mandatory
 	DESCRIPTION
		"The information regarding a single Data Link
		Connection Identifier."
	INDEX { cktSrcIfIndex, cktSrcDlci }
	::= { cktTable 1 }

CktEntry ::=
	SEQUENCE {
		cktSrcIfIndex
			Index,
 		cktSrcDlci
			INTEGER,
		cktPriority
			INTEGER,
		cktCir
			INTEGER,
		cktBc
			INTEGER,
		cktBe
			INTEGER,
		cktDestNodeId
			INTEGER,
		cktDestIfIndex
			INTEGER,
		cktDestDlci
			INTEGER,
		cktTos
			INTEGER,
		cktOde
			INTEGER,
		cktAdminStatus
			INTEGER,
 		cktCreationTime
			TimeTicks,
 		cktLastTimeChange
			TimeTicks,
		cktVcState
			INTEGER,
		cktDceState
			INTEGER,
		cktDteStatus
			INTEGER,
		cktRnr
			INTEGER,
		cktNiDown
			INTEGER,
		cktDteState
			INTEGER,
		cktOperStatus
			INTEGER,
		cktOutForward
			INTEGER,
		cktRerouteCnt
			INTEGER,
		cktVcPtr
			OCTET STRING,
		cktHopCnt
			INTEGER,
 		cktPath
 			OCTET STRING,
		cktFailReason
			INTEGER,
		cktFailNode
			INTEGER,
		cktFailPort
			INTEGER,
		cktMcastGroupId
			INTEGER,
		cktMcastMemberList
			OCTET STRING,
		cktMcastParentGroups
			OCTET STRING,
 		cktInFrames
			Counter,
		cktInDEFrames
			Counter,
		cktInODEFrames
			Counter,
		cktInFECNFrames
			Counter,
		cktInBECNFrames
			Counter,
		cktInDiscards
			Counter,
		cktInOctets
			Counter,
		cktInDEOctets
			Counter,
		cktInODEOctets
			Counter,
 		cktOutFrames
			Counter,
		cktOutDEFrames
			Counter,
		cktOutODEFrames
			Counter,
		cktOutFECNFrames
			Counter,
		cktOutBECNFrames
			Counter,
		cktOutOctets
			Counter,
		cktOutDEOctets
			Counter,
		cktOutODEOctets
			Counter,
		cktOutLostFrames
			Counter,
		cktOutLostDEFrames
			Counter,
		cktOutLostODEFrames
			Counter,
		cktOutLostOctets
			Counter,
		cktOutLostDEOctets
			Counter,
		cktOutLostODEOctets
			Counter,
		cktRtMinDelay
			INTEGER,
		cktRtMaxDelay
			INTEGER,
		cktRtAvgDelay
			INTEGER,
		cktDiagTestId
			INTEGER,
		cktDiagTestRuns
			INTEGER,
		cktHelloCounter
			INTEGER,
		cktHelloAckCounter
			INTEGER,
		cktDefinedPath
			OCTET STRING,
		cktDefinedPathCount
			INTEGER,
		cktDefinedPathEnable
			INTEGER,
		cktDefinedPathAltOption
			INTEGER,
		cktUsingDefinedPath
			INTEGER,
		cktTryAltPath
			INTEGER,
		cktNotVirgin
			INTEGER,
		cktInForward
			INTEGER,
		cktBtusSeg
			INTEGER,
		cktInSegmentsDiscards
			Counter,
		cktAtmVPI
			INTEGER,
		cktAtmVCI
			INTEGER,
		cktType
			INTEGER,
		cktSvcCallingParty
			OCTET STRING,
		cktSvcCalledParty
			OCTET STRING,
		cktSvcDuration
			TimeTicks,
		cktSvcCause
			INTEGER,
		cktXlatFlag
			INTEGER,
		cktDestLaddr
			INTEGER,
		cktSrcLaddr
			INTEGER,
		cktLoop
			INTEGER,
		cktRerouteBalance
			INTEGER,
		cktCallingBackup
			INTEGER,
		cktRCir
			INTEGER,
		cktAtmQoS
			INTEGER,
                cktAtmInCells
                        Counter,
                cktAtmOutCells
                        Counter,
                cktAtmInDiscardedClp0Cells
                        Counter,
                cktAtmInDiscardedClp1Cells
                        Counter,
                cktAtmVcType
                        INTEGER,
                cktAtmPCR
                        INTEGER,
                cktAtmSCR
                        INTEGER,
                cktAtmMBS
                        INTEGER,
                cktAtmInPassedClp0Cells
                        Counter,
                cktAtmInPassedClp1Cells
                        Counter,
                cktAtmInTaggedCells
                        Counter,
                cktAtmOutClp0Cells
                        Counter,
                cktAtmOutClp1Cells
                        Counter,
                cktAtmRQoS
                        INTEGER,
                cktAtmTfdType
                        INTEGER,
                cktAtmRTfdType
                        INTEGER,
                cktAtmTfdParam1
                        INTEGER,
                cktAtmTfdParam2
                        INTEGER,
                cktAtmTfdParam3
                        INTEGER,
                cktAtmRTfdParam1
                        INTEGER,
                cktAtmRTfdParam2
                        INTEGER,
                cktAtmRTfdParam3
                        INTEGER,
                cktAtmFrameIWF
                        INTEGER,
                cktAtmUserPlane
                        INTEGER,
                cktRBc
                        INTEGER,
                cktRBe
                        INTEGER,
		cktOamLoopbackDirection
			INTEGER,
		cktOamLoopbackType
			INTEGER,
		cktOamLoopbackHops
			INTEGER,
		cktOamLoopbackCount
			INTEGER,
		cktOamLoopbackReceived
			Counter,
		cktOamLoopbackTimeouts
			Counter,
		cktOamLoopbackReceivedHigh
			INTEGER,
		cktOamLoopbackReceivedLow
			INTEGER,
		cktOamLoopbackReceivedAvg
			INTEGER,
		cktOamAlarmDisable
			INTEGER,
		cktShaperId
			INTEGER,
		cktOspfCtd
			INTEGER,
		cktOspfCdv
			INTEGER,
		cktOutPort
			INTEGER,
		cktOutVc
			INTEGER,
		cktRVc
			INTEGER,
		cktEntryType
			INTEGER,
		cktDiagStr
			OCTET STRING,
		cktSvcAalType
			INTEGER,
		cktSvcBBearerClass
			INTEGER,
		cktSvcBBearerClippingSusc
			INTEGER,
		cktSvcBBearerTmgReq
			INTEGER,
		cktSvcBBearerTfcType
			INTEGER,
		cktAtmUPCEnable
			INTEGER,
		cktRPriority
			INTEGER,
		cktRtPriority
			INTEGER,
		cktDeltaBc
			INTEGER,
		cktDeltaBe
			INTEGER,
		cktDeltaRBc
			INTEGER,
		cktDeltaRBe
			INTEGER,
		cktRedFrPcnt
			INTEGER,
		cktRedFrRPcnt
			INTEGER,
		cktRateEnforceSchm
			INTEGER,
		cktRateEnforceRSchm
			INTEGER,
		cktROde
			INTEGER,
		cktPrivateNet
			INTEGER,
		cktPrivateNetOverflow
			INTEGER,
		cktCustomerID
			INTEGER,
		cktAtmCDVT
			INTEGER,
		cktNdcEnable
			INTEGER,
                cktInterworkingFrToAtmCLP
                        INTEGER,
                cktInterworkingFrToAtmDe
                        INTEGER,
		cktNrtsCLP1
			INTEGER,
		cktNrtsDiscardClp0
			Counter,
		cktNrtsDiscardClp1
			Counter,
		cktMPEnableAMF
			INTEGER,
		cktMPEligible
			INTEGER,
		cktMPForcedCaller
			INTEGER,
		cktMPForcedCallee
			INTEGER,
		cktFrameSize
			INTEGER,
		cktRFrameSize
			INTEGER,
		cktRNrtsCLP1
			INTEGER,
		cktBBearerAtmTransferCapability
			INTEGER,
		cktAtmFrameDiscard
			INTEGER,
		cktRAtmFrameDiscard
			INTEGER,
		cktAbrFRMRTT
			INTEGER,
		cktAbrICR
			INTEGER,
		cktRAbrICR
			INTEGER,
		cktAbrRIF
			INTEGER,
		cktRAbrRIF
			INTEGER,
		cktAbrRDF
			INTEGER,
		cktRAbrRDF
			INTEGER,
		cktAbrTBE
			INTEGER,
		cktRAbrTBE
			INTEGER,
		cktAbrNRM
			INTEGER,
		cktRAbrNRM
			INTEGER,
		cktAbrTRM
			INTEGER,
		cktRAbrTRM
			INTEGER,
		cktAbrCDF
			INTEGER,
		cktRAbrCDF
			INTEGER,
		cktAbrADTF
			INTEGER,
		cktRAbrADTF
			INTEGER,
		cktAccumCTD
			INTEGER,
		cktAccumCDV
			INTEGER,
		cktAccumRCDV
			INTEGER,
		cktCLR
			INTEGER,
		cktRCLR
			INTEGER,
		cktAtmLijId
			INTEGER,
		cktAtmLijType
			INTEGER,
		cktRtLastDelay
			INTEGER,
		cktRtAccuMinDelay
			INTEGER,
		cktRtAccuMaxDelay
			INTEGER,
		cktRtAccuAvgDelay
			INTEGER,
		cktQosIntPeriod
			INTEGER,
		cktAtmOutOAMClp0Cells
			Counter,
		cktAtmOutOAMClp1Cells
			Counter,
		cktReqCTD
			INTEGER,
		cktInOctetsPeak
			Counter,
		cktOutOctetsPeak
			Counter,
		cktInDEOctetsPeak
			Counter,
		cktOutDEOctetsPeak
			Counter,
		cktInODEOctetsPeak
			Counter,
		cktOutODEOctetsPeak
			Counter,
		cktAdminCostThreshold
			INTEGER,
		cktAtmSvcServiceCategory
			INTEGER,
		cktAtmSvcRServiceCategory
			INTEGER,
		cktInterworkingFrToAtmEFCI
			INTEGER,
		cktDiagSARMon
			INTEGER,
		cktAdminCostReal
			INTEGER,
		cktAtmInClp0Cells
			Counter,
		cktAtmInClp1Cells
			Counter,
		cktATMAAL5CRC32Error
			Counter,
		cktATMAAL5CPIError
			Counter,
		cktATMAAL5LengthError
			Counter,
		cktATMAAL5ReassemblyTimerError
			Counter,
		cktATMAAL5MaxNrSegError
			Counter,
		cktIWF1490to1483Error
			Counter,
		cktIWF1490to1483LastBadHeader
			DisplayString,
		cktIWF1483to1490Error
			Counter,
		cktIWF1483to1490LastBadHeader
			DisplayString

	}

cktSrcIfIndex OBJECT-TYPE
 	SYNTAX	Index
 	ACCESS	read-only
 	STATUS	mandatory
 	DESCRIPTION
		"The ifIndex value of the corresponding ifEntry."
	::= { cktEntry 1 }

cktSrcDlci OBJECT-TYPE
 	SYNTAX  INTEGER
 	ACCESS  read-only
 	STATUS  mandatory
 	DESCRIPTION
		"The DLCI used as the key for the circuit. For local DLCI
                 significance, this is the local DLCI. For Global DLCI 
                 significance, this is the remote DLCI."
  	::= { cktEntry 2 }

cktPriority OBJECT-TYPE
 	SYNTAX	INTEGER
 	ACCESS	read-write
 	STATUS	mandatory
 	DESCRIPTION
		"The priority level (1 through 3) for this circuit."
	::= { cktEntry 3 }

cktCir OBJECT-TYPE
 	SYNTAX	INTEGER
 	ACCESS	read-write
 	STATUS	mandatory
 	DESCRIPTION
		"The average number of user data (bits) that the network agrees 
		to transfer over the circuit in one direction, measured over 
		the measurement interval T = cktBc/cktCir."
	::= { cktEntry 4 }

cktBc OBJECT-TYPE
 	SYNTAX	INTEGER
 	ACCESS	read-write
 	STATUS	mandatory
 	DESCRIPTION
		"The maximum amount of data (bits) that the network agrees
		to transfer over the circuit under normal conditions, during 
		the measurement interval."
	::= { cktEntry 5 }

cktBe OBJECT-TYPE
 	SYNTAX	INTEGER
 	ACCESS	read-write
 	STATUS	mandatory
 	DESCRIPTION
		"The maximum amount of uncommitted data (bits) that the network
		will attempt to transfer over the circuit during the 
		measurement interval.  By default, if not configured when
		creating the entry, the Excess Information Burst Size is set
                to the value of ifSpeed."
	::= { cktEntry 6 }

cktDestNodeId OBJECT-TYPE
 	SYNTAX	INTEGER
 	ACCESS	read-write
 	STATUS	mandatory
 	DESCRIPTION
		"The destination node ID for this circuit."
  	::= { cktEntry 7 }

cktDestIfIndex OBJECT-TYPE
 	SYNTAX  INTEGER
 	ACCESS  read-write
 	STATUS  mandatory
 	DESCRIPTION
		"The interface identifier at the destination node for this
		circuit."
  	::= { cktEntry 8 }

cktDestDlci OBJECT-TYPE
 	SYNTAX  INTEGER
 	ACCESS  read-write
 	STATUS  mandatory
 	DESCRIPTION
		"The DLCI which is the destination of the key DLCI. For
                 local DLCI significance, this is the remote DLCI since the 
                 key DLCI is the local DLCI. For global significance, this is
                 the local DLCI since the key DLCI is the remote DLCI." 
  	::= { cktEntry 9 }

cktTos OBJECT-TYPE
 	SYNTAX  INTEGER {
		    committed (1),
		    shared (2)
		}
 	ACCESS  read-only
 	STATUS  mandatory
 	DESCRIPTION
		"The type of service for the circuit. Only committed is
		supported in the FCS."
  	::= { cktEntry 10 }

cktOde OBJECT-TYPE
	SYNTAX	INTEGER {
		    -- off (0),
		    on (1)
		}
	ACCESS	read-write
	STATUS	mandatory
	DESCRIPTION
		"This variable states whether graceful discard is enabled
		for the ckt."
	::= { cktEntry 11 }

cktAdminStatus OBJECT-TYPE
 	SYNTAX  INTEGER {
 		    -- invalid (0),
		    down (1),
		    up (2)
 		}
 	ACCESS  read-write
 	STATUS  mandatory
 	DESCRIPTION
		"The desired state of the ckt."
	DEFVAL { up }
	::= { cktEntry 12 }

cktCreationTime OBJECT-TYPE
 	SYNTAX  TimeTicks
 	ACCESS  read-only
 	STATUS  mandatory
 	DESCRIPTION
		"The value of sysUpTime when the circuit was created
		(activated)."
	::= { cktEntry 13 }

cktLastTimeChange OBJECT-TYPE
 	SYNTAX  TimeTicks
 	ACCESS  read-only
 	STATUS  mandatory
 	DESCRIPTION
		"The sysUpTime value when the circuit was last changed to 
		the current state."
	::= { cktEntry 14 }

cktVcState OBJECT-TYPE
 	SYNTAX  INTEGER {
 		    -- invalid (0),
		    inactive (1),
		    retry (2),
		    calling (3),
		    wcbdeact(4),
                    wcbdelete(5),
		    active (6),
                    svcall (7),
                    svclr (8),
                    backedup (9),
                    wcbbkdp (10),
                    wcbreact (11),
		    slowretry (12)
 		}
 	ACCESS  read-only
 	STATUS  mandatory
 	DESCRIPTION
		"The current state of the PVC segment in the Cascade network."
	::= { cktEntry 15 }

cktDceState OBJECT-TYPE
 	SYNTAX  INTEGER {
		    -- invalid (0),
		    inactive (1),
		    active (2)
		}
 	ACCESS  read-only
 	STATUS  mandatory
 	DESCRIPTION
		"The DCE state of the circuit."
  	::= { cktEntry 16 }

cktDteStatus OBJECT-TYPE
 	SYNTAX  INTEGER {
		    -- invalid (0),
		    inactive (1),
		    active (2)
		}
 	ACCESS  read-only
 	STATUS  mandatory
 	DESCRIPTION
		"The DTE status of the circuit."
  	::= { cktEntry 17 }

cktRnr OBJECT-TYPE
 	SYNTAX  INTEGER {
		    -- recvready (0),
		    recvnotready (1)
		}
 	ACCESS  read-only
 	STATUS  mandatory
 	DESCRIPTION
		"The receiver's readiness for accepting data flow."
  	::= { cktEntry 18 }

cktNiDown OBJECT-TYPE
 	SYNTAX  INTEGER {
		    -- niup (0),
		    nidown (1)
		}
 	ACCESS  read-only
 	STATUS  mandatory
 	DESCRIPTION
		"The state of the network interface."
  	::= { cktEntry 19 }

cktDteState OBJECT-TYPE
 	SYNTAX  INTEGER {
		    -- invalid (0),
		    inactive (1),
		    active (2)
		}
 	ACCESS  read-only
 	STATUS  mandatory
 	DESCRIPTION
		"The DTE state of the circuit."
  	::= { cktEntry 20 }

cktOperStatus OBJECT-TYPE
 	SYNTAX  INTEGER {
		    -- invalid (0),
		    inactive (1),
		    active (2)
		}
 	ACCESS  read-only
 	STATUS  mandatory
 	DESCRIPTION
		"The current operational status of the entire PVC."
  	::= { cktEntry 21 }

cktOutForward OBJECT-TYPE
 	SYNTAX  INTEGER {
		    -- off (0),
		    on (1)
		}
 	ACCESS  read-only
 	STATUS  mandatory
 	DESCRIPTION
		"If the value is 1, it means the outbound flow is on."
  	::= { cktEntry 22 }

cktRerouteCnt OBJECT-TYPE
 	SYNTAX  INTEGER
 	ACCESS  read-only
 	STATUS  mandatory
 	DESCRIPTION
		"The reroute count."
	::= { cktEntry 23 }

cktVcPtr OBJECT-TYPE
 	SYNTAX  OCTET STRING
 	ACCESS  read-only
 	STATUS  mandatory
 	DESCRIPTION
		"An 8-byte Octect string indicating the vc pointer."
  	::= { cktEntry 24 }

cktHopCnt OBJECT-TYPE
	SYNTAX	INTEGER
	ACCESS	read-only
	STATUS	mandatory
	DESCRIPTION
		"The count of hops along the circuit path. (Max is 16)"
	::= { cktEntry 25 }

cktPath OBJECT-TYPE
	SYNTAX	OCTET STRING
	ACCESS	read-only
	STATUS	mandatory
	DESCRIPTION
		"The circuit path consisting a sequence of outbound interface
		indexes at nodes along the established circuit. The format is
		interface:interface:interface......"
	::= { cktEntry 26 }

cktFailReason OBJECT-TYPE
 	SYNTAX  INTEGER {
		    -- none (0),
		    admindown (1),
		    novcbuff (2),
		    nobw (3),
		    noroute (4),
		    timeout (5),
		    nopdubuff (6),
		    nodest (7),
		    trkrnr (8),
		    trkdown (9),
		    balancereroute (10),
		    dead(11),
		    defpathreroute(12),
		    nidown(13),
		    otherpvcsegdown(14),
		    otherpvcsegrnr(15),
		    usingaltpathwarning(16),
                    iopdown(17),
                    numsgbuffer(18),
                    noport(19),
                    misconfig(20),
                    svcsetupfail(21),
                    srcbackedup(22),
                    srcunknown(23),
                    dstunknown(24),
                    bkpdlcicollision(25),
                    oldrevinpath(26),
		    smdsmgmttrunk(27),
		    nevercalled(28),
		    bothendptbackup(29),
		    pvcroutemgttrunk(30),
		    nomultipointparent(31),
		    pvcroutefail(32),
		    novpivci(33)
		}
 	ACCESS  read-only
 	STATUS  mandatory
 	DESCRIPTION
		"The reason for the PVC establishment failure."
	::= { cktEntry 27 }

cktFailNode OBJECT-TYPE
 	SYNTAX  INTEGER
 	ACCESS  read-only
 	STATUS  mandatory
 	DESCRIPTION
		"The node which causes the PVC failure."
	::= { cktEntry 28 }

cktFailPort OBJECT-TYPE
 	SYNTAX  INTEGER
 	ACCESS  read-only
 	STATUS  mandatory
 	DESCRIPTION
		"The port on the fail node which causes the PVC failure."
	::= { cktEntry 29 }

cktMcastGroupId OBJECT-TYPE
 	SYNTAX  INTEGER
 	ACCESS  read-write
 	STATUS  mandatory
 	DESCRIPTION
		"Multicast group identifier (1..32). 
		This field is 0 for unicast PVCs."
  	::= { cktEntry 30 }

cktMcastMemberList OBJECT-TYPE
 	SYNTAX  OCTET STRING
 	ACCESS  read-write
 	STATUS  mandatory
 	DESCRIPTION
		"A list of operations and the affected unicast DLCIs (lportId,
		cktId)s in a multicast group.  The syntax is as follows:
		[op:dlci,dlci,...,op:dlci,dlci,...] where op can either be
		delete (0) or add (1)"
  	::= { cktEntry 31 }

cktMcastParentGroups OBJECT-TYPE
 	SYNTAX  OCTET STRING
 	ACCESS  read-only
 	STATUS  mandatory
 	DESCRIPTION
		"An 8-byte Octect string indicating the parent groups this 
		DLCI belongs to."
  	::= { cktEntry 32 }

cktInFrames OBJECT-TYPE
	SYNTAX  Counter
 	ACCESS  read-only
 	STATUS  mandatory
 	DESCRIPTION
		"The number of inbound frames since the last reset."
	::= { cktEntry 33 }

cktInDEFrames OBJECT-TYPE
	SYNTAX  Counter
 	ACCESS  read-only
 	STATUS  mandatory
 	DESCRIPTION
		"The number of inbound DE-marked frames since the last reset."
	::= { cktEntry 34 }

cktInODEFrames OBJECT-TYPE
 	SYNTAX  Counter
 	ACCESS  read-only
 	STATUS  mandatory
 	DESCRIPTION
		"The number of inbound ODE-marked frames since the last reset."
	::= { cktEntry 35 }

cktInFECNFrames OBJECT-TYPE
 	SYNTAX  Counter
 	ACCESS  read-only
 	STATUS  mandatory
 	DESCRIPTION
		"The number of inbound frames indicating forward congestion
		since the last reset."
  	::= { cktEntry 36 }

cktInBECNFrames OBJECT-TYPE
 	SYNTAX   	Counter
 	ACCESS   	read-only
 	STATUS   	mandatory
 	DESCRIPTION
		"The number of inbound frames indicating backward congestion
		since the last reset."
  	::= { cktEntry 37 }

cktInDiscards OBJECT-TYPE
 	SYNTAX  Counter
 	ACCESS  read-only
 	STATUS  mandatory
 	DESCRIPTION
		"Number of inbound frames discarded by rate enforcement."
  	::= { cktEntry 38 }

cktInOctets OBJECT-TYPE
	SYNTAX  Counter
 	ACCESS  read-only
 	STATUS  mandatory
 	DESCRIPTION
		"The number of inbound octets since the last reset."
	::= { cktEntry 39 }

cktInDEOctets OBJECT-TYPE
	SYNTAX  Counter
 	ACCESS  read-only
 	STATUS  mandatory
 	DESCRIPTION
		"The number of inbound DE-marked octets since the last reset."
	::= { cktEntry 40 }

cktInODEOctets OBJECT-TYPE
	SYNTAX  Counter
 	ACCESS  read-only
 	STATUS  mandatory
 	DESCRIPTION
		"The number of inbound ODE-marked octets since the last reset."
	::= { cktEntry 41 }

cktOutFrames OBJECT-TYPE
 	SYNTAX  Counter
 	ACCESS  read-only
 	STATUS  mandatory
 	DESCRIPTION
		"The number of outbound frames since the last reset."
	::= { cktEntry 42 }

cktOutDEFrames OBJECT-TYPE
 	SYNTAX  Counter
 	ACCESS  read-only
 	STATUS  mandatory
 	DESCRIPTION
		"The number of outbound DE-marked frames since the last reset."
	::= { cktEntry 43 }

cktOutODEFrames OBJECT-TYPE
 	SYNTAX  Counter
 	ACCESS  read-only
 	STATUS  mandatory
 	DESCRIPTION
		"The number of outbound ODE-marked frames since the last reset."
	::= { cktEntry 44 }

cktOutFECNFrames OBJECT-TYPE
	SYNTAX  Counter
 	ACCESS  read-only
 	STATUS  mandatory
 	DESCRIPTION
		"The number of outbound FECN-marked frames since the last
		reset."
	::= { cktEntry 45 }

cktOutBECNFrames OBJECT-TYPE
 	SYNTAX  Counter
 	ACCESS  read-only
 	STATUS  mandatory
 	DESCRIPTION
		"The number of outbound BECN-marked frames since the last 
		reset."
	::= { cktEntry 46 }

cktOutOctets OBJECT-TYPE
 	SYNTAX  Counter
 	ACCESS  read-only
 	STATUS  mandatory
 	DESCRIPTION
		"The number of outbound octets since the last reset."
	::= { cktEntry 47 }

cktOutDEOctets OBJECT-TYPE
	SYNTAX  Counter
 	ACCESS  read-only
 	STATUS  mandatory
 	DESCRIPTION
		"The number of outbound DE-marked octets since the last reset."
	::= { cktEntry 48 }

cktOutODEOctets OBJECT-TYPE
	SYNTAX  Counter
 	ACCESS  read-only
 	STATUS  mandatory
 	DESCRIPTION
		"The number of outbound ODE-marked octets since the last reset."
	::= { cktEntry 49 }

cktOutLostFrames OBJECT-TYPE
	SYNTAX  Counter
 	ACCESS  read-only
 	STATUS  mandatory
 	DESCRIPTION
		"The number of outbound frames that have been lost since the
		last reset."
	::= { cktEntry 50 }

cktOutLostDEFrames OBJECT-TYPE
 	SYNTAX  Counter
 	ACCESS  read-only
 	STATUS  mandatory
 	DESCRIPTION
		"The number of outbound DE-marked frames that have been lost
		since the last reset."
	::= { cktEntry 51 }

cktOutLostODEFrames OBJECT-TYPE
 	SYNTAX  Counter
 	ACCESS  read-only
 	STATUS  mandatory
 	DESCRIPTION
		"The number of outbound ODE-marked frames that have been lost
		since the last reset."
	::= { cktEntry 52 }

cktOutLostOctets OBJECT-TYPE
	SYNTAX  Counter
 	ACCESS  read-only
 	STATUS  mandatory
 	DESCRIPTION
		"The number of outbound octets that have been lost since the
		last reset."
	::= { cktEntry 53 }

cktOutLostDEOctets OBJECT-TYPE
 	SYNTAX  Counter
 	ACCESS  read-only
 	STATUS  mandatory
 	DESCRIPTION
		"The number of outbound DE-marked octets that have been lost
		since the last reset."
	::= { cktEntry 54 }

cktOutLostODEOctets OBJECT-TYPE
 	SYNTAX  Counter
 	ACCESS  read-only
 	STATUS  mandatory
 	DESCRIPTION
		"The number of outbound ODE-marked octets that have been lost
		since the last reset."
	::= { cktEntry 55 }

cktRtMinDelay OBJECT-TYPE
 	SYNTAX  INTEGER
 	ACCESS  read-only
 	STATUS  mandatory
 	DESCRIPTION
		"The minimum round-trip delay (micro-seconds)."
	::= { cktEntry 56 }

cktRtMaxDelay OBJECT-TYPE
 	SYNTAX  INTEGER
 	ACCESS  read-only
 	STATUS  mandatory
 	DESCRIPTION
		"The maximum round-trip delay (micro-seconds)."
	::= { cktEntry 57 }

cktRtAvgDelay OBJECT-TYPE
 	SYNTAX  INTEGER
 	ACCESS  read-only
 	STATUS  mandatory
 	DESCRIPTION
		"The average round-trip delay (micro-seconds)."
	::= { cktEntry 58 }

cktDiagTestId OBJECT-TYPE
	SYNTAX	INTEGER
	ACCESS	read-write
	STATUS	mandatory
	DESCRIPTION
		"Identification for the diagnostics tests to be run."
	::= { cktEntry 59 }

cktDiagTestRuns OBJECT-TYPE
	SYNTAX	INTEGER 
	ACCESS	read-write
	STATUS	mandatory
	DESCRIPTION
		"Number of passes of the diagnostics tests to be run.
		The default value is 1."
	::= { cktEntry 60 }

cktHelloCounter OBJECT-TYPE
	SYNTAX	INTEGER 
	ACCESS	read-only
	STATUS	mandatory
	DESCRIPTION
		"Number of PVC hello pdu frames received in the VC entry of the
		called side."
	::= { cktEntry 61 }

cktHelloAckCounter OBJECT-TYPE
	SYNTAX	INTEGER 
	ACCESS	read-only
	STATUS	mandatory
	DESCRIPTION
		"Number of PVC hello Ack pdu frames received in the VC entry of the
		calling side."
	::= { cktEntry 62 }

cktDefinedPath OBJECT-TYPE
	SYNTAX	OCTET STRING 
	ACCESS	read-write
	STATUS	mandatory
	DESCRIPTION
		"User defined path. in the format of Nx,x,x,Nx,.... If x is
		not prefixed with 'N', x is an interface ID. If x is
		prefixed with `N`, x is a node ID."
	::= { cktEntry 63 }

cktDefinedPathCount OBJECT-TYPE
	SYNTAX	INTEGER 
	ACCESS	read-only
	STATUS	mandatory
	DESCRIPTION
		"User defined path hop count."
	::= { cktEntry 64 }


cktDefinedPathEnable OBJECT-TYPE
	SYNTAX	INTEGER 
	ACCESS	read-write
	STATUS	mandatory
	DESCRIPTION
		"If set to 1, it means there is an user defined path for this
		circuit and it is enabled."
	::= { cktEntry 65 }

cktDefinedPathAltOption OBJECT-TYPE
	SYNTAX	INTEGER 
	ACCESS	read-write
	STATUS	mandatory
	DESCRIPTION
		"If set to 1, it means that if the user defined path fails,
		use the ospf-determined path."
	::= { cktEntry 66 }

cktUsingDefinedPath OBJECT-TYPE
	SYNTAX	INTEGER 
	ACCESS	read-only
	STATUS	mandatory
	DESCRIPTION
		"If set to 1, it indicates the PVC is currently using the
		defined path."
	::= { cktEntry 67 }


cktTryAltPath OBJECT-TYPE
	SYNTAX	INTEGER 
	ACCESS	read-only
	STATUS	mandatory
	DESCRIPTION
		"If set to 1, it means the inactive PVC will be activated
		on the ospf-determined path in the next retry."
	::= { cktEntry 68 }

cktNotVirgin OBJECT-TYPE
	SYNTAX	INTEGER 
	ACCESS	read-only
	STATUS	mandatory
	DESCRIPTION
		"If set to 1, it means this VC entry has been successfuly
		activated before."
	::= { cktEntry 69 }

cktInForward OBJECT-TYPE
	SYNTAX	INTEGER 
	ACCESS	read-only
	STATUS	mandatory
	DESCRIPTION
		"If the value is 1, it means the inbound flow is OK."
	::= { cktEntry 70 }

cktBtusSeg OBJECT-TYPE
	SYNTAX	INTEGER 
	ACCESS	read-write
	STATUS	mandatory
	DESCRIPTION
		"Number of Bus xmit units per data segment"
	::= { cktEntry 71 }

cktInSegmentsDiscards OBJECT-TYPE
	SYNTAX	Counter 
	ACCESS	read-only
	STATUS	mandatory
	DESCRIPTION
		"Number of segments received that were discarded because
		of frame reassembly errors."
	::= { cktEntry 72 }

cktAtmVPI OBJECT-TYPE
	SYNTAX	INTEGER
	ACCESS	read-write
	STATUS	mandatory
	DESCRIPTION
		"VPI value in the ATM cell header:
		 ATM DXI with HSSI IOP VPI (4 lsb bit) range: 0 - 15
		 ATM UNI DS3/E3 IOP    VPI (4 lsb bit) range: 0 - 15
                 T1 ATM 4 lsb  range 0-15
		 ATM-IWU STM-1/STS-3c  VPI (<=12 lsb bit) range: 0-4095"
	::= { cktEntry 73 }

cktAtmVCI OBJECT-TYPE
	SYNTAX	INTEGER
	ACCESS	read-write
	STATUS	mandatory
	DESCRIPTION
		"VCI value in the ATM cell header:
		 ATM DXI with HSSI IOP VCI (6 lsb bit) range: 0 - 63
		 ATM UNI DS3/E3 IOP    VCI (8 lsb bit) range: 0 - 255
                 T1 ATM 4 lsb          VCI (6 lsb bit) range  0 - 255
		 ATM-IWU STM-1/STS-3c  VCI (<=12 lsb bit) range: 0-4095"
	::= { cktEntry 74 }

cktType OBJECT-TYPE
        SYNTAX  INTEGER  {
			pvc (1),
			svc (2)
		}
        ACCESS  read-only
        STATUS  mandatory 
        DESCRIPTION 
                "1 if a permanent virtual circuit; 2 if a switched virtual circuit."
        ::= { cktEntry 75 } 

cktSvcCallingParty OBJECT-TYPE
        SYNTAX  OCTET STRING
        ACCESS  read-only
        STATUS  mandatory
        DESCRIPTION
                "The calling party number if this is a switched virtual circuit."
        ::= { cktEntry 76 }

cktSvcCalledParty OBJECT-TYPE
        SYNTAX  OCTET STRING
        ACCESS  read-only
        STATUS  mandatory
        DESCRIPTION
                "The called party number if this is a switched virtual circuit."
        ::= { cktEntry 77 }

cktSvcDuration OBJECT-TYPE
        SYNTAX  TimeTicks
        ACCESS  read-only
        STATUS  mandatory
        DESCRIPTION
                "The duration since the SVC circuit has been running."
        ::= { cktEntry 78 }

cktSvcCause OBJECT-TYPE
        SYNTAX  INTEGER
        ACCESS  read-only
        STATUS  mandatory
        DESCRIPTION
                "SVC cause number. The index will be 0.0 and should be
                 disregarded.

                 The following cause numbers maybe returned by stdx:

                1   -   unassigned number, callee is not assigned
                2   -   no route to specified transit network
                3   -   no route to destination
                6   -   channel unacceptable
                16  -   normal clearing
                17  -   user busy
                18  -   no user responding
                21  -   call rejected by whoever is sending this cause
                22  -   number changed, called party has changed its number
                27  -   destination out of order (the interface to called user)
                28  -   called party number is invalid
                29  -   facility requested can't be provided by network
                30  -   included in STATUS message to indicate it is responding
                        to a STATUS ENQUIRY
                31  -   unspecified, used if no other cause is appropriate
                34  -   no circuit or channel available to handle the call
                38  -   network is out of order
                41  -   tempprary failure, i.e., caller may try again
                42  -   network congestion
                43  -   access information (user-to-user) discarded
                44  -   requested circuit unavailable
                58  -   bearer capability not available
                63  -   requested service unavailable
                65  -   requested bearer capability is not implemented
                81  -   call reference is unknown
                95  -   invalid message
                96  -   mandatory information element is missing
                97  -   message type is unknown
                98  -   message not compatible with call state
                99  -   information element is unknown or not implemented
                100 -   invalid information element contents
                101 -   message not compatible with call state
        "
        ::= { cktEntry 79 }

cktXlatFlag OBJECT-TYPE
        SYNTAX  INTEGER  {
                        -- no-translation (0),
                        rfc1483 (1)
                }
        ACCESS  read-write
        STATUS  mandatory
        DESCRIPTION
                "0 if RFC1490 or no translation; 1 if RFC1483 translation."
        ::= { cktEntry 80 }

cktDestLaddr OBJECT-TYPE
	SYNTAX INTEGER
	ACCESS read-write
	STATUS mandatory
	DESCRIPTION
		"The destination logical address of the circuit."
	::= { cktEntry 81 }

cktSrcLaddr OBJECT-TYPE
	SYNTAX INTEGER
	ACCESS read-write
	STATUS mandatory
	DESCRIPTION
		"The source logical address of the circuit."
	::= { cktEntry 82 }

cktLoop OBJECT-TYPE
	SYNTAX INTEGER {
		-- disabled(0),
		local(1),
		remote(2),
		both(3)
	}
	ACCESS read-write
	STATUS mandatory
	DESCRIPTION
		"Setting this variable controls the loopback status of the
		given circuit endpoint."
	::= { cktEntry 83 }

cktRerouteBalance OBJECT-TYPE
	SYNTAX INTEGER {
		-- enabled(0),
		disabled(1)
	}
	ACCESS read-write
	STATUS mandatory
	DESCRIPTION
		"Setting this variable controls the use of rerouting to
		balance link usage."
	::= { cktEntry 84 }

cktCallingBackup OBJECT-TYPE
	SYNTAX INTEGER {
		-- false(0),
		true(1)
	}
	ACCESS read-only
	STATUS mandatory
	DESCRIPTION
		"Indicates if a caller endpoint is calling a backup PVC."
	::= { cktEntry 85 }

cktRCir OBJECT-TYPE
 	SYNTAX	INTEGER
 	ACCESS	read-write
 	STATUS	mandatory
 	DESCRIPTION
		"The average number of user data (bits) that the network agrees 
		to transfer over the circuit in the opposite direction,
		measured over the measurement interval T = cktBc/cktCir."
	::= { cktEntry 86 }

cktAtmQoS OBJECT-TYPE
	SYNTAX INTEGER {
		cbr  (1),
		vbr1 (2),
                vbr2 (3),
                vbr3 (4)
	}
 	ACCESS	read-write
 	STATUS	mandatory
 	DESCRIPTION
		"The Quality of Service of the ATM Circuit. Valid only for
                 ATM type circuits."
	::= { cktEntry 87 }
 
cktAtmInCells OBJECT-TYPE
 	SYNTAX	Counter
 	ACCESS	read-only
 	STATUS	mandatory
 	DESCRIPTION "The Number of ATM cells received on a VC (VPC or VCC)."
	::= { cktEntry 88 }

cktAtmOutCells OBJECT-TYPE
 	SYNTAX	Counter
 	ACCESS  read-only
 	STATUS	mandatory
 	DESCRIPTION "The Number of ATM cells transmitted on a VC (VPC or VCC).."
	::= { cktEntry 89 }

cktAtmInDiscardedClp0Cells OBJECT-TYPE
 	SYNTAX	Counter
 	ACCESS  read-only
 	STATUS	mandatory
 	DESCRIPTION "The Number of ATM CLP0 cells received and discarded on a VC (VPC or VCC).."
	::= { cktEntry 90 }

cktAtmInDiscardedClp1Cells OBJECT-TYPE
 	SYNTAX	Counter
 	ACCESS  read-only
 	STATUS	mandatory
 	DESCRIPTION "The Number of ATM CLP1 cells received and discarded on a VC (VPC or VCC)."
	::= { cktEntry 91 }

cktAtmVcType OBJECT-TYPE
	SYNTAX  INTEGER {
		    vpc  (1),
		    vcc  (2)
                }
 	ACCESS	read-write
 	STATUS	mandatory
 	DESCRIPTION "Type of ATM connection (VPC or VCC)."
	::= { cktEntry 92 }

cktAtmPCR OBJECT-TYPE
 	SYNTAX	INTEGER
 	ACCESS	read-write
 	STATUS	mandatory
 	DESCRIPTION
		"The Peak Cell Rate  measured in cells/second at which
		 cells are transmitted for this circuit."
	::= { cktEntry 93 }

cktAtmSCR OBJECT-TYPE
 	SYNTAX	INTEGER
 	ACCESS	read-write
 	STATUS	mandatory
 	DESCRIPTION
		"The Sustainable Cell Rate is the average transmission rate 
		 in cells per second for this circuit. It must be less than or 
		 or equal to the Peak Cell Rate."
	::= { cktEntry 94 }

cktAtmMBS OBJECT-TYPE
 	SYNTAX	INTEGER
 	ACCESS	read-write
 	STATUS	mandatory
 	DESCRIPTION
		"The Maximum Burst size determines the maximum number of cells
		 that can be transmitted at the peak cell rate."
	::= { cktEntry 95 }

cktAtmInPassedClp0Cells OBJECT-TYPE
 	SYNTAX	Counter
 	ACCESS	read-only
 	STATUS	mandatory
 	DESCRIPTION "The Number of ATM CLP 0 cells received and passed UPC on a VC (VPC or VCC)."
	::= { cktEntry 96 }

cktAtmInPassedClp1Cells OBJECT-TYPE
 	SYNTAX	Counter
 	ACCESS	read-only
 	STATUS	mandatory
 	DESCRIPTION "The Number of ATM CLP 1 cells received and passed UPC on a VC (VPC or VCC)."
	::= { cktEntry 97 }

cktAtmInTaggedCells OBJECT-TYPE
 	SYNTAX	Counter
 	ACCESS	read-only
 	STATUS	mandatory
 	DESCRIPTION "The Number of ATM cells received and tagged on a VC (VPC or VCC)."
	::= { cktEntry 98 }

cktAtmOutClp0Cells OBJECT-TYPE
 	SYNTAX	Counter
 	ACCESS  read-only
 	STATUS	mandatory
 	DESCRIPTION "The Number of ATM CLP 0 cells transmitted on a VC (VPC or VCC).."
	::= { cktEntry 99 }

cktAtmOutClp1Cells OBJECT-TYPE
 	SYNTAX	Counter
 	ACCESS  read-only
 	STATUS	mandatory
 	DESCRIPTION "The Number of ATM CLP 1 cells transmitted on a VC (VPC or VCC).."
	::= { cktEntry 100 }

cktAtmRQoS OBJECT-TYPE
	SYNTAX INTEGER {
		cbr  (1),
		vbr1 (2),
                vbr2 (3),
                vbr3 (4)
	}
 	ACCESS	read-write
 	STATUS	mandatory
 	DESCRIPTION
		"The Quality of Service of the ATM connection in the opposite direction." 
	::= { cktEntry 101 }

cktAtmTfdType OBJECT-TYPE
	SYNTAX INTEGER {
		pcr-0-01 (1),
		pcr-0-01-tag (2),
		pcr-01-scr-0-mbs-0 (3),
		pcr-01-scr-0-mbs-0-tag (4),
		pcr-01 (5),
		pcr-01-scr-01-mbs-01(6),
		pcr-01-bestEffort(7)
	}
 	ACCESS	read-write
 	STATUS	mandatory
 	DESCRIPTION
		"The combination of traffic parameters." 
	::= { cktEntry 102 }

cktAtmRTfdType OBJECT-TYPE
	SYNTAX INTEGER {
		pcr-0-01 (1),
		pcr-0-01-tag (2),
		pcr-01-scr-0-mbs-0 (3),
		pcr-01-scr-0-mbs-0-tag (4),
		pcr-01 (5),
		pcr-01-scr-01-mbs-01 (6),
		pcr-01-bestEffort(7)
	}
 	ACCESS	read-write
 	STATUS	mandatory
 	DESCRIPTION
		"The combination of traffic parameters in opposite direction." 
	::= { cktEntry 103 }

cktAtmTfdParam1 OBJECT-TYPE
 	SYNTAX	INTEGER
 	ACCESS	read-write
 	STATUS	mandatory
 	DESCRIPTION
		"The traffic descriptor parameter 1."
	::= { cktEntry 104 }

cktAtmTfdParam2 OBJECT-TYPE
 	SYNTAX	INTEGER
 	ACCESS	read-write
 	STATUS	mandatory
 	DESCRIPTION
		"The traffic descriptor parameter 2."
	::= { cktEntry 105 }

cktAtmTfdParam3 OBJECT-TYPE
 	SYNTAX	INTEGER
 	ACCESS	read-write
 	STATUS	mandatory
 	DESCRIPTION
		"The traffic descriptor parameter 3."
	::= { cktEntry 106 }

cktAtmRTfdParam1 OBJECT-TYPE
 	SYNTAX	INTEGER
 	ACCESS	read-write
 	STATUS	mandatory
 	DESCRIPTION
		"The traffic descriptor parameter 1 for opposite direction."
	::= { cktEntry 107 }

cktAtmRTfdParam2 OBJECT-TYPE
 	SYNTAX	INTEGER
 	ACCESS	read-write
 	STATUS	mandatory
 	DESCRIPTION
		"The traffic descriptor parameter 3 for opposite direction."
	::= { cktEntry 108 }

cktAtmRTfdParam3 OBJECT-TYPE
 	SYNTAX	INTEGER
 	ACCESS	read-write
 	STATUS	mandatory
 	DESCRIPTION
		"The traffic descriptor parameter 3 for opposite direction."
	::= { cktEntry 109 }

cktAtmFrameIWF OBJECT-TYPE
 	SYNTAX	INTEGER {
                    default(1),
                    iwf(2)
                }
 	ACCESS	read-write
 	STATUS	mandatory
 	DESCRIPTION
		"Frame Relay/ATM Interworking Function indicator."
	::= { cktEntry 110 }

cktAtmUserPlane OBJECT-TYPE
	SYNTAX  INTEGER {
		    point-to-point(1),
		    point-to-multipoint(2)
                }
 	ACCESS	read-write
 	STATUS	mandatory
 	DESCRIPTION "Bitmap defining user plane capabilities."
	::= { cktEntry 111 }

cktRBc OBJECT-TYPE
 	SYNTAX	INTEGER
 	ACCESS	read-write
 	STATUS	mandatory
 	DESCRIPTION
		"The maximum amount of data (bits) that the network agrees
		to transfer over the circuit in the opposite direction under 
                normal conditions, during the measurement interval."
	::= { cktEntry 112 }

cktRBe OBJECT-TYPE
 	SYNTAX	INTEGER
 	ACCESS	read-write
 	STATUS	mandatory
 	DESCRIPTION
		"The maximum amount of uncommitted data (bits) that the network
		will attempt to transfer over the circuit in the opposite direction
                during the measurement interval.  By default, if not configured when
		creating the entry, the Excess Information Burst Size is set
                to the value of ifSpeed."
	::= { cktEntry 113 }


cktOamLoopbackDirection OBJECT-TYPE
 	SYNTAX	INTEGER {
                    local(1),
		    remote(2)
		}
 	ACCESS	read-write
 	STATUS	mandatory
 	DESCRIPTION
		"Which direction to send the loopback cell.  If 'local', send out this
		circuit entry's port.  If 'remote', send out the remote circuit
		entry's port."
	::= { cktEntry 114}

cktOamLoopbackType OBJECT-TYPE
 	SYNTAX	INTEGER {
                    segment(1),
		    end-to-end(2)
		}
 	ACCESS	read-write
 	STATUS	mandatory
 	DESCRIPTION
		"Type of oam loopback to send - either segment or end to end."
	::= { cktEntry 115}

cktOamLoopbackHops OBJECT-TYPE
 	SYNTAX	INTEGER
 	ACCESS	read-write
 	STATUS	mandatory
 	DESCRIPTION
		"Number of hops the loopback cell should traverse inside the
		Cascade network before being echoed back by the far Cascade
		device."
	::= { cktEntry 116}

cktOamLoopbackCount OBJECT-TYPE
 	SYNTAX	INTEGER
 	ACCESS	read-write
 	STATUS	mandatory
 	DESCRIPTION
		"Number of oam loopback cells left to send this session.  Setting
		this from zero to non-zero starts the loopback session."
	::= { cktEntry 117}

cktOamLoopbackReceived OBJECT-TYPE
 	SYNTAX	Counter
 	ACCESS	read-only
 	STATUS	mandatory
 	DESCRIPTION
		"Number of oam responses received for this loopback session."
	::= { cktEntry 118}

cktOamLoopbackTimeouts OBJECT-TYPE
 	SYNTAX	Counter
 	ACCESS	read-only
 	STATUS	mandatory
 	DESCRIPTION
		"Number of times a loopback response was not received within
		the timeout period during this loopback session."
	::= { cktEntry 119}

cktOamLoopbackReceivedHigh OBJECT-TYPE
 	SYNTAX	INTEGER
 	ACCESS	read-only
 	STATUS	mandatory
 	DESCRIPTION
		"Highest response time (in milliseconds) of an oam loopback
		response this loopback session."
	::= { cktEntry 120}

cktOamLoopbackReceivedLow OBJECT-TYPE
 	SYNTAX	INTEGER
 	ACCESS	read-only
 	STATUS	mandatory
 	DESCRIPTION
		"Lowest response time (in milliseconds) of an oam loopback
		response this loopback session."
	::= { cktEntry 121}

cktOamLoopbackReceivedAvg OBJECT-TYPE
 	SYNTAX	INTEGER
 	ACCESS	read-only
 	STATUS	mandatory
 	DESCRIPTION
		"Average response time (in milliseconds) of an oam loopback
		response this loopback session."
	::= { cktEntry 122}

cktOamAlarmDisable OBJECT-TYPE
 	SYNTAX	INTEGER {
		enabled(1),
		disabled(2)
	}
 	ACCESS	read-write
 	STATUS	mandatory
 	DESCRIPTION
		"If disabled, then don't generate oam alarms if this circuit is down."
	::= { cktEntry 123}

cktShaperId OBJECT-TYPE
	SYNTAX  INTEGER
	ACCESS  read-write
	STATUS  mandatory
	DESCRIPTION
	       "The shaper to be used for this virtual connection interworking
		with frame relay:

		1-port ATM-IWU STM-1/STS-3c card
		--------------------------------

		Values: 1..16"
	::= { cktEntry 124 }

cktOspfCtd OBJECT-TYPE
	SYNTAX  INTEGER (1..100)
	ACCESS  read-write
	STATUS  mandatory
	DESCRIPTION
	       "The allowed cell delay:

		4-port CBR E1/DS1 card
		----------------------

		The maximum allowed cell delay in msec"
	::= { cktEntry 125 }

cktOspfCdv OBJECT-TYPE
	SYNTAX  INTEGER (100..1000)
	ACCESS  read-write
	STATUS  mandatory
	DESCRIPTION
	       "The allowed cell delay variation:

		4-port CBR E1/DS1 card
		----------------------

		The maximum allowed cell delay variation in msec"
	::= { cktEntry 126 }

cktOutPort OBJECT-TYPE
 	SYNTAX  INTEGER
 	ACCESS  read-only
 	STATUS  mandatory
 	DESCRIPTION
		"The outgoing port number for the adjacent VC entry in this switch."
	::= { cktEntry 127 }

cktOutVc OBJECT-TYPE
 	SYNTAX  INTEGER
 	ACCESS  read-only
 	STATUS  mandatory
 	DESCRIPTION
		"The adjacent VC entry corresponding to this circuit accross the bus."
	::= { cktEntry 128 }

cktRVc OBJECT-TYPE
 	SYNTAX  INTEGER
 	ACCESS  read-only
 	STATUS  mandatory
 	DESCRIPTION
		"The adjacent VC entry corresponding to this circuit accross the trunk."
	::= { cktEntry 129 }

cktEntryType OBJECT-TYPE
 	SYNTAX	INTEGER {
                    fr-user(1),
		    as-trunk(2),
		    on-trunk(3),
		    lmi(4),
		    multicast(5),
		    mgmt(6),
		    smds(7),
		    split-multicast(8),
		    control(9),
		    atm-user(10),
		    atm-leaf(11)
		}
 	ACCESS	read-only
 	STATUS	mandatory
 	DESCRIPTION
		"The internal type of circuit entry allocated by the circuit manager."
	::= { cktEntry 130 }

cktDiagStr OBJECT-TYPE
	SYNTAX	OCTET STRING 
	ACCESS	read-only
	STATUS	mandatory
	DESCRIPTION
		"Internal diagnostic information."
	::= { cktEntry 131 }

cktSvcAalType OBJECT-TYPE
	SYNTAX	INTEGER {
		aal1 (1),
		unspecified (2),
		aal3-4 (3),
		user-defined (4),
		aal5 (5)
	}
	ACCESS	read-only
	STATUS	mandatory
	DESCRIPTION
		"The AAL type for this SVC."
	::= { cktEntry 132 }

cktSvcBBearerClass OBJECT-TYPE
	SYNTAX	INTEGER {
		unspecified (1),
		class-A (2),
		class-C (3),
		class-X (4),
		class-VP (5)
	}
	ACCESS	read-only
	STATUS	mandatory
	DESCRIPTION
		"The Broadband bearer capability class for this SVC."
	::= { cktEntry 133 }

cktSvcBBearerClippingSusc OBJECT-TYPE
	SYNTAX	INTEGER {
		unspecified (1),
		not-susceptible (2),
		susceptible (3)
	}
	ACCESS	read-only
	STATUS	mandatory
	DESCRIPTION
		"The Broadband bearer capability clipping susceptibility for this SVC."
	::= { cktEntry 134 }

cktSvcBBearerTmgReq OBJECT-TYPE
	SYNTAX	INTEGER {
		not-indicated (1),
		end-to-end (2),
		not-end-to-end (3)
	}
	ACCESS	read-only
	STATUS	mandatory
	DESCRIPTION
		"The Broadband bearer capability timing requirements for this SVC."
	::= { cktEntry 135 }

cktSvcBBearerTfcType OBJECT-TYPE
	SYNTAX	INTEGER {
		not-indicated (1),
		cbr (2),
		vbr (3)
	}
	ACCESS	read-only
	STATUS	mandatory
	DESCRIPTION
		"The Broadband bearer capability traffic type for this SVC."
	::= { cktEntry 136 }

cktAtmUPCEnable OBJECT-TYPE
	SYNTAX	INTEGER {
		disabled	(1),
		enabled 	(2)
	}
	ACCESS	read-write
	STATUS	mandatory
	DESCRIPTION
	"Enable ATM UPC Function."
	::= { cktEntry 137 }

cktRPriority OBJECT-TYPE
	SYNTAX	INTEGER
	ACCESS	read-write
	STATUS	mandatory
	DESCRIPTION
		"The priority level (0 through 3) for this circuit in the opposite direction.
                 When port service type is defined as 'mono-class', this
                 priority means the forward priority of the circuit.
                 When port service type is defined as 'multi-class', this
                 priority means the discard priority of the circuit."
	::= { cktEntry 138 }

cktRtPriority OBJECT-TYPE
	SYNTAX INTEGER
	ACCESS read-write
	STATUS mandatory
	DESCRIPTION
		"The routing priority level of the circuit which is a 8 bit
                 number where the 3-bit bumping priority is contained in bits
                 0-2 and the 4-bit bandwidth  priority is contained in bits 3-6.
		 For ATM multipoint ckts, bw and bumping priorities should be zero."
	::= { cktEntry 139 }

cktDeltaBc OBJECT-TYPE
	SYNTAX INTEGER
	ACCESS read-write
	STATUS mandatory
	DESCRIPTION
		"The maximum number of bits that the network agree to transfer
		 over the circuit as committed bits during the measurement
		 interval under the CONDITION that the circuit still has POSITIVE
		 committed bit (Bc) credits before receiving a frame but will have
		 NEGATIVE Bc credits after accepting the frame. The range of this
		 variable is 0 to 65,528 bits. By default, if not configured when
		 creating the entry, it is set to 65,528 bits."
	::= { cktEntry 140 }

cktDeltaBe OBJECT-TYPE
	SYNTAX INTEGER
	ACCESS read-write
	STATUS mandatory
	DESCRIPTION
		"The maximum number of bits that the network agree to transfer
		 over the circuit as allowed excess bits during the measurement
		 interval under the CONDITION that the circuit still has POSITIVE
		 excess bit (Be) credits before receiving a frame but will have
		 NEGATIVE Be credits after accepting the frame. The range of this
		 variable is 0 to 65,528 bits. By default, if not configured when
		 creating the entry, it is set to 65,528 bits."
	::= { cktEntry 141 }

cktDeltaRBc OBJECT-TYPE
	SYNTAX INTEGER
	ACCESS read-write
	STATUS mandatory
	DESCRIPTION
		"The maximum number of bits that the network agree to transfer
		 over the circuit as committed bits in the opposite direction
		 during the measurement
		 interval under the CONDITION that the circuit still has POSITIVE
		 committed bit (Bc) credits before receiving a frame but will have
		 NEGATIVE Bc credits after accepting the frame. The range of this
		 variable is 0 to 65,528 bits. By default, if not configured when
		 creating the entry, it is set to 65,528 bits."
	::= { cktEntry 142 }

cktDeltaRBe OBJECT-TYPE
	SYNTAX INTEGER
	ACCESS read-write
	STATUS mandatory
	DESCRIPTION
		"The maximum number of bits that the network agree to transfer
		 over the circuit as allowed excess bits in the opposite
		 direction during the measurement
		 interval under the CONDITION that the circuit still has POSITIVE
		 excess bit (Be) credits before receiving a frame but will have
		 NEGATIVE Be credits after accepting the frame. The range of this
		 variable is 0 to 65,528 bits. By default, if not configured when
		 creating the entry, it is set to 65,528 bits."
	::= { cktEntry 143 }

cktRedFrPcnt OBJECT-TYPE
	SYNTAX INTEGER
	ACCESS read-write
	STATUS mandatory
	DESCRIPTION
		"The percentage of RED frame bits that are allowed to enter the
		 network, during the measurement interval, under non-congestion
		 condition. Its value range is 0 - 100 and default value is 100. Its
		 calculation is as follows:

		 cktRedFrPcn = (allowed RED frame bits)/(Bc+Be+allowed RED frame bits)"
	::= { cktEntry 144 }

cktRedFrRPcnt OBJECT-TYPE
	SYNTAX INTEGER
	ACCESS read-write
	STATUS mandatory
	DESCRIPTION
		"The percentage of RED frame bits that are allowed to enter the
		 network in the opposite direction,
		 during the measurement interval, under non-congestion
		 condition. Its value range is 0 - 100 and default value is 100.
		 Its calculation is as follows:

                 cktRedFrRPcn = (allowed RED frame bits)/(rBc+rBe+allowed RED frame bits)"
	::= { cktEntry 145 }

cktRateEnforceSchm OBJECT-TYPE
	SYNTAX INTEGER {
		-- slide (0),
		jump (1),
  		simple (2)
	}
	ACCESS read-write
	STATUS mandatory
	DESCRIPTION
		"Variable used to indicate the rate enforcement scheme employed.
		     0: Slide window rate enforcement scheme
		     1: Jump window rate enforcement scheme
		     2: Simple rate enforcement scheme
		 Default value is 2."
	::= { cktEntry 146 }

cktRateEnforceRSchm OBJECT-TYPE
	SYNTAX INTEGER {
		-- slide (0),
		jump (1),
		simple (2)
	}
	ACCESS read-write
	STATUS mandatory
	DESCRIPTION
		"Variable used to indicate the rate enforcement scheme employed
		 in the opposite direction.
		     0: Slide window rate enforcement scheme
		     1: Jump window rate enforcement scheme
		     2: Simple rate enforcement scheme
		 Default value is 2."
	::= { cktEntry 147 }

cktROde OBJECT-TYPE
	SYNTAX	INTEGER {
		    -- off (0),
		    on (1)
		}
	ACCESS	read-write
	STATUS	mandatory
	DESCRIPTION
		"This variable states whether graceful discard is enabled
		for the ckt in the opposite direction."
	::= { cktEntry 148 }

cktPrivateNet OBJECT-TYPE
	SYNTAX	INTEGER
	ACCESS	read-write
	STATUS	mandatory
	DESCRIPTION "If non-zero, indicates the private network that the
		circuit belongs to. If 0, the circuit has access to the
		entire public portion of the network."
	::= { cktEntry 149 }

cktPrivateNetOverflow OBJECT-TYPE
	SYNTAX	INTEGER {
		    -- restrict (0),
		    use-public (1)
		}
	ACCESS	read-write
	STATUS	mandatory
	DESCRIPTION "Indicates how private network circuits are handled,
		when the resources of the network have become exhausted.
		If set to use-public, the resources of the public network
		can be used during overflow conditions."
	::= { cktEntry 150 }

cktCustomerID OBJECT-TYPE
	SYNTAX	INTEGER
	ACCESS	read-write
	STATUS	mandatory
	DESCRIPTION "The Customer that owns this circuit. For Virtual
		Private Networking Support."
	::= { cktEntry 151 }

cktAtmCDVT OBJECT-TYPE
	SYNTAX	INTEGER
	ACCESS	read-write
	STATUS	mandatory
	DESCRIPTION
	"The Cell Delay Variation Tolerance for the VC"
	::= { cktEntry 152 }


cktNdcEnable OBJECT-TYPE
	SYNTAX  INTEGER {
		off (1),
		on (2)
	}
	ACCESS  read-write
	STATUS  mandatory
	DESCRIPTION
		"Enable/disable Network Data Collection for a PVC on an IOM.
		 The number of NDC-monitored PVCs is limited as follows:
		 30 per DS3 interface, 90 per OC3 interface, and 360 per OC12
		 interface."
	::= { cktEntry 153 }

cktInterworkingFrToAtmCLP OBJECT-TYPE
	SYNTAX  INTEGER {
		-- clp0  (0),
		clp1  (1),
                fr-de (2)
	}
	ACCESS  read-write
	STATUS  mandatory
	DESCRIPTION
		"CLP mapping for Frame Relay To ATM Service Interworking."
	::= { cktEntry 154 }

cktInterworkingFrToAtmDe OBJECT-TYPE
	SYNTAX  INTEGER {
		-- de0     (0),
		de1     (1),
                atm-clp (2)
	}
	ACCESS  read-write
	STATUS  mandatory
	DESCRIPTION
		"DE bit mapping for ATM To Frame Relay  Service Interworking."
	::= { cktEntry 155 }

cktNrtsCLP1 OBJECT-TYPE
	SYNTAX  INTEGER {
		no (1),
		yes (2)
	}
	ACCESS  read-write
	STATUS  mandatory
	DESCRIPTION
		"Whether to use the discard threshold as the CLP1
		 Discard threshold upon reception of a cell by the NRTS
		 processor in the forward direction."
	::= { cktEntry 156 }

cktNrtsDiscardClp0 OBJECT-TYPE
	SYNTAX	Counter
	ACCESS	read-only
	STATUS	mandatory
	DESCRIPTION
		"The number of the CLP0 cells received and discarded by the
		 NRTS processor."
	::= { cktEntry 157 }

cktNrtsDiscardClp1 OBJECT-TYPE
	SYNTAX	Counter
	ACCESS	read-only
	STATUS	mandatory
	DESCRIPTION
		"The number of the CLP1 cells received and discarded by the
		 NRTS processor."
	::= { cktEntry 158 }

cktMPEnableAMF OBJECT-TYPE
	SYNTAX	INTEGER {
		disableAMF (1),
		enableAMF (2)
	}
	ACCESS	read-write
	STATUS	mandatory
	DESCRIPTION
		"Whether the Multilink PPP PVC Attributes Modification Feature
		 is enabled."
	::= { cktEntry 159 }

cktMPEligible OBJECT-TYPE
	SYNTAX	INTEGER {
		isMPEligible (1),
		isNotMPEligible (2)
	}
	ACCESS	read-write
	STATUS	mandatory
	DESCRIPTION
		"Whether this circuit is eligible to be a member of a
		 Multilink PPP bundle."
	::= { cktEntry 160 }

cktMPForcedCaller OBJECT-TYPE
	SYNTAX	INTEGER {
		isMPForcedCaller (1),
		isNotMPForcedCaller (2)
	}
	ACCESS	read-write
	STATUS	mandatory
	DESCRIPTION
		"Whether this end of the circuit has been forced to be caller
		 to support Multilink PPP PVC Attributes Modification Feature."
	::= { cktEntry 161 }

cktMPForcedCallee OBJECT-TYPE
	SYNTAX	INTEGER {
		isMPForcedCallee (1),
		isNotMPForcedCallee (2)
	}
	ACCESS	read-write
	STATUS	mandatory
	DESCRIPTION
		"Whether this end of the circuit has been forced to be callee
		 to support Multilink PPP PVC Attributes Modification Feature."
	::= { cktEntry 162 }

cktFrameSize	OBJECT-TYPE
        SYNTAX  INTEGER
        ACCESS  read-write
        STATUS  mandatory
        DESCRIPTION
                "The average frame size (measured in number of bytes) of the traffic
		 on the circuit. If not configured, it is set to 280 (bytes) by default."
        ::= { cktEntry 163 }

cktRFrameSize    OBJECT-TYPE
        SYNTAX  INTEGER
        ACCESS  read-write
        STATUS  mandatory
        DESCRIPTION
                "The average frame size (measured in number of bytes) of the traffic
                 on the circuit on the reverse direction. If not configured, it is
		 set to 280 (bytes) by default."
        ::= { cktEntry 164 }

cktRNrtsCLP1 OBJECT-TYPE
	SYNTAX  INTEGER {
		no (1),
		yes (2)
	}
	ACCESS  read-write
	STATUS  mandatory
	DESCRIPTION
		"Whether to use the discard threshold as the CLP1
		 Discard threshold upon reception of a cell by the NRTS
		 processor in the reverse direction."
	::= { cktEntry 165 }

cktBBearerAtmTransferCapability OBJECT-TYPE
	SYNTAX INTEGER {
		none (1),
		cbr (2),
		cbr-with-clr-01 (3),
		vbr-rt (4),
		vbr-rt-with-clr-01 (5),
		vbr-nrt (6),
		vbr-nrt-with-clr-01 (7),
		abr (8)
	}
	ACCESS  read-only
	STATUS  mandatory
	DESCRIPTION
		"The broadband bearer ATM transfer capability of this SVC.  This object is
		 not pertinent to IISP 3.x, UNI 3.x or Q.2931 signaling."
	::= { cktEntry 166 }

cktAtmFrameDiscard OBJECT-TYPE
	SYNTAX INTEGER {
		disabled (1),
		enabled (2)
	}
	ACCESS  read-write
	STATUS  mandatory
	DESCRIPTION
		"The ATM frame discard state for this circuit."
	DEFVAL { disabled }
	::= { cktEntry 167 }

cktRAtmFrameDiscard OBJECT-TYPE
	SYNTAX INTEGER {
		disabled (1),
		enabled (2)
	}
	ACCESS  read-write
	STATUS  mandatory
	DESCRIPTION
		"The reverse ATM frame discard state for this circuit."
	DEFVAL { disabled }
	::= { cktEntry 168 }

cktAbrFRMRTT OBJECT-TYPE
	SYNTAX INTEGER
	ACCESS  read-only
	STATUS  mandatory
	DESCRIPTION
		"The ABR fixed RM round trip time for this SVC."
	::= { cktEntry 169 }

cktAbrICR OBJECT-TYPE
	SYNTAX INTEGER
	ACCESS  read-only
	STATUS  mandatory
	DESCRIPTION
		"The ABR initial cell rate for this SVC."
	::= { cktEntry 170 }

cktRAbrICR OBJECT-TYPE
	SYNTAX INTEGER
	ACCESS  read-only
	STATUS  mandatory
	DESCRIPTION
		"The reverse ABR initial cell rate for this SVC."
	::= { cktEntry 171 }

cktAbrRIF OBJECT-TYPE
	SYNTAX INTEGER
	ACCESS  read-only
	STATUS  mandatory
	DESCRIPTION
		"The ABR rate increase factor for this SVC."
	::= { cktEntry 172 }

cktRAbrRIF OBJECT-TYPE
	SYNTAX INTEGER
	ACCESS  read-only
	STATUS  mandatory
	DESCRIPTION
		"The reverse ABR rate increase factor for this SVC."
	::= { cktEntry 173 }

cktAbrRDF OBJECT-TYPE
	SYNTAX INTEGER
	ACCESS  read-only
	STATUS  mandatory
	DESCRIPTION
		"The ABR rate decrease factor for this SVC."
	::= { cktEntry 174 }

cktRAbrRDF OBJECT-TYPE
	SYNTAX INTEGER
	ACCESS  read-only
	STATUS  mandatory
	DESCRIPTION
		"The reverse ABR rate decrease factor for this SVC."
	::= { cktEntry 175 }

cktAbrTBE OBJECT-TYPE
	SYNTAX INTEGER
	ACCESS  read-only
	STATUS  mandatory
	DESCRIPTION
		"The ABR transient buffer exposure for this SVC."
	::= { cktEntry 176 }

cktRAbrTBE OBJECT-TYPE
	SYNTAX INTEGER
	ACCESS  read-only
	STATUS  mandatory
	DESCRIPTION
		"The reverse ABR transient buffer exposure for this SVC."
	::= { cktEntry 177 }

cktAbrNRM OBJECT-TYPE
	SYNTAX INTEGER
	ACCESS  read-only
	STATUS  mandatory
	DESCRIPTION
		"The ABR NRM for this SVC."
	::= { cktEntry 178 }

cktRAbrNRM OBJECT-TYPE
	SYNTAX INTEGER
	ACCESS  read-only
	STATUS  mandatory
	DESCRIPTION
		"The reverse ABR NRM for this SVC."
	::= { cktEntry 179 }

cktAbrTRM OBJECT-TYPE
	SYNTAX INTEGER
	ACCESS  read-only
	STATUS  mandatory
	DESCRIPTION
		"The ABR TRM for this SVC."
	::= { cktEntry 180 }

cktRAbrTRM OBJECT-TYPE
	SYNTAX INTEGER
	ACCESS  read-only
	STATUS  mandatory
	DESCRIPTION
		"The reverse ABR TRM for this SVC."
	::= { cktEntry 181 }

cktAbrCDF OBJECT-TYPE
	SYNTAX INTEGER
	ACCESS  read-only
	STATUS  mandatory
	DESCRIPTION
		"The ABR CDF for this SVC."
	::= { cktEntry 182 }

cktRAbrCDF OBJECT-TYPE
	SYNTAX INTEGER
	ACCESS  read-only
	STATUS  mandatory
	DESCRIPTION
		"The reverse ABR CDF for this SVC."
	::= { cktEntry 183 }

cktAbrADTF OBJECT-TYPE
	SYNTAX INTEGER
	ACCESS  read-only
	STATUS  mandatory
	DESCRIPTION
		"The ABR ADTF for this SVC."
	::= { cktEntry 184 }

cktRAbrADTF OBJECT-TYPE
	SYNTAX INTEGER
	ACCESS  read-only
	STATUS  mandatory
	DESCRIPTION
		"The reverse ABR ADTF for this SVC."
	::= { cktEntry 185 }

cktAccumCTD OBJECT-TYPE
	SYNTAX INTEGER
	ACCESS  read-only
	STATUS  mandatory
	DESCRIPTION
		"The accumulated cell(frame) transfer delay for this circuit, in microseconds.
		The distinguished value 0x00FFFFFF means not valid."
	::= { cktEntry 186 }

cktAccumCDV OBJECT-TYPE
	SYNTAX INTEGER
	ACCESS  read-only
	STATUS  mandatory
	DESCRIPTION
		"The accumulated cell delay variation for this circuit, in microseconds.
		The distinguished value 0x00FFFFFF means not valid."
	::= { cktEntry 187 }

cktAccumRCDV OBJECT-TYPE
	SYNTAX INTEGER
	ACCESS  read-only
	STATUS  mandatory
	DESCRIPTION
		"The accumulated reverse cell delay variation for this circuit, in microseconds.
		The distinguished value 0x00FFFFFF means not valid."
	::= { cktEntry 188 }

cktCLR OBJECT-TYPE
	SYNTAX INTEGER
	ACCESS  read-write
	STATUS  mandatory
	DESCRIPTION
		"The cell loss ratio requirement, expressed as a negative exponent of 10.
		 The default value 255 represents any cell loss ratio acceptable."
	::= { cktEntry 189 }

cktRCLR OBJECT-TYPE
	SYNTAX INTEGER
	ACCESS  read-write
	STATUS  mandatory
	DESCRIPTION
		"The reverse cell loss ratio requirement, expressed as a negative exponent
		 of 10.  The default value 255 represents any cell loss ratio
		 acceptable."
	::= { cktEntry 190 }

cktAtmLijId OBJECT-TYPE
	SYNTAX INTEGER
	ACCESS  read-only
	STATUS  mandatory
	DESCRIPTION
		"The Leaf Initiated Join ID of the PMP SVC rooted at this interface."
	::= { cktEntry 191 }

cktAtmLijType OBJECT-TYPE
	SYNTAX INTEGER {
		not-lij (1),		-- not a PMP SVC
		root-lij (2),		-- network LIJ disallowed
		network-lij (3)		-- network LIJ allowed
        }
	ACCESS  read-only
	STATUS  mandatory
	DESCRIPTION
		"The Leaf Initiated Join type of the PMP SVC rooted at this interface."
	::= { cktEntry 192 }

cktRtLastDelay OBJECT-TYPE
        SYNTAX  INTEGER
        ACCESS  read-only
        STATUS  mandatory
        DESCRIPTION
                "The last round-trip delay (micro-seconds)."
        ::= { cktEntry 193 }

cktRtAccuMinDelay OBJECT-TYPE
        SYNTAX  INTEGER
        ACCESS  read-only
        STATUS  mandatory
        DESCRIPTION
                "The prev min round-trip delay (micro-seconds)."
        ::= { cktEntry 194 }

cktRtAccuMaxDelay OBJECT-TYPE
        SYNTAX  INTEGER
        ACCESS  read-only
        STATUS  mandatory
        DESCRIPTION
                "The prev max round-trip delay (micro-seconds)."
        ::= { cktEntry 195 }

cktRtAccuAvgDelay OBJECT-TYPE
        SYNTAX  INTEGER
        ACCESS  read-only
        STATUS  mandatory
        DESCRIPTION
                "The prev avg round-trip delay (micro-seconds)."
        ::= { cktEntry 196 }

cktQosIntPeriod OBJECT-TYPE
        SYNTAX  INTEGER
        ACCESS  read-write
        STATUS  mandatory
        DESCRIPTION
                "The number of periods for calculating qos params."
        ::= { cktEntry 197 }

cktAtmOutOAMClp0Cells OBJECT-TYPE
	SYNTAX	Counter
	ACCESS	read-only
	STATUS	mandatory
	DESCRIPTION
		"The number of OAM CLP0 cells transmitted on this circuit. For BIO1 card (on Garnet Platform), this count is not reported separately - see cktEntry 99. "
	::= { cktEntry 198 }

cktAtmOutOAMClp1Cells OBJECT-TYPE
	SYNTAX	Counter
	ACCESS	read-only
	STATUS	mandatory
	DESCRIPTION
		"The number of OAM CLP1 cells transmitted on this circuit. For BIO1 card (on Garnet Platform), this count is not reported separately - see cktEntry 100."
	::= { cktEntry 199 }

cktReqCTD OBJECT-TYPE
	SYNTAX	INTEGER
	ACCESS	read-write
	STATUS	mandatory
	DESCRIPTION
		"The requested cell/frame delay variation for this circuit, in microseconds.
		The range for PVC is 1 - 0x00FFFFFF. The default is 0x00FFFFFF, which
	        means not valid."
	::= { cktEntry 200 }

cktInOctetsPeak OBJECT-TYPE
	SYNTAX	Counter
	ACCESS	read-only
	STATUS	mandatory
	DESCRIPTION
		"The 5-minute peak value of the number of inbound octets (bytes)
		for the circuit - from Bulk Statistics."
	::= { cktEntry 201 }

cktOutOctetsPeak OBJECT-TYPE
	SYNTAX	Counter
	ACCESS	read-only
	STATUS	mandatory
	DESCRIPTION
		"The 5-minute peak value of the number of outbound octets
		(bytes) for the circuit - from Bulk Statistics."
	::= { cktEntry 202 }

cktInDEOctetsPeak OBJECT-TYPE
	SYNTAX	Counter
	ACCESS	read-only
	STATUS	mandatory
	DESCRIPTION
		"The 5-minute peak value of the number of inbound DE-marked
		octets (bytes) for the circuit - from Bulk Statistics."
	::= { cktEntry 203 }

cktOutDEOctetsPeak OBJECT-TYPE
	SYNTAX	Counter
	ACCESS	read-only
	STATUS	mandatory
	DESCRIPTION
		"The 5-minute peak value of the number of outbound DE-marked
		octets (bytes) for the circuit - from Bulk Statistics."
	::= { cktEntry 204 }

cktInODEOctetsPeak OBJECT-TYPE
	SYNTAX	Counter
	ACCESS	read-only
	STATUS	mandatory
	DESCRIPTION
		"The 5-minute peak value of the number of inbound ODE-marked
		octets (bytes) for the circuit - from Bulk Statistics."
	::= { cktEntry 205 }

cktOutODEOctetsPeak OBJECT-TYPE
	SYNTAX	Counter
	ACCESS	read-only
	STATUS	mandatory
	DESCRIPTION
		"The 5-minute peak value of the number of outbound ODE-marked
		octets (bytes) for the circuit - from Bulk Statistics."
	::= { cktEntry 206 }

cktAdminCostThreshold OBJECT-TYPE
	SYNTAX	INTEGER
	ACCESS	read-write
	STATUS	mandatory
	DESCRIPTION "Maximum allowable admin cost for the circuit.
		If no paths are available with cost less than or
		equal to this value, the circuit is not established.
		DEFVAL is 0 which means invalid, valid values range
		from 1 to 0xFFFFFFFF."
	::= { cktEntry 207 }

cktAtmSvcServiceCategory OBJECT-TYPE
	SYNTAX INTEGER {
		cbr  (1),
		vbr1 (2),
		vbr2 (3),
		ubr-abr (4),
		unspecified (5)
	}
	ACCESS	read-only
	STATUS	mandatory
	DESCRIPTION
		"The derived service category in the forward direction for this ATM SVC."
	::= { cktEntry 208 }

cktAtmSvcRServiceCategory OBJECT-TYPE
	SYNTAX INTEGER {
		cbr  (1),
		vbr1 (2),
		vbr2 (3),
		ubr-abr (4),
		unspecified (5)
	}
	ACCESS	read-only
	STATUS	mandatory
	DESCRIPTION
		"The derived service category in the reverse direction for this ATM SVC."
	::= { cktEntry 209 }

cktInterworkingFrToAtmEFCI OBJECT-TYPE
	SYNTAX  INTEGER {
		fr-fecn (1),
		efci0 (2)
	}
	ACCESS  read-write
	STATUS  mandatory
	DESCRIPTION
		"EFCI mapping for Frame Relay To ATM Service Interworking."
	::= { cktEntry 210 }

cktDiagSARMon OBJECT-TYPE
	SYNTAX INTEGER {
		flowOnInbound  (1),
		flowOffInbound (2),
		flowOnOutbound (3),
		flowOffOutbound (4),
		flowOnInboundOutbound (5),
		flowOffInboundOutbound (6)
	}
	ACCESS  read-write
	STATUS  mandatory
	DESCRIPTION
		"Used to start or stop flow on the inbound/outbound ATMizer
		 without informing the PPC."
	::= { cktEntry 211 }

cktAdminCostReal OBJECT-TYPE
	SYNTAX INTEGER
	ACCESS read-only
	STATUS mandatory
	DESCRIPTION
		"Actual value of total administration cost of a circuit.
		Ranges from 0 to 0xFFFFFFFF."
	::= { cktEntry 212 }

cktAtmInClp0Cells OBJECT-TYPE
	SYNTAX  Counter
	ACCESS  read-only
	STATUS  mandatory
	DESCRIPTION
		"The Number of ATM CLP 0 cells received on a VC
		(VPC or VCC)."
	::= { cktEntry 213 }

cktAtmInClp1Cells OBJECT-TYPE
	SYNTAX  Counter
	ACCESS  read-only
	STATUS  mandatory
	DESCRIPTION
		"The Number of ATM CLP 1 cells received on a VC
		(VPC or VCC)."
	::= { cktEntry 214 }

cktATMAAL5CRC32Error OBJECT-TYPE
	SYNTAX  Counter
	ACCESS  read-only
	STATUS  mandatory
	DESCRIPTION
		"Number of received AAL5 packets with CRC32 errors."
	::= { cktEntry 215 }

cktATMAAL5CPIError OBJECT-TYPE
	SYNTAX	Counter
	ACCESS  read-only
	STATUS  mandatory
	DESCRIPTION
		"Number of received AAL5 packets with CPI errors
		The only valid value currently defined for the CPI
		field is all zeros"
	::= { cktEntry 216 }

cktATMAAL5LengthError OBJECT-TYPE
	SYNTAX  Counter
	ACCESS  read-only
	STATUS  mandatory
	DESCRIPTION
		"Number of received AAL5 packets which satisfied one of the following
		error conditions:
		1. number of received cells * 48 bytes - length value in trailer > 55 bytes
		2. number of received cells * 48 bytes - length value in trailer < 8 bytes"
	::= { cktEntry 217 }

cktATMAAL5ReassemblyTimerError OBJECT-TYPE
	SYNTAX  Counter
	ACCESS  read-only
	STATUS  mandatory
	DESCRIPTION
		"Number of expired reassembly timers"
	::= { cktEntry 218 }

cktATMAAL5MaxNrSegError OBJECT-TYPE
	SYNTAX  Counter
	ACCESS  read-only
	STATUS  mandatory
	DESCRIPTION
		"Number of received AAL5 packets which exceeds the maximum allowed length"
	::= { cktEntry 219 }

cktIWF1490to1483Error OBJECT-TYPE
        SYNTAX  Counter
        ACCESS  read-only
        STATUS  mandatory
        DESCRIPTION
                "Number of Frames received that failed the rfc1490 to rfc 1483 header
                 translation. This error counter indicates that frames being recevied
                 from the frame relay side of the connection have an incorrectly formatted
                 1490 header and cannot be translated. See cktIWF1490to1483LastBadHeader
                for the last received 1490 header"
        ::= { cktEntry 220 }

cktIWF1490to1483LastBadHeader OBJECT-TYPE
        SYNTAX  DisplayString
        ACCESS  read-only
        STATUS  mandatory
        DESCRIPTION
                "Ascii string of the first 8 bytes of the header from the last frame
                 discarded because the 1490 to 1483 header translation failed. The
                 string displays the hexidecimal values for the data bytes"
        ::= { cktEntry 221 }

cktIWF1483to1490Error OBJECT-TYPE
        SYNTAX  Counter
        ACCESS  read-only
        STATUS  mandatory
        DESCRIPTION
                "Number of Frames received that failed the rfc1483 to rfc 1490 header
                 translation. This error counter indicates that frames being recevied
                 from the atm side of the connection have an incorrectly formatted
                 1483 header and cannot be translated. See cktIWF1483to1490LastBadHeader
                for the last received 1490 header"
        ::= { cktEntry 222 }

cktIWF1483to1490LastBadHeader OBJECT-TYPE
        SYNTAX  DisplayString
        ACCESS  read-only
        STATUS  mandatory
        DESCRIPTION
                "Ascii string of the first 10 bytes of the header from the last frame
                 discarded because the 1483 to 1490 header translation failed. The
                 string displays the hexidecimal values for the data bytes"
        ::= { cktEntry 223 }


--
-- The cktLeafTable
--

cktLeafTable OBJECT-TYPE
	SYNTAX	SEQUENCE OF CktLeafEntry
	ACCESS	not-accessible
	STATUS	mandatory
	DESCRIPTION
		"A table containing information about leaves of multipoint circuits."
	::= { ckt 2 }

cktLeafEntry OBJECT-TYPE
 	SYNTAX	CktLeafEntry
 	ACCESS	not-accessible
 	STATUS	mandatory
 	DESCRIPTION
		"The objects relevant to a single leaf in a multipoint circuit."
	INDEX { cktLeafSrcIfIndex, cktLeafSrcDlci, cktLeafEndpointIndex }
	::= { cktLeafTable 1 }

CktLeafEntry ::=
	SEQUENCE {
		cktLeafSrcIfIndex
			Index,
		cktLeafSrcDlci
			INTEGER,
		cktLeafEndpointIndex
			INTEGER,
		cktLeafCreationTime
			TimeTicks,
		cktLeafEgressIfIndex
			Index,
		cktLeafEgressDlci
			INTEGER,
		cktLeafDestNodeId
			INTEGER,
		cktLeafDestIfIndex
			Index,
		cktLeafDestDlci
			INTEGER,
		cktLeafSvcCallingParty
			OCTET STRING,
		cktLeafSvcCalledParty
			OCTET STRING,
		cktLeafAdminStatus
			INTEGER,
		cktLeafVcState
			INTEGER,
		cktLeafOperStatus
			INTEGER,
		cktLeafDceState
			INTEGER,
		cktLeafDteStatus
			INTEGER,
		cktLeafDteState
			INTEGER,
		cktLeafVcPtr
			OCTET STRING,
		cktLeafHopCnt
			INTEGER,
		cktLeafPath
			OCTET STRING,
		cktLeafFailReason
			INTEGER,
		cktLeafFailNode
			INTEGER,
		cktLeafFailPort
			INTEGER,
		cktLeafHelloCounter
			INTEGER,
		cktLeafHelloAckCounter
			INTEGER,
		cktLeafAtmVPI
			INTEGER,
		cktLeafAtmVCI
			INTEGER,
		cktLeafType
			INTEGER,
		cktLeafAtmInCells
			Counter,
		cktLeafAtmOutCells
			Counter,
		cktLeafAtmInDiscardedClp0Cells
			Counter,
		cktLeafAtmInDiscardedClp1Cells
			Counter,
		cktLeafAtmInPassedClp0Cells
			Counter,
		cktLeafAtmInPassedClp1Cells
			Counter,
		cktLeafAtmInTaggedCells
			Counter,
		cktLeafAtmOutClp0Cells
			Counter,
		cktLeafAtmOutClp1Cells
			Counter
	}

cktLeafSrcIfIndex OBJECT-TYPE
	SYNTAX 	Index
	ACCESS	read-only
	STATUS	mandatory
	DESCRIPTION
		"The interface ID at this node's ingress port for the corresponding 
		 multipoint circuit."
	::= { cktLeafEntry 1 }	

cktLeafSrcDlci OBJECT-TYPE
	SYNTAX 	INTEGER
	ACCESS	read-only
	STATUS	mandatory
	DESCRIPTION
		"The DLCI, if a frame relay circuit, or concatenated VPI and VCI, if an
		 ATM circuit, at this node's ingress port for the corresponding 
		 multipoint circuit."
	::= { cktLeafEntry 2 }	

cktLeafEndpointIndex OBJECT-TYPE
	SYNTAX 	INTEGER
	ACCESS	read-only
	STATUS	mandatory
	DESCRIPTION
		"An identifier unique to this leaf for the corresponding multipoint
		 circuit."
	::= { cktLeafEntry 3 }	

cktLeafCreationTime OBJECT-TYPE
 	SYNTAX  TimeTicks
 	ACCESS  read-only
 	STATUS  mandatory
 	DESCRIPTION
		"The value of sysUpTime when this leaf was created for the corresponding
		 multipoint circuit."
	::= { cktLeafEntry 4 }

cktLeafEgressIfIndex OBJECT-TYPE
	SYNTAX 	Index
	ACCESS	read-only
	STATUS	mandatory
	DESCRIPTION
		"The interface ID at this node's egress port for this leaf's segment of
		 the corresponding multipoint circuit."
	::= { cktLeafEntry 5 }	

cktLeafEgressDlci OBJECT-TYPE
	SYNTAX 	INTEGER
	ACCESS	read-only
	STATUS	mandatory
	DESCRIPTION
		"The DLCI, if a frame relay circuit, or concatenated VPI and VCI, if an
		 ATM circuit, at this node's egress port for this leaf's segment of the
		 corresponding multipoint circuit."
	::= { cktLeafEntry 6 }	

cktLeafDestNodeId OBJECT-TYPE
	SYNTAX 	INTEGER
	ACCESS	read-write
	STATUS	mandatory
	DESCRIPTION
		"The node ID of the node where this leaf terminates."
	::= { cktLeafEntry 7 }	

cktLeafDestIfIndex OBJECT-TYPE
	SYNTAX 	Index
	ACCESS	read-write
	STATUS	mandatory
	DESCRIPTION
		"The interface ID at the egress port of the destination node for this leaf,
		 if this is a PVC."
	::= { cktLeafEntry 8 }	

cktLeafDestDlci OBJECT-TYPE
	SYNTAX 	INTEGER
	ACCESS	read-only
	STATUS	mandatory
	DESCRIPTION
		"The DLCI, if a frame relay circuit, or concatenated VPI and VCI, if an
		 ATM circuit, at this node's destination port for the corresponding 
		 multipoint circuit."
	::= { cktLeafEntry 9 }	

cktLeafSvcCallingParty OBJECT-TYPE
        SYNTAX  OCTET STRING
        ACCESS  read-only
        STATUS  mandatory
        DESCRIPTION
                "The calling party number for this leaf, if this is an SVC."
        ::= { cktLeafEntry 10 }

cktLeafSvcCalledParty OBJECT-TYPE
        SYNTAX  OCTET STRING
        ACCESS  read-only
        STATUS  mandatory
        DESCRIPTION
                "The called party number for this leaf, if this is an SVC."
        ::= { cktLeafEntry 11 }

cktLeafAdminStatus OBJECT-TYPE
        SYNTAX  INTEGER {
 		    -- invalid (0),
		    down (1),
		    up (2)
	}
        ACCESS  read-write
        STATUS  mandatory
        DESCRIPTION
                "The desired state for the leaf entry."
        ::= { cktLeafEntry 12 }

cktLeafVcState OBJECT-TYPE
 	SYNTAX  INTEGER {
 		    -- invalid (0),
		    inactive (1),
		    retry (2),
		    calling (3),
		    wcbdeact(4),
                    wcbdelete(5),
		    active (6),
                    svcall (7),
                    svclr (8),
                    backedup (9),
                    wcbbkdp (10),
                    wcbreact (11),
		    slowretry (12)
 		}
 	ACCESS  read-only
 	STATUS  mandatory
 	DESCRIPTION
		"The current state of the leaf PVC segment in the Cascade network."
	::= { cktLeafEntry 13 }

cktLeafOperStatus OBJECT-TYPE
 	SYNTAX  INTEGER {
		    -- invalid (0),
		    inactive (1),
		    active (2)
		}
 	ACCESS  read-only
 	STATUS  mandatory
 	DESCRIPTION
		"The current operational status of the entire leaf PVC."
  	::= { cktLeafEntry 14 }

cktLeafDceState OBJECT-TYPE
 	SYNTAX  INTEGER {
		    -- invalid (0),
		    inactive (1),
		    active (2)
		}
 	ACCESS  read-only
 	STATUS  mandatory
 	DESCRIPTION
		"The DCE state of the circuit."
  	::= { cktLeafEntry 15 }

cktLeafDteStatus OBJECT-TYPE
 	SYNTAX  INTEGER {
		    -- invalid (0),
		    inactive (1),
		    active (2)
		}
 	ACCESS  read-only
 	STATUS  mandatory
 	DESCRIPTION
		"The DTE status of the circuit."
  	::= { cktLeafEntry 16 }

cktLeafDteState OBJECT-TYPE
 	SYNTAX  INTEGER {
		    -- invalid (0),
		    inactive (1),
		    active (2)
		}
 	ACCESS  read-only
 	STATUS  mandatory
 	DESCRIPTION
		"The DTE state of the circuit."
  	::= { cktLeafEntry 17 }

cktLeafVcPtr OBJECT-TYPE
 	SYNTAX  OCTET STRING
 	ACCESS  read-only
 	STATUS  mandatory
 	DESCRIPTION
		"An 8-byte Octect string indicating the vc pointer."
  	::= { cktLeafEntry 18 }

cktLeafHopCnt OBJECT-TYPE
	SYNTAX	INTEGER
	ACCESS	read-only
	STATUS	mandatory
	DESCRIPTION
		"The count of hops along the circuit path. (Max is 16)"
	::= { cktLeafEntry 19 }

cktLeafPath OBJECT-TYPE
	SYNTAX	OCTET STRING
	ACCESS	read-only
	STATUS	mandatory
	DESCRIPTION
		"The circuit path consisting a sequence of outbound interface
		indexes at nodes along the established circuit. The format is
		interface:interface:interface......"
	::= { cktLeafEntry 20 }

cktLeafFailReason OBJECT-TYPE
 	SYNTAX  INTEGER {
		    -- none (0),
		    admindown (1),
		    novcbuff (2),
		    nobw (3),
		    noroute (4),
		    timeout (5),
		    nopdubuff (6),
		    nodest (7),
		    trkrnr (8),
		    trkdown (9),
		    balancereroute (10),
		    dead(11),
		    defpathreroute(12),
		    nidown(13),
		    otherpvcsegdown(14),
		    otherpvcsegrnr(15),
		    usingaltpathwarning(16),
                    iopdown(17),
                    numsgbuffer(18),
                    noport(19),
                    misconfig(20),
                    svcsetupfail(21),
                    srcbackedup(22),
                    srcunknown(23),
                    dstunknown(24),
                    bkpdlcicollision(25),
                    oldrevinpath(26),
		    smdsmgmttrunk(27),
		    nevercalled(28),
		    bothendptbackup(29),
		    pvcroutemgttrunk(30),
		    nomultipointparent(31),
		    pvcroutefail(32),
		    novpivci(33)
		}
 	ACCESS  read-only
 	STATUS  mandatory
 	DESCRIPTION
		"The reason for the PVC establishment failure."
	::= { cktLeafEntry 21 }

cktLeafFailNode OBJECT-TYPE
 	SYNTAX  INTEGER
 	ACCESS  read-only
 	STATUS  mandatory
 	DESCRIPTION
		"The node which causes the PVC failure."
	::= { cktLeafEntry 22 }

cktLeafFailPort OBJECT-TYPE
 	SYNTAX  INTEGER
 	ACCESS  read-only
 	STATUS  mandatory
 	DESCRIPTION
		"The port on the fail node which causes the PVC failure."
	::= { cktLeafEntry 23 }

cktLeafHelloCounter OBJECT-TYPE
	SYNTAX	INTEGER 
	ACCESS	read-only
	STATUS	mandatory
	DESCRIPTION
		"Number of PVC hello pdu frames received in the VC entry of the
		called side."
	::= { cktLeafEntry 24 }

cktLeafHelloAckCounter OBJECT-TYPE
	SYNTAX	INTEGER 
	ACCESS	read-only
	STATUS	mandatory
	DESCRIPTION
		"Number of PVC hello Ack pdu frames received in the VC entry of the
		calling side."
	::= { cktLeafEntry 25 }

cktLeafAtmVPI OBJECT-TYPE
	SYNTAX	INTEGER
	ACCESS	read-write
	STATUS	mandatory
	DESCRIPTION
		"VPI value in the ATM cell header"
	::= { cktLeafEntry 26 }

cktLeafAtmVCI OBJECT-TYPE
	SYNTAX	INTEGER
	ACCESS	read-write
	STATUS	mandatory
	DESCRIPTION
		"VCI value in the ATM cell header"
	::= { cktLeafEntry 27 }

cktLeafType OBJECT-TYPE
        SYNTAX  INTEGER  {
			pvc (1),
			svc (2)
		}
        ACCESS  read-only
        STATUS  mandatory 
        DESCRIPTION 
                "1 if a permanent virtual circuit; 2 if a switched virtual circuit."
        ::= { cktLeafEntry 28 } 

cktLeafAtmInCells OBJECT-TYPE
 	SYNTAX	Counter
 	ACCESS	read-only
 	STATUS	mandatory
 	DESCRIPTION "The Number of ATM cells received on a VCC."
	::= { cktLeafEntry 29 }

cktLeafAtmOutCells OBJECT-TYPE
 	SYNTAX	Counter
 	ACCESS  read-only
 	STATUS	mandatory
 	DESCRIPTION "The Number of ATM cells transmitted on a VCC."
	::= { cktLeafEntry 30 }

cktLeafAtmInDiscardedClp0Cells OBJECT-TYPE
 	SYNTAX	Counter
 	ACCESS  read-only
 	STATUS	mandatory
 	DESCRIPTION "The Number of ATM CLP0 cells received and discarded on a VCC."
	::= { cktLeafEntry 31 }

cktLeafAtmInDiscardedClp1Cells OBJECT-TYPE
 	SYNTAX	Counter
 	ACCESS  read-only
 	STATUS	mandatory
 	DESCRIPTION "The Number of ATM CLP1 cells received and discarded on a VCC."
	::= { cktLeafEntry 32 }

cktLeafAtmInPassedClp0Cells OBJECT-TYPE
 	SYNTAX	Counter
 	ACCESS	read-only
 	STATUS	mandatory
 	DESCRIPTION "The Number of ATM CLP 0 cells received and passed UPC on a VCC."
	::= { cktLeafEntry 33 }

cktLeafAtmInPassedClp1Cells OBJECT-TYPE
 	SYNTAX	Counter
 	ACCESS	read-only
 	STATUS	mandatory
 	DESCRIPTION "The Number of ATM CLP 1 cells received and passed UPC on a VCC."
	::= { cktLeafEntry 34 }

cktLeafAtmInTaggedCells OBJECT-TYPE
 	SYNTAX	Counter
 	ACCESS	read-only
 	STATUS	mandatory
 	DESCRIPTION "The Number of ATM cells received and tagged on a VCC."
	::= { cktLeafEntry 35 }

cktLeafAtmOutClp0Cells OBJECT-TYPE
 	SYNTAX	Counter
 	ACCESS  read-only
 	STATUS	mandatory
 	DESCRIPTION "The Number of ATM CLP 0 cells transmitted on a VCC."
	::= { cktLeafEntry 36 }

cktLeafAtmOutClp1Cells OBJECT-TYPE
 	SYNTAX	Counter
 	ACCESS  read-only
 	STATUS	mandatory
 	DESCRIPTION "The Number of ATM CLP 1 cells transmitted on a VCC."
	::= { cktLeafEntry 37 }


--  A Circuit Table to manage SMDS routes
--

cktSmdsRtTable	OBJECT-TYPE
		SYNTAX	SEQUENCE OF CktSmdsRtEntry
		ACCESS	not-accessible
		STATUS	mandatory
		DESCRIPTION
			"A table containing information about destination, VC, 
			hops and routes."
		::= { ckt 3 }

cktSmdsRtEntry OBJECT-TYPE
 	SYNTAX	CktSmdsRtEntry
 	ACCESS	not-accessible
 	STATUS	mandatory
 	DESCRIPTION
		"The information regarding routes from a node to all its
		 neighbors."
	INDEX { cktSmdsRemoteNode }
	::= { cktSmdsRtTable 1 }

CktSmdsRtEntry ::=
	SEQUENCE {
 		cktSmdsRemoteNode
			INTEGER,
		cktSmdsHopCnt
			INTEGER,
		cktSmdsRoute
			OCTET STRING,
		cktSmdsLocalPort
			INTEGER,
		cktSmdsRemotePort
			INTEGER,
		cktSmdsVcState
			INTEGER
	}

cktSmdsRemoteNode OBJECT-TYPE
 	SYNTAX  INTEGER
 	ACCESS  read-only
 	STATUS  mandatory
 	DESCRIPTION
		"The nodeId of the node to which a rought is sought."
  	::= { cktSmdsRtEntry 1 }

cktSmdsHopCnt 	OBJECT-TYPE
 	SYNTAX	INTEGER
 	ACCESS	read-only
 	STATUS	mandatory
 	DESCRIPTION
		"The number of hops to reach the desired destination node."
	::= { cktSmdsRtEntry 2 }

cktSmdsRoute OBJECT-TYPE
 	SYNTAX	OCTET STRING
 	ACCESS	read-only
 	STATUS	mandatory
 	DESCRIPTION
		"The out-going Interface Id of each of the nodes in the path."
	::= { cktSmdsRtEntry 3 }

cktSmdsLocalPort OBJECT-TYPE
 	SYNTAX	INTEGER
 	ACCESS	read-only
 	STATUS	mandatory
 	DESCRIPTION
		"The out-going local portId."
	::= { cktSmdsRtEntry 4 }

cktSmdsRemotePort OBJECT-TYPE
 	SYNTAX	INTEGER
 	ACCESS	read-only
 	STATUS	mandatory
 	DESCRIPTION
		"The remote portId of the destination nodeId."
	::= { cktSmdsRtEntry 5 }

cktSmdsVcState OBJECT-TYPE
 	SYNTAX	INTEGER
 	ACCESS	read-only
 	STATUS	mandatory
 	DESCRIPTION
		"The state of the circuit."
	::= { cktSmdsRtEntry 6 }



-- the DS1 Configuration Table

dsx1ConfigTable OBJECT-TYPE
	SYNTAX  SEQUENCE OF Dsx1ConfigEntry
	ACCESS  not-accessible
	STATUS  mandatory
	DESCRIPTION
		"The DS1 Configuration table."
	::= { ds1 1 }


dsx1ConfigEntry OBJECT-TYPE
	SYNTAX  Dsx1ConfigEntry
	ACCESS  not-accessible
	STATUS  mandatory
	DESCRIPTION
		"An entry in the DS1 Configuration table."
	INDEX   { dsx1SlotId, dsx1PortId }
	::= { dsx1ConfigTable 1 }

Dsx1ConfigEntry ::=
	SEQUENCE {
		dsx1SlotId	
			INTEGER,
		dsx1PortId		
			INTEGER,
		dsx1TimeElapsed
			INTEGER,
		dsx1ValidIntervals
			INTEGER,
		dsx1LineType
			INTEGER,
		dsx1LineCoding
			INTEGER,
		dsx1SendCode
			INTEGER,
		dsx1CircuitIdentifier
			DisplayString,
		dsx1LoopbackConfig
			INTEGER,
		dsx1LineStatus
			INTEGER,
		dsx1SignalMode
			INTEGER,
		dsx1TransmitClockSource
			INTEGER,
		dsx1Fdl
			INTEGER,
		dsx1FdlVersion
			INTEGER
	}

dsx1SlotId OBJECT-TYPE
	SYNTAX	INTEGER
	ACCESS	read-only
	STATUS	mandatory
	DESCRIPTION
		"The slot number of the corresponding DS1."
	::= { dsx1ConfigEntry 1 }


dsx1PortId OBJECT-TYPE
	SYNTAX	INTEGER
	ACCESS	read-only
	STATUS	mandatory
	DESCRIPTION
		"The port number of the corresponding DS1
		on the board."
	::= { dsx1ConfigEntry 2 }


dsx1TimeElapsed OBJECT-TYPE
	SYNTAX  INTEGER (0..899)
	ACCESS  read-only
	STATUS  mandatory
	DESCRIPTION
		"The number of seconds that have elapsed  since
		the  beginning of the current error-measurement
		period."
	::= { dsx1ConfigEntry 3 }


dsx1ValidIntervals OBJECT-TYPE
	SYNTAX  INTEGER (0..96)
	ACCESS  read-only
	STATUS  mandatory
	DESCRIPTION
		"The number of  previous  intervals  for  which
		valid data was collected.  The value will be 96
		unless the interface was brought on-line within
		the last 24 hours, in which case the value will
		be the number of complete 15  minute  intervals
		the since interface has been online."
	::= { dsx1ConfigEntry 4 }


dsx1LineType OBJECT-TYPE
	SYNTAX  INTEGER {
		other(1),
		dsx1ESF(2),
		dsx1D4(3),
		dsx1E1(4),
		dsx1E1-CRC(5),
		dsx1E1-MF(6),
		dsx1E1-CRC-MF(7)
	}
	ACCESS  read-only
	STATUS  mandatory
	DESCRIPTION
		"This variable indicates  the  variety  of  DS1
		Line  implementing  this  circuit.  The type of
		circuit affects the number of bits  per  second
		that  the circuit can reasonably carry, as well
		as the interpretation of the  usage  and  error
		statistics.  The values, in sequence, describe:

		TITLE:        SPECIFICATION:
		dsx1ESF       Extended SuperFrame DS1
		dsx1D4        AT&T D4 format DS1
		dsx1E1        CCITT Recommendation G.704
			      (Table 4a)
		dsx1E1-CRC    CCITT Recommendation G.704
			      (Table 4b)
		dsxE1-MF      G.704 (Table 4a) with TS16
			      multiframing enabled
		dsx1E1-CRC-MF G.704 (Table 4b) with TS16
			      multiframing enabled"

	::= { dsx1ConfigEntry 5 }


dsx1LineCoding OBJECT-TYPE
	SYNTAX  INTEGER {
		dsx1JBZS (1),
		dsx1B8ZS (2),
		dsx1HDB3 (3),
		dsx1ZBTSI (4),
		dsx1AMI (5),
		other(6)
	}
	ACCESS  read-only
	STATUS  mandatory
	DESCRIPTION
		"This variable describes the  variety  of  Zero
		Code  Suppression  used  on  the link, which in
		turn affects a number of its characteristics.

		dsx1JBZS refers the Jammed  Bit  Zero  Suppres-
		sion,  in  which  the  AT&T specification of at
		least one pulse every 8 bit periods is literal-
		ly  implemented  by forcing a pulse in bit 8 of
		each channel.  Thus, only seven bits per  chan-
		nel, or 1.344 Mbps, is available for data.

		dsx1B8ZS refers to the use of a specified  pat-
		tern  of  normal  bits  and  bipolar violations
		which are used to replace a sequence  of  eight
		zero bits.

		ANSI Clear Channels may use dsx1ZBTSI, or  Zero
		Byte Time Slot Interchange.
	
		E1 links, with or without CRC, use dsx1HDB3  or
		dsx1AMI.

		dsx1AMI refers to a mode wherein no  zero  code
		suppression  is  present  and the line encoding
		does not solve the problem directly.   In  this
		application, the higher layer must provide data
		which meets or exceeds the  pulse  density  re-
		quirements, such as inverting HDLC data."
	::= { dsx1ConfigEntry 6 }


dsx1SendCode OBJECT-TYPE
	SYNTAX  INTEGER {
		dsx1SendNoCode(1),
		dsx1SendLineCode(2),
		dsx1SendPayloadCode(3),
		dsx1SendResetCode(4),
		dsx1SendQRS(5),
		dsx1Send511Pattern(6),
		dsx1Send3in24Pattern(7),
		dsx1SendOtherTestPattern(8)
	}
	ACCESS  read-only
	STATUS  mandatory
	DESCRIPTION
		"This variable indicates what type of  code  is
		being sent across the DS1 interface by the dev-
		ice.  The values mean:

		dsx1SendNoCode
			sending looped or normal data

		dsx1SendLineCode
			sending a request for a line loopback

		dsx1SendPayloadCode
			sending a request for a payload loopback

		dsx1SendResetCode
			sending a loopback termination request

		dsx1SendQRS
			sending a Quasi-Random Signal  (QRS)  test
			pattern

		dsx1Send511Pattern
			sending a 511 bit fixed test pattern

		dsx1Send3in24Pattern
			sending a fixed test pattern of 3 bits set
			in 24

		dsx1SendOtherTestPattern
			sending a test pattern  other  than  those
			described by this object"
	::= { dsx1ConfigEntry 7 }


dsx1CircuitIdentifier OBJECT-TYPE
	SYNTAX  DisplayString (SIZE (0..255))
	ACCESS  read-only
	STATUS  mandatory
	DESCRIPTION
		"This  variable   contains   the   transmission
		vendor's circuit identifier, for the purpose of
		facilitating troubleshooting."
	::= { dsx1ConfigEntry 8 }


dsx1LoopbackConfig OBJECT-TYPE
	SYNTAX  INTEGER {
		dsx1NoLoop(1),
		dsx1PayloadLoop(2),
		dsx1LineLoop(3),
		dsx1OtherLoop(4)
	}
	ACCESS  read-only
	STATUS  mandatory
	DESCRIPTION
		"This variable represents the  loopback  confi-
		guration of the DS1 interface.  Agents support-
		ing read/write access should return badValue in
		response to a requested loopback state that the
		interface does not support.  The values mean:

		dsx1NoLoop
			Not in the loopback state.  A device  that
			is not capable of performing a loopback on
			the interface shall always return this  as
			it's value.

		dsx1PayloadLoop
			The received signal at this  interface  is
			looped  through  the device. Typically the
			received signal is  looped  back  for  re-
			transmission  after  it has passed through
			the device's framing function.

		dsx1LineLoop
			The received signal at this interface does
			not  go  through the device (minimum pene-
			tration) but is looped back out.

		dsx1OtherLoop
			Loopbacks that are not defined here."
	::= { dsx1ConfigEntry 9 }


dsx1LineStatus OBJECT-TYPE
	SYNTAX  INTEGER (1..8191)
	ACCESS  read-only
	STATUS  mandatory
	DESCRIPTION
		"This variable indicates the Line Status of the
		interface.   It contains loopback, failure, re-
		ceived 'alarm'  and transmitted 'alarm'  infor-
		mation.

		The dsx1LineStatus is a bit  map  represented  as  a  sum,
		therefore, it can represent multiple failures (alarms) and
		a LoopbackState simultaneously.

		dsx1NoAlarm should be set if and only if no other flag  is
		set.

		If the dsx1LoopbackState bit is set, the loopback  in  ef-
		fect can be determined from the dsx1LoopbackConfig object.

		The various bit positions are:
		1     dsx1NoAlarm           No Alarm Present
		2     dsx1RcvFarEndLOF      Far end LOF (a.k.a., Yellow Alarm)
		4     dsx1XmtFarEndLOF      Near end sending LOF Indication
		8     dsx1RcvAIS            Far end sending AIS
		16    dsx1XmtAIS            Near end sending AIS
		32    dsx1LossOfFrame       Near end LOF (a.k.a., Red Alarm)
		64    dsx1LossOfSignal      Near end Loss Of Signal
		128   dsx1LoopbackState     Near end is looped
		256   dsx1T16AIS            E1 TS16 AIS
		512   dsx1RcvFarEndLOMF     Far End Sending TS16 LOMF
		1024  dsx1XmtFarEndLOMF     Near End Sending TS16 LOMF
		2048  dsx1RcvTestCode       Near End detects a test code
		4096  dsx1OtherFailure      any line status not defined here"
	::= { dsx1ConfigEntry 10 }


dsx1SignalMode OBJECT-TYPE
	SYNTAX  INTEGER {
		none (1),
		robbedBit (2),
		bitOriented (3),
		messageOriented (4)
	}
	ACCESS  read-only
	STATUS  mandatory
	DESCRIPTION
		"'none' indicates that no bits are reserved for
		signaling on this channel.

		'robbedBit' indicates that T1 Robbed Bit  Sig-
		naling is in use.

		'bitOriented' indicates that E1 Channel  Asso-
		ciated Signaling is in use.

		'messageOriented' indicates that Common  Chan-
		nel Signaling is in use either on channel 16 of
		an E1 link or channel 24 of a T1."
	::= { dsx1ConfigEntry 11 }


dsx1TransmitClockSource OBJECT-TYPE
	SYNTAX  INTEGER {
		loopTiming (1),
		localTiming (2),
		throughTiming (3)
	}
	ACCESS  read-only
	STATUS  mandatory
	DESCRIPTION
		"The source of Tranmit Clock.

		'loopTiming' indicates that the recovered  re-
		ceive clock is used as the transmit clock.

		'localTiming' indicates  that  a  local  clock
		source is used.

		'throughTiming' indicates that  recovered  re-
		ceive  clock  from another interface is used as
		the transmit clock."
	::= { dsx1ConfigEntry 12 }


dsx1Fdl OBJECT-TYPE
	SYNTAX  INTEGER {
		other(1),
		dsx1Ansi-T1-403(2),
		dsx1Att-54016(4),
		dsx1Fdl-none(8)
	}
	ACCESS  read-only
	STATUS  mandatory
	DESCRIPTION
		"This bitmap describes the use of  the  facili-
		ties data link, and is the sum of the capabili-
		ties:

		'other' indicates that a protocol  other  than
		one following is used.

		'dsx1Ansi-T1-403' refers to the  FDL  exchange
		recommended by ANSI.

		'dsx1Att-54016' refers to ESF FDL exchanges.

		'dsx1Fdl-none' indicates that the device  does
		not use the FDL."
	::= { dsx1ConfigEntry 13 }


dsx1FdlVersion OBJECT-TYPE
	SYNTAX  INTEGER
	ACCESS  read-only
	STATUS  mandatory
	DESCRIPTION
		"The version of the Dallas FDL firmware"
	::= { dsx1ConfigEntry 14 }


-- the DS1 Current Table

-- The DS1 current table contains various statistics being
-- collected for the current 15 minute interval.

dsx1CurrentTable OBJECT-TYPE
	SYNTAX  SEQUENCE OF Dsx1CurrentEntry
	ACCESS  not-accessible
	STATUS  mandatory
	DESCRIPTION
		"The DS1 Current table."
	::= { ds1 2 }


dsx1CurrentEntry OBJECT-TYPE
	SYNTAX  Dsx1CurrentEntry
	ACCESS  not-accessible
	STATUS  mandatory
	DESCRIPTION
		"An entry in the DS1 Current table."
	INDEX   { dsx1CurrentSlotId, dsx1CurrentPortId }
	::= { dsx1CurrentTable 1 }

Dsx1CurrentEntry ::=
	SEQUENCE {
		dsx1CurrentSlotId
			INTEGER,
		dsx1CurrentPortId
			INTEGER,
		dsx1CurrentESs
			Gauge,
		dsx1CurrentSESs
			Gauge,
		dsx1CurrentSEFSs
			Gauge,
		dsx1CurrentUASs
			Gauge,
		dsx1CurrentCSSs
			Gauge,
		dsx1CurrentBESs
			Gauge
	}

dsx1CurrentSlotId OBJECT-TYPE
	SYNTAX	INTEGER
	ACCESS	read-only
	STATUS	mandatory
	DESCRIPTION
		"The slot number of the corresponding DS1."
	::= { dsx1CurrentEntry 1 }
	
dsx1CurrentPortId OBJECT-TYPE
	SYNTAX	INTEGER
	ACCESS	read-only
	STATUS	mandatory
	DESCRIPTION
		"The port number of the corresponding DS1
		on the board."
	::= { dsx1CurrentEntry 2 }

dsx1CurrentESs OBJECT-TYPE
	SYNTAX  Gauge
	ACCESS  read-only
	STATUS  mandatory
	DESCRIPTION
		"The number of Errored Seconds, encountered  by
		a DS1 interface in the current 15 minute inter-
		val."
	::= { dsx1CurrentEntry 3 }


dsx1CurrentSESs OBJECT-TYPE
	SYNTAX  Gauge
	ACCESS  read-only
	STATUS  mandatory
	DESCRIPTION
		"The number of Severely Errored Seconds encoun-
		tered  by  a  DS1  interface  in the current 15
		minute interval."
	::= { dsx1CurrentEntry 4 }


dsx1CurrentSEFSs OBJECT-TYPE
	SYNTAX  Gauge
	ACCESS  read-only
	STATUS  mandatory
	DESCRIPTION
		"The number of Severely Errored Framing Seconds
		encountered  by  a DS1 interface in the current
		15 minute interval."
	::= { dsx1CurrentEntry 5 }


dsx1CurrentUASs OBJECT-TYPE
	SYNTAX  Gauge
	ACCESS  read-only
	STATUS  mandatory
	DESCRIPTION
		"The number of Unavailable Seconds  encountered
		by a DS1 interface in the current 15 minute in-
		terval."
	::= { dsx1CurrentEntry 6 }


dsx1CurrentCSSs OBJECT-TYPE
	SYNTAX  Gauge
	ACCESS  read-only
	STATUS  mandatory
	DESCRIPTION
		"The number of Controlled Slip Seconds  encoun-
		tered  by  a  DS1  interface  in the current 15
		minute interval."
	::= { dsx1CurrentEntry 7 }


dsx1CurrentBESs OBJECT-TYPE
	SYNTAX Gauge
	ACCESS read-only
	STATUS mandatory
	DESCRIPTION
		"The number of Bursty  Errored  Seconds  (BESs)
		encountered  by  a DS1 interface in the current
		15 minute interval."
	::= {dsx1CurrentEntry 8 }


-- the DS1 Interval

-- The DS1 Interval Table contains various statistics
-- collected by each DS1 Interface over the previous 24 hours of
-- operation.  The past 24 hours are broken into 96 completed
-- 15 minute intervals.

dsx1IntervalTable OBJECT-TYPE
	SYNTAX  SEQUENCE OF Dsx1IntervalEntry
	ACCESS  not-accessible
	STATUS  mandatory
	DESCRIPTION
		"The DS1 Interval table."
	::= { ds1 3 }


dsx1IntervalEntry OBJECT-TYPE
	SYNTAX  Dsx1IntervalEntry
	ACCESS  not-accessible
	STATUS  mandatory
	DESCRIPTION
		"An entry in the DS1 Interval table."
	INDEX   { dsx1IntervalSlotId, dsx1IntervalPortId, dsx1IntervalNumber }
	::= { dsx1IntervalTable 1 }

Dsx1IntervalEntry ::=
	SEQUENCE {
		dsx1IntervalSlotId
			INTEGER,
		dsx1IntervalPortId
			INTEGER,
		dsx1IntervalNumber
			INTEGER,
		dsx1IntervalESs
			Gauge,
		dsx1IntervalSESs
			Gauge,
		dsx1IntervalSEFSs
			Gauge,
		dsx1IntervalUASs
			Gauge,
		dsx1IntervalCSSs
			Gauge,
		dsx1IntervalBESs
			Gauge
	}

dsx1IntervalSlotId OBJECT-TYPE
	SYNTAX	INTEGER
	ACCESS	read-only
	STATUS	mandatory
	DESCRIPTION
		"The slot number of the corresponding DS1."
	::= { dsx1IntervalEntry 1 }
	
dsx1IntervalPortId OBJECT-TYPE
	SYNTAX	INTEGER
	ACCESS	read-only
	STATUS	mandatory
	DESCRIPTION
		"The port number of the corresponding DS1
		on the board."
	::= { dsx1IntervalEntry 2 }

dsx1IntervalNumber OBJECT-TYPE
	SYNTAX  INTEGER (1..96)
	ACCESS  read-only
	STATUS  mandatory
	DESCRIPTION
		"A number between 1 and 96, where 1 is the most
		recently completed 15 minute interval and 96 is
		the least recently completed 15 minutes  inter-
		val   (assuming   that  all  96  intervals  are
		valid)."
	::= { dsx1IntervalEntry 3 }


dsx1IntervalESs OBJECT-TYPE
	SYNTAX  Gauge
	ACCESS  read-only
	STATUS  mandatory
	DESCRIPTION
		"The number of Errored Seconds encountered by a
		DS1  interface in one of the previous 96, indi-
		vidual 15 minute, intervals."
	::= { dsx1IntervalEntry 4 }


dsx1IntervalSESs OBJECT-TYPE
	SYNTAX  Gauge
	ACCESS  read-only
	STATUS  mandatory
	DESCRIPTION
		"The number of Severely Errored Seconds encoun-
		tered by a DS1 interface in one of the previous
		96, individual 15 minute, intervals."
	::= { dsx1IntervalEntry 5 }


dsx1IntervalSEFSs OBJECT-TYPE
	SYNTAX  Gauge
	ACCESS  read-only
	STATUS  mandatory
	DESCRIPTION
		"The number of Severely Errored Framing Seconds
		encountered  by  a  DS1 interface in one of the
		previous 96, individual 15 minute, intervals."
	::= { dsx1IntervalEntry 6 }


dsx1IntervalUASs OBJECT-TYPE
	SYNTAX  Gauge
	ACCESS  read-only
	STATUS  mandatory
	DESCRIPTION
		"The number of Unavailable Seconds  encountered
		by  a  DS1 interface in one of the previous 96,
		individual 15 minute, intervals."
	::= { dsx1IntervalEntry 7 }


dsx1IntervalCSSs OBJECT-TYPE
	SYNTAX  Gauge
	ACCESS  read-only
	STATUS  mandatory
	DESCRIPTION
		"The number of Controlled Slip Seconds  encoun-
		tered by a DS1 interface in one of the previous
		96, individual 15 minute, intervals."
	::= { dsx1IntervalEntry 8 }


dsx1IntervalBESs OBJECT-TYPE
	SYNTAX Gauge
	ACCESS read-only
	STATUS mandatory
	DESCRIPTION
		"The number of Bursty  Errored  Seconds  (BESs)
		encountered  by  a  DS1 interface in one of the
		previous 96, individual 15 minute, intervals."
	::= {dsx1IntervalEntry 9 }


-- the DS1 Total

-- The DS1 Total Table contains the cumulative sum of the
-- various statistics for the 24 hour period preceding the
-- current interval.

dsx1TotalTable OBJECT-TYPE
	SYNTAX  SEQUENCE OF Dsx1TotalEntry
	ACCESS  not-accessible
	STATUS  mandatory
	DESCRIPTION
		"The DS1 Total table.  24 hour interval."
	::= { ds1 4 }


dsx1TotalEntry OBJECT-TYPE
	SYNTAX  Dsx1TotalEntry
	ACCESS  not-accessible
	STATUS  mandatory
	DESCRIPTION
		"An entry in the DS1 Total table."
	INDEX   { dsx1TotalSlotId, dsx1TotalPortId }
	::= { dsx1TotalTable 1 }

Dsx1TotalEntry ::=
	SEQUENCE {
		dsx1TotalSlotId
			INTEGER,
		dsx1TotalPortId
			INTEGER,
		dsx1TotalESs
			Gauge,
		dsx1TotalSESs
			Gauge,
		dsx1TotalSEFSs
			Gauge,
		dsx1TotalUASs
			Gauge,
		dsx1TotalCSSs
			Gauge,
		dsx1TotalBESs
			Gauge
	}

dsx1TotalSlotId OBJECT-TYPE
	SYNTAX	INTEGER
	ACCESS	read-only
	STATUS	mandatory
	DESCRIPTION
		"The slot number of the corresponding DS1."
	::= { dsx1TotalEntry 1 }
	
dsx1TotalPortId OBJECT-TYPE
	SYNTAX	INTEGER
	ACCESS	read-only
	STATUS	mandatory
	DESCRIPTION
		"The port number of the corresponding DS1
		on the board."
	::= { dsx1TotalEntry 2 }

dsx1TotalESs OBJECT-TYPE
	SYNTAX  Gauge
	ACCESS  read-only
	STATUS  mandatory
	DESCRIPTION
		"The number of Errored Seconds encountered by a
		DS1 interface in the previous 24 hour interval"
	::= { dsx1TotalEntry 3 }


dsx1TotalSESs OBJECT-TYPE
	SYNTAX  Gauge
	ACCESS  read-only
	STATUS  mandatory
	DESCRIPTION
		"The number of Severely Errored Seconds encoun-
		tered  by  a  DS1  interface in the previous 24
		hour interval."
	::= { dsx1TotalEntry 4 }


dsx1TotalSEFSs OBJECT-TYPE
	SYNTAX  Gauge
	ACCESS  read-only
	STATUS  mandatory
	DESCRIPTION
		"The number of Severely Errored Framing Seconds
		encountered  by a DS1 interface in the previous
		24 hour interval."
	::= { dsx1TotalEntry 5 }


dsx1TotalUASs OBJECT-TYPE
	SYNTAX  Gauge
	ACCESS  read-only
	STATUS  mandatory
	DESCRIPTION
		"The number of Unavailable Seconds  encountered
		by  a DS1 interface in the previous 24 hour in-
		terval."
	::= { dsx1TotalEntry 6 }


dsx1TotalCSSs OBJECT-TYPE
	SYNTAX  Gauge
	ACCESS  read-only
	STATUS  mandatory
	DESCRIPTION
		"The number of Controlled Slip Seconds  encoun-
		tered  by  a  DS1  interface in the previous 24
		hour interval."
	::= { dsx1TotalEntry 7 }


dsx1TotalBESs OBJECT-TYPE
	SYNTAX Gauge
	ACCESS read-only
	STATUS mandatory
	DESCRIPTION
		"The number of Bursty  Errored  Seconds  (BESs)
		encountered  by a DS1 interface in the previous
		24 hour interval."
	::= { dsx1TotalEntry 8 }


--
--	SMDS address : An SMDS address can be a local individual address
--      assigned to a DXI/SNI, a local group address defined in the STDX,
--	an individual address which is not assigned to any DXI/SNI in this    
--	STDX but is a member of an individual address screen, or can be 
--	a group address which is not defined in the STDX but is a member  
--      of a group address screen.
--

smdsaddrTable OBJECT-TYPE
	SYNTAX	SEQUENCE OF SmdsaddrEntry
	ACCESS	not-accessible
	STATUS	mandatory
	DESCRIPTION
		"A list of smds adress entries."
	::= { smdsaddr 1 }

smdsaddrEntry OBJECT-TYPE
	SYNTAX	SmdsaddrEntry
	ACCESS	not-accessible
	STATUS	mandatory
	DESCRIPTION
		"An smds address and its associated information."
	INDEX	{ smdsaddrAddr }
	::= { smdsaddrTable 1 }

SmdsaddrEntry ::= 
	SEQUENCE {
		smdsaddrAddr	
			OCTET STRING,
		smdsaddrType	
			INTEGER,
		smdsaddrId
			INTEGER,
		smdsaddrIf
			INTEGER,
		smdsaddrParentGrpMap
			OCTET STRING,
		smdsaddrParentScrnMap
			OCTET STRING,
		smdsaddrMemberAddrMap
			OCTET STRING,
		smdsaddrAdminStatus
			INTEGER,
		smdsaddrSlot
			INTEGER,
		smdsaddrSsiIfNum
			INTEGER
	}

smdsaddrAddr OBJECT-TYPE
	SYNTAX	OCTET STRING
	ACCESS	read-write
	STATUS	mandatory
	DESCRIPTION
		"SMDS address. The 4 most significant bits are the address
                 type : 1100 for an individual address, 1110 for a group
                 address. The following 4 bits are 0001. The following 5 bytes
                 are the 10 digits number in BCD format. The following 16 bits
		 are padded with 1's"
	::= { smdsaddrEntry 1 }

smdsaddrType OBJECT-TYPE
	SYNTAX	INTEGER {
        	local-individual-address(1),
		local-group-address(2),
		non-local-individual-address(3),
		non-local-group-address(4)
		}
	ACCESS	read-write
	STATUS	mandatory
	DESCRIPTION
		"SMDS address internal type."
	::= { smdsaddrEntry 2 }

smdsaddrId OBJECT-TYPE
	SYNTAX	INTEGER
	ACCESS	read-write
	STATUS	mandatory
	DESCRIPTION
		"smds address internal ID.
                 Range from 1 to 192 for local individual addresses.
		 Range from 193 to 704 for Alien individual addresses.
		 Range from 1 to 64 for local group addresses.
		 Range from 65 to 576 for alien group addresses."
	::= { smdsaddrEntry 3 }

smdsaddrIf OBJECT-TYPE
	SYNTAX	INTEGER
	ACCESS	read-write
	STATUS	mandatory
	DESCRIPTION
		"The interface to which this address is assigned."
	::= { smdsaddrEntry 4 }

smdsaddrParentGrpMap OBJECT-TYPE
 	SYNTAX  OCTET STRING
 	ACCESS  read-only
 	STATUS  mandatory
 	DESCRIPTION
		"The parent group bit map. The bit position of each bit
                 in this bit map represent a parent group address ID. The most
                 significant bit is corresponding to group address ID 1. This 
                 MIB object applies to a local individual address only." 
	::= { smdsaddrEntry 5 }

smdsaddrParentScrnMap OBJECT-TYPE
	SYNTAX	OCTET STRING
	ACCESS	read-only
	STATUS	mandatory
	DESCRIPTION
		"This MIB object not applicable to switch software versions
		 03.99.00 and above.
		 The parent screen bit map. The bit position of each bit
                 in this bit map represent a parent screen ID. The most
                 significant bit is corresponding to screen ID 1." 
	::= { smdsaddrEntry 6 }


smdsaddrMemberAddrMap OBJECT-TYPE
	SYNTAX	OCTET STRING
	ACCESS	read-write
	STATUS	mandatory
	DESCRIPTION
		"The member individual address bit map. For set request, 
                 the first byte is the operation : 1 for deleting, 2 for
                 adding. The following bytes are the bit
                 map. The bit position of each bit in this bit map represent
                 a member local individual address ID. The most significant
                 bit is corresponding to local individual address ID 1. For
                 get response, The whole string is the bit map."
	::= { smdsaddrEntry 7 }

smdsaddrAdminStatus OBJECT-TYPE
	SYNTAX	INTEGER {
		-- invalid(0),
		down(1),
		up(2)
                }	
	ACCESS	read-write
	STATUS	mandatory
	DESCRIPTION
		"administration status"
	::= { smdsaddrEntry 8 }

smdsaddrSlot OBJECT-TYPE
	SYNTAX	INTEGER
	ACCESS	read-write
	STATUS	mandatory
	DESCRIPTION
		"The Slot in which this address is assigned."
	::= { smdsaddrEntry 9 }

smdsaddrSsiIfNum OBJECT-TYPE
	SYNTAX	INTEGER
	ACCESS	read-write
	STATUS	mandatory
	DESCRIPTION
		"The SSI to which this address is associated."
	::= { smdsaddrEntry 10 }

--
--	ISDN Addr Group
--
-- 	The ISDN addr group is comprised of two tables: 
--	1) indexed based on interface id, this table contains the lport E.164 address
--	   and the lport type - b-channel or sw56
--	2) indexed based on interface id, this table contains valid caller ids
--
isdnAddrTable OBJECT-TYPE
	SYNTAX	SEQUENCE OF IsdnAddrEntry
	ACCESS	not-accessible
	STATUS	mandatory
	DESCRIPTION
		"A list of E.164 address entries."
	::= { isdnaddr 1 }

isdnAddrEntry OBJECT-TYPE
	SYNTAX	IsdnAddrEntry
	ACCESS	not-accessible
	STATUS	mandatory
	DESCRIPTION
		"Information about a single local E.164 address in the table.
		Setting this varible to 0 removes the entry."
	INDEX	{ isdnAddrIf }
	::= { isdnAddrTable 1 }

IsdnAddrEntry ::= 
	SEQUENCE {
		isdnAddrIf	
			INTEGER,	
		isdnAddr	
			OCTET STRING,	
	 	isdnChanType	
			INTEGER	
		}

isdnAddrIf OBJECT-TYPE
        SYNTAX  INTEGER 
        ACCESS  read-write
        STATUS  mandatory
        DESCRIPTION
                "The interface id of the logical port in question"
        ::= { isdnAddrEntry 1 }

isdnAddr OBJECT-TYPE
        SYNTAX  OCTET STRING
        ACCESS  read-write
        STATUS  mandatory
        DESCRIPTION
                "ISDN address. The actual E164 number. For example,
		 ISDN address 15086922600 is stored as string 15086922600.
		 Setting this value to a null string removes this entry."
        ::= { isdnAddrEntry 2 }


isdnChanType OBJECT-TYPE
        SYNTAX  INTEGER
        ACCESS  read-write
        STATUS  mandatory
        DESCRIPTION
		" type of logical port 0 => isdn b-channel, 
		  1 => sw56 "
	::= { isdnAddrEntry 3}

isdnCallerIDTable OBJECT-TYPE
	SYNTAX	SEQUENCE OF IsdnCallerIDEntry
	ACCESS	not-accessible
	STATUS	mandatory
	DESCRIPTION
		"A list of valid caller ids "
	::= { isdnaddr 2 }

isdnCallerIDEntry OBJECT-TYPE
	SYNTAX	IsdnCallerIDEntry
	ACCESS	not-accessible
	STATUS	mandatory
	DESCRIPTION
		"Information about a single valid caller id."
	INDEX	{ isdnCallerIDIf, isdnCallerIDAddr }
	::= { isdnCallerIDTable 1 }

IsdnCallerIDEntry ::= 
	SEQUENCE {
		isdnCallerIDIf	
			INTEGER,	
		isdnCallerIDAddr	
			OCTET STRING,	
		isdnCallerAdminStatus
			INTEGER
		}

isdnCallerIDIf OBJECT-TYPE
        SYNTAX  INTEGER 
        ACCESS  read-write
        STATUS  mandatory
        DESCRIPTION
                "The interface id of the logical port in question"
        ::= { isdnCallerIDEntry 1 }

isdnCallerIDAddr OBJECT-TYPE
        SYNTAX  OCTET STRING
        ACCESS  read-write
        STATUS  mandatory
        DESCRIPTION
                "ISDN address. The actual E164 number. For example,
		 ISDN address 15086922600 is stored as string 15086922600."
        ::= { isdnCallerIDEntry 2 }

isdnCallerAdminStatus OBJECT-TYPE
	SYNTAX	INTEGER {
		-- remove (0),
		add (1)
		} 
	ACCESS	read-write
	STATUS	mandatory
	DESCRIPTION
		"administration status"
	::= { isdnCallerIDEntry 3 }


--  The Service Name Binding Group
--
--  The variables that are relevant to a Service Name Binding Table
--

namebindingTable OBJECT-TYPE
	SYNTAX SEQUENCE OF NamebindingEntry
	ACCESS not-accessible
	STATUS mandatory
	DESCRIPTION
		"A table of name bindings to a set of logical ports."
	::= { namebinding 1 }

namebindingEntry OBJECT-TYPE
	SYNTAX NamebindingEntry
	ACCESS not-accessible
	STATUS mandatory
	DESCRIPTION
		"The name binding entry contains objects relative to a
		name binding."
	INDEX { nameType, nameName, namePrimary }
	::= { namebindingTable 1 }

NamebindingEntry ::=
	SEQUENCE {
		nameType
		INTEGER,
		nameName
		OCTET STRING,
		namePrimary
		INTEGER,
		nameIfIndex
		INTEGER,
		nameNodeId
		INTEGER,
		nameStatus
		INTEGER
	}

nameType OBJECT-TYPE
	SYNTAX INTEGER {
		uninniladdr(1), -- this is a logical address for frame relay
		e164(2),	-- this is an E.164 address
		nsap(3),	-- this is an NSAP address
		sni(4)		-- this is an SNI SMDS address
	}
	ACCESS read-write
	STATUS mandatory
	DESCRIPTION
		"The name type."
	::= { namebindingEntry 1 }

nameName OBJECT-TYPE
	SYNTAX OCTET STRING
	ACCESS read-write
	STATUS mandatory
	DESCRIPTION
		"A name of the type indicated by nameType."
	::= { namebindingEntry 2 }

namePrimary OBJECT-TYPE
	SYNTAX INTEGER {
		primary(1),	-- a primary backup
		backup(2)	-- a backup binding
	}
	ACCESS read-write
	STATUS mandatory
	DESCRIPTION
		"The current binding type for this entry."
	::= { namebindingEntry 3 }

nameIfIndex OBJECT-TYPE
	SYNTAX INTEGER
	ACCESS read-write
	STATUS mandatory
	DESCRIPTION
		"The interface number of the logical port for this binding."
	::= { namebindingEntry 4 }

nameNodeId OBJECT-TYPE
	SYNTAX INTEGER
	ACCESS read-only
	STATUS mandatory
	DESCRIPTION
		"The identifier number of the node for this binding."
	::= { namebindingEntry 5 }

nameStatus OBJECT-TYPE
	SYNTAX INTEGER {
		active(1),	-- binding is active
		invalid(2)	-- binding is invalid and is deleted
	}
	ACCESS read-write
	STATUS mandatory
	DESCRIPTION
		"The status of the binding."
	::= { namebindingEntry 6 }


--  The SVC Address Group
--
--  The tables that are relevant to managing SVC addresses and prefixes
--  in a Cascade network. 
--

--
--  SVC Node Prefix Table
--

svcNodePrefixTable OBJECT-TYPE
	SYNTAX SEQUENCE OF SvcNodePrefixEntry
	ACCESS not-accessible
	STATUS mandatory
	DESCRIPTION
		"A table of prefixes associated with this node."
	::= { svcaddress 1 }

svcNodePrefixEntry OBJECT-TYPE
	SYNTAX SvcNodePrefixEntry
	ACCESS not-accessible
	STATUS mandatory
	DESCRIPTION
		"The node prefix entry contains objects relevant to SVC prefixes
 	 	 associated with the node."
	INDEX { svcNodePrefixPrefix }
	::= { svcNodePrefixTable 1 }

SvcNodePrefixEntry ::=
	SEQUENCE {
		svcNodePrefixPrefix
			OCTET STRING,
		svcNodePrefixNumBits
			INTEGER,
		svcNodePrefixNmbPlan
			INTEGER,
		svcNodePrefixAdminStatus
			INTEGER
	}
	
svcNodePrefixPrefix OBJECT-TYPE
	SYNTAX OCTET STRING (SIZE(1..20))
	ACCESS read-only
	STATUS mandatory
	DESCRIPTION
		"A prefix associated with this node.  E.164 prefixes are coded as 
		 1-15 ASCII octets with no leading padding required.  ATM endsystem
		 prefixes are coded as 1-20 binary octets.  Unused bits in the last 
		 octet must be set to 0."
	::= { svcNodePrefixEntry 1 }

svcNodePrefixNumBits OBJECT-TYPE
	SYNTAX INTEGER (1..160)
	ACCESS read-write
	STATUS mandatory
	DESCRIPTION
		"The number of valid bits associated with this entry's prefix object.
		 By default, this value will be 8 times the prefix object's octet 
		 string length."
	::= { svcNodePrefixEntry 2 }

svcNodePrefixNmbPlan OBJECT-TYPE
	SYNTAX INTEGER {
		e164 (1),
		atm-endsystem (2),
		unknown (4)
	}
	ACCESS read-write
	STATUS mandatory
	DESCRIPTION
		"The numbering plan corresponding to this entry's prefix object."
	::= { svcNodePrefixEntry 3 }

svcNodePrefixAdminStatus OBJECT-TYPE
	SYNTAX INTEGER {
		configured (1), 	-- this entry has been configured by NMS
		invalid (2)		-- this entry shall be deleted
	}
	ACCESS read-write
	STATUS mandatory
	DESCRIPTION
		"The status of this entry."
	::= { svcNodePrefixEntry 4 }


--
--  SVC Prefix Table
--

svcPrefixTable OBJECT-TYPE
	SYNTAX SEQUENCE OF SvcPrefixEntry
	ACCESS not-accessible
	STATUS mandatory
	DESCRIPTION
		"A table of SVC address prefixes associated with ports on this node."
	::= { svcaddress 2 }

svcPrefixEntry OBJECT-TYPE
	SYNTAX SvcPrefixEntry
	ACCESS not-accessible
	STATUS mandatory
	DESCRIPTION
		"The prefix entry contains objects relevant to SVC prefixes 
		 associated with this port."
	INDEX { svcPrefixIfIndex, svcPrefixPrefix }
	::= { svcPrefixTable 1 }

SvcPrefixEntry ::=
	SEQUENCE {
		svcPrefixIfIndex
			Index,
		svcPrefixPrefix
			OCTET STRING,
		svcPrefixNumBits
			INTEGER,
		svcPrefixNmbPlan
			INTEGER,
		svcPrefixAdminCost
			INTEGER,
		svcPrefixLocalGatewayAddress
			OCTET STRING,
		svcPrefixLocalGatewayNmbPlan
			INTEGER,
		svcPrefixRemoteGatewayAddress
			OCTET STRING,
		svcPrefixRemoteGatewayNmbPlan
			INTEGER,
		svcPrefixAdminStatus
			INTEGER
	}
	
svcPrefixIfIndex OBJECT-TYPE
	SYNTAX Index
	ACCESS read-only
	STATUS mandatory
	DESCRIPTION
		"The interface value of the corresponding MIB-II ifEntry."
	::= { svcPrefixEntry 1 }

svcPrefixPrefix OBJECT-TYPE
	SYNTAX OCTET STRING (SIZE(1..20))
	ACCESS read-only
	STATUS mandatory
	DESCRIPTION
		"A prefix associated with this port.  E.164 prefixes are coded as 
		 1-15 ASCII octets with no leading padding required.  ATM endsystem
		 prefixes are coded as 1-20 binary octets.  Unused bits in the last 
		 octet must be set to 0.

		 For ATM DCE ports, only, atm-endsystem prefixes with length 104 bits 
		 (13 octets) and all E.164 prefixes are eligible for ILMI address 
		 registration."
	::= { svcPrefixEntry 2 }

svcPrefixNumBits OBJECT-TYPE
	SYNTAX INTEGER (1..160)
	ACCESS read-write
	STATUS mandatory
	DESCRIPTION
		"The number of valid bits associated with this entry's prefix object.
		 By default, this value will be 8 times the prefix object's octet 
		 string length."
	::= { svcPrefixEntry 3 }

svcPrefixNmbPlan OBJECT-TYPE
	SYNTAX INTEGER {
		e164 (1),
		atm-endsystem (2),
		unknown (4)
	}
	ACCESS read-write
	STATUS mandatory
	DESCRIPTION
		"The numbering plan corresponding to this entry's prefix object."
	::= { svcPrefixEntry 4 }

svcPrefixAdminCost OBJECT-TYPE
	SYNTAX INTEGER (0..65535)
	ACCESS read-write
	STATUS mandatory
	DESCRIPTION
		"This object is only relevant for ports connecting this network to 
		 another network and is used to represent the administrative cost of 
		 reaching destinations containing this entry's prefix value."
	::= { svcPrefixEntry 5 }

svcPrefixLocalGatewayAddress OBJECT-TYPE
	SYNTAX OCTET STRING (SIZE(0..20))
	ACCESS read-write
	STATUS mandatory
	DESCRIPTION
		"This object is only relevant for ports connecting this network to 
		 another network and is used to replace the calling party number
		 when egress address translation is configured to the appropriate mode.
		 E.164 addresses are coded as 1-15 ASCII octets  Atm-endsystem addresses
		 are coded as 20 octet binary addresses."
	::= { svcPrefixEntry 6 }

svcPrefixLocalGatewayNmbPlan OBJECT-TYPE
	SYNTAX INTEGER  {
		e164 (1),
		atm-endsystem (2),
		unknown (4)
	}
	ACCESS read-write
	STATUS mandatory
	DESCRIPTION
		"The numbering plan corresponding to this entry's local gateway address
		 object."
	::= { svcPrefixEntry 7 }

svcPrefixRemoteGatewayAddress OBJECT-TYPE
	SYNTAX OCTET STRING (SIZE(1..20))
	ACCESS read-write
	STATUS mandatory
	DESCRIPTION
		"This object is only relevant for ports connecting this network to 
		 another network and is used to replace the calling party number
		 when egress address translation is configured to the appropriate mode.
		 E.164 addresses are coded as 1-15 ASCII octets  Atm-endsystem addresses
		 are coded as 20 octet binary addresses."
	::= { svcPrefixEntry 8 }

svcPrefixRemoteGatewayNmbPlan OBJECT-TYPE
	SYNTAX INTEGER  {
		e164 (1),
		atm-endsystem (2),
		unknown (4)
	}
	ACCESS read-write
	STATUS mandatory
	DESCRIPTION
		"The numbering plan corresponding to this entry's remote gateway address
		 object."
	::= { svcPrefixEntry 9 }

svcPrefixAdminStatus OBJECT-TYPE
	SYNTAX INTEGER {
		configured (1), 	-- this entry has been configured by NMS
		invalid (2),		-- this entry shall be deleted
		dynamic (3)		-- this entry created via peer device (ATM UNI DTE, only)
	}
	ACCESS read-write
	STATUS mandatory
	DESCRIPTION
		"The status of this entry."
	::= { svcPrefixEntry 10 }


--
--   SVC Addr Table
--

svcAddrTable OBJECT-TYPE
	SYNTAX SEQUENCE OF SvcAddrEntry
	ACCESS not-accessible
	STATUS mandatory
	DESCRIPTION
		"A table of SVC addresses associated with with ports on this node."
	::= { svcaddress 3 }

svcAddrEntry OBJECT-TYPE
	SYNTAX SvcAddrEntry
	ACCESS not-accessible
	STATUS mandatory
	DESCRIPTION
		"The  address entry contains objects relevant to SVC addresses
		 associated with this port."
	INDEX { svcAddrIfIndex, svcAddrAddress }
	::= { svcAddrTable 1 }

SvcAddrEntry ::=
	SEQUENCE {
		svcAddrIfIndex
			Index,
		svcAddrAddress
			OCTET STRING,
		svcAddrNmbPlan
			INTEGER,
		svcAddrAdminStatus
			INTEGER
	}
	
svcAddrIfIndex OBJECT-TYPE
	SYNTAX Index
	ACCESS read-only
	STATUS mandatory
	DESCRIPTION
		"The interface value of the corresponding MIB-II ifEntry."
	::= { svcAddrEntry 1 }

svcAddrAddress OBJECT-TYPE
	SYNTAX OCTET STRING (SIZE(1..20))
	ACCESS read-only
	STATUS mandatory
	DESCRIPTION
		"An address associated with this port.  E.164 addresses are coded as 
		 1-15 ASCII octets.  ATM-Endsystem addresses are coded as 20 binary
		 octets."
	::= { svcAddrEntry 2 }

svcAddrNmbPlan OBJECT-TYPE
	SYNTAX INTEGER {
		e164 (1),
		atm-endsystem (2),
		unknown (4)
	}
	ACCESS read-write
	STATUS mandatory
	DESCRIPTION
		"The numbering plan corresponding to this entry's address object."
	::= { svcAddrEntry 3 }

svcAddrAdminStatus OBJECT-TYPE
	SYNTAX INTEGER {
		configured (1), 	-- this entry has been configured by NMS
		invalid (2),		-- this entry shall be deleted
		dynamic (3)		-- this entry created by peer device (ATM UNI DCE, only)
	}
	ACCESS read-write
	STATUS mandatory
	DESCRIPTION
		"The status of this entry."
	::= { svcAddrEntry 4 }


--
--   SVC ATM User Part Table
--

svcAtmUserPartTable OBJECT-TYPE
	SYNTAX SEQUENCE OF SvcAtmUserPartEntry
	ACCESS not-accessible
	STATUS mandatory
	DESCRIPTION
		"A table of partial SVC addresses associated with ports on this node,
 		 relevant only to ATM DTE ports for use in ILMI address registration."
	::= { svcaddress 4 }

svcAtmUserPartEntry OBJECT-TYPE
	SYNTAX SvcAtmUserPartEntry
	ACCESS not-accessible
	STATUS mandatory
	DESCRIPTION
		"The user part entry contains objects relevant to partial SVC addresses
 		 associated with ATM DTE ports on this node."
	INDEX { svcAtmUserPartIfIndex, svcAtmUserPartUserPart }
	::= { svcAtmUserPartTable 1 }

SvcAtmUserPartEntry ::=
	SEQUENCE {
		svcAtmUserPartIfIndex
			Index,
		svcAtmUserPartUserPart
			OCTET STRING,
		svcAtmUserPartAdminStatus
			INTEGER
	}
	
svcAtmUserPartIfIndex OBJECT-TYPE
	SYNTAX Index
	ACCESS read-only
	STATUS mandatory
	DESCRIPTION
		"The interface value of the corresponding MIB-II ifEntry."
	::= { svcAtmUserPartEntry 1 }

svcAtmUserPartUserPart OBJECT-TYPE
	SYNTAX OCTET STRING (SIZE(7))
	ACCESS read-only
	STATUS mandatory
	DESCRIPTION
		"A partial ATM endsystem address associated with this ATM DTE port.
		 It will be combined with ATM endsystem prefixes received from the 
		 peer DCE to form a full ATM endsystem address.  This object is coded 
		 as 7 binary octets." 
	::= { svcAtmUserPartEntry 2 }

svcAtmUserPartAdminStatus OBJECT-TYPE
	SYNTAX INTEGER {
		configured (1), 	-- this entry has been configured by NMS
		invalid (2)		-- this entry shall be deleted
	}
	ACCESS read-write
	STATUS mandatory
	DESCRIPTION
		"The status of this entry."
	::= { svcAtmUserPartEntry 3 }


--  The SVC Management Group
--
--  The tables that are relevant to managing ATM SVC's in a Cascade network.
--

--
-- 	SVC Configuration Table
--

svcConfigTable OBJECT-TYPE
	SYNTAX	SEQUENCE OF SvcConfigEntry
	ACCESS	not-accessible
	STATUS	mandatory
	DESCRIPTION
		"A table of SVC configuration paramaters associated with logical ports.
 		 The number of entries is given by the value of ifNumber in MIB-II."
	::= { svcmgt 1 }

svcConfigEntry OBJECT-TYPE
	SYNTAX	SvcConfigEntry
	ACCESS	not-accessible
	STATUS	mandatory
	DESCRIPTION
		"The  SVC configuration  entry contains objects relevant to SVC 
		 operation on a logical port."
	INDEX	{ svcConfigIfIndex }
	::= { svcConfigTable 1 }

SvcConfigEntry ::=
	SEQUENCE {
		svcConfigIfIndex
			Index,
		svcConfigInitiateIdentStatsUpload
			IpAddress,
		svcConfigCgPtyInsertionMode
			INTEGER,
		svcConfigCgPtyInsertionAddress
			OCTET STRING,
		svcConfigCgPtyInsertionNmbPlan
			INTEGER,
		svcConfigCgPtyScreenMode
			INTEGER,
		svcConfigEgressAddrXlateMode
			INTEGER,
		svcConfigIngressAddrXlateMode
			INTEGER,
		svcConfigCgPtyPresentationMode
			INTEGER
}

svcConfigIfIndex OBJECT-TYPE
	SYNTAX	Index
	ACCESS	read-only
	STATUS	mandatory
	DESCRIPTION
		"The ifIndex value of the  corresponding ifEntry."
	::= { svcConfigEntry 1 }

svcConfigInitiateIdentStatsUpload OBJECT-TYPE
	SYNTAX	IpAddress
	ACCESS	read-write
	STATUS	mandatory
	DESCRIPTION
		"Setting this object initiates a TFTP upload of SVC identification 
		 statistics to the specified IP address.  These statistics may be 
		 used to identify SVC's of interest on this port and to determine the
		 keys for those SVC's so that further information may be obtained by
		 accessing the circuit table."
	::= { svcConfigEntry 2 }

svcConfigCgPtyInsertionMode OBJECT-TYPE
	SYNTAX	INTEGER {
		disabled (1),
		insert (2),	-- insert when absent
		replace (3)	-- insert/replace always
	}
	ACCESS	read-write
	STATUS	mandatory
	DESCRIPTION
		"This object determines whether a statically configured address 
		 shall be inserted in the calling party address IE for calls entering
		 the network at this port."
	::= { svcConfigEntry 3 }

svcConfigCgPtyInsertionAddress OBJECT-TYPE
	SYNTAX	OCTET STRING (SIZE(15..20))
	ACCESS	read-write
	STATUS	mandatory
	DESCRIPTION
		"The calling party address to use in conjunction with the calling
		 party insertion function.  E.164 addresses are coded as 15 ASCII 
		 octets, utilizing leading ASCII '0' characters, as necessary.  
		 Atm-endsystem addresses are coded as 20 octet binary addresses."
	::= { svcConfigEntry 4 }

svcConfigCgPtyInsertionNmbPlan OBJECT-TYPE
	SYNTAX INTEGER {
		e164 (1),
		atm-endsystem (2),
		unknown (4)
	}
	ACCESS read-write
	STATUS mandatory
	DESCRIPTION
		"The numbering plan corresponding to this entry's calling party 
		 insertion address object."
	::= { svcConfigEntry 5 }

svcConfigCgPtyScreenMode OBJECT-TYPE
	SYNTAX  INTEGER {
			node-prefix (1),
			port-prefix (2),
			node-prefix-or-port-prefix (3),
			address (4),
			node-prefix-or-address (5),
			port-prefix-or-address (6),
			node-prefix-or-port-prefix-or-address (7),
			disabled (255)
                }
 	ACCESS	read-write
 	STATUS	mandatory
 	DESCRIPTION 
		"The type of screening to perform on the calling party number for
	 	 calls entering the network at this port.  Screening will be conducted 
		 by performing a bit-wise (for prefixes) or byte-wise (for addresses) 
		 comparison of the calling party number with the appropriate prefix or 
		 address database(s), as configured."
	::= { svcConfigEntry 6 }

svcConfigEgressAddrXlateMode OBJECT-TYPE
	SYNTAX  INTEGER {
			disabled (1),
			tunnel-when-called-party-matches-prefix (2),
			replace-when-called-party-matches-prefix (3),
			translate-e164-native-to-nsap (4),
			translate-e164-nsap-to-native (5)
                }
 	ACCESS	read-write
 	STATUS	mandatory
 	DESCRIPTION 
		"This object determines the type of address translation, if any
		 to occur for calls exiting the network at this port.  
	
		 The tunnelling mode will screen the called address against the 
		 prefixes configured for this port.  If no match is found, no
		 action is taken.  If a remote gateway address is configured for the 
		 matching prefix entry, the called party address will be tunnelled 
		 as a called subaddress and the configured remote gateway address will 
		 be inserted as the called party address.  If a local gateway address 
		 is configured for the matching prefix entry, the calling party address,
		 if present, will be tunnelled as a calling subaddress and the
		 configured local gateway address, if present, will be inserted as 
		 the calling party.

		 The replacement mode will operate as does the tunnelling mode, except
		 the original called and calling party addresses will be discarded.

		 The two translation modes are used for address interworking between 
		 networks using E.164 ATM Endsystem addresses and native ISDN E.164 addresses."
	::= { svcConfigEntry 7 }

svcConfigIngressAddrXlateMode OBJECT-TYPE
	SYNTAX  INTEGER {
			disabled (1),
			tunnel(2),
			translate-e164-native-to-nsap (4),
			translate-e164-nsap-to-native (5)
                }
 	ACCESS	read-write
 	STATUS	mandatory
 	DESCRIPTION 
		"This object determines the type of address translation, if any
		 to occur for calls entering the network at this port.  
	
		 The tunnelling mode reverses the actions of egress tunnelling.  If a 
		 called subaddress is present, it will replace the called party address, 
		 which will be discarded.  If a calling subaddress is present, it will 
		 replace the calling party address, which will be discarded.

		 The two translation modes are used for address interworking between networks
		 using E.164 ATM Endsystem addresses and native ISDN E.164 addresses."
	::= { svcConfigEntry 8 }

svcConfigCgPtyPresentationMode OBJECT-TYPE
	SYNTAX  INTEGER {
			user (1),	-- use signalled presentation indicator
			never (2),	-- override signalled presentation and never present
			always (3)	-- override signalled presentation and always present 
                }
 	ACCESS	read-write
 	STATUS	mandatory
 	DESCRIPTION 
		"This object controls the circumstances under which the calling party 
		 number shall be presented at the egress port of the network."
	::= { svcConfigEntry 9 }


--
-- 	SVC ATM Configuration Table
--

svcAtmConfigTable OBJECT-TYPE
	SYNTAX	SEQUENCE OF SvcAtmConfigEntry
	ACCESS	not-accessible
	STATUS	mandatory
	DESCRIPTION
		"A table of ATM signalling paramaters associated with ATM logical 
		 ports.  The maximum number of entries is given by the value of 
		 ifNumber in MIB-II."
	::= { svcmgt 2 }

svcAtmConfigEntry OBJECT-TYPE
	SYNTAX	SvcAtmConfigEntry
	ACCESS	not-accessible
	STATUS	mandatory
	DESCRIPTION
		"The SVC ATM configuration entry contains objects relevant to 
		 the configuration and monitoring of ATM signalling on an ATM 
		 logical port."
	INDEX	{ svcAtmConfigIfIndex }
	::= { svcAtmConfigTable 1 }

SvcAtmConfigEntry ::=
	SEQUENCE {		
		svcAtmConfigIfIndex
			Index,
		svcAtmConfigAdminStatus
			INTEGER,
		svcAtmConfigOperStatus
			INTEGER,
		svcAtmConfigQ93bMaxRestart
			INTEGER,
		svcAtmConfigQ93bMaxStatEnq
			INTEGER,	
		svcAtmConfigQ93bT303
			INTEGER,	
		svcAtmConfigQ93bT308
			INTEGER,	
		svcAtmConfigQ93bT309
			INTEGER,	
		svcAtmConfigQ93bT310
			INTEGER,	
		svcAtmConfigQ93bT313
			INTEGER,	
		svcAtmConfigQ93bT316
			INTEGER,
		svcAtmConfigQ93bT322
			INTEGER,
		svcAtmConfigQ93bT398
			INTEGER,
		svcAtmConfigQ93bT399
			INTEGER,
		svcAtmConfigQ93bTotalConns
			Counter,
		svcAtmConfigQ93bActiveConns
			Counter,
		svcAtmConfigQ93bLastCauseTx
			INTEGER,
		svcAtmConfigQ93bLastCauseRx
			INTEGER,
		svcAtmConfigQ93bNumSetupPduTx
			Counter,
		svcAtmConfigQ93bNumSetupPduRx
			Counter,
		svcAtmConfigQ93bNumCallProcPduTx
			Counter,
		svcAtmConfigQ93bNumCallProcPduRx
			Counter,
		svcAtmConfigQ93bNumConnectPduTx
			Counter,
		svcAtmConfigQ93bNumConnectPduRx
			Counter,
		svcAtmConfigQ93bNumConnectAckPduTx
			Counter,
		svcAtmConfigQ93bNumConnectAckPduRx
			Counter,
		svcAtmConfigQ93bNumReleasePduTx
			Counter,
		svcAtmConfigQ93bNumReleasePduRx
			Counter,
		svcAtmConfigQ93bNumReleaseCmpltPduTx
			Counter,
		svcAtmConfigQ93bNumReleaseCmpltPduRx
			Counter,
		svcAtmConfigQ93bNumAddPtyPduTx
			Counter,
		svcAtmConfigQ93bNumAddPtyPduRx
			Counter,
		svcAtmConfigQ93bNumAddPtyAckPduTx
			Counter,
		svcAtmConfigQ93bNumAddPtyAckPduRx
			Counter,
		svcAtmConfigQ93bNumAddPtyRejPduTx
			Counter,
		svcAtmConfigQ93bNumAddPtyRejPduRx
			Counter,
		svcAtmConfigQ93bNumDropPtyPduTx
			Counter,
		svcAtmConfigQ93bNumDropPtyPduRx
			Counter,
		svcAtmConfigQ93bNumDropPtyAckPduTx
			Counter,
		svcAtmConfigQ93bNumDropPtyAckPduRx
			Counter,
		svcAtmConfigQ93bNumStatusEnqPduTx
			Counter,
		svcAtmConfigQ93bNumStatusEnqPduRx
			Counter,
		svcAtmConfigQ93bNumStatusPduTx
			Counter,
		svcAtmConfigQ93bNumStatusPduRx
			Counter,
		svcAtmConfigQ93bNumRestartPduTx
			Counter,
		svcAtmConfigQ93bNumRestartPduRx
			Counter,
		svcAtmConfigQ93bNumRestartAckPduTx
			Counter,
		svcAtmConfigQ93bNumRestartAckPduRx
			Counter,
		svcAtmConfigQSaalMaxCC
			INTEGER,
		svcAtmConfigQSaalMaxPD
			INTEGER,
		svcAtmConfigQSaalMaxStat
			INTEGER,
		svcAtmConfigQSaalTPoll
			INTEGER,
		svcAtmConfigQSaalTKeepalive
			INTEGER,
		svcAtmConfigQSaalTNoResponse
			INTEGER,
		svcAtmConfigQSaalTCC
			INTEGER,
		svcAtmConfigQSaalTIdle
			INTEGER,
		svcAtmConfigQSaalNumDiscardTx
			Counter,
		svcAtmConfigQSaalNumDiscardRx
			Counter,
		svcAtmConfigQSaalNumErrorTx
			Counter,
		svcAtmConfigQSaalNumErrorRx
			Counter,
		svcAtmConfigQSaalNumBgnPduTx
			Counter,
		svcAtmConfigQSaalNumBgnPduRx
			Counter,
		svcAtmConfigQSaalNumBgakPduTx
			Counter,
		svcAtmConfigQSaalNumBgakPduRx
			Counter,
		svcAtmConfigQSaalNumBgrejPduTx
			Counter,
		svcAtmConfigQSaalNumBgrejPduRx
			Counter,
		svcAtmConfigQSaalNumEndPduTx
			Counter,
		svcAtmConfigQSaalNumEndPduRx
			Counter,
		svcAtmConfigQSaalNumEndakPduTx
			Counter,
		svcAtmConfigQSaalNumEndakPduRx
			Counter,
		svcAtmConfigQSaalNumRsPduTx
			Counter,
		svcAtmConfigQSaalNumRsPduRx
			Counter,
		svcAtmConfigQSaalNumRsakPduTx
			Counter,
		svcAtmConfigQSaalNumRsakPduRx
			Counter,
		svcAtmConfigQSaalNumErPduTx
			Counter,
		svcAtmConfigQSaalNumErPduRx
			Counter,
		svcAtmConfigQSaalNumErakPduTx
			Counter,
		svcAtmConfigQSaalNumErakPduRx
			Counter,
		svcAtmConfigQSaalNumSdPduTx
			Counter,
		svcAtmConfigQSaalNumSdPduRx
			Counter,
		svcAtmConfigQSaalNumPollPduTx
			Counter,
		svcAtmConfigQSaalNumPollPduRx
			Counter,
		svcAtmConfigQSaalNumStatPduTx
			Counter,
		svcAtmConfigQSaalNumStatPduRx
			Counter,
		svcAtmConfigQSaalNumUstatPduTx
			Counter,
		svcAtmConfigQSaalNumUstatPduRx
			Counter,
		svcAtmConfigQSaalNumUdPduTx
			Counter,
		svcAtmConfigQSaalNumUdPduRx
			Counter,
		svcAtmConfigQSaalNumMdPduTx
			Counter,
		svcAtmConfigQSaalNumMdPduRx
			Counter
	}

svcAtmConfigIfIndex OBJECT-TYPE
	SYNTAX	Index
	ACCESS	read-only
	STATUS	mandatory
	DESCRIPTION
		"The ifIndex value of the  corresponding ifEntry."
	::= { svcAtmConfigEntry 1 }

svcAtmConfigAdminStatus OBJECT-TYPE
	SYNTAX	INTEGER {
		enabled (1),
		disabled (2)
	}
	ACCESS	read-write
	STATUS	mandatory
	DESCRIPTION
		"The configured state of the ATM signalling function for this port."
	::= { svcAtmConfigEntry 2 }

svcAtmConfigOperStatus OBJECT-TYPE
	SYNTAX	INTEGER {
		down (1),
		connecting (2),
		up (3)
	}
	ACCESS	read-only
	STATUS	mandatory
	DESCRIPTION
		"The operational status of the signalling function on this port."
	::= { svcAtmConfigEntry 3 }

svcAtmConfigQ93bMaxRestart OBJECT-TYPE
	SYNTAX	INTEGER
	ACCESS	read-write
	STATUS	mandatory
	DESCRIPTION
		"The maximum number of unacknowledged restarts to send before 
		 declaring a signalling failure."
	::= { svcAtmConfigEntry 4 }

svcAtmConfigQ93bMaxStatEnq OBJECT-TYPE
	SYNTAX	INTEGER
	ACCESS	read-write
	STATUS	mandatory
	DESCRIPTION
		"The maximum number of unacknowledged status enquiries to send
		 before issuing a restart."
	::= { svcAtmConfigEntry 5 }

svcAtmConfigQ93bT303 OBJECT-TYPE
	SYNTAX	INTEGER
	ACCESS	read-write
	STATUS	mandatory
	DESCRIPTION
		"Protocol Timer T303, specified in milliseconds."
	::= { svcAtmConfigEntry 6 }

svcAtmConfigQ93bT308 OBJECT-TYPE
	SYNTAX	INTEGER
	ACCESS	read-write
	STATUS	mandatory
	DESCRIPTION
		"Protocol Timer T308, specified in milliseconds."
	::= { svcAtmConfigEntry 7 }

svcAtmConfigQ93bT309 OBJECT-TYPE
	SYNTAX	INTEGER
	ACCESS	read-write
	STATUS	mandatory
	DESCRIPTION
		"Protocol Timer T309, specified in milliseconds."
	::= { svcAtmConfigEntry 8 }

svcAtmConfigQ93bT310 OBJECT-TYPE
	SYNTAX	INTEGER
	ACCESS	read-write
	STATUS	mandatory
	DESCRIPTION
		"Protocol Timer T310, specified in milliseconds."
	::= { svcAtmConfigEntry 9 }

svcAtmConfigQ93bT313 OBJECT-TYPE
	SYNTAX	INTEGER
	ACCESS	read-write
	STATUS	mandatory
	DESCRIPTION
		"Protocol Timer T313, specified in milliseconds."
	::= { svcAtmConfigEntry 10 }

svcAtmConfigQ93bT316 OBJECT-TYPE
	SYNTAX	INTEGER
	ACCESS	read-write
	STATUS	mandatory
	DESCRIPTION
		"Protocol Timer T316, specified in milliseconds."
	::= { svcAtmConfigEntry 11 }

svcAtmConfigQ93bT322 OBJECT-TYPE
	SYNTAX	INTEGER
	ACCESS	read-write
	STATUS	mandatory
	DESCRIPTION
		"Protocol Timer T322, specified in milliseconds."
	::= { svcAtmConfigEntry 12 }

svcAtmConfigQ93bT398 OBJECT-TYPE
	SYNTAX	INTEGER
	ACCESS	read-write
	STATUS	mandatory
	DESCRIPTION
		"Protocol Timer T398, specified in milliseconds."
	::= { svcAtmConfigEntry 13 }

svcAtmConfigQ93bT399 OBJECT-TYPE
	SYNTAX	INTEGER
	ACCESS	read-write
	STATUS	mandatory
	DESCRIPTION
		"Protocol Timer T399, specified in milliseconds."
	::= { svcAtmConfigEntry 14 }

svcAtmConfigQ93bTotalConns OBJECT-TYPE
	SYNTAX	Counter
	ACCESS	read-only
	STATUS	mandatory
	DESCRIPTION
		"The total number of SVC's established on this port."
	::= { svcAtmConfigEntry 15 }

svcAtmConfigQ93bActiveConns OBJECT-TYPE
	SYNTAX	Counter
	ACCESS	read-only
	STATUS	mandatory
	DESCRIPTION
		"The number of SVC's present on this port."
	::= { svcAtmConfigEntry 16 }

svcAtmConfigQ93bLastCauseTx OBJECT-TYPE
	SYNTAX	INTEGER {
		unalloc-nmb		(1),	-- unallocated (unassigned) number 
		no-route-transnet	(2),	-- no route to transit network
		no-route-dest		(3),   	-- no route to destination 
		vcc-unacceptable-30	(10), 	-- UNI 3.0: VPCI/VCI unacceptable
		normal-call-clr-31	(16),  	-- UNI 3.1: normal call clearing
		user-busy		(17),  	-- user busy
		no-user-response	(18),  	-- no user response
		call-reject		(21),  	-- call rejected
		nmb-changed		(22),  	-- number changed
		call-reject-clir	(23),  	-- user rejects all calls with CLIR
		dest-out-of-order	(27),  	-- destination out of order
		invalid-nmb-format	(28),  	-- invalid number format
		response-stat-enq	(30),  	-- response to STATUS ENQUIRY
		normal-unspecified	(31),  	-- normal unspecified
		req-vcc-unavailable	(35),  	-- requested VPCI/VCI unavailable
		vcc-fail-31		(36),  	-- UNI 3.1: VPCI/VCI assignment failure
		rate-unavail-31		(37),  	-- UNI 3.1: user cell rate unavailable
		network-out-of-order	(38),  	-- network out of order
		temp-fail		(41),  	-- Temporary failure
		access-info-discard	(43),	-- access info discarded
		no-vcc-available	(45),   -- no VPCI/VCI unavailable
		resources-unavailable	(47),   -- resources unavailable, unspecified
		qos-unavailable		(49),   -- Quality of Service unavailable
		rate-unavailable-30 	(51),   -- UNI 3.0: user cell rate unavailable
		b-cap-not-authorized 	(57),   -- bearer capability not authorized
		b-cap-unavailable 	(58),   -- bearer capability not available
		service-unavailable 	(63),   -- Service or option unavailable
		b-cap-not-implemented 	(65),   -- bearer capability not implemented
		combination-unsupported	(73),   -- unsupported comb. of traffic parameters
		aal-params-unsupp-31 	(78),   -- UNI 3.1: AAL paramteres cannot be supported
		invalid-call-reference 	(81),   -- invalid call reference
		no-channel	 	(82),   -- identified channel does not exist
		dest-incompatible 	(88),   -- incompatible destination
		invalid-endpoint-ref 	(89),   -- invalid endpoint reference
		invalid-transit-net 	(91),   -- invalid transit network selection
		too-many-add-pty-req 	(92),   -- too many add party requests
		aal-params-unsupp-30 	(93),   -- UNI 3.0:AAL paramteres cannot be supported
		info-element-missing 	(96),   -- mandatory info element is missing
		msg-type-not-imp 	(97),   -- message type not implemented
		info-element-not-imp 	(99),   -- info element not implemented
		invalid-info-element 	(100),  -- invalid info element
		message-not-compatible 	(101),  -- msg type not compatible with call st
		timer-recovery		(102),  -- recovery on timer expiry
		invalid-message-len 	(104),  -- incorrect message length
		protocol-error		(111),  -- protocol error, unspecified
		optional-element-error 	(127)	-- opt info el content error (non-std)
	}
	ACCESS	read-only
	STATUS	mandatory
	DESCRIPTION
		"The last transmitted cause code for this port."
	::= { svcAtmConfigEntry 17 }

svcAtmConfigQ93bLastCauseRx OBJECT-TYPE
	SYNTAX	INTEGER {
		unalloc-nmb		(1),	-- unallocated (unassigned) number 
		no-route-transnet	(2),	-- no route to transit network
		no-route-dest		(3),   	-- no route to destination 
		vcc-unacceptable-30	(10), 	-- UNI 3.0: VPCI/VCI unacceptable
		normal-call-clr-31	(16),  	-- UNI 3.1: normal call clearing
		user-busy		(17),  	-- user busy
		no-user-response	(18),  	-- no user response
		call-reject		(21),  	-- call rejected
		nmb-changed		(22),  	-- number changed
		call-reject-clir	(23),  	-- user rejects all calls with CLIR
		dest-out-of-order	(27),  	-- destination out of order
		invalid-nmb-format	(28),  	-- invalid number format
		response-stat-enq	(30),  	-- response to STATUS ENQUIRY
		normal-unspecified	(31),  	-- normal unspecified
		req-vcc-unavailable	(35),  	-- requested VPCI/VCI unavailable
		vcc-fail-31		(36),  	-- UNI 3.1: VPCI/VCI assignment failure
		rate-unavail-31		(37),  	-- UNI 3.1: user cell rate unavailable
		network-out-of-order	(38),  	-- network out of order
		temp-fail		(41),  	-- Temporary failure
		access-info-discard	(43),	-- access info discarded
		no-vcc-available	(45),   -- no VPCI/VCI unavailable
		resources-unavailable	(47),   -- resources unavailable, unspecified
		qos-unavailable		(49),   -- Quality of Service unavailable
		rate-unavailable-30 	(51),   -- UNI 3.0: user cell rate unavailable
		b-cap-not-authorized 	(57),   -- bearer capability not authorized
		b-cap-unavailable 	(58),   -- bearer capability not available
		service-unavailable 	(63),   -- Service or option unavailable
		b-cap-not-implemented 	(65),   -- bearer capability not implemented
		combination-unsupported	(73),   -- unsupported comb. of traffic parameters
		aal-params-unsupp-31 	(78),   -- UNI 3.1: AAL paramteres cannot be supported
		invalid-call-reference 	(81),   -- invalid call reference
		no-channel	 	(82),   -- identified channel does not exist
		dest-incompatible 	(88),   -- incompatible destination
		invalid-endpoint-ref 	(89),   -- invalid endpoint reference
		invalid-transit-net 	(91),   -- invalid transit network selection
		too-many-add-pty-req 	(92),   -- too many add party requests
		aal-params-unsupp-30 	(93),   -- UNI 3.0:AAL paramteres cannot be supported
		info-element-missing 	(96),   -- mandatory info element is missing
		msg-type-not-imp 	(97),   -- message type not implemented
		info-element-not-imp 	(99),   -- info element not implemented
		invalid-info-element 	(100),  -- invalid info element
		message-not-compatible 	(101),  -- msg type not compatible with call st
		timer-recovery		(102),  -- recovery on timer expiry
		invalid-message-len 	(104),  -- incorrect message length
		protocol-error		(111),  -- protocol error, unspecified
		optional-element-error 	(127)	-- opt info el content error (non-std)
	}
	ACCESS	read-only
	STATUS	mandatory
	DESCRIPTION
		"The last received cause code for this port."
	::= { svcAtmConfigEntry 18 }

svcAtmConfigQ93bNumSetupPduTx OBJECT-TYPE
	SYNTAX  Counter
	ACCESS  read-only
	STATUS  mandatory
	DESCRIPTION
		"The number of setup PDU's transmitted on this port."
	::= { svcAtmConfigEntry 19 }

svcAtmConfigQ93bNumSetupPduRx OBJECT-TYPE
	SYNTAX  Counter
	ACCESS  read-only
	STATUS  mandatory
	DESCRIPTION
		"The number of setup PDU's received on this port."
	::= { svcAtmConfigEntry 20 }

svcAtmConfigQ93bNumCallProcPduTx OBJECT-TYPE
	SYNTAX  Counter
	ACCESS  read-only
	STATUS  mandatory
	DESCRIPTION
		"The number of call proceeding PDU's transmitted on this port."
	::= { svcAtmConfigEntry 21 }

svcAtmConfigQ93bNumCallProcPduRx OBJECT-TYPE
	SYNTAX  Counter
	ACCESS  read-only
	STATUS  mandatory
	DESCRIPTION
		"The number of call proceeding PDU's received on this port."
	::= { svcAtmConfigEntry 22 }

svcAtmConfigQ93bNumConnectPduTx OBJECT-TYPE
	SYNTAX  Counter
	ACCESS  read-only
	STATUS  mandatory
	DESCRIPTION
		"The number of connect PDU's transmitted on this port."
	::= { svcAtmConfigEntry 23 }

svcAtmConfigQ93bNumConnectPduRx OBJECT-TYPE
	SYNTAX  Counter
	ACCESS  read-only
	STATUS  mandatory
	DESCRIPTION
		"The number of connect PDU's received on this port."
	::= { svcAtmConfigEntry 24 }

svcAtmConfigQ93bNumConnectAckPduTx OBJECT-TYPE
	SYNTAX  Counter
	ACCESS  read-only
	STATUS  mandatory
	DESCRIPTION
		"The number of connect ack PDU's transmitted on this port."
	::= { svcAtmConfigEntry 25 }

svcAtmConfigQ93bNumConnectAckPduRx OBJECT-TYPE
	SYNTAX  Counter
	ACCESS  read-only
	STATUS  mandatory
	DESCRIPTION
		"The number of connect ack PDU's received on this port."
	::= { svcAtmConfigEntry 26 }

svcAtmConfigQ93bNumReleasePduTx OBJECT-TYPE
	SYNTAX  Counter
	ACCESS  read-only
	STATUS  mandatory
	DESCRIPTION
		"The number of release PDU's transmitted on this port."
	::= { svcAtmConfigEntry 27 }

svcAtmConfigQ93bNumReleasePduRx OBJECT-TYPE
	SYNTAX  Counter
	ACCESS  read-only
	STATUS  mandatory
	DESCRIPTION
		"The number of release PDU's received on this port."
	::= { svcAtmConfigEntry 28 }

svcAtmConfigQ93bNumReleaseCmpltPduTx OBJECT-TYPE
	SYNTAX  Counter
	ACCESS  read-only
	STATUS  mandatory
	DESCRIPTION
		"The number of release complete PDU's transmitted on this port."
	::= { svcAtmConfigEntry 29 }

svcAtmConfigQ93bNumReleaseCmpltPduRx OBJECT-TYPE
	SYNTAX  Counter
	ACCESS  read-only
	STATUS  mandatory
	DESCRIPTION
		"The number of release complete PDU's received on this port."
	::= { svcAtmConfigEntry 30 }

svcAtmConfigQ93bNumAddPtyPduTx OBJECT-TYPE
	SYNTAX  Counter
	ACCESS  read-only
	STATUS  mandatory
	DESCRIPTION
		"The number of add party PDU's transmitted on this port."
	::= { svcAtmConfigEntry 31 }

svcAtmConfigQ93bNumAddPtyPduRx OBJECT-TYPE
	SYNTAX  Counter
	ACCESS  read-only
	STATUS  mandatory
	DESCRIPTION
		"The number of add party PDU's received on this port."
	::= { svcAtmConfigEntry 32 }

svcAtmConfigQ93bNumAddPtyAckPduTx OBJECT-TYPE
	SYNTAX  Counter
	ACCESS  read-only
	STATUS  mandatory
	DESCRIPTION
		"The number of add party acknowledge PDU's transmitted on this port."
	::= { svcAtmConfigEntry 33 }

svcAtmConfigQ93bNumAddPtyAckPduRx OBJECT-TYPE
	SYNTAX  Counter
	ACCESS  read-only
	STATUS  mandatory
	DESCRIPTION
		"The number of add party acknowledge PDU's received on this port."
	::= { svcAtmConfigEntry 34 }

svcAtmConfigQ93bNumAddPtyRejPduTx OBJECT-TYPE
	SYNTAX  Counter
	ACCESS  read-only
	STATUS  mandatory
	DESCRIPTION
		"The number of add party reject PDU's transmitted on this port."
	::= { svcAtmConfigEntry 35 }

svcAtmConfigQ93bNumAddPtyRejPduRx OBJECT-TYPE
	SYNTAX  Counter
	ACCESS  read-only
	STATUS  mandatory
	DESCRIPTION
		"The number of add party reject PDU's received on this port."
	::= { svcAtmConfigEntry 36 }

svcAtmConfigQ93bNumDropPtyPduTx OBJECT-TYPE
	SYNTAX  Counter
	ACCESS  read-only
	STATUS  mandatory
	DESCRIPTION
		"The number of drop party PDU's transmitted on this port."
	::= { svcAtmConfigEntry 37 }

svcAtmConfigQ93bNumDropPtyPduRx OBJECT-TYPE
	SYNTAX  Counter
	ACCESS  read-only
	STATUS  mandatory
	DESCRIPTION
		"The number of drop party PDU's received on this port."
	::= { svcAtmConfigEntry 38 }

svcAtmConfigQ93bNumDropPtyAckPduTx OBJECT-TYPE
	SYNTAX  Counter
	ACCESS  read-only
	STATUS  mandatory
	DESCRIPTION
		"The number of drop party acknowledge PDU's transmitted on this port."
	::= { svcAtmConfigEntry 39 }

svcAtmConfigQ93bNumDropPtyAckPduRx OBJECT-TYPE
	SYNTAX  Counter
	ACCESS  read-only
	STATUS  mandatory
	DESCRIPTION
		"The number of drop party acknowledge PDU's received on this port."
	::= { svcAtmConfigEntry 40 }

svcAtmConfigQ93bNumStatusEnqPduTx OBJECT-TYPE
	SYNTAX  Counter
	ACCESS  read-only
	STATUS  mandatory
	DESCRIPTION
		"The number of status enquiry PDU's transmitted on this port."
	::= { svcAtmConfigEntry 41 }

svcAtmConfigQ93bNumStatusEnqPduRx OBJECT-TYPE
	SYNTAX  Counter
	ACCESS  read-only
	STATUS  mandatory
	DESCRIPTION
		"The number of status enquiry PDU's received on this port."
	::= { svcAtmConfigEntry 42 }

svcAtmConfigQ93bNumStatusPduTx OBJECT-TYPE
	SYNTAX  Counter
	ACCESS  read-only
	STATUS  mandatory
	DESCRIPTION
		"The number of status PDU's transmitted on this port."
	::= { svcAtmConfigEntry 43 }

svcAtmConfigQ93bNumStatusPduRx OBJECT-TYPE
	SYNTAX  Counter
	ACCESS  read-only
	STATUS  mandatory
	DESCRIPTION
		"The number of status PDU's received on this port."
	::= { svcAtmConfigEntry 44 }

svcAtmConfigQ93bNumRestartPduTx OBJECT-TYPE
	SYNTAX  Counter
	ACCESS  read-only
	STATUS  mandatory
	DESCRIPTION
		"The number of restart PDU's transmitted on this port."
	::= { svcAtmConfigEntry 45 }

svcAtmConfigQ93bNumRestartPduRx OBJECT-TYPE
	SYNTAX  Counter
	ACCESS  read-only
	STATUS  mandatory
	DESCRIPTION
		"The number of restart PDU's received on this port."
	::= { svcAtmConfigEntry 46 }

svcAtmConfigQ93bNumRestartAckPduTx OBJECT-TYPE
	SYNTAX  Counter
	ACCESS  read-only
	STATUS  mandatory
	DESCRIPTION
		"The number of restart acknowledge PDU's transmitted on this port."
	::= { svcAtmConfigEntry 47 }

svcAtmConfigQ93bNumRestartAckPduRx OBJECT-TYPE
	SYNTAX  Counter
	ACCESS  read-only
	STATUS  mandatory
	DESCRIPTION
		"The number of restart acknowledge PDU's received on this port."
	::= { svcAtmConfigEntry 48 }

svcAtmConfigQSaalMaxCC OBJECT-TYPE
	SYNTAX	INTEGER
	ACCESS	read-write
	STATUS	mandatory
	DESCRIPTION
		"The maximum number of unacknowledged transmitted control PDU's 
		 before declaring a loss of connection."
	::= { svcAtmConfigEntry 49 }

svcAtmConfigQSaalMaxPD OBJECT-TYPE
	SYNTAX	INTEGER
	ACCESS	read-write
	STATUS	mandatory
	DESCRIPTION
		"The maximum number of PDU's transmitted before a POLL PDU is 
		 transmitted."
	::= { svcAtmConfigEntry 50 }

svcAtmConfigQSaalMaxStat OBJECT-TYPE
	SYNTAX	INTEGER
	ACCESS	read-write
	STATUS	mandatory
	DESCRIPTION
		"The maximum number of list elements in a STAT PDU."
	::= { svcAtmConfigEntry 51 }

svcAtmConfigQSaalTPoll OBJECT-TYPE
	SYNTAX	INTEGER
	ACCESS	read-write
	STATUS	mandatory
	DESCRIPTION
		"The protocol timer corresponding to the polling function,
		 specified in milliseconds."
	::= { svcAtmConfigEntry 52 }

svcAtmConfigQSaalTKeepalive OBJECT-TYPE
	SYNTAX	INTEGER
	ACCESS	read-write
	STATUS	mandatory
	DESCRIPTION
		"The protocol timer corresponding to the keepalive function,
		 specified in milliseconds."
	::= { svcAtmConfigEntry 53 }

svcAtmConfigQSaalTNoResponse OBJECT-TYPE
	SYNTAX	INTEGER
	ACCESS	read-write
	STATUS	mandatory
	DESCRIPTION
		"The protocol timer corresponding to the response timeout function,
		 specified in milliseconds."
	::= { svcAtmConfigEntry 54 }

svcAtmConfigQSaalTCC OBJECT-TYPE
	SYNTAX	INTEGER
	ACCESS	read-write
	STATUS	mandatory
	DESCRIPTION
		"The protocol timer corresponding to the transmission of 
		 control PDU's, specified in milliseconds."
	::= { svcAtmConfigEntry 55 }

svcAtmConfigQSaalTIdle OBJECT-TYPE
	SYNTAX	INTEGER
	ACCESS	read-write
	STATUS	mandatory
	DESCRIPTION
		"The protocol timer corresponding to the idle function for
		 UNI 3.1, only, specified in milliseconds."
	::= { svcAtmConfigEntry 56 }

svcAtmConfigQSaalNumDiscardTx OBJECT-TYPE
	SYNTAX	Counter
	ACCESS	read-only
	STATUS	mandatory
	DESCRIPTION
		"The number of QSaal transmit discards on this port."
	::= { svcAtmConfigEntry 57 }

svcAtmConfigQSaalNumDiscardRx OBJECT-TYPE
	SYNTAX	Counter
	ACCESS	read-only
	STATUS	mandatory
	DESCRIPTION
		"The number of QSaal receive discards on this port."
	::= { svcAtmConfigEntry 58 }

svcAtmConfigQSaalNumErrorTx OBJECT-TYPE
	SYNTAX	Counter
	ACCESS	read-only
	STATUS	mandatory
	DESCRIPTION
		"The number of QSaal transmit errors on this port."
	::= { svcAtmConfigEntry 59 }

svcAtmConfigQSaalNumErrorRx OBJECT-TYPE
	SYNTAX	Counter
	ACCESS	read-only
	STATUS	mandatory
	DESCRIPTION
		"The number of QSaal receive errors on this port."
	::= { svcAtmConfigEntry 60 }

svcAtmConfigQSaalNumBgnPduTx OBJECT-TYPE
	SYNTAX  Counter
	ACCESS  read-only
	STATUS  mandatory
	DESCRIPTION
		"The number of begin PDU's transmitted on this port."
	::= { svcAtmConfigEntry 61 }

svcAtmConfigQSaalNumBgnPduRx OBJECT-TYPE
	SYNTAX  Counter
	ACCESS  read-only
	STATUS  mandatory
	DESCRIPTION
		"The number of begin PDU's received on this port."
	::= { svcAtmConfigEntry 62 }

svcAtmConfigQSaalNumBgakPduTx OBJECT-TYPE
	SYNTAX  Counter
	ACCESS  read-only
	STATUS  mandatory
	DESCRIPTION
		"The number of begin acknowledge PDU's transmitted on this port."
	::= { svcAtmConfigEntry 63 }

svcAtmConfigQSaalNumBgakPduRx OBJECT-TYPE
	SYNTAX  Counter
	ACCESS  read-only
	STATUS  mandatory
	DESCRIPTION
		"The number of begin acknowledge PDU's received on this port."
	::= { svcAtmConfigEntry 64 }

svcAtmConfigQSaalNumBgrejPduTx OBJECT-TYPE
	SYNTAX  Counter
	ACCESS  read-only
	STATUS  mandatory
	DESCRIPTION
		"The number of begin reject PDU's transmitted on this port."
	::= { svcAtmConfigEntry 65 }

svcAtmConfigQSaalNumBgrejPduRx OBJECT-TYPE
	SYNTAX  Counter
	ACCESS  read-only
	STATUS  mandatory
	DESCRIPTION
		"The number of begin reject PDU's received on this port."
	::= { svcAtmConfigEntry 66 }

svcAtmConfigQSaalNumEndPduTx OBJECT-TYPE
	SYNTAX  Counter
	ACCESS  read-only
	STATUS  mandatory
	DESCRIPTION
		"The number of end PDU's transmitted on this port."
	::= { svcAtmConfigEntry 67 }

svcAtmConfigQSaalNumEndPduRx OBJECT-TYPE
	SYNTAX  Counter
	ACCESS  read-only
	STATUS  mandatory
	DESCRIPTION
		"The number of end PDU's received on this port."
	::= { svcAtmConfigEntry 68 }

svcAtmConfigQSaalNumEndakPduTx OBJECT-TYPE
	SYNTAX  Counter
	ACCESS  read-only
	STATUS  mandatory
	DESCRIPTION
		"The number of end acknowledge PDU's transmitted on this port."
	::= { svcAtmConfigEntry 69 }

svcAtmConfigQSaalNumEndakPduRx OBJECT-TYPE
	SYNTAX  Counter
	ACCESS  read-only
	STATUS  mandatory
	DESCRIPTION
		"The number of end acknowldge PDU's received on this port."
	::= { svcAtmConfigEntry 70 }

svcAtmConfigQSaalNumRsPduTx OBJECT-TYPE
	SYNTAX  Counter
	ACCESS  read-only
	STATUS  mandatory
	DESCRIPTION
		"The number of resynchronization PDU's transmitted on this port."
	::= { svcAtmConfigEntry 71 }

svcAtmConfigQSaalNumRsPduRx OBJECT-TYPE
	SYNTAX  Counter
	ACCESS  read-only
	STATUS  mandatory
	DESCRIPTION
		"The number of resynchronization PDU's received on this port."
	::= { svcAtmConfigEntry 72 }

svcAtmConfigQSaalNumRsakPduTx OBJECT-TYPE
	SYNTAX  Counter
	ACCESS  read-only
	STATUS  mandatory
	DESCRIPTION
		"The number of resynchronization acknowledge PDU's transmitted on this port."
	::= { svcAtmConfigEntry 73 }

svcAtmConfigQSaalNumRsakPduRx OBJECT-TYPE
	SYNTAX  Counter
	ACCESS  read-only
	STATUS  mandatory
	DESCRIPTION
		"The number of resynchronization acknowldge PDU's received on this port."
	::= { svcAtmConfigEntry 74 }

svcAtmConfigQSaalNumErPduTx OBJECT-TYPE
	SYNTAX  Counter
	ACCESS  read-only
	STATUS  mandatory
	DESCRIPTION
		"The number of error recovery PDU's transmitted on this port."
	::= { svcAtmConfigEntry 75 }

svcAtmConfigQSaalNumErPduRx OBJECT-TYPE
	SYNTAX  Counter
	ACCESS  read-only
	STATUS  mandatory
	DESCRIPTION
		"The number of errror recovery PDU's received on this port."
	::= { svcAtmConfigEntry 76 }

svcAtmConfigQSaalNumErakPduTx OBJECT-TYPE
	SYNTAX  Counter
	ACCESS  read-only
	STATUS  mandatory
	DESCRIPTION
		"The number of error recovery acknowledge PDU's transmitted on this port."
	::= { svcAtmConfigEntry 77 }

svcAtmConfigQSaalNumErakPduRx OBJECT-TYPE
	SYNTAX  Counter
	ACCESS  read-only
	STATUS  mandatory
	DESCRIPTION
		"The number of errror recovery acknowledge PDU's received on this port."
	::= { svcAtmConfigEntry 78 }

svcAtmConfigQSaalNumSdPduTx OBJECT-TYPE
	SYNTAX  Counter
	ACCESS  read-only
	STATUS  mandatory
	DESCRIPTION
		"The number of sequenced data PDU's transmitted on this port."
	::= { svcAtmConfigEntry 79 }

svcAtmConfigQSaalNumSdPduRx OBJECT-TYPE
	SYNTAX  Counter
	ACCESS  read-only
	STATUS  mandatory
	DESCRIPTION
		"The number of sequenced data PDU's received on this port."
	::= { svcAtmConfigEntry 80 }

svcAtmConfigQSaalNumPollPduTx OBJECT-TYPE
	SYNTAX  Counter
	ACCESS  read-only
	STATUS  mandatory
	DESCRIPTION
		"The number of poll PDU's transmitted on this port."
	::= { svcAtmConfigEntry 81 }

svcAtmConfigQSaalNumPollPduRx OBJECT-TYPE
	SYNTAX  Counter
	ACCESS  read-only
	STATUS  mandatory
	DESCRIPTION
		"The number of poll PDU's received on this port."
	::= { svcAtmConfigEntry 82 }

svcAtmConfigQSaalNumStatPduTx OBJECT-TYPE
	SYNTAX  Counter
	ACCESS  read-only
	STATUS  mandatory
	DESCRIPTION
		"The number of status PDU's transmitted on this port."
	::= { svcAtmConfigEntry 83 }

svcAtmConfigQSaalNumStatPduRx OBJECT-TYPE
	SYNTAX  Counter
	ACCESS  read-only
	STATUS  mandatory
	DESCRIPTION
		"The number of status PDU's received on this port."
	::= { svcAtmConfigEntry 84 }

svcAtmConfigQSaalNumUstatPduTx OBJECT-TYPE
	SYNTAX  Counter
	ACCESS  read-only
	STATUS  mandatory
	DESCRIPTION
		"The number of unsolicited status PDU's transmitted on this port."
	::= { svcAtmConfigEntry 85 }

svcAtmConfigQSaalNumUstatPduRx OBJECT-TYPE
	SYNTAX  Counter
	ACCESS  read-only
	STATUS  mandatory
	DESCRIPTION
		"The number of unsolicited status PDU's received on this port."
	::= { svcAtmConfigEntry 86 }

svcAtmConfigQSaalNumUdPduTx OBJECT-TYPE
	SYNTAX  Counter
	ACCESS  read-only
	STATUS  mandatory
	DESCRIPTION
		"The number of unnumbered user data PDU's transmitted on this port."
	::= { svcAtmConfigEntry 87 }

svcAtmConfigQSaalNumUdPduRx OBJECT-TYPE
	SYNTAX  Counter
	ACCESS  read-only
	STATUS  mandatory
	DESCRIPTION
		"The number of unnumbered user data PDU's received on this port."
	::= { svcAtmConfigEntry 88 }

svcAtmConfigQSaalNumMdPduTx OBJECT-TYPE
	SYNTAX  Counter
	ACCESS  read-only
	STATUS  mandatory
	DESCRIPTION
		"The number of unnumbered management data PDU's transmitted on this port."
	::= { svcAtmConfigEntry 89 }

svcAtmConfigQSaalNumMdPduRx OBJECT-TYPE
	SYNTAX  Counter
	ACCESS  read-only
	STATUS  mandatory
	DESCRIPTION
		"The number of unnumbered management data PDU's received on this port."
	::= { svcAtmConfigEntry 90 }


--
--  SVC ATM Failed Call Table
--

svcAtmFailedCallTable OBJECT-TYPE
	SYNTAX SEQUENCE OF SvcAtmFailedCallEntry
	ACCESS not-accessible
	STATUS mandatory
	DESCRIPTION
		"A table of objects describing the N most recent SVC failures per
		 port, in FIFO order."
	::= { svcmgt 3 }

svcAtmFailedCallEntry OBJECT-TYPE
	SYNTAX SvcAtmFailedCallEntry
	ACCESS not-accessible
	STATUS mandatory
	DESCRIPTION
		"The failed call entry contains objects relevant to abnormal SVC
	  	 call failures."
	INDEX { svcAtmFailedCallIfIndex, svcAtmFailedCallIndex }
	::= { svcAtmFailedCallTable 1 }

SvcAtmFailedCallEntry ::=
	SEQUENCE {
		svcAtmFailedCallIfIndex
			Index,
		svcAtmFailedCallIndex
			INTEGER,
		svcAtmFailedCallDirection
			INTEGER,
		svcAtmFailedCallPduType
			INTEGER,
		svcAtmFailedCallPduDirection
			INTEGER,
		svcAtmFailedCallCause
			INTEGER,
		svcAtmFailedCallLocation
			INTEGER,
		svcAtmFailedCallDiagnostic
			OCTET STRING,
		svcAtmFailedCallCreationTime
			TimeTicks,
		svcAtmFailedCallTerminationTime
			TimeTicks,
		svcAtmFailedCallFailureNodeId
			INTEGER,
		svcAtmFailedCallFailureIfIndex
			Index,
		svcAtmFailedCallCallingParty
			OCTET STRING,
		svcAtmFailedCallCalledParty
			OCTET STRING,
                svcAtmFailedCallAtmTfdType
                        INTEGER,
                svcAtmFailedCallAtmTfdParam1
                        INTEGER,
                svcAtmFailedCallAtmTfdParam2
                        INTEGER,
                svcAtmFailedCallAtmTfdParam3
                        INTEGER,
                svcAtmFailedCallAtmQosClass
                        INTEGER,
                svcAtmFailedCallAtmRTfdType
                        INTEGER,
                svcAtmFailedCallAtmRTfdParam1
                        INTEGER,
                svcAtmFailedCallAtmRTfdParam2
                        INTEGER,
                svcAtmFailedCallAtmRTfdParam3
                        INTEGER,
                svcAtmFailedCallAtmRQoSClass
                        INTEGER,
                svcAtmFailedCallBBearerClass
                        INTEGER,
                svcAtmFailedCallBBearerTfcType
                        INTEGER,
                svcAtmFailedCallBBearerTmgRqmt
                        INTEGER,
                svcAtmFailedCallBBearerUplaneCfg
                        INTEGER,
                svcAtmFailedCallBBearerClippingSusc
                        INTEGER,
		svcAtmFailedCallAdminStatus
			INTEGER
	}

svcAtmFailedCallIfIndex OBJECT-TYPE
	SYNTAX 	Index
	ACCESS	read-only
	STATUS	mandatory
	DESCRIPTION
		"The interface value of the corresponding MIB-II ifEntry for the
		 port at which this call failure was declared."
	::= { svcAtmFailedCallEntry 1 }

svcAtmFailedCallIndex OBJECT-TYPE
	SYNTAX 	INTEGER
	ACCESS	read-only
	STATUS	mandatory
	DESCRIPTION
		"The instance number for this failed call at this port."
	::= { svcAtmFailedCallEntry 2 }

svcAtmFailedCallDirection OBJECT-TYPE
	SYNTAX 	INTEGER {
		caller(1),
		callee(2)
	}
	ACCESS	read-only
	STATUS	mandatory
	DESCRIPTION
		"The direction of the failed call."
	::= { svcAtmFailedCallEntry 3 }

svcAtmFailedCallPduType OBJECT-TYPE
	SYNTAX 	INTEGER {
		release(1),
		addPartyReject(2),
		dropParty(3)
	}
	ACCESS	read-only
	STATUS	mandatory
	DESCRIPTION
		"The Pdu Type containing the cause IE."
	::= { svcAtmFailedCallEntry 4 }

svcAtmFailedCallPduDirection OBJECT-TYPE
	SYNTAX 	INTEGER {
		transmitted(1),
		received(2)
	}
	ACCESS	read-only
	STATUS	mandatory
	DESCRIPTION
		"Whether the terminating PDU was transmitted or received on this port."
	::= { svcAtmFailedCallEntry 5 }

svcAtmFailedCallCause OBJECT-TYPE
	SYNTAX 	INTEGER {
		unalloc-nmb		(1),	-- unallocated (unassigned) number 
		no-route-transnet	(2),	-- no route to transit network
		no-route-dest		(3),   	-- no route to destination 
		vcc-unacceptable-30	(10), 	-- UNI 3.0: VPCI/VCI unacceptable
		normal-call-clr-31	(16),  	-- UNI 3.1: normal call clearing
		user-busy		(17),  	-- user busy
		no-user-response	(18),  	-- no user response
		call-reject		(21),  	-- call rejected
		nmb-changed		(22),  	-- number changed
		call-reject-clir	(23),  	-- user rejects all calls with CLIR
		dest-out-of-order	(27),  	-- destination out of order
		invalid-nmb-format	(28),  	-- invalid number format
		response-stat-enq	(30),  	-- response to STATUS ENQUIRY
		normal-unspecified	(31),  	-- normal unspecified
		req-vcc-unavailable	(35),  	-- requested VPCI/VCI unavailable
		vcc-fail-31		(36),  	-- UNI 3.1: VPCI/VCI assignment failure
		rate-unavail-31		(37),  	-- UNI 3.1: user cell rate unavailable
		network-out-of-order	(38),  	-- network out of order
		temp-fail		(41),  	-- Temporary failure
		access-info-discard	(43),	-- access info discarded
		no-vcc-available	(45),   -- no VPCI/VCI unavailable
		resources-unavailable	(47),   -- resources unavailable, unspecified
		qos-unavailable		(49),   -- Quality of Service unavailable
		rate-unavailable-30 	(51),   -- UNI 3.0: user cell rate unavailable
		b-cap-not-authorized 	(57),   -- bearer capability not authorized
		b-cap-unavailable 	(58),   -- bearer capability not available
		service-unavailable 	(63),   -- Service or option unavailable
		b-cap-not-implemented 	(65),   -- bearer capability not implemented
		combination-unsupported	(73),   -- unsupported comb. of traffic parameters
		aal-params-unsupp-31 	(78),   -- UNI 3.1: AAL paramteres cannot be supported
		invalid-call-reference 	(81),   -- invalid call reference
		no-channel	 	(82),   -- identified channel does not exist
		dest-incompatible 	(88),   -- incompatible destination
		invalid-endpoint-ref 	(89),   -- invalid endpoint reference
		invalid-transit-net 	(91),   -- invalid transit network selection
		too-many-add-pty-req 	(92),   -- too many add party requests
		aal-params-unsupp-30 	(93),   -- UNI 3.0:AAL paramteres cannot be supported
		info-element-missing 	(96),   -- mandatory info element is missing
		msg-type-not-imp 	(97),   -- message type not implemented
		info-element-not-imp 	(99),   -- info element not implemented
		invalid-info-element 	(100),  -- invalid info element
		message-not-compatible 	(101),  -- msg type not compatible with call st
		timer-recovery		(102),  -- recovery on timer expiry
		invalid-message-len 	(104),  -- incorrect message length
		protocol-error		(111),  -- protocol error, unspecified
		optional-element-error 	(127)	-- opt info el content error (non-std)
	}
	ACCESS	read-only
	STATUS	mandatory
	DESCRIPTION
		"The failure cause contained in the cause IE."
	::= { svcAtmFailedCallEntry 6 }

svcAtmFailedCallLocation OBJECT-TYPE
	SYNTAX 	INTEGER {
		user (1),		-- user
		privNetServLocal (2),	-- private network serving local user
		pubNetServLocal (3),	-- public network serving local user
		transitNet (4),		-- transit network
		pubNetServRemote (5),	-- public network serving remote user
		privNetServRemote (6),	-- private network serving remote user
		intlNet (7),		-- international network
		netBeyondInterwkPt (8)	-- network beyond interworking point
	}
	ACCESS	read-only
	STATUS	mandatory
	DESCRIPTION
		"The failure location contained in the cause IE."
	::= { svcAtmFailedCallEntry 7 }

svcAtmFailedCallDiagnostic OBJECT-TYPE
 	SYNTAX  OCTET STRING
 	ACCESS  read-only
 	STATUS  mandatory
 	DESCRIPTION
		"The diagnostic information contained in the cause IE."
	::= { svcAtmFailedCallEntry 8 }

svcAtmFailedCallCreationTime OBJECT-TYPE
 	SYNTAX  TimeTicks
 	ACCESS  read-only
 	STATUS  mandatory
 	DESCRIPTION
		"The sysUpTime when this call was initiated."
	::= { svcAtmFailedCallEntry 9 }

svcAtmFailedCallTerminationTime OBJECT-TYPE
 	SYNTAX  TimeTicks
 	ACCESS  read-only
 	STATUS  mandatory
 	DESCRIPTION
		"The sysUpTime when this call was terminated."
	::= { svcAtmFailedCallEntry 10 }

svcAtmFailedCallFailureNodeId OBJECT-TYPE
 	SYNTAX  INTEGER
 	ACCESS  read-only
 	STATUS  mandatory
 	DESCRIPTION
		"The node which caused the SVC failure."
	::= { svcAtmFailedCallEntry 11 }

svcAtmFailedCallFailureIfIndex OBJECT-TYPE
 	SYNTAX  Index
 	ACCESS  read-only
 	STATUS  mandatory
 	DESCRIPTION
		"The port on the failure node which caused the SVC failure."
	::= { svcAtmFailedCallEntry 12 }

svcAtmFailedCallCallingParty OBJECT-TYPE
        SYNTAX  OCTET STRING
        ACCESS  read-only
        STATUS  mandatory
        DESCRIPTION
                "The calling party number for this failed call, if present."
        ::= { svcAtmFailedCallEntry 13 }

svcAtmFailedCallCalledParty OBJECT-TYPE
        SYNTAX  OCTET STRING
        ACCESS  read-only
        STATUS  mandatory
        DESCRIPTION
                "The called party number for this failed call."
        ::= { svcAtmFailedCallEntry 14 }

svcAtmFailedCallAtmTfdType OBJECT-TYPE
	SYNTAX INTEGER {
		pcr-0-01 (1),
		pcr-0-01-tag (2),
		pcr-01-scr-0-mbs-0 (3),
		pcr-01-scr-0-mbs-0-tag (4),
		pcr-01 (5),
		pcr-01-scr-01-mbs-01 (6),
		pcr-01-bestEffort (7), 
		unknown (8)
	}
 	ACCESS	read-only
 	STATUS	mandatory
 	DESCRIPTION
		"The combination of forward traffic parameters for this failed call." 
	::= { svcAtmFailedCallEntry 15 }

svcAtmFailedCallAtmTfdParam1 OBJECT-TYPE
 	SYNTAX	INTEGER
 	ACCESS	read-only
 	STATUS	mandatory
 	DESCRIPTION
		"Forward traffic descriptor parameter 1 for this failed call."
	::= { svcAtmFailedCallEntry 16 }

svcAtmFailedCallAtmTfdParam2 OBJECT-TYPE
 	SYNTAX	INTEGER
 	ACCESS	read-only
 	STATUS	mandatory
 	DESCRIPTION
		"Forward traffic descriptor parameter 2 for this failed call."
	::= { svcAtmFailedCallEntry 17 }

svcAtmFailedCallAtmTfdParam3 OBJECT-TYPE
 	SYNTAX	INTEGER
 	ACCESS	read-only
 	STATUS	mandatory
 	DESCRIPTION
		"Forward traffic descriptor parameter 3 for this failed call."
	::= { svcAtmFailedCallEntry 18 }

svcAtmFailedCallAtmQosClass OBJECT-TYPE
 	SYNTAX	INTEGER
 	ACCESS	read-only
 	STATUS	mandatory
 	DESCRIPTION
		"Forward QOS class for this failed call."
	::= { svcAtmFailedCallEntry 19 }

svcAtmFailedCallAtmRTfdType OBJECT-TYPE
	SYNTAX INTEGER {
		pcr-0-01 (1),
		pcr-0-01-tag (2),
		pcr-01-scr-0-mbs-0 (3),
		pcr-01-scr-0-mbs-0-tag (4),
		pcr-01 (5),
		pcr-01-scr-01-mbs-01 (6),
		pcr-01-bestEffort (7),
		unknown (8)
	}
 	ACCESS	read-only
 	STATUS	mandatory
 	DESCRIPTION
		"The combination of reverse traffic parameters for this failed call." 
	::= { svcAtmFailedCallEntry 20 }

svcAtmFailedCallAtmRTfdParam1 OBJECT-TYPE
 	SYNTAX	INTEGER
 	ACCESS	read-only
 	STATUS	mandatory
 	DESCRIPTION
		"Reverse traffic descriptor parameter 1 for this failed call."
	::= { svcAtmFailedCallEntry 21 }

svcAtmFailedCallAtmRTfdParam2 OBJECT-TYPE
 	SYNTAX	INTEGER
 	ACCESS	read-only
 	STATUS	mandatory
 	DESCRIPTION
		"Reverse traffic descriptor parameter 2 for this failed call."
	::= { svcAtmFailedCallEntry 22 }

svcAtmFailedCallAtmRTfdParam3 OBJECT-TYPE
 	SYNTAX	INTEGER
 	ACCESS	read-only
 	STATUS	mandatory
 	DESCRIPTION
		"Reverse traffic descriptor parameter 3 for this failed call."
	::= { svcAtmFailedCallEntry 23 }

svcAtmFailedCallAtmRQoSClass OBJECT-TYPE
 	SYNTAX	INTEGER
 	ACCESS	read-only
 	STATUS	mandatory
 	DESCRIPTION
		"Reverse QOS class for this failed call."
	::= { svcAtmFailedCallEntry 24 }

svcAtmFailedCallBBearerClass OBJECT-TYPE
 	SYNTAX	INTEGER {
		class-A(1),
		class-C(3),
		class-X(16)
	}
 	ACCESS	read-only
 	STATUS	mandatory
 	DESCRIPTION
		"Broadband bearer class for this failed call."
	::= { svcAtmFailedCallEntry 25 }

svcAtmFailedCallBBearerTfcType OBJECT-TYPE
 	SYNTAX	INTEGER {
		notIndicated(1),
		cbr(2),
		vbr(3)
	}
 	ACCESS	read-only
 	STATUS	mandatory
 	DESCRIPTION
		"Broadband bearer traffic type for this failed call."
	::= { svcAtmFailedCallEntry 26 }

svcAtmFailedCallBBearerTmgRqmt OBJECT-TYPE
 	SYNTAX	INTEGER {
		notIndicated(1),
		required(2),
		not-required(3)
	}
 	ACCESS	read-only
 	STATUS	mandatory
 	DESCRIPTION
		"Broadband bearer timing requirement for this failed call."
	::= { svcAtmFailedCallEntry 27 }

svcAtmFailedCallBBearerUplaneCfg OBJECT-TYPE
 	SYNTAX	INTEGER {
		point-point(1),
		point-multipoint(2)
	}
 	ACCESS	read-only
 	STATUS	mandatory
 	DESCRIPTION
		"Broadband bearer user plane configuration for this failed call."
	::= { svcAtmFailedCallEntry 28 }

svcAtmFailedCallBBearerClippingSusc OBJECT-TYPE
 	SYNTAX	INTEGER {
		not-susceptible(1),
		susceptible(2)
	}
 	ACCESS	read-only
 	STATUS	mandatory
 	DESCRIPTION
		"Broadband bearer clipping susceptability for this failed call."
	::= { svcAtmFailedCallEntry 29 }

svcAtmFailedCallAdminStatus OBJECT-TYPE
 	SYNTAX	INTEGER {
		valid (1),	-- entry is valid
		invalid (2)	-- entry is invalid
	}
 	ACCESS	read-only
 	STATUS	mandatory
 	DESCRIPTION
		"All entries are initially invalid.  Due to the FIFO nature of this
		 table, once N entries have been created, all entries will always
		 be valid."
	::= { svcAtmFailedCallEntry 30 }


--
--  The Software Group
--
--  The variables that describe the software running on a particular card.
--


swTable  OBJECT-TYPE
	SYNTAX	SEQUENCE OF SwEntry    
	ACCESS  not-accessible
	STATUS  mandatory
	DESCRIPTION
		"A list of swEntry's. The number of entries is given by the value of
		swCardNumber"
	::= { software 1 }

swEntry  OBJECT-TYPE
	SYNTAX  SwEntry    
	ACCESS  not-accessible
	STATUS  mandatory
	DESCRIPTION
		"The software entry contains objects describing the software  
		cards."
	INDEX	    { swLogicalSlotId, swRedundState }
	::= { swTable 1 }

SwEntry  ::=
	SEQUENCE {
		swLogicalSlotId
			INTEGER,
		swRedundState
			INTEGER,
		swRevision
			DisplayString,
		swBuildID
			DisplayString,
		swBuildDate
			DisplayString,
		swBuildDescription
			DisplayString,
		swCopyrightNotice
			DisplayString,
		swCapabilityMask
			INTEGER,
		swFeatureMask
			INTEGER,
		swPatchMask
			INTEGER,
		swBuildUserId
			DisplayString,
		swBuildView
			DisplayString,
		swBuildConfigSpec
			DisplayString
	}

swLogicalSlotId OBJECT-TYPE
	SYNTAX  INTEGER
	ACCESS  read-only
	STATUS  mandatory
	DESCRIPTION
		"The logical slot number of this card. This is used as an index for
		the swTable. In redundant configurations, this can be the physical
		slot number of either redundant card. In non redundant
		configurations, this is the same as cardPhysicalSlotId."
	::= { swEntry 1}

swRedundState OBJECT-TYPE
	SYNTAX  INTEGER {
			active (1),
			standby (2)
		    }
	ACCESS  read-only
	STATUS  mandatory
	DESCRIPTION
		"The current redundancy state of this card."
	::= { swEntry 2 }

swRevision OBJECT-TYPE
	SYNTAX	DisplayString
	ACCESS	read-only
	STATUS	mandatory
	DESCRIPTION
		"The software revision number in the form (major.minor.maint.patch)
		where major == the major release number
		      minor == the minor release number
		      maint == a maintenance release based on major.minor
		      patch == a patch release based on major.minor.maint"
	::= { swEntry 3 }
swBuildID OBJECT-TYPE
	SYNTAX	DisplayString
	ACCESS	read-only
	STATUS	mandatory
	DESCRIPTION
		"An identifier which uniquely identifies the software image within
		the scope of the release.  The build ID is generated automatically 
		through the build process and assigned to the software image during 
		the final load generation."
	::= { swEntry 4 }

swBuildDate OBJECT-TYPE
	SYNTAX	DisplayString
	ACCESS	read-only
	STATUS	mandatory
	DESCRIPTION
		"The date on which the software image was generated."
	::= { swEntry 5 }

swBuildDescription OBJECT-TYPE
	SYNTAX	DisplayString
	ACCESS	read-only
	STATUS	mandatory
	DESCRIPTION
		"A general description of the release."
	::= { swEntry 6 }

swCopyrightNotice OBJECT-TYPE
	SYNTAX	DisplayString
	ACCESS	read-only
	STATUS	mandatory
	DESCRIPTION
		"Legalese describing the Copyrights covering this software
		image."
	::= { swEntry 7 }

swCapabilityMask OBJECT-TYPE
	SYNTAX	INTEGER
	ACCESS	read-only
	STATUS	mandatory
	DESCRIPTION
		"A 32-bit integer which bitmaps optional or additional features
		supported by this software release.  For use by the NMS in
		determining capabilities of the software.  The significance of
		this bitmap varies by release.  For Cascade internal use."
	::= { swEntry 8 }

swFeatureMask OBJECT-TYPE
	SYNTAX	INTEGER
	ACCESS	read-only
	STATUS	mandatory
	DESCRIPTION
		"A 32-bit integer which bitmaps optional or additional features
		supported by this software release.  For use by the NMS in
		determining capabilities of the software.  The significance of
		this bitmap varies by release.  For Cascade internal use."
	::= { swEntry 9 }

swPatchMask OBJECT-TYPE
	SYNTAX	INTEGER
	ACCESS	read-only
	STATUS	mandatory
	DESCRIPTION
		"A 32-bit integer which bitmaps incremental patches which have
		been applied to the software release.  The significance of
		this bitmap varies by release.  For Cascade internal use."
	::= { swEntry 10 }

swBuildUserId OBJECT-TYPE
	SYNTAX	DisplayString
	ACCESS	read-only
	STATUS	mandatory
	DESCRIPTION
		"The user ID of the person responsible for generating the software
		image. For Cascade internal use."
	::= { swEntry 11 }

swBuildView OBJECT-TYPE
	SYNTAX	DisplayString
	ACCESS	read-only
	STATUS	mandatory
	DESCRIPTION
		"Source control information for image generation.  For Cascade
		internal use."
	::= { swEntry 12 }

swBuildConfigSpec OBJECT-TYPE
	SYNTAX	DisplayString
	ACCESS	read-only
	STATUS	mandatory
	DESCRIPTION
		"Source control information for image generation.  For Cascade
		internal use."
	::= { swEntry 13 }


--	The Traps Group
--
--	Definitions for Cascade Frame Relay Specific Traps.
--

nodeBoardInserted TRAP-TYPE
	ENTERPRISE cascfr
	VARIABLES  { pportSlotId, pportType }
	DESCRIPTION
		"This trap indicates that a board has been inserted into
		the indicated slot."
	::= 1

nodeBoardPulled TRAP-TYPE
	ENTERPRISE cascfr
	VARIABLES  { pportSlotId, pportType }
	DESCRIPTION
		"This trap indicates that a board has been pulled out from
		the indicated slot."
	::= 2

nodeBoardMismatch TRAP-TYPE
	ENTERPRISE cascfr
	VARIABLES  { pportSlotId, pportType }
	DESCRIPTION
		"This trap indicates that the actual board type on the
		indicated slot is inconsistent with what is configured."
	::= 3

nodePsAStatusChange TRAP-TYPE
	ENTERPRISE cascfr
	VARIABLES  { nodePsAStatus }
	DESCRIPTION
		"This trap indicates that the power supply A has changed state
		(toggled between up and down states)."
	::= 4

nodePsBStatusChange TRAP-TYPE
	ENTERPRISE cascfr
	VARIABLES  { nodePsBStatus }
	DESCRIPTION
		"This trap indicates that the power supply B has changed state
		(toggled between up and down states)."
	::= 5

nodeFanStatusChange TRAP-TYPE
	ENTERPRISE cascfr
	VARIABLES  { nodeFanIndex, nodeFanStatus }
	DESCRIPTION
		"This trap indicates that a fan has changed state 
		(toggled between up and down states)."
	::= 6

nodeSwDownloadComplete TRAP-TYPE
	ENTERPRISE cascfr
	VARIABLES { nodeSwFilename }
	DESCRIPTION
		"This trap indicates that a software download was complete."
	::= 7

nodeSwDownloadFailed TRAP-TYPE
	ENTERPRISE cascfr
	VARIABLES { nodeSwFilename }
	DESCRIPTION
		"This trap indicates that a software download failed."
	::= 8

nodePrDownloadComplete TRAP-TYPE
	ENTERPRISE cascfr
	VARIABLES { nodePrFilename }
	DESCRIPTION
		"This trap indicates that a PRAM download was complete."
	::= 9

nodePrDownloadFailed TRAP-TYPE
	ENTERPRISE cascfr
	VARIABLES { nodePrFilename }
	DESCRIPTION
		"This trap indicates that a PRAM download failed."
	::= 10

nodeTracefull TRAP-TYPE
	ENTERPRISE cascfr
	DESCRIPTION
		"This trap indicates that the node trace table was full and 
		has been copied to a TFTP buffer awaiting to be xfered to the
		NMS."
	::= 11

nodeDiagLogfull TRAP-TYPE
	ENTERPRISE cascfr
	DESCRIPTION
		"This trap indicates that the diagnostic log table was full 
		and has been copied to a TFTP buffer awaiting to be xfered to 
		the NMS."
	::= 12

nodeFlashMemErr TRAP-TYPE
	ENTERPRISE cascfr
	DESCRIPTION
		"This trap indicates that a checksum or CRC-32 error occurred
		in Flash."
	::= 13

nodePramErr TRAP-TYPE
	ENTERPRISE cascfr
	DESCRIPTION
		"This trap indicates that a checksum error or battery problem
		occurred in PRAM."
	::= 14

nodeRamErr TRAP-TYPE
	ENTERPRISE cascfr
	DESCRIPTION
		"This trap indicates that an I/O error occurred in DRAM or
		SRAM."
	::= 15

nodeInternalErr TRAP-TYPE
	ENTERPRISE cascfr
	DESCRIPTION
		"This trap indicates that a fatal internal hardware or software
		error encountered and system needs to be re-booted."
	::= 16

pportStatusChange TRAP-TYPE
	ENTERPRISE cascfr
	VARIABLES { pportSlotId, pportId, pportOperStatus, pportLinkDownReason }
	DESCRIPTION 
		"This trap indicates that the indicated physical port has
		changed state."
	::= 17

lportCongests TRAP-TYPE
	ENTERPRISE cascfr
	VARIABLES { lportIfIndex, lportCongestRate }
	DESCRIPTION 
		"This trap indicates that the rate of entering severely and
		absolutely congested state on the indicated logical port 
		has exceeded the threshold."
	::= 18

trkStatusChange TRAP-TYPE
	ENTERPRISE cascfr
	VARIABLES { lportIfIndex, lportSlotId, lportPportId, lportId, lportTrkStatus }
	DESCRIPTION 
		"This trap indicates that the trunk associated with the
		indicated logical port has changed state."
	::= 19

cktDlciStatusChange TRAP-TYPE
	ENTERPRISE cascfr
	VARIABLES  { cktSrcIfIndex, cktSrcDlci, cktOperStatus, cktFailReason, cktFailNode, cktFailPort }
	DESCRIPTION
		"This trap indicates that the user-to-user PVC state has been
		changed for this virtual circuit. It has either been created
		or invalidated, or has toggled between the active and inactive
		states."
	::= 20

cktDlciReroute TRAP-TYPE
	ENTERPRISE cascfr
	VARIABLES  { cktSrcIfIndex, cktSrcDlci }
	DESCRIPTION
		"This trap indicates that a PVC has been re-routed."
	::= 21

pportInterfaceMismatch TRAP-TYPE
	ENTERPRISE cascfr
	VARIABLES  { pportSlotId, pportId, pportAdminInterface, pportInterface }
	DESCRIPTION
		"This trap indicates the actual physical interface is
		different than the configured physical interface."
	::= 22

lportErrorExceedThreshold TRAP-TYPE
	ENTERPRISE cascfr
	VARIABLES  { lportIfIndex, ifInErrors }
	DESCRIPTION
		"This trap indicates the frame errors per minute on this
		lport exceeded the threshold."
	::= 23

nodeErrorReport TRAP-TYPE
	ENTERPRISE cascfr
	VARIABLES  { nodeDiagNonFatalSource, nodeDiagNonFatalTime, nodeDiagNonFatalErrMajor, nodeDiagNonFatalErrMinor, nodeDiagNonFatalStr }
	DESCRIPTION
		"A component in the switch discovered a non-fatal error
		condition."
	::= 24

cktGrpStatusChange TRAP-TYPE
	ENTERPRISE cascfr
	VARIABLES  { cardCktGroupTrap }
	DESCRIPTION
		"Circuits on interfaces go up or down."
	::= 25

nodeUserLogin TRAP-TYPE
	ENTERPRISE cascfr
	VARIABLES  { nodeConsoleIndex, nodeUserName, nodeUserFrom, nodeConsoleUptime }
	DESCRIPTION
		"An user has logged in STDX through either serial console or telnet."
	::= 26

nodeUserLogout TRAP-TYPE
	ENTERPRISE cascfr
	VARIABLES  { nodeConsoleIndex, nodeUserName, nodeUserFrom, nodeConsoleUptime }
	DESCRIPTION
		"An user has logged out."
	::= 27

cardUp TRAP-TYPE
	ENTERPRISE cascfr
	VARIABLES  { cardPhysicalSlotId }
	DESCRIPTION
		"This trap indicates that an intelligent card has transitioned
		to an ACTIVE state."
	::= 28

cardDown TRAP-TYPE
	ENTERPRISE cascfr
	VARIABLES  { cardPhysicalSlotId }
	DESCRIPTION
		"This trap indicates that an intelligent card has transitioned
		to a NON-ACTIVE state."
	::= 29

lnkStatusChange TRAP-TYPE
	ENTERPRISE cascfr
	VARIABLES { lportIfIndex, lportSlotId, lportPportId, lportId, lportLinkStatus}
	DESCRIPTION 
		"This trap indicates that the link status (Link protocol)
                 associated with the indicated logical port has changed state."
	::= 30

lnkSmdsHbpNaTca TRAP-TYPE
	ENTERPRISE cascfr
	VARIABLES { lportIfIndex, lportSlotId, lportPportId, lportId }
	DESCRIPTION 
		"This trap indicates that non-Ack count for SMDS DXI heartbeat
		 poll exceedes the threshold. The non-Ack count is reset every
		 15 minutes."
	::= 31

lnkSmdsDiscardTca TRAP-TYPE
	ENTERPRISE cascfr
	VARIABLES { lportIfIndex, lportSlotId, lportPportId, lportId }
	DESCRIPTION 
		"This trap indicates that Total Discard packet count for SMDS 
		packet exceedes the threshold. ( This trap has not been implemented 
		in this release yet )."
	::= 32

cardRedundSwitchOver TRAP-TYPE
	ENTERPRISE cascfr
	VARIABLES { cardPhysicalSlotId }
	DESCRIPTION 
		"This trap indicates that the card in the specified slot has shot its 
		active partner and has become the active card of the pair."
	::= 33

cardErrorReport TRAP-TYPE
	ENTERPRISE cascfr
	VARIABLES  { cardDiagNonFatalSource, cardDiagNonFatalTime, cardDiagNonFatalErrMajor,
		     cardDiagNonFatalErrMinor, cardDiagNonFatalStr, cardPhysicalSlotId }
	DESCRIPTION
		"The specified card discovered a non-fatal error condition."
	::= 34

svcSetup TRAP-TYPE
        ENTERPRISE cascfr
        VARIABLES  { cktSrcIfIndex, cktSrcDlci, cktSvcCallingParty,
		     cktSvcCalledParty }
        DESCRIPTION
                "This trap is generated by the ingress switch whenever a Frame
		 Relay Svc is setup or cleared. cktStatus indicates whether it is 
		 a setup or a clearing."
        ::= 35

svcClearing TRAP-TYPE
        ENTERPRISE cascfr
        DESCRIPTION
                "Reserved for Frame Relay SVC."
        ::= 36

svcFailure TRAP-TYPE
        ENTERPRISE cascfr
        VARIABLES  { cktSvcCallingParty, cktSvcCalledParty, cktSvcCause }
        DESCRIPTION
                "This trap is generated by the ingress switch whenever a Frame Relay
		 svc setup fails. cktSvcCause contains the cause number."
        ::= 37

trkBuAttempt TRAP-TYPE
	ENTERPRISE cascfr
	VARIABLES { lportIfIndex, lportSlotId, lportPportId, lportId }
	DESCRIPTION 
		"This trap indicates that an attempt to establish the backup 
		 trunk associated with the indicated logical port is being
		 made."
	::= 38


trkBuFailure TRAP-TYPE
	ENTERPRISE cascfr
	VARIABLES { lportIfIndex, lportSlotId, lportPportId, lportId, 
		    lportBuFailReason }
	DESCRIPTION 
		"This trap indicates that the primary trunk associated 
		 with the indicated logical port has not been backed
		 up or the backup trunk associated with the indicated 
		 logical port has not been restored.  The reason for 
		 failure is provided.  The lportBuFailReason indicates 
		 the trunk type as follows:

		   lportBuFailReson		Trunk Type
		     buTrkNotDef		  primary trunk
		     buTrkNotEstab		  backup trunk"
	::= 39


trkBuReleased TRAP-TYPE
	ENTERPRISE cascfr
	VARIABLES { lportIfIndex, lportSlotId, lportPportId, lportId }
	DESCRIPTION 
		"This trap indicates that the backup trunk associated with the
		 indicated logical port has been released."
	::= 40

pportDS0LoopUpChange TRAP-TYPE
        ENTERPRISE cascfr
        VARIABLES  { pportSlotId, pportId, pportDS0LoopUpStatus }
        DESCRIPTION
                "This trap indicates one or more DS0's have gone into 
            loopback.pportDS0LoopUpStatus reports the DS0's that have
            gone into loopback."
        ::= 41

pportDS0LoopDownChange TRAP-TYPE
        ENTERPRISE cascfr
        VARIABLES  { pportSlotId, pportId, pportDS0LoopDownStatus }
        DESCRIPTION
                "This trap indicates one or more DS0's have gone out of 
            loopback.pportDS0LoopDownStatus reports the DS0's that have
            gone out of loopback."
        ::= 42

lportISDNCallRej TRAP-TYPE
        ENTERPRISE cascfr
        VARIABLES  { lportIfIndex, lportISDNCallRejCause }
        DESCRIPTION
                "This trap indicates that a call has been rejected due  
		either the inability to authenticate the call or lack of
		B-channel pool resources."
        ::= 43

pportdsx3LoopChange TRAP-TYPE
        ENTERPRISE cascfr
        VARIABLES { pportSlotId, pportId, pportdsx3LoopStatus }
        DESCRIPTION
                "This trap indicates when the DS3 or E3 has changed its current
                 loopback state."
        ::= 44

pportds1LoopChange TRAP-TYPE
        ENTERPRISE cascfr
        VARIABLES { pportSlotId, pportId, pportds1LoopStatus }
        DESCRIPTION
                "This trap indicates when the DS1 has changed its current
                 loopback state."
        ::= 45


pportExtClockBackup TRAP-TYPE
        ENTERPRISE cascfr
        VARIABLES { pportSlotId, pportId, pportSetClkBkup }
        DESCRIPTION
                "This trap indicates that a pport has lost the external clock
                 source and is switching over to the backup clock selected."
        ::= 46


pportExtClockRestore TRAP-TYPE
        ENTERPRISE cascfr
        VARIABLES { pportSlotId, pportId }
        DESCRIPTION
                "This trap indicates that external clock is recovered and the
                pport will switch back to external clock."
        ::= 47

pportExtClkCapabilityMismatch TRAP-TYPE
        ENTERPRISE cascfr
        VARIABLES { pportSlotId, pportId }
        DESCRIPTION
                "This trap indicates the port on this card (and the card
                 itself) is not capable of running external clock."
        ::= 48

nodeFileTransferReport TRAP-TYPE
        ENTERPRISE cascade
        VARIABLES  { nodeFileTransferRequest, nodeFileTransferStatus }
        DESCRIPTION
             "Reporting the outcome of a previous file transfer request.
              nodeFileTransferRequest specifies the request and
              nodeFileTransferStatus gives the outcome."
        ::= 49

nodeBillingUsageRecOvflWarning TRAP-TYPE
	ENTERPRISE cascfr
	VARIABLES { nodeBillingService }
	DESCRIPTION 
		"Warning that a usage record counter-value overflow condition
		has occurred while aggregating usage data recently collected
		from one or more IOPs. An overflow condition exists when an 
		attempt was made to update a usage record counter, but such an 
		update would have overflowed the counter.  In this case, the 
		usage record is closed and a new one is opened, if there is 
		sufficient space in the service's aggregated usage data store.
		"
	::= 50

nodeBillingUsageRecCrFailed TRAP-TYPE
	ENTERPRISE cascfr
	VARIABLES { nodeBillingService }
	DESCRIPTION 
		"Notification that a usage record could not be created."
	::= 51

nodeBillingStateChange TRAP-TYPE
	ENTERPRISE cascfr
	VARIABLES { nodeBillingService, nodeBilling }
	DESCRIPTION 
		"Notification that billing has been enabled or disabled on the
		switch. This trap is generated at switch boot or when the 
		value of the nodeBilling object is modified."
	::= 52

lportBillingStateChange TRAP-TYPE
	ENTERPRISE cascfr
	VARIABLES { nodeBillingService, lportBilling, lportIfIndex, 
		    lportSlotId, lportPportId, lportId }
	DESCRIPTION 
		"Notification that billing has been enabled or disabled on a 
		particular logical port.  This trap is generated the value of 
		the lportBilling is modified for a particular port;  this trap
		IS NOT generated when the global nodeBilling is modified or 
		when at switch boot."
	::= 53

nodeBillingSwAPCommsFailure TRAP-TYPE
	ENTERPRISE cascfr
	VARIABLES { nodeBillingAPAddress }
	DESCRIPTION 
		"
		Notification that switch to Adjunct Processor communication 
		has failed and that a usage file transfer has failed to 
		complete.
		"
	::= 54

svcAtmFailedCall TRAP-TYPE
	ENTERPRISE cascsvc
	VARIABLES { svcAtmFailedCallIfIndex, svcAtmFailedCallIndex }
	DESCRIPTION 
		"Notification that one or more SVC call failures have been logged
		 in the svcAtmFailedCallTable."
	::= 55

svcAtmSigStatusChange TRAP-TYPE
	ENTERPRISE cascsvc
	VARIABLES { svcAtmConfigIfIndex, svcAtmConfigOperStatus }
	DESCRIPTION 
		"Notification that the status of the ATM signalling function
		 has changed on the port."
	::= 56

lportCBRLineDataError TRAP-TYPE
	ENTERPRISE      cascfr
	VARIABLES       { lportIfIndex, lportSlotId, lportPportId, lportId,
			lportStarvation, lportRecOverflow, lportLossOfCellSequence,
			lportLossOfStructurePointer }
	DESCRIPTION
		"This trap indicates the error state of the CBR lport."
	::= 57

clkSourceSwitch TRAP-TYPE
	ENTERPRISE      cascfr
	VARIABLES       { pportSlotId, pportId, pportCbrCurrentClockMode }
	DESCRIPTION
		"This trap indicates that the CBR port switched its clock method."
	::= 58

clkSourceFailure TRAP-TYPE
	ENTERPRISE      cascfr
	VARIABLES       { pportSlotId, pportId, nodeRefclockActiveSrc }
	DESCRIPTION
		"This trap indicates that the clock generation unit switched
		 between holdover mode and synchronization to reference clock."
	::= 59


lportSmdsSip3SaNotFoundTca TRAP-TYPE
	ENTERPRISE cascfr
	VARIABLES { lportIfIndex, lportSlotId, lportPportId, lportId }
	DESCRIPTION 
		"This trap indicates that the number of Sa Not Found 
		violations exceeded the specified Smds pdu violation
		threshold for the logical port.
		"
	::= 60 

lportSmdsSip3SaDaOnSamePortTca TRAP-TYPE
	ENTERPRISE cascfr
	VARIABLES { lportIfIndex, lportSlotId, lportPportId, lportId }
	DESCRIPTION 
		"This trap indicates that the number of Sa Da On Same Port 
		violations exceeded the specified Smds pdu violation
		threshold for the logical port.
		"
	::= 61 

lportSmdsSip3DstGaNotFoundTca TRAP-TYPE
	ENTERPRISE cascfr
	VARIABLES { lportIfIndex, lportSlotId, lportPportId, lportId }
	DESCRIPTION 
		"This trap indicates that the number of Dst Ga Not Found 
		violations exceeded the specified Smds pdu violation
		threshold for the logical port.
		"
	::= 62 

lportSmdsSip3DstIaScrnFailTca TRAP-TYPE
	ENTERPRISE cascfr
	VARIABLES { lportIfIndex, lportSlotId, lportPportId, lportId }
	DESCRIPTION 
		"This trap indicates that the number of Dst Ia Scrn Fail 
		violations exceeded the specified Smds pdu violation
		threshold for the logical port.
		"
	::= 63 

lportSmdsSip3SaValFailTca TRAP-TYPE
	ENTERPRISE cascfr
	VARIABLES { lportIfIndex, lportSlotId, lportPportId, lportId }
	DESCRIPTION 
		"This trap indicates that the number of Sa Val Fail 
		violations exceeded the specified Smds pdu violation
		threshold for the logical port.
		"
	::= 64 

lportSmdsSip3DstIaNotFoundTca TRAP-TYPE
	ENTERPRISE cascfr
	VARIABLES { lportIfIndex, lportSlotId, lportPportId, lportId }
	DESCRIPTION 
		"This trap indicates that the number of Dst Ia Not Found 
		violations exceeded the specified Smds pdu violation
		threshold for the logical port.
		"
	::= 65 

lportSmdsSip3SrcIaScrnFailTca TRAP-TYPE
	ENTERPRISE cascfr
	VARIABLES { lportIfIndex, lportSlotId, lportPportId, lportId }
	DESCRIPTION 
		"This trap indicates that the number of Src Ia Scrn Fail 
		violations exceeded the specified Smds pdu violation
		threshold for the logical port.
		"
	::= 66 

lportSmdsSip3DstGaScrnFailTca TRAP-TYPE
	ENTERPRISE cascfr
	VARIABLES { lportIfIndex, lportSlotId, lportPportId, lportId }
	DESCRIPTION 
		"This trap indicates that the number of Dst Ga Scrn Fail 
		violations exceeded the specified Smds pdu violation
		threshold for the logical port.
		"
	::= 67 

lportSmdsDxi2LinkIdInvalidTca TRAP-TYPE
	ENTERPRISE cascfr
	VARIABLES { lportIfIndex, lportSlotId, lportPportId, lportId }
	DESCRIPTION 
		"This trap indicates that the number of Link Id Invalid 
		violations exceeded the specified Smds pdu violation
		threshold for the logical port.
		"
	::= 68 

nodePrimarySyncReferenceChange TRAP-TYPE
	ENTERPRISE cascfr
	VARIABLES { nodePrimarySyncRefOperationalState }
	DESCRIPTION
		"Notification that the Primary Synchronization Reference
		 operational state has changed."
	::= 69

nodeSecondarySyncReferenceChange TRAP-TYPE
	ENTERPRISE cascfr
	VARIABLES { nodeSecondarySyncRefOperationalState }
	DESCRIPTION
		"Notification that the Secondary Synchronization Reference
		 operational state has changed."
	::= 70

nodeExternalClockAChange TRAP-TYPE
	ENTERPRISE cascfr
	VARIABLES { nodeExternalClockAOperationalState }
	DESCRIPTION
		"Notification that the External Reference Clock A
		 operational state has changed."
	::= 71

nodeExternalClockBChange TRAP-TYPE
	ENTERPRISE cascfr
	VARIABLES { nodeExternalClockBOperationalState }
	DESCRIPTION
		"Notification that the External Reference Clock B
		 operational state has changed."
	::= 72

nodePortReferenceAChange TRAP-TYPE
	ENTERPRISE cascfr
	VARIABLES { nodePortClockAOperationalState }
	DESCRIPTION
		"Notification that the Port Reference Clock A
		 operational state has changed."
	::= 73

nodePortReferenceBChange TRAP-TYPE
	ENTERPRISE cascfr
	VARIABLES { nodePortClockBOperationalState }
	DESCRIPTION
		"Notification that the Port Reference Clock B
		 operational state has changed."
	::= 74

pportDS0InitiateLpbkFailure TRAP-TYPE
        ENTERPRISE cascfr
        VARIABLES { pportSlotId, pportId, pportDS0FarendDS0InLpbk }
        DESCRIPTION
                "This trap indicates that the DS0 requested to be
	set into far end loopback has failed to do so."
        ::= 75

pportDS0InitiateLpbkSuccess TRAP-TYPE
        ENTERPRISE cascfr
        VARIABLES { pportSlotId, pportId, pportDS0FarendDS0InLpbk }
        DESCRIPTION
                "This trap indicates that the DS0 requested to be
	set into far end loopback has succeeded."
        ::= 76

lportISDNIpAddrRej TRAP-TYPE
        ENTERPRISE cascfr
        VARIABLES  { lportIfIndex, lportISDNIpAddrAssignFail }
        DESCRIPTION
                "This trap indicates that an Ip Address assignment failed."  
        ::= 77

cktAtmStatusChange TRAP-TYPE
        ENTERPRISE cascfr
        VARIABLES  { cktSrcIfIndex, cktAtmVPI, cktAtmVCI, cktOperStatus, cktFailReason, cktFailNode, cktFailPort }
        DESCRIPTION
                "This trap indicates that the user-to-user ATM PVC state has been
                changed for this virtual circuit. It has either been created
                or invalidated, or has toggled between the active and inactive
                states."
        ::= 78

cktAtmReroute TRAP-TYPE
        ENTERPRISE cascfr
        VARIABLES  { cktSrcIfIndex, cktAtmVPI, cktAtmVCI }
        DESCRIPTION
                "This trap indicates that an ATM PVC has been re-routed."
        ::= 79
 
cardTransmitClockStatusChange TRAP-TYPE
        ENTERPRISE cascfr
        VARIABLES  { cardPhysicalSlotId, cardTransmitClockStatus }
        DESCRIPTION
                "This trap indicates the IOM transmit clock synchronization status has chnaged."
        ::= 80

cardSystemPrimaryClockStatusChange TRAP-TYPE
        ENTERPRISE cascfr
        VARIABLES  { cardPhysicalSlotId, cardSystemPrimaryClockStatus }
        DESCRIPTION
                "This trap indicates that the IOM system primary clock reference status has changed."
        ::= 81

cardSystemSecondaryClockStatusChange TRAP-TYPE
        ENTERPRISE cascfr
        VARIABLES  { cardPhysicalSlotId, cardSystemSecondaryClockStatus }
        DESCRIPTION
                "This trap indicates that the IOM system primary clock reference status has changed."
        ::= 82
END
