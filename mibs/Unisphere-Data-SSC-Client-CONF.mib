-- *****************************************************************************
-- Unisphere-Data-SSC-Client-CONF
--
-- SNMP Agent Capabilities definitions for the SSC Client MIB.
--
-- Copyright (c) 2001 Unisphere Networks, Inc.  All rights reserved.
-- *****************************************************************************

Unisphere-Data-SSC-Client-CONF DEFINITIONS ::= BEGIN

IMPORTS
    MODULE-IDENTITY
        FROM SNMPv2-SMI
    AGENT-CAPABILITIES
        FROM SNMPv2-CONF
    usDataAgents
        FROM Unisphere-Data-Agents
    usdSscClientGroup,
    usdSscClientGroup2,
    usdSscClientGroup3
        FROM Unisphere-Data-SSC-CLIENT-MIB;

usdSscClientAgent MODULE-IDENTITY
    LAST-UPDATED "200109192029Z"  -- 19-Sep-01 04:29 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Service Selection Center
        (SSC) Client component of the SNMP agent in the Unisphere Routing Switch
        family of products."
    -- Revision History
    REVISION    "200109192029Z"  -- 19-Sep-01 04:29 PM EDT  - RX 4.0
    DESCRIPTION
        "Add version number object."
    REVISION    "200103301518Z"  -- 30-Mar-01 10:18 AM EST  - RX 3.2
    DESCRIPTION
        "The initial release of this management information module."
    ::= { usDataAgents 41 }

usdSscClientAgentV1 AGENT-CAPABILITIES
    PRODUCT-RELEASE
        "Version 1 of the SSC Client component of the Unisphere Routing Switch
        SNMP agent.  This version of the SSC Client component was supported in
        the Unisphere RX 2.0 thru 3.0 system releases."
    STATUS      obsolete
    DESCRIPTION
        "The MIB supported by the SNMP agent for the SSC Client application in
        the Unisphere Routing Switch.  These capabilities became obsolete when
        DHCP-LS, Web and SSC support objects were added to the MIB."
    SUPPORTS    Unisphere-Data-SSC-CLIENT-MIB
        INCLUDES  {
            usdSscClientGroup }
    ::= { usdSscClientAgent 1 }

usdSscClientAgentV2 AGENT-CAPABILITIES
    PRODUCT-RELEASE
        "Version 2 of the SSC Client component of the Unisphere Routing Switch
        SNMP agent.  This version of the SSC Client component is supported in
        the Unisphere RX 3.1 thru 3.x system releases."
    STATUS      obsolete
    DESCRIPTION
        "The MIB supported by the SNMP agent for the SSC Client application in
        the Unisphere Routing Switch.  These capabilities became obsolete when
        the version number object was added to the MIB."
    SUPPORTS    Unisphere-Data-SSC-CLIENT-MIB
        INCLUDES  {
            usdSscClientGroup2 }
    ::= { usdSscClientAgent 2 }

usdSscClientAgentV3 AGENT-CAPABILITIES
    PRODUCT-RELEASE
        "Version 3 of the SSC Client component of the Unisphere Routing Switch
        SNMP agent.  This version of the SSC Client component is supported in
        the Unisphere RX 4.0 and subsequent system releases."
    STATUS      current
    DESCRIPTION
        "The MIB supported by the SNMP agent for the SSC Client application in
        the Unisphere Routing Switch."
    SUPPORTS    Unisphere-Data-SSC-CLIENT-MIB
        INCLUDES  {
            usdSscClientGroup3 }
    ::= { usdSscClientAgent 3 }

END
