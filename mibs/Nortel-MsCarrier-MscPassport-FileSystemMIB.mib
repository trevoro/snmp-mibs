Nortel-MsCarrier-MscPassport-FileSystemMIB
DEFINITIONS ::= BEGIN



IMPORTS

      OBJECT-TYPE
   FROM RFC-1212

      mscPassportMIBs,
      mscComponents
   FROM Nortel-MsCarrier-MscPassport-UsefulDefinitionsMIB

      RowPointer,
      DisplayString,
      StorageType,
      RowStatus,
      Gauge32,
      Integer32,
      Unsigned32
   FROM Nortel-MsCarrier-MscPassport-StandardTextualConventionsMIB

      AsciiString,
      NonReplicated
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FileSystem Enterprise MIB."

fileSystemMIB OBJECT IDENTIFIER ::= { mscPassportMIBs 16 }










-- FILESYSTEM
-- The Filesystem component provides and controls access to files and 
-- directories stored on one or two disks. It is automatically created 
-- and always present.
-- 
-- The Filesystem restricts files and directories names to 40 characters. 
-- It also restricts filenames including path to 128 characters. 
-- Directory names including the path cannot exceed 125 characters. 
-- There must be 112 or less directories and files at the root level. The 
-- maximum hierarchy depth is 10 directory levels. 
-- The only characters that can appear in a filename are the alpha-
-- numeric characters, the . (dot) and the _ (underscore). The names 
-- are case sensitive. A pathname is a sequence of zero to ten directory 
-- names along the path and separated by the / (slash) character. A 
-- pathname that begins with a slash is an absolute pathname, 
-- otherwise it is a relative pathname. Access to the standby disk is not 
-- allowed. 
-- 
-- When there are two disks, the standby control processor disk is 
-- normally synchronized with the disk of the active control processor. 
-- After a crash or a disk failure the standby control processor disk 
-- becomes unsynchronized with respect to the disk on the active CP. 
-- 

mscFs OBJECT IDENTIFIER ::= { mscComponents 15 }



mscFsRowStatusTable OBJECT-TYPE
   SYNTAX     SEQUENCE OF MscFsRowStatusEntry
   ACCESS     not-accessible
   STATUS     mandatory
   DESCRIPTION
     "This entry controls the addition and deletion of 
      mscFs components."
::= { mscFs 1 }

mscFsRowStatusEntry OBJECT-TYPE
   SYNTAX     MscFsRowStatusEntry
   ACCESS     not-accessible
   STATUS     mandatory
   DESCRIPTION
     "A single entry in the table represents a single 
      mscFs component."
   INDEX {
      mscFsIndex }
::= { mscFsRowStatusTable 1 }

MscFsRowStatusEntry ::= SEQUENCE {
   mscFsRowStatus
      RowStatus,
   mscFsComponentName
      DisplayString,
   mscFsStorageType
      StorageType,
   mscFsIndex
      NonReplicated }

mscFsRowStatus OBJECT-TYPE
   SYNTAX     RowStatus 
   ACCESS     read-only
   STATUS     mandatory
   DESCRIPTION
     "This variable is used as the basis for SNMP naming of
      mscFs components.
      These components cannot be added nor deleted."
::= { mscFsRowStatusEntry 1 }

mscFsComponentName OBJECT-TYPE
   SYNTAX     DisplayString 
   ACCESS     read-only
   STATUS     mandatory
   DESCRIPTION
     "This variable provides the component's string name for
      use with the ASCII Console Interface"
::= { mscFsRowStatusEntry 2 }

mscFsStorageType OBJECT-TYPE
   SYNTAX     StorageType 
   ACCESS     read-only
   STATUS     mandatory
   DESCRIPTION
     "This variable represents the storage type value for the
      mscFs tables."
::= { mscFsRowStatusEntry 4 }

mscFsIndex OBJECT-TYPE
   SYNTAX     NonReplicated 
   ACCESS     not-accessible
   STATUS     mandatory
   DESCRIPTION
     "This variable represents the index for the mscFs tables."
::= { mscFsRowStatusEntry 10 }

mscFsStateTable OBJECT-TYPE
   SYNTAX     SEQUENCE OF MscFsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFs 10 }

mscFsStateEntry OBJECT-TYPE
   SYNTAX     MscFsStateEntry
   ACCESS     not-accessible
   STATUS     mandatory
   DESCRIPTION
     "An entry in the mscFsStateTable."
   INDEX {
      mscFsIndex }
::= { mscFsStateTable 1 }

MscFsStateEntry ::= SEQUENCE {
   mscFsAdminState
      INTEGER,
   mscFsOperationalState
      INTEGER,
   mscFsUsageState
      INTEGER }

mscFsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFsStateEntry 1 }

mscFsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFsStateEntry 2 }

mscFsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFsStateEntry 3 }

mscFsOperTable OBJECT-TYPE
   SYNTAX     SEQUENCE OF MscFsOperEntry
   ACCESS     not-accessible
   STATUS     mandatory
   DESCRIPTION
     "This group contains the filesystem operational data."
::= { mscFs 11 }

mscFsOperEntry OBJECT-TYPE
   SYNTAX     MscFsOperEntry
   ACCESS     not-accessible
   STATUS     mandatory
   DESCRIPTION
     "An entry in the mscFsOperTable."
   INDEX {
      mscFsIndex }
::= { mscFsOperTable 1 }

MscFsOperEntry ::= SEQUENCE {
   mscFsVolumeName
      AsciiString,
   mscFsActiveDisk
      RowPointer,
   mscFsSyncStatus
      INTEGER,
   mscFsSyncProgress
      Gauge32,
   mscFsCapacity
      Unsigned32,
   mscFsFreeSpace
      Unsigned32,
   mscFsUsage
      Gauge32 }

mscFsVolumeName OBJECT-TYPE
   SYNTAX     AsciiString (SIZE (1..11))
   ACCESS     read-only
   STATUS     mandatory
   DESCRIPTION
     "This attribute describes the volume name of the filesystem. This is 
      the active disk volume name."
::= { mscFsOperEntry 1 }

mscFsActiveDisk OBJECT-TYPE
   SYNTAX     RowPointer 
   ACCESS     read-only
   STATUS     mandatory
   DESCRIPTION
     "The activeDisk attribute value is the Disk component instance value 
      of the active disk. This is also the card number of the active control 
      processor."
::= { mscFsOperEntry 2 }

mscFsSyncStatus OBJECT-TYPE
   SYNTAX     INTEGER  {
                 synchronized(0),
                 unSynchronized(1),
                 synchronizing(2) }
   ACCESS     read-only
   STATUS     mandatory
   DESCRIPTION
     "The synchronization status value indicates whether the file system is 
      synchronized or not."
::= { mscFsOperEntry 3 }

mscFsSyncProgress OBJECT-TYPE
   SYNTAX     Gauge32 (0..100)
   ACCESS     read-only
   STATUS     mandatory
   DESCRIPTION
     "The synchronization progress value indicates the percentage of the 
      standby disk already synchronized with the active disk. This value 
      is equal to 100 if the two disks are synchronized or 0 if they are out 
      of synchronization."
::= { mscFsOperEntry 4 }

mscFsCapacity OBJECT-TYPE
   SYNTAX     Unsigned32 (0..4294967295)
   ACCESS     read-only
   STATUS     mandatory
   DESCRIPTION
     "The Capacity attribute value is the total size of the filesystem (in 
      bytes). This value is equal to the smallest disk size in a 
      synchronized filesystem, otherwise it is the capacity of the active 
      disk."
::= { mscFsOperEntry 5 }

mscFsFreeSpace OBJECT-TYPE
   SYNTAX     Unsigned32 (0..4294967295)
   ACCESS     read-only
   STATUS     mandatory
   DESCRIPTION
     "This attribute describes the free disk space (in bytes) currently 
      available in the filesystem. It is equal to the smallest free disk space 
      size of the active and standby disks in a synchronized filesystem. 
      When the filesystem is unsynchronized it is the free disk space of 
      the active disk."
::= { mscFsOperEntry 6 }

mscFsUsage OBJECT-TYPE
   SYNTAX     Gauge32 (0..100)
   ACCESS     read-only
   STATUS     mandatory
   DESCRIPTION
     "This attribute describes the percentage of the free space available on 
      the filesystem."
::= { mscFsOperEntry 7 }

-- 
-- *** THIS SUBTREE CURRENTLY NOT IMPLEMENTED ***
-- 

-- 
-- A disk component is an operational subcomponent of the 
-- filesystem. When the system is in dual-mode configuration, there 
-- will be two instances of the disk component. The 0 instance 
-- represents the disk on the card 0 and the instance 15 represents the 
-- disk on the card 15. 

mscFsDisk OBJECT IDENTIFIER ::= { mscFs 2 }



mscFsDiskRowStatusTable OBJECT-TYPE
   SYNTAX     SEQUENCE OF MscFsDiskRowStatusEntry
   ACCESS     not-accessible
   STATUS     mandatory
   DESCRIPTION
     "*** THIS TABLE CURRENTLY NOT IMPLEMENTED ***

      This entry controls the addition and deletion of 
      mscFsDisk components."
::= { mscFsDisk 1 }

mscFsDiskRowStatusEntry OBJECT-TYPE
   SYNTAX     MscFsDiskRowStatusEntry
   ACCESS     not-accessible
   STATUS     mandatory
   DESCRIPTION
     "A single entry in the table represents a single 
      mscFsDisk component."
   INDEX {
      mscFsIndex,
      mscFsDiskIndex }
::= { mscFsDiskRowStatusTable 1 }

MscFsDiskRowStatusEntry ::= SEQUENCE {
   mscFsDiskRowStatus
      RowStatus,
   mscFsDiskComponentName
      DisplayString,
   mscFsDiskStorageType
      StorageType,
   mscFsDiskIndex
      Integer32 }

mscFsDiskRowStatus OBJECT-TYPE
   SYNTAX     RowStatus 
   ACCESS     read-only
   STATUS     mandatory
   DESCRIPTION
     "This variable is used as the basis for SNMP naming of
      mscFsDisk components.
      These components cannot be added nor deleted."
::= { mscFsDiskRowStatusEntry 1 }

mscFsDiskComponentName OBJECT-TYPE
   SYNTAX     DisplayString 
   ACCESS     read-only
   STATUS     mandatory
   DESCRIPTION
     "This variable provides the component's string name for
      use with the ASCII Console Interface"
::= { mscFsDiskRowStatusEntry 2 }

mscFsDiskStorageType OBJECT-TYPE
   SYNTAX     StorageType 
   ACCESS     read-only
   STATUS     mandatory
   DESCRIPTION
     "This variable represents the storage type value for the
      mscFsDisk tables."
::= { mscFsDiskRowStatusEntry 4 }

mscFsDiskIndex OBJECT-TYPE
   SYNTAX     Integer32 (0..15)
   ACCESS     not-accessible
   STATUS     mandatory
   DESCRIPTION
     "This variable represents the index for the mscFsDisk tables."
::= { mscFsDiskRowStatusEntry 10 }

mscFsDiskStateTable OBJECT-TYPE
   SYNTAX     SEQUENCE OF MscFsDiskStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFsDisk 10 }

mscFsDiskStateEntry OBJECT-TYPE
   SYNTAX     MscFsDiskStateEntry
   ACCESS     not-accessible
   STATUS     mandatory
   DESCRIPTION
     "An entry in the mscFsDiskStateTable."
   INDEX {
      mscFsIndex,
      mscFsDiskIndex }
::= { mscFsDiskStateTable 1 }

MscFsDiskStateEntry ::= SEQUENCE {
   mscFsDiskAdminState
      INTEGER,
   mscFsDiskOperationalState
      INTEGER,
   mscFsDiskUsageState
      INTEGER }

mscFsDiskAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFsDiskStateEntry 1 }

mscFsDiskOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFsDiskStateEntry 2 }

mscFsDiskUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFsDiskStateEntry 3 }

mscFsDiskOperTable OBJECT-TYPE
   SYNTAX     SEQUENCE OF MscFsDiskOperEntry
   ACCESS     not-accessible
   STATUS     mandatory
   DESCRIPTION
     "*** THIS TABLE CURRENTLY NOT IMPLEMENTED ***

      This group contains the disk component operational data."
::= { mscFsDisk 11 }

mscFsDiskOperEntry OBJECT-TYPE
   SYNTAX     MscFsDiskOperEntry
   ACCESS     not-accessible
   STATUS     mandatory
   DESCRIPTION
     "An entry in the mscFsDiskOperTable."
   INDEX {
      mscFsIndex,
      mscFsDiskIndex }
::= { mscFsDiskOperTable 1 }

MscFsDiskOperEntry ::= SEQUENCE {
   mscFsDiskVolumeName
      AsciiString,
   mscFsDiskCapacity
      Unsigned32,
   mscFsDiskFreeSpace
      Unsigned32,
   mscFsDiskBadBlocksPercentage
      Gauge32,
   mscFsDiskUnformattedCapacity
      Unsigned32 }

mscFsDiskVolumeName OBJECT-TYPE
   SYNTAX     AsciiString (SIZE (1..11))
   ACCESS     read-write
   STATUS     mandatory
   DESCRIPTION
     "This attribute describes the volume name of the disk. The volume 
      names of the two disks must be identical to be synchronized."
::= { mscFsDiskOperEntry 1 }

mscFsDiskCapacity OBJECT-TYPE
   SYNTAX     Unsigned32 (0..4294967295)
   ACCESS     read-only
   STATUS     mandatory
   DESCRIPTION
     "This attribute describes the total formatted disk size (in bytes) of the 
      disk."
::= { mscFsDiskOperEntry 2 }

mscFsDiskFreeSpace OBJECT-TYPE
   SYNTAX     Unsigned32 (0..4294967295)
   ACCESS     read-only
   STATUS     mandatory
   DESCRIPTION
     "freeSpace
      This attribute indicates the available free disk space(in bytes) on the 
      disk. Free space is reduced by bad blocks (if any). If there are 
      different numbers of bad blocks on the disks in a dual-disk system, 
      the reported free space will differ on the two disks.
      
      Moreover, due to the DOS file system internal representation of 
      directories and files, adding and deleting files may fragment the 
      disks differently resulting in some disk space wasted. A small 
      discrepancy (less than 1% of the disk size) in the disks free space is 
      considered as normal."
::= { mscFsDiskOperEntry 3 }

mscFsDiskBadBlocksPercentage OBJECT-TYPE
   SYNTAX     Gauge32 (0..100)
   ACCESS     read-only
   STATUS     mandatory
   DESCRIPTION
     "This attribute records the percentage of the disk space lost because 
      of defects. If this percentage is high, it is recommended to change 
      the disk."
::= { mscFsDiskOperEntry 4 }

mscFsDiskUnformattedCapacity OBJECT-TYPE
   SYNTAX     Unsigned32 (0..4294967295)
   ACCESS     read-only
   STATUS     mandatory
   DESCRIPTION
     "unformattedCapacity 
      This attribute indicates the physical disk size (in bytes). The 
      physical disk size may be different from the formatted disk size if 
      there are bad blocks or the disk has been formatted to a smaller disk 
      size for backward compatibility with older releases."
::= { mscFsDiskOperEntry 5 }

-- 
-- *** THIS SUBTREE CURRENTLY NOT IMPLEMENTED ***
-- 

-- Test
-- The Test component embodies logical and physical filesystem tests. 
-- It is an operational subcomponent of the Disk component. 

mscFsDiskTest OBJECT IDENTIFIER ::= { mscFsDisk 2 }



mscFsDiskTestRowStatusTable OBJECT-TYPE
   SYNTAX     SEQUENCE OF MscFsDiskTestRowStatusEntry
   ACCESS     not-accessible
   STATUS     mandatory
   DESCRIPTION
     "*** THIS TABLE CURRENTLY NOT IMPLEMENTED ***

      This entry controls the addition and deletion of 
      mscFsDiskTest components."
::= { mscFsDiskTest 1 }

mscFsDiskTestRowStatusEntry OBJECT-TYPE
   SYNTAX     MscFsDiskTestRowStatusEntry
   ACCESS     not-accessible
   STATUS     mandatory
   DESCRIPTION
     "A single entry in the table represents a single 
      mscFsDiskTest component."
   INDEX {
      mscFsIndex,
      mscFsDiskIndex,
      mscFsDiskTestIndex }
::= { mscFsDiskTestRowStatusTable 1 }

MscFsDiskTestRowStatusEntry ::= SEQUENCE {
   mscFsDiskTestRowStatus
      RowStatus,
   mscFsDiskTestComponentName
      DisplayString,
   mscFsDiskTestStorageType
      StorageType,
   mscFsDiskTestIndex
      NonReplicated }

mscFsDiskTestRowStatus OBJECT-TYPE
   SYNTAX     RowStatus 
   ACCESS     read-only
   STATUS     mandatory
   DESCRIPTION
     "This variable is used as the basis for SNMP naming of
      mscFsDiskTest components.
      These components cannot be added nor deleted."
::= { mscFsDiskTestRowStatusEntry 1 }

mscFsDiskTestComponentName OBJECT-TYPE
   SYNTAX     DisplayString 
   ACCESS     read-only
   STATUS     mandatory
   DESCRIPTION
     "This variable provides the component's string name for
      use with the ASCII Console Interface"
::= { mscFsDiskTestRowStatusEntry 2 }

mscFsDiskTestStorageType OBJECT-TYPE
   SYNTAX     StorageType 
   ACCESS     read-only
   STATUS     mandatory
   DESCRIPTION
     "This variable represents the storage type value for the
      mscFsDiskTest tables."
::= { mscFsDiskTestRowStatusEntry 4 }

mscFsDiskTestIndex OBJECT-TYPE
   SYNTAX     NonReplicated 
   ACCESS     not-accessible
   STATUS     mandatory
   DESCRIPTION
     "This variable represents the index for the mscFsDiskTest tables."
::= { mscFsDiskTestRowStatusEntry 10 }

mscFsDiskTestStateTable OBJECT-TYPE
   SYNTAX     SEQUENCE OF MscFsDiskTestStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFsDiskTest 10 }

mscFsDiskTestStateEntry OBJECT-TYPE
   SYNTAX     MscFsDiskTestStateEntry
   ACCESS     not-accessible
   STATUS     mandatory
   DESCRIPTION
     "An entry in the mscFsDiskTestStateTable."
   INDEX {
      mscFsIndex,
      mscFsDiskIndex,
      mscFsDiskTestIndex }
::= { mscFsDiskTestStateTable 1 }

MscFsDiskTestStateEntry ::= SEQUENCE {
   mscFsDiskTestAdminState
      INTEGER,
   mscFsDiskTestOperationalState
      INTEGER,
   mscFsDiskTestUsageState
      INTEGER }

mscFsDiskTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFsDiskTestStateEntry 1 }

mscFsDiskTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFsDiskTestStateEntry 2 }

mscFsDiskTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFsDiskTestStateEntry 3 }

mscFsDiskTestSetupTable OBJECT-TYPE
   SYNTAX     SEQUENCE OF MscFsDiskTestSetupEntry
   ACCESS     not-accessible
   STATUS     mandatory
   DESCRIPTION
     "*** THIS TABLE CURRENTLY NOT IMPLEMENTED ***

      This group contains the Test component operational data. The 
      testCount, duration and type can be set to control the duration and 
      the test type which will be run."
::= { mscFsDiskTest 11 }

mscFsDiskTestSetupEntry OBJECT-TYPE
   SYNTAX     MscFsDiskTestSetupEntry
   ACCESS     not-accessible
   STATUS     mandatory
   DESCRIPTION
     "An entry in the mscFsDiskTestSetupTable."
   INDEX {
      mscFsIndex,
      mscFsDiskIndex,
      mscFsDiskTestIndex }
::= { mscFsDiskTestSetupTable 1 }

MscFsDiskTestSetupEntry ::= SEQUENCE {
   mscFsDiskTestTestCount
      Unsigned32,
   mscFsDiskTestDuration
      Unsigned32,
   mscFsDiskTestType
      INTEGER }

mscFsDiskTestTestCount OBJECT-TYPE
   SYNTAX     Unsigned32 (0..4294967295)
   ACCESS     read-write
   STATUS     mandatory
   DESCRIPTION
     "This attribute indicates the number of times that the test will run. 
      Note that the test will not run that many times if 'duration' is not 
      long enough to allow the test to complete. The test will execute at 
      least one and then stop at the count where duration has just 
      exceeded."
   DEFVAL     { 1 }
::= { mscFsDiskTestSetupEntry 1 }

mscFsDiskTestDuration OBJECT-TYPE
   SYNTAX     Unsigned32 (0..35791394)
   ACCESS     read-write
   STATUS     mandatory
   DESCRIPTION
     "This attribute is the maximum duration (in minutes) that the test 
      will run. The test can finish in less time if the number of tests, as 
      recorded by testCount, is reached before this time. A test may take 
      longer than the specified duration since a test cycle (or pass) is not 
      interruptible."
   DEFVAL     { 60 }
::= { mscFsDiskTestSetupEntry 2 }

mscFsDiskTestType OBJECT-TYPE
   SYNTAX     INTEGER  {
                 filesystemCheck(0),
                 diskRead(1),
                 flakyBitDetection(2),
                 surfaceAnalysis(3) }
   ACCESS     read-write
   STATUS     mandatory
   DESCRIPTION
     "This attribute is the type of the test to be run. The diskRead test 
      reads every sector on the disk once and reports bad sectors. The 
      filesystemCheck does a sanity check and attempts to repair 
      corruption. The flakyBitDetection test reads every sector on the disk 
      twice and compares the two read results. The surfaceAnalysis test 
      writes a magnetically hard to record pattern to the disk and reads 
      back the pattern to determine the condition of the magnetic surface 
      of the disk. The surface analysis test destroys all the data and disk 
      should be formatted afterward."
   DEFVAL     { filesystemCheck }
::= { mscFsDiskTestSetupEntry 3 }

mscFsDiskTestResultsTable OBJECT-TYPE
   SYNTAX     SEQUENCE OF MscFsDiskTestResultsEntry
   ACCESS     not-accessible
   STATUS     mandatory
   DESCRIPTION
     "*** THIS TABLE CURRENTLY NOT IMPLEMENTED ***

      This group contains the results of the test."
::= { mscFsDiskTest 12 }

mscFsDiskTestResultsEntry OBJECT-TYPE
   SYNTAX     MscFsDiskTestResultsEntry
   ACCESS     not-accessible
   STATUS     mandatory
   DESCRIPTION
     "An entry in the mscFsDiskTestResultsTable."
   INDEX {
      mscFsIndex,
      mscFsDiskIndex,
      mscFsDiskTestIndex }
::= { mscFsDiskTestResultsTable 1 }

MscFsDiskTestResultsEntry ::= SEQUENCE {
   mscFsDiskTestCauseOfTermination
      INTEGER,
   mscFsDiskTestNatureOfError
      INTEGER,
   mscFsDiskTestSeverity
      INTEGER,
   mscFsDiskTestElapsedTime
      Unsigned32,
   mscFsDiskTestTestExecutionCount
      Unsigned32 }

mscFsDiskTestCauseOfTermination OBJECT-TYPE
   SYNTAX     INTEGER  {
                 testCountReached(0),
                 testTimeExpired(1),
                 stoppedByOperator(2),
                 neverStarted(3),
                 testRunning(4),
                 error(5),
                 internalError(6),
                 unknown(7) }
   ACCESS     read-only
   STATUS     mandatory
   DESCRIPTION
     "This attribute records the reason why the test was terminated. The 
      reasons are:
      testCountReached: the test ran the number of times specified in the 
      attribute testCount and ended normally.
      error: the test was terminated by an error that is recorded in the 
      natureOfError attribute.
      neverStarted: the test was never started.
      stoppedByOperator: the test was terminated by the Stop command.
      testTimeExpired: the duration of the test expired.
      testRunning: the test is still running.
      unknown: the test terminated for unknown reasons.
      internalError: An internal error terminated the test."
::= { mscFsDiskTestResultsEntry 1 }

mscFsDiskTestNatureOfError OBJECT-TYPE
   SYNTAX     INTEGER  {
                 logical(0),
                 media(1),
                 noErrorDetected(2),
                 failedToComplete(3) }
   ACCESS     read-only
   STATUS     mandatory
   DESCRIPTION
     "This attribute describes the error found by a test. A logical error can 
      be fixed by a filesystemCheck test followed eventually by a 
      synchronization. A media error indicates that a fault in the disk 
      hardware is suspected. A failedToComplete error indicates that the 
      test was terminated."
::= { mscFsDiskTestResultsEntry 2 }

mscFsDiskTestSeverity OBJECT-TYPE
   SYNTAX     INTEGER  {
                 noDataLost(0),
                 dataLost(1),
                 hardwareProblem(2),
                 noError(3) }
   ACCESS     read-only
   STATUS     mandatory
   DESCRIPTION
     "This attribute describes the severity of the error found by a test. 
      There are three types of severity: no data was lost, data was lost and 
      hardware problem. If the test found no error(s), this will be reported 
      as noError. If the test found error(s) but no data was lost, then 
      noDataLost is reported."
::= { mscFsDiskTestResultsEntry 3 }

mscFsDiskTestElapsedTime OBJECT-TYPE
   SYNTAX     Unsigned32 (0..4294967295)
   ACCESS     read-only
   STATUS     mandatory
   DESCRIPTION
     "This attribute records the elapsed time (in minutes) since the test 
      was started."
::= { mscFsDiskTestResultsEntry 4 }

mscFsDiskTestTestExecutionCount OBJECT-TYPE
   SYNTAX     Unsigned32 (0..4294967295)
   ACCESS     read-only
   STATUS     mandatory
   DESCRIPTION
     "The number of times the test had actually run."
::= { mscFsDiskTestResultsEntry 5 }




-- 
-- Version and Compliance statements
-- 



-- Object-Group Statement:
-- A list of all current accessible leaf objects.

-- OBJECTS { mscFsCapacity,
--           mscFsOperationalState,
--           mscFsDiskUsageState,
--           mscFsDiskRowStatus,
--           mscFsDiskTestRowStatus,
--           mscFsDiskTestDuration,
--           mscFsUsageState,
--           mscFsDiskTestAdminState,
--           mscFsDiskTestStorageType,
--           mscFsDiskTestElapsedTime,
--           mscFsComponentName,
--           mscFsDiskCapacity,
--           mscFsDiskTestTestExecutionCount,
--           mscFsSyncProgress,
--           mscFsStorageType,
--           mscFsDiskUnformattedCapacity,
--           mscFsDiskFreeSpace,
--           mscFsUsage,
--           mscFsDiskComponentName,
--           mscFsDiskVolumeName,
--           mscFsDiskOperationalState,
--           mscFsDiskTestUsageState,
--           mscFsVolumeName,
--           mscFsDiskBadBlocksPercentage,
--           mscFsDiskStorageType,
--           mscFsActiveDisk,
--           mscFsDiskTestComponentName,
--           mscFsDiskTestCauseOfTermination,
--           mscFsAdminState,
--           mscFsDiskTestTestCount,
--           mscFsDiskTestNatureOfError,
--           mscFsFreeSpace,
--           mscFsSyncStatus,
--           mscFsRowStatus,
--           mscFsDiskTestSeverity,
--           mscFsDiskAdminState,
--           mscFsDiskTestType,
--           mscFsDiskTestOperationalState }
-- STATUS  mandatory
-- DESCRIPTION
--   "A list of all current accessible leaf objects."

fileSystemGroup OBJECT IDENTIFIER ::= { fileSystemMIB 1 }
fileSystemGroupCA OBJECT IDENTIFIER ::= { fileSystemGroup 1 }
fileSystemGroupCA02 OBJECT IDENTIFIER ::= { fileSystemGroupCA 3 }
fileSystemGroupCA02A OBJECT IDENTIFIER ::= { fileSystemGroupCA02 2 }



-- Agent-Capabilities Statement:

-- PRODUCT-RELEASE "MscPassport Release 1.2 FileSystem."
-- STATUS          mandatory
-- DESCRIPTION     "Carrier Passport FileSystem MIB: MIB Version CA02A,
--                  Software Version CA02S9C."
-- SUPPORTS        Nortel-MsCarrier-MscPassport-FileSystemMIB
--    INCLUDES     { fileSystemGroupCA02A }

fileSystemCapabilities OBJECT IDENTIFIER ::= { fileSystemMIB 3 }
fileSystemCapabilitiesCA OBJECT IDENTIFIER ::= { fileSystemCapabilities 1 }
fileSystemCapabilitiesCA02 OBJECT IDENTIFIER ::= { fileSystemCapabilitiesCA 3 }
fileSystemCapabilitiesCA02A OBJECT IDENTIFIER ::= { fileSystemCapabilitiesCA02 2 }





END
