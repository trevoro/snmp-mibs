--	Aptis Enterprise MIB
--
--	Nortel Networks
--	11 Elizabeth Drive
--	Chelmsford, MA 01824
--
--	Copyright (c) 1997-2000 Nortel Networks
--	All Rights Reserved.
--

APTIS-HDLC-MIB DEFINITIONS ::= BEGIN

     IMPORTS
             OBJECT-TYPE
                     FROM RFC-1212
             Counter
                     FROM RFC1155-SMI
             aptis-generic
                     FROM APTIS-MIB;

     aptisHdlc     OBJECT IDENTIFIER ::= { aptis-generic 7 }

     --
     --      the range of ifIndex
     --
     Index ::= INTEGER       -- 1..ifNumber

        -- This begins Aptis HDLC MIB

        aptisHdlcTable    OBJECT-TYPE
                SYNTAX  SEQUENCE OF AptisHdlcEntry
                ACCESS  not-accessible
                STATUS  mandatory
                DESCRIPTION
                        "These parameters represent statistics for all of the 
			            HDLC channels for a single HDLC chip. These are errors 
			            that cannot be specified on a specific HDLC channel."
                ::= { aptisHdlc 1 }

        aptisHdlcEntry    OBJECT-TYPE
                SYNTAX  AptisHdlcEntry
                ACCESS  not-accessible
                STATUS  mandatory
                DESCRIPTION
                        "The Parameters for the all of the HDLC connections 
			for a specific HDLC chip."
                INDEX   { aptisHdlcIfIndex }
                ::= { aptisHdlcTable 1 }

        AptisHdlcEntry ::= SEQUENCE {
                        aptisHdlcIfIndex             Index,
                        aptisHdlcReceiveDrops        Counter,
                        aptisHdlcTransmitDrops       Counter,
                        aptisHdlcSysErrors           Counter,
                        aptisHdlcParityErrors        Counter,
                        aptisHdlcFCSErrors           Counter,
                        aptisHdlcAborts              Counter,
                        aptisHdlcFramingErrors       Counter,
                        aptisHdlcReceiveOverruns     Counter,
                        aptisHdlcTransmitUnderflows  Counter
                }

        aptisHdlcIfIndex  OBJECT-TYPE
                SYNTAX  Index
                ACCESS  read-only
                STATUS  mandatory
                DESCRIPTION
                        "The ifIndex value of the corresponding ifEntry."
                ::= { aptisHdlcEntry 1 }

        aptisHdlcReceiveDrops OBJECT-TYPE
             SYNTAX   Counter
             ACCESS   read-only
             STATUS   mandatory
             DESCRIPTION
                "Number of HDLC frames received that were dropped."
            ::= { aptisHdlcEntry 2 }

        aptisHdlcTransmitDrops OBJECT-TYPE
             SYNTAX   Counter
             ACCESS   read-only
             STATUS   mandatory
             DESCRIPTION
                "Number of HDLC frames to be transmitted that were dropped."
            ::= { aptisHdlcEntry 3 }

        aptisHdlcSysErrors OBJECT-TYPE
             SYNTAX   Counter
             ACCESS   read-only
             STATUS   mandatory
             DESCRIPTION
                "Number of HDLC system errors."
            ::= { aptisHdlcEntry 4 }

        aptisHdlcParityErrors OBJECT-TYPE
             SYNTAX   Counter
             ACCESS   read-only
             STATUS   mandatory
             DESCRIPTION
                "Number of HDLC parity errors."
            ::= { aptisHdlcEntry 5 }

        aptisHdlcFCSErrors OBJECT-TYPE
             SYNTAX   Counter
             ACCESS   read-only
             STATUS   mandatory
             DESCRIPTION
                "Number of HDLC Frame CheckSum errors."
            ::= { aptisHdlcEntry 6 }

        aptisHdlcAborts OBJECT-TYPE
             SYNTAX   Counter
             ACCESS   read-only
             STATUS   mandatory
             DESCRIPTION
                "Number of HDLC aborts."
            ::= { aptisHdlcEntry 7 }

        aptisHdlcFramingErrors OBJECT-TYPE
             SYNTAX   Counter
             ACCESS   read-only
             STATUS   mandatory
             DESCRIPTION
                "Number of HDLC framing errors."
            ::= { aptisHdlcEntry 8 }

        aptisHdlcReceiveOverruns OBJECT-TYPE
             SYNTAX   Counter
             ACCESS   read-only
             STATUS   mandatory
             DESCRIPTION
                "Number of HDLC receive overruns."
            ::= { aptisHdlcEntry 9 }

        aptisHdlcTransmitUnderflows OBJECT-TYPE
             SYNTAX   Counter
             ACCESS   read-only
             STATUS   mandatory
             DESCRIPTION
                "Number of HDLC transmit underflows."
            ::= { aptisHdlcEntry 10 }


        aptisHdlcChannelTable    OBJECT-TYPE
                SYNTAX  SEQUENCE OF AptisHdlcChannelEntry
                ACCESS  not-accessible
                STATUS  mandatory
                DESCRIPTION
                        "These parameters represent statistics for all of the HDLC channels for a 
                         single HDLC chip. These are errors that cannot be specified on a specific 
                         HDLC channel."
                ::= { aptisHdlc 2 }

        aptisHdlcChannelEntry    OBJECT-TYPE
                SYNTAX  AptisHdlcChannelEntry
                ACCESS  not-accessible
                STATUS  mandatory
                DESCRIPTION
                        "The Parameters for the all of the HDLC connections for a specific HDLC chip."
                INDEX   { aptisHdlcIfIndex, aptisHdlcChannelIfIndex }
                ::= { aptisHdlcChannelTable 1 }

        AptisHdlcChannelEntry ::= SEQUENCE {
                        aptisHdlcChannelIfIndex            Index,
                        aptisHdlcChannelStatus             INTEGER,
                        aptisHdlcChannelRcvFrames          Counter,
                        aptisHdlcChannelRcvOctets          Counter,
                        aptisHdlcChannelRcvDrops           Counter,
                        aptisHdlcChannelRcvMaxPacket       Counter,
                        aptisHdlcChannelRcvOverruns        Counter,
                        aptisHdlcChannelRcvFCSErrors       Counter,
                        aptisHdlcChannelRcvByteAlign       Counter,
                        aptisHdlcChannelRcvAborts          Counter,
                        aptisHdlcChannelTransmitFrames     Counter,
                        aptisHdlcChannelTransmitOctets     Counter,
                        aptisHdlcChannelTransmitDrops      Counter,
                        aptisHdlcChannelTransmitUnderflows Counter,
                        aptisHdlcChannelTransmitBuffer     Counter
                }


          aptisHdlcChannelIfIndex OBJECT-TYPE
             SYNTAX   Index
             ACCESS   read-only
             STATUS   mandatory
             DESCRIPTION
                "HDLC channel interface index."
            ::= { aptisHdlcChannelEntry 1 }

          aptisHdlcChannelStatus OBJECT-TYPE
             SYNTAX   INTEGER    {
                       init             (1),
                       down             (2),
                       disabled         (3),
                       smconnnectwait   (4),
                       up               (5),
                       smdisconnectwait (6)
                     }
             ACCESS   read-only
             STATUS   mandatory
             DESCRIPTION
                "This indicates the status of the HDLC Channel."
             ::= { aptisHdlcChannelEntry 2 }


          aptisHdlcChannelRcvFrames OBJECT-TYPE
             SYNTAX   Counter
             ACCESS   read-only
             STATUS   mandatory
             DESCRIPTION
                "Number of frames received on the HDLC channel."
            ::= { aptisHdlcChannelEntry 3 }

          aptisHdlcChannelRcvOctets OBJECT-TYPE
             SYNTAX   Counter
             ACCESS   read-only
             STATUS   mandatory
             DESCRIPTION
                "Number of octets received on the HDLC channel."
            ::= { aptisHdlcChannelEntry 4 }

          aptisHdlcChannelRcvDrops OBJECT-TYPE
             SYNTAX   Counter
             ACCESS   read-only
             STATUS   mandatory
             DESCRIPTION
                "Number of frames received on the HDLC channel that were dropped."
            ::= { aptisHdlcChannelEntry 5 }

          aptisHdlcChannelRcvMaxPacket OBJECT-TYPE
             SYNTAX   Counter
             ACCESS   read-only
             STATUS   mandatory
             DESCRIPTION
                "Maximum receive packet size on the HDLC channel."
            ::= { aptisHdlcChannelEntry 6 }

          aptisHdlcChannelRcvOverruns OBJECT-TYPE
             SYNTAX   Counter
             ACCESS   read-only
             STATUS   mandatory
             DESCRIPTION
                "Number of frames received on the HDLC channel with overrun errors."
            ::= { aptisHdlcChannelEntry 7 }

          aptisHdlcChannelRcvFCSErrors OBJECT-TYPE
             SYNTAX   Counter
             ACCESS   read-only
             STATUS   mandatory
             DESCRIPTION
                "Number of frames received on the HDLC channel with frame checksum errors."
            ::= { aptisHdlcChannelEntry 8 }

          aptisHdlcChannelRcvByteAlign OBJECT-TYPE
             SYNTAX   Counter
             ACCESS   read-only
             STATUS   mandatory
             DESCRIPTION
                "Number of frames received on the HDLC channel with byte alignment errors."
            ::= { aptisHdlcChannelEntry 9 }

          aptisHdlcChannelRcvAborts OBJECT-TYPE
             SYNTAX   Counter
             ACCESS   read-only
             STATUS   mandatory
             DESCRIPTION
                "Number of receive attempts on the HDLC channel that were aborted."
            ::= { aptisHdlcChannelEntry 10 }

          aptisHdlcChannelTransmitFrames OBJECT-TYPE
             SYNTAX   Counter
             ACCESS   read-only
             STATUS   mandatory
             DESCRIPTION
                "Number of frames transmitted on the HDLC channel."
            ::= { aptisHdlcChannelEntry 11 }

          aptisHdlcChannelTransmitOctets OBJECT-TYPE
             SYNTAX   Counter
             ACCESS   read-only
             STATUS   mandatory
             DESCRIPTION
                "Number of octets transmitted on the HDLC channel."
            ::= { aptisHdlcChannelEntry 12 }

          aptisHdlcChannelTransmitDrops OBJECT-TYPE
             SYNTAX   Counter
             ACCESS   read-only
             STATUS   mandatory
             DESCRIPTION
                "Number of transmitted frames dropped on the HDLC channel."
            ::= { aptisHdlcChannelEntry 13 }

          aptisHdlcChannelTransmitUnderflows OBJECT-TYPE
             SYNTAX   Counter
             ACCESS   read-only
             STATUS   mandatory
             DESCRIPTION
                "Number of transmit underflows on the HDLC channel."
            ::= { aptisHdlcChannelEntry 14 }

          aptisHdlcChannelTransmitBuffer OBJECT-TYPE
             SYNTAX   Counter
             ACCESS   read-only
             STATUS   mandatory
             DESCRIPTION
                "HDLC channel transmit buffer size."
            ::= { aptisHdlcChannelEntry 15 }

     END
