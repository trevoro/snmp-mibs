Usr-Nat-MIB DEFINITIONS ::= BEGIN

        IMPORTS
          IpAddress
                  FROM RFC1155-SMI
          OBJECT-TYPE
                  FROM RFC-1212
          DisplayString FROM RFC1213-MIB
			 usrNat
                  FROM USR-DEFINITIONS-MIB;


     usrNatAddr         OBJECT IDENTIFIER ::= { usrNat 1 }
     usrNatTcp          OBJECT IDENTIFIER ::= { usrNat 2 }
     usrNatUdp          OBJECT IDENTIFIER ::= { usrNat 3 }
     usrNatGre          OBJECT IDENTIFIER ::= { usrNat 4 }
     usrNatOtherPid     OBJECT IDENTIFIER ::= { usrNat 5 }


     UsrNatName ::= DisplayString

     usrNatAddrTable OBJECT-TYPE
         SYNTAX   SEQUENCE OF UsrNatAddrEntry
         ACCESS   not-accessible
         STATUS   mandatory
         DESCRIPTION
            "A table of IP NAT entries."
     ::= { usrNatAddr 1 }
 
     usrNatAddrEntry OBJECT-TYPE
         SYNTAX  UsrNatAddrEntry
         ACCESS  not-accessible
         STATUS  mandatory
         DESCRIPTION
                 "Each entry contains the active mappings between 
                  Private and Public addresses and a count of exiting
                  UDP and TCP connections. "
         INDEX   { usrNatAddrUserName, usrNatAddrPrivateAddr }
    ::= { usrNatAddrTable 1 }

 
     UsrNatAddrEntry ::=
         SEQUENCE {
            usrNatAddrUserName
               UsrNatName,
            usrNatAddrPrivateAddr
               IpAddress,
            usrNatAddrPublicAddr
               IpAddress,
            usrNatAddrConfig
               INTEGER,
            usrNatAddrUdpConnections
               INTEGER,
            usrNatAddrTcpConnections
               INTEGER,
            usrNatAddrGreConnections
               INTEGER
         }
 
     usrNatAddrUserName OBJECT-TYPE
         SYNTAX      UsrNatName
         ACCESS      read-only
         STATUS      mandatory
         DESCRIPTION
            "The name of the User profile for which this entry exists. "
     ::= { usrNatAddrEntry 1 }

     usrNatAddrPrivateAddr OBJECT-TYPE
         SYNTAX  IpAddress
         ACCESS  read-only
         STATUS  mandatory
         DESCRIPTION
            "Private Address for this mapping."
     ::= { usrNatAddrEntry 2 }
 
     usrNatAddrPublicAddr OBJECT-TYPE
         SYNTAX  IpAddress
         ACCESS  read-only
         STATUS  mandatory
         DESCRIPTION
            "Public Address for this mapping." 
     ::= { usrNatAddrEntry 3 }

     usrNatAddrConfig OBJECT-TYPE
         SYNTAX  INTEGER {
                 static(1),
                 dynamic(2)
                 }
         ACCESS  read-only
         STATUS  mandatory
         DESCRIPTION
            "Type of mapping, static or dynamic."
     ::= { usrNatAddrEntry 4 }

     usrNatAddrUdpConnections OBJECT-TYPE
         SYNTAX  INTEGER
         ACCESS  read-only
         STATUS  mandatory
         DESCRIPTION
            "Count of UDP connections active on this Adddress."
     ::= { usrNatAddrEntry 5 }

     usrNatAddrTcpConnections OBJECT-TYPE
         SYNTAX  INTEGER
         ACCESS  read-only
         STATUS  mandatory
         DESCRIPTION
            "Count of TCP connections active on this Adddress."
     ::= { usrNatAddrEntry 6 }

     usrNatAddrGreConnections OBJECT-TYPE
         SYNTAX  INTEGER
         ACCESS  read-only
         STATUS  mandatory
         DESCRIPTION
            "Count of GRE connections active on this Adddress."
     ::= { usrNatAddrEntry 7 }

 --
 --  TCP Port connections
 --

     usrNatTcpTable OBJECT-TYPE
         SYNTAX   SEQUENCE OF UsrNatTcpEntry
         ACCESS   not-accessible
         STATUS   mandatory
         DESCRIPTION
            "A table of TCP connections."
     ::= { usrNatTcp 1 }
 
     usrNatTcpEntry OBJECT-TYPE
         SYNTAX  UsrNatTcpEntry
         ACCESS  not-accessible
         STATUS  mandatory
         DESCRIPTION
                 "Each entry contains the active mapping of a TCP  
                  connection."
         INDEX   { usrNatTcpUserName, usrNatTcpPrivateAddr,
                   usrNatTcpPrivatePort, usrNatTcpRemoteAddr, 
                   usrNatTcpRemotePort }
    ::= { usrNatTcpTable 1 }

 
     UsrNatTcpEntry ::=
         SEQUENCE {
            usrNatTcpUserName
               UsrNatName,
            usrNatTcpPrivateAddr
               IpAddress,
            usrNatTcpPrivatePort
               INTEGER,
            usrNatTcpRemoteAddr
               IpAddress,
            usrNatTcpRemotePort
               INTEGER,
            usrNatTcpPublicAddr
               IpAddress,
            usrNatTcpPublicPort
               INTEGER,
            usrNatTcpTimer
               INTEGER
         }
 
     usrNatTcpUserName OBJECT-TYPE
         SYNTAX      UsrNatName
         ACCESS      read-only
         STATUS      mandatory
         DESCRIPTION
            "The name of the User profile for which this entry exists. "
     ::= { usrNatTcpEntry 1 }
 
     usrNatTcpPrivateAddr OBJECT-TYPE
         SYNTAX  IpAddress
         ACCESS  read-only
         STATUS  mandatory
         DESCRIPTION
            "Private Address for this mapping."
     ::= { usrNatTcpEntry 2 }

     usrNatTcpPrivatePort OBJECT-TYPE
         SYNTAX  INTEGER
         ACCESS  read-only
         STATUS  mandatory
         DESCRIPTION
            "Private Port number of the mapping."
     ::= { usrNatTcpEntry 3 }
 
     usrNatTcpRemoteAddr OBJECT-TYPE
         SYNTAX  IpAddress
         ACCESS  read-only
         STATUS  mandatory
         DESCRIPTION
            "Remote Address for this mapping."
     ::= { usrNatTcpEntry 4 }

     usrNatTcpRemotePort OBJECT-TYPE
         SYNTAX  INTEGER
         ACCESS  read-only
         STATUS  mandatory
         DESCRIPTION
            "Remote Port number of the mapping."
     ::= { usrNatTcpEntry 5 }
 
     usrNatTcpPublicAddr OBJECT-TYPE
         SYNTAX  IpAddress
         ACCESS  read-only
         STATUS  mandatory
         DESCRIPTION
            "Public Address for this mapping." 
     ::= { usrNatTcpEntry 6 }

     usrNatTcpPublicPort OBJECT-TYPE
         SYNTAX  INTEGER
         ACCESS  read-only
         STATUS  mandatory
         DESCRIPTION
            "Public Port number of the mapping."
     ::= { usrNatTcpEntry 7 }
 
     usrNatTcpTimer OBJECT-TYPE
         SYNTAX  INTEGER
         ACCESS  read-only
         STATUS  mandatory
         DESCRIPTION
            "Number of Seconds before TCP connection mapping times out."
     ::= { usrNatTcpEntry 8 }


 --
 --  UDP Port connections
 --

     usrNatUdpTable OBJECT-TYPE
         SYNTAX   SEQUENCE OF UsrNatUdpEntry
         ACCESS   not-accessible
         STATUS   mandatory
         DESCRIPTION
            "A table of UDP conversations."
     ::= { usrNatUdp 1 }
 
     usrNatUdpEntry OBJECT-TYPE
         SYNTAX  UsrNatUdpEntry
         ACCESS  not-accessible
         STATUS  mandatory
         DESCRIPTION
                 "Each entry contains the active mapping of a UDP
                  conversation."
         INDEX   { usrNatUdpUserName, usrNatUdpPrivateAddr,
                   usrNatUdpPrivatePort, usrNatUdpRemoteAddr, 
                   usrNatUdpRemotePort }
    ::= { usrNatUdpTable 1 }

 
     UsrNatUdpEntry ::=
         SEQUENCE {
            usrNatUdpUserName
               UsrNatName,
            usrNatUdpPrivateAddr
               IpAddress,
            usrNatUdpPrivatePort
               INTEGER,
            usrNatUdpRemoteAddr
               IpAddress,
            usrNatUdpRemotePort
               INTEGER,
            usrNatUdpPublicAddr
               IpAddress,
            usrNatUdpPublicPort
               INTEGER,
            usrNatUdpTimer
               INTEGER
         }
 
     usrNatUdpUserName OBJECT-TYPE
         SYNTAX      UsrNatName
         ACCESS      read-only
         STATUS      mandatory
         DESCRIPTION
            "The name of the User profile for which this entry exists. "
     ::= { usrNatUdpEntry 1 }
 
     usrNatUdpPrivateAddr OBJECT-TYPE
         SYNTAX  IpAddress
         ACCESS  read-only
         STATUS  mandatory
         DESCRIPTION
            "Private Address for this mapping."
     ::= { usrNatUdpEntry 2 }

     usrNatUdpPrivatePort OBJECT-TYPE
         SYNTAX  INTEGER
         ACCESS  read-only
         STATUS  mandatory
         DESCRIPTION
            "Private Port number of the mapping."
     ::= { usrNatUdpEntry 3 }
 
     usrNatUdpRemoteAddr OBJECT-TYPE
         SYNTAX  IpAddress
         ACCESS  read-only
         STATUS  mandatory
         DESCRIPTION
            "Remote Address for this mapping."
     ::= { usrNatUdpEntry 4 }

     usrNatUdpRemotePort OBJECT-TYPE
         SYNTAX  INTEGER
         ACCESS  read-only
         STATUS  mandatory
         DESCRIPTION
            "Remote Port number of the mapping."
     ::= { usrNatUdpEntry 5 }
 
     usrNatUdpPublicAddr OBJECT-TYPE
         SYNTAX  IpAddress
         ACCESS  read-only
         STATUS  mandatory
         DESCRIPTION
            "Public Address for this mapping." 
     ::= { usrNatUdpEntry 6 }

     usrNatUdpPublicPort OBJECT-TYPE
         SYNTAX  INTEGER
         ACCESS  read-only
         STATUS  mandatory
         DESCRIPTION
            "Public Port number of the mapping."
     ::= { usrNatUdpEntry 7 }

     usrNatUdpTimer OBJECT-TYPE
         SYNTAX  INTEGER
         ACCESS  read-only
         STATUS  mandatory
         DESCRIPTION
            "Number of Seconds before UDP conversation mapping times out."
     ::= { usrNatUdpEntry 8 }


 --
 --  GRE connections
 --

     usrNatGreTable OBJECT-TYPE
         SYNTAX   SEQUENCE OF UsrNatGreEntry
         ACCESS   not-accessible
         STATUS   mandatory
         DESCRIPTION
            "A table of UDP conversations."
     ::= { usrNatGre 1 }
 
     usrNatGreEntry OBJECT-TYPE
         SYNTAX  UsrNatGreEntry
         ACCESS  not-accessible
         STATUS  mandatory
         DESCRIPTION
                 "Each entry contains the active mapping of a UDP
                  conversation."
         INDEX   { usrNatGreUserName, usrNatGrePrivateAddr,
                   usrNatGrePrivateCallId, usrNatGreRemoteAddr, 
                   usrNatGreRemoteCallId }
    ::= { usrNatGreTable 1 }

 
     UsrNatGreEntry ::=
         SEQUENCE {
            usrNatGreUserName
               UsrNatName,
            usrNatGrePrivateAddr
               IpAddress,
            usrNatGrePrivateCallId
               INTEGER,
            usrNatGreRemoteAddr
               IpAddress,
            usrNatGreRemoteCallId
               INTEGER,
            usrNatGrePublicAddr
               IpAddress,
            usrNatGrePublicCallId
               INTEGER,
            usrNatGreTimer
               INTEGER
         }
 
     usrNatGreUserName OBJECT-TYPE
         SYNTAX      UsrNatName
         ACCESS      read-only
         STATUS      mandatory
         DESCRIPTION
            "The name of the User profile for which this entry exists. "
     ::= { usrNatGreEntry 1 }
 
     usrNatGrePrivateAddr OBJECT-TYPE
         SYNTAX  IpAddress
         ACCESS  read-only
         STATUS  mandatory
         DESCRIPTION
            "Private Address for this mapping."
     ::= { usrNatGreEntry 2 }

     usrNatGrePrivateCallId OBJECT-TYPE
         SYNTAX  INTEGER
         ACCESS  read-only
         STATUS  mandatory
         DESCRIPTION
            "Private Call Id number of the mapping."
     ::= { usrNatGreEntry 3 }
 
     usrNatGreRemoteAddr OBJECT-TYPE
         SYNTAX  IpAddress
         ACCESS  read-only
         STATUS  mandatory
         DESCRIPTION
            "Remote Address for this mapping."
     ::= { usrNatGreEntry 4 }

     usrNatGreRemoteCallId OBJECT-TYPE
         SYNTAX  INTEGER
         ACCESS  read-only
         STATUS  mandatory
         DESCRIPTION
            "Remote Call ID number of the mapping."
     ::= { usrNatGreEntry 5 }
 
     usrNatGrePublicAddr OBJECT-TYPE
         SYNTAX  IpAddress
         ACCESS  read-only
         STATUS  mandatory
         DESCRIPTION
            "Public Address for this mapping." 
     ::= { usrNatGreEntry 6 }

     usrNatGrePublicCallId OBJECT-TYPE
         SYNTAX  INTEGER
         ACCESS  read-only
         STATUS  mandatory
         DESCRIPTION
            "Public Call ID number of the mapping."
     ::= { usrNatGreEntry 7 }

     usrNatGreTimer OBJECT-TYPE
         SYNTAX  INTEGER
         ACCESS  read-only
         STATUS  mandatory
         DESCRIPTION
            "Number of Seconds before UDP conversation mapping times out."
     ::= { usrNatGreEntry 8 }

 --
 --  Other PID connections
 --  These are connections which NAT maps the PID as opposed to the Ports
 --

     usrNatOtherPidTable OBJECT-TYPE
         SYNTAX   SEQUENCE OF UsrNatOtherPidEntry
         ACCESS   not-accessible
         STATUS   mandatory
         DESCRIPTION
            "A table of active mappings based on the Protocol ID as opposed 
             to the port number or call id used when mapping TCP, UDP, or GRE." 
     ::= { usrNatOtherPid 1 }
 
     usrNatOtherPidEntry OBJECT-TYPE
         SYNTAX  UsrNatOtherPidEntry
         ACCESS  not-accessible
         STATUS  mandatory
         DESCRIPTION
                 "Each entry contains the active mapping of a Protocol Ids 
                  other than TCP, UDP, ICMP, and GRE."
         INDEX   { usrNatOtherPidUserName, usrNatOtherPidPrivateAddr,
                   usrNatOtherPidProtocolId, usrNatOtherPidRemoteAddr }

    ::= { usrNatOtherPidTable 1 }

 
     UsrNatOtherPidEntry ::=
         SEQUENCE {
            usrNatOtherPidUserName
               UsrNatName,
            usrNatOtherPidPrivateAddr
               IpAddress,
            usrNatOtherPidProtocolId
               INTEGER,
            usrNatOtherPidRemoteAddr
               IpAddress,
            usrNatOtherPidPublicAddr
               IpAddress,
            usrNatOtherPidTimer
               INTEGER
         }
 
     usrNatOtherPidUserName OBJECT-TYPE
         SYNTAX      UsrNatName
         ACCESS      read-only
         STATUS      mandatory
         DESCRIPTION
            "The name of the User profile for which this entry exists. "
     ::= { usrNatOtherPidEntry 1 }
 
     usrNatOtherPidPrivateAddr OBJECT-TYPE
         SYNTAX  IpAddress
         ACCESS  read-only
         STATUS  mandatory
         DESCRIPTION
            "Private Address for this mapping."
     ::= { usrNatOtherPidEntry 2 }

     usrNatOtherPidProtocolId OBJECT-TYPE
         SYNTAX  INTEGER
         ACCESS  read-only
         STATUS  mandatory
         DESCRIPTION
            "Protocol ID of the mapping." 
     ::= { usrNatOtherPidEntry 3 }
 
     usrNatOtherPidRemoteAddr OBJECT-TYPE
         SYNTAX  IpAddress
         ACCESS  read-only
         STATUS  mandatory
         DESCRIPTION
            "Remote Address for this mapping."
     ::= { usrNatOtherPidEntry 4 }

     usrNatOtherPidPublicAddr OBJECT-TYPE
         SYNTAX  IpAddress
         ACCESS  read-only
         STATUS  mandatory
         DESCRIPTION
            "Public Address for this mapping." 
     ::= { usrNatOtherPidEntry 5 }

     usrNatOtherPidTimer OBJECT-TYPE
         SYNTAX  INTEGER
         ACCESS  read-only
         STATUS  mandatory
         DESCRIPTION
            "Number of Seconds before this mapping times out."
     ::= { usrNatOtherPidEntry 6 }

END         -- End IP Translation MIB definitions
