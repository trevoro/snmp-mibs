-- extracted from draft-kajos-hmultimediamib-00.txt
-- at Mon Nov 15 17:11:06 1999

                 MP-MIB DEFINITIONS ::= BEGIN
                 IMPORTS
                  Counter32, Integer32, enterprises, OBJECT-TYPE,
        MODULE-IDENTITY, NOTIFICATION-TYPE
                       FROM SNMPv2-SMI
                   TAddress, RowStatus, TruthValue, DateAndTime
                         FROM SNMPv2-TC
                   MODULE-COMPLIANCE, OBJECT-GROUP
                         FROM SNMPv2-CONF
                   MmGatekeeperID, MmTAddressTag,MmEndpointID,
        MmGlobalIdentifier
        
                         FROM MULTI-MEDIA-MIB-TC;
        
        
        
                 -- Define the top of this MIB.
                media OBJECT IDENTIFIER ::= { enterprises videoserver(3011) 2 }
                  --  this is the MIB module for the H.323 MP objects
             h323MP  MODULE-IDENTITY
                     LAST-UPDATED "9808062253Z"      -- August 6, 1998
                     ORGANIZATION "VideoServer"
                     CONTACT-INFO
                     "               Irina Suconick
                            Postal: Video Server
                                     63 Third st.
                                     Burlington, MA 01803
                             Tel:    (781)505-2155
                             E-Mail: isuconick@videoserver.com "
                     DESCRIPTION
                        " "
                           ::= { media 2 }
        
                 --groups in H.323 mp
        
                 mpConfig         OBJECT IDENTIFIER ::= { h323MP 1 }
                 mpConference     OBJECT IDENTIFIER ::= { h323MP 2 }
        
        
        
                mpConfigMaxAudioMixCount OBJECT-TYPE
                     SYNTAX Integer32
                     MAX-ACCESS read-only
                     STATUS current
                     DESCRIPTION
                        "Maximum number of participants allowed in the audio mix."
                        ::= { mpConfig 1 }
                mpConfigMaxVideoMixCount OBJECT-TYPE
                     SYNTAX Integer32
                     MAX-ACCESS read-only
                     STATUS current
                     DESCRIPTION
                        "Maximum number of participants allowed in the video mix."
                        ::= { mpConfig 2 }
        
                mpConferenceTable OBJECT-TYPE
                     SYNTAX SEQUENCE OF MpConferenceTableEntry
                     MAX-ACCESS not-accessible
                     STATUS current
                     DESCRIPTION
                        "This table contains information about running conferences.
                         It is a list of conference entries. The number of entries
                         equals to the number of running conferences."
                     ::= { mpConference 1 }
                 mpConferenceTableEntry OBJECT-TYPE
                     SYNTAX MpConferenceTableEntry
                     MAX-ACCESS not-accessible
                     STATUS current
                     DESCRIPTION
                         "It contains objects that describe a specific conference."
                     INDEX { mpConferenceConferenceId}
                       ::= { mpConferenceTable 1 }
                 MpConferenceTableEntry ::=
                      SEQUENCE {
                      mpConferenceConferenceId
                          MmGlobalIdentifier,
                     mpConferenceAudioNoiseThreshold
                          Integer32,
                      mpConferenceLipSyncEnable
                          TruthValue
                      }
        
                 mpConferenceConferenceId OBJECT-TYPE
                     SYNTAX MmGlobalIdentifier
                     MAX-ACCESS read-only
                     STATUS current
                     DESCRIPTION
                        "The conference identifier as specified in ITU-T H.323V2
                         specification."
                        ::= { mpConferenceTableEntry 1 }
        
                mpConferenceAudioNoiseThreshold OBJECT-TYPE
                     SYNTAX Integer32
                     MAX-ACCESS read-only
                     STATUS current
                     DESCRIPTION
                        "This value represents the audio power level
                         above which the signal is detected as speech."
                        ::= { mpConferenceTableEntry 2 }
        
                 mpConferenceLipSyncEnable OBJECT-TYPE
                     SYNTAX TruthValue
                     MAX-ACCESS read-only
                     STATUS current
                     DESCRIPTION
                        "This value indicates rather the lip
                         syncronization adjustments are performed."
                        ::= { mpConferenceTableEntry 3 }
        
                 mpConferenceParticipantsTable OBJECT-TYPE
                     SYNTAX SEQUENCE OF MpConferenceParticipantsTableEntry
                     MAX-ACCESS not-accessible
                     STATUS current
                     DESCRIPTION
                        "This table contains information about conference
                         participants. It is a list of participant entries. The
                         number of entries equals the number of participants for all
                         conferences."
                     ::= { mpConference 2 }

                 mpConferenceParticipantsTableEntry OBJECT-TYPE
                     SYNTAX MpConferenceParticipantsTableEntry
                     MAX-ACCESS not-accessible
                     STATUS current
                     DESCRIPTION
                         "It contains objects that describe a specific conference
                          participant."
                     INDEX { mpConferenceConferenceId,
                  mpConferenceParticipantsTableIndex }
                       ::= { mpConferenceParticipantsTable 1 }
        
                 MpConferenceParticipantsTableEntry ::=
                      SEQUENCE {
                    mpConferenceParticipantsTableIndex
                            Integer32,
                    mpConferenceParticipantsEndpointId
                            MmEndpointID,
                    mpConferenceParticipantsTransmitAudioState
                            INTEGER,
                    mpConferenceParticipantsReceiveAudioState
                            INTEGER,
                    mpConferenceParticipantsTransmitVideoState
                            INTEGER,
                    mpConferenceParticipantsReceiveVideoState
                            INTEGER,
                    mpConferenceParticipantsLoudnessMeasurement
                            Integer32,
                    mpConferenceParticipantsVoiceActivity
                            TruthValue,
                    mpConferenceParticipantsInputAudioGain
                            Integer32,
                    mpConferenceParticipantsOutputAudioGain
                            Integer32,
                    mpConferenceParticipantsMaxAudioEncoderPayloadSize
                            Integer32,
                    mpConferenceParticipantsMaxAudioDecoderPayloadSize
                            Integer32,
                    mpConferenceParticipantsTotalPacketsTransmitted
                            Counter32,
                    mpConferenceParticipantsTotalPacketsReceived
                            Counter32,
                    mpConferenceParticipantsInvalidPacketErrors
                            Counter32,
                    mpConferenceParticipantsLateAudioPacketsDropped
                            Counter32,
                    mpConferenceParticipantsReceivedSilencePackets
                            Counter32,
                    mpConferenceParticipantsSilencePacketsGenerated
                            Counter32,
                    mpConferenceParticipantsVideoFrameRate
                            Integer32,
                    mpConferenceParticipantsVideoResolution
                            INTEGER,
                    mpConferenceParticipantsFullPictureCounter
                            Integer32
                    }
        
                 mpConferenceParticipantsTableIndex OBJECT-TYPE
                     SYNTAX Integer32
                     MAX-ACCESS read-only
                     STATUS current
                     DESCRIPTION
                        "An arbitrary index to this table. This index is one for the
                         first participant for every given conference. It is
                         incremented by one for each subsequent participant of the
                         same conference. The last index for a particular conference
                         is equal to the number of participants for that conference."
                        ::= { mpConferenceParticipantsTableEntry 1 }
                 mpConferenceParticipantsEndpointId OBJECT-TYPE
                     SYNTAX MmEndpointID
                     MAX-ACCESS read-only
                     STATUS current
                     DESCRIPTION
                        "The H.323 id of this participant as described in ITU-T
                          H.323V2 specification."
                        ::= { mpConferenceParticipantsTableEntry 2 }
                 mpConferenceParticipantsTransmitAudioState OBJECT-TYPE
                     SYNTAX INTEGER {normal (1), mute (2), toneGeneration (3), off (4)}
                     MAX-ACCESS read-only
                     STATUS current
                     DESCRIPTION
                        "This value indicates the state of transmitted audio:
                         normal         - transmit normal audio
                         toneGeneration - transmit test tone
                         mute           - transmit silence audio
                         off            - no audio is transmitted"
                        ::= { mpConferenceParticipantsTableEntry 3 }
                 mpConferenceParticipantsReceiveAudioState OBJECT-TYPE
                     SYNTAX INTEGER {normal (1), loopBack (2), block (3), off (4)}
                     MAX-ACCESS read-only
                     STATUS current
                     DESCRIPTION
                        "This value indicates the state of received audio:
                         normal         - receive normal audio
                         loopBack       - received audio presented unchanged to the
                                          transmitter
                         block          - received audio is not part of the mix
                         off            - no audio is received"
                        ::= { mpConferenceParticipantsTableEntry 4 }
        
                 mpConferenceParticipantsTransmitVideoState OBJECT-TYPE
                     SYNTAX INTEGER {on (1), off (2)}
                     MAX-ACCESS read-only
                     STATUS current
                     DESCRIPTION
                        "This value indicates the state of transmitted video:
                         on  - normal video is transmitted
                         off - no video is transmitted."
                        ::= { mpConferenceParticipantsTableEntry 5 }
                 mpConferenceParticipantsReceiveVideoState OBJECT-TYPE
                     SYNTAX INTEGER {normal (1), block (2), off (3)}
                     MAX-ACCESS read-only
                     STATUS current
                     DESCRIPTION
                        "This value indicates the state of transmitted video:
                         normal  - normal video is received
                         block   - received video is not displayed
                         off     - no video is transmitted."
                        ::= { mpConferenceParticipantsTableEntry 6 }
                 mpConferenceParticipantsLoudnessMeasurement OBJECT-TYPE
                     SYNTAX Integer32
                     MAX-ACCESS read-only
                     STATUS current
                     DESCRIPTION
                        "This is the current loudness measurement value in dB."
                        ::= { mpConferenceParticipantsTableEntry 7 }
                 mpConferenceParticipantsVoiceActivity OBJECT-TYPE
                     SYNTAX TruthValue
                     MAX-ACCESS read-only
                     STATUS current
                     DESCRIPTION
                        "This value is True when the speech is detected."
                        ::= { mpConferenceParticipantsTableEntry 8 }
                 mpConferenceParticipantsInputAudioGain OBJECT-TYPE
                     SYNTAX Integer32
                     MAX-ACCESS read-only
                     STATUS current
                     DESCRIPTION
                        "This value reflects the current input volume adjustment in
                         dB."
                        ::= { mpConferenceParticipantsTableEntry 9 }
                 mpConferenceParticipantsOutputAudioGain OBJECT-TYPE
                     SYNTAX Integer32
                     MAX-ACCESS read-only
                     STATUS current
                     DESCRIPTION
                        "This value reflects the current output volume adjustment in
                         dB."
                        ::= { mpConferenceParticipantsTableEntry 10 }
                 mpConferenceParticipantsMaxAudioEncoderPayloadSize OBJECT-TYPE
                     SYNTAX Integer32
                     MAX-ACCESS read-only
                     STATUS current
                     DESCRIPTION
                        "The maximum size of payload in ms."
                        ::= { mpConferenceParticipantsTableEntry 11 }
                 mpConferenceParticipantsMaxAudioDecoderPayloadSize OBJECT-TYPE
                     SYNTAX Integer32
                     MAX-ACCESS read-only
                     STATUS current
                     DESCRIPTION
                        "The maximum size of payload in ms."
                        ::= { mpConferenceParticipantsTableEntry 12 }
                 mpConferenceParticipantsTotalPacketsTransmitted OBJECT-TYPE
                     SYNTAX Counter32
                     MAX-ACCESS read-only
                     STATUS current
                     DESCRIPTION
                        "The total number of transmitted packets."
                        ::= { mpConferenceParticipantsTableEntry 13 }
                 mpConferenceParticipantsTotalPacketsReceived OBJECT-TYPE
                     SYNTAX Counter32
                     MAX-ACCESS read-only
                     STATUS current
                     DESCRIPTION
                        "The total number of received packets."
                        ::= { mpConferenceParticipantsTableEntry 14 }
                 mpConferenceParticipantsInvalidPacketErrors OBJECT-TYPE
                     SYNTAX Counter32
                     MAX-ACCESS read-only
                     STATUS current
                     DESCRIPTION
                        "The total number of packets with invalid packet errors."
                        ::= { mpConferenceParticipantsTableEntry 15 }
        
                 mpConferenceParticipantsLateAudioPacketsDropped OBJECT-TYPE
                     SYNTAX Counter32
                     MAX-ACCESS read-only
                     STATUS current
                     DESCRIPTION
                        "The total number of packets that arrived too late to be
		        processed."
                        ::= { mpConferenceParticipantsTableEntry 16 }
                 mpConferenceParticipantsReceivedSilencePackets OBJECT-TYPE
                     SYNTAX Counter32
                     MAX-ACCESS read-only
                     STATUS current
                     DESCRIPTION
                        "The total number of silence packets that were received."
                        ::= { mpConferenceParticipantsTableEntry 17 }
                 mpConferenceParticipantsSilencePacketsGenerated OBJECT-TYPE
                     SYNTAX Counter32
                     MAX-ACCESS read-only
                     STATUS current
                     DESCRIPTION
                        "The total number of silence packets that were generated."
                        ::= { mpConferenceParticipantsTableEntry 18 }
                 mpConferenceParticipantsVideoFrameRate OBJECT-TYPE
                     SYNTAX Integer32
                     MAX-ACCESS read-only
                     STATUS current
                     DESCRIPTION
                        "This value represents the current measured frame rate
                         received."
                        ::= { mpConferenceParticipantsTableEntry 19 }
                 mpConferenceParticipantsVideoResolution OBJECT-TYPE
                     SYNTAX INTEGER { h263SubQCIF (1),h263QCIF (2),
                                      h263CIF(3), h2634CIF(4),
                                      h26316CIF(5),  h263Reserved (6),
                                      h261QCIF(7),h261CIF(8)  }
                     MAX-ACCESS read-only
                     STATUS current
                     DESCRIPTION
                        "Received video resolution."
                        ::= { mpConferenceParticipantsTableEntry 20 }
        
                 mpConferenceParticipantsFullPictureCounter OBJECT-TYPE
                     SYNTAX Integer32
                     MAX-ACCESS read-only
                     STATUS current
                     DESCRIPTION
                        "This value represents the number of full image pictures
			 received."
                        ::= { mpConferenceParticipantsTableEntry 21 }
                 mpConferenceGlobalAudioMixTable OBJECT-TYPE
                     SYNTAX SEQUENCE OF
	        MpConferenceGlobalAudioMixTableEntry
                     MAX-ACCESS not-accessible
                     STATUS current
                     DESCRIPTION
                        "This table contains information about conference
                         participants that are present in a global audio mix.
                         It is a list of participant entries. The number of entries
                         equals to the sum of all audio mix participants in all
                         conferences."
                     ::= { mpConference 3 }
                 mpConferenceGlobalAudioMixTableEntry OBJECT-TYPE
                     SYNTAX MpConferenceGlobalAudioMixTableEntry
                     MAX-ACCESS not-accessible
                     STATUS current
                     DESCRIPTION
                         "It contains objects that describe the participants."
                     INDEX { mpConferenceConferenceId,
        mpConferenceGlobalAudioMixTableIndex }
                       ::= { mpConferenceGlobalAudioMixTable 1 }
                 MpConferenceGlobalAudioMixTableEntry ::=
                      SEQUENCE {
                      mpConferenceGlobalAudioMixTableIndex
                          Integer32,
                     mpConferenceGlobalAudioMixTerminalIdentifier
                          MmEndpointID
                      }
                 mpConferenceGlobalAudioMixTableIndex OBJECT-TYPE
                     SYNTAX Integer32
                     MAX-ACCESS read-only
                     STATUS current
                     DESCRIPTION
                        "An arbitrary index to this table. This index is one for the
                         first participant for every given conference. It is
                         incremented by one for each subsequent participant of the
                         same conference. The last index for a particular conference
                         is equal to the number of participants for that conference."
                        ::= { mpConferenceGlobalAudioMixTableEntry 1 }
        
                 mpConferenceGlobalAudioMixTerminalIdentifier OBJECT-TYPE
                     SYNTAX MmEndpointID
                     MAX-ACCESS read-only
                     STATUS current
                     DESCRIPTION
                      "The H.323 id of this participant as described in ITU-T H.323V2
                          specification."
                        ::= { mpConferenceGlobalAudioMixTableEntry 2 }
        
                 mpConferenceGlobalVideoMixTable OBJECT-TYPE
                     SYNTAX SEQUENCE OF
                 MpConferenceGlobalVideoMixTableEntry
                     MAX-ACCESS not-accessible
                     STATUS current
                     DESCRIPTION
                        "This table contains information about conference
                         participants that are present in a global video mix.
                         It is a list of participant entries. The number of entries
                         equals to the sum of all video mix participants in all
                         conferences."
                     ::= { mpConference 4 }
                 mpConferenceGlobalVideoMixTableEntry OBJECT-TYPE
                     SYNTAX MpConferenceGlobalVideoMixTableEntry
                     MAX-ACCESS not-accessible
                     STATUS current
                     DESCRIPTION
                         "It contains objects that describe the participants."
                     INDEX { mpConferenceConferenceId,
        mpConferenceGlobalVideoMixTableIndex }
                       ::= { mpConferenceGlobalVideoMixTable 1 }
                 MpConferenceGlobalVideoMixTableEntry ::=
                      SEQUENCE {
                      mpConferenceGlobalVideoMixTableIndex
                          Integer32,
                     mpConferenceGlobalVideoMixTerminalIdentifier
                          MmEndpointID
                      }
                 mpConferenceGlobalVideoMixTableIndex OBJECT-TYPE
                     SYNTAX Integer32
                     MAX-ACCESS read-only
                     STATUS current
                     DESCRIPTION
                        "An arbitrary index to this table. This index is one for the
                         first participant for every given conference. It is
                         incremented by one for each subsequent participant of the
                         same conference. The last index for a particular conference
                         is equal to the number of participants for that conference."
                        ::= { mpConferenceGlobalVideoMixTableEntry 1 }
                 mpConferenceGlobalVideoMixTerminalIdentifier OBJECT-TYPE
                     SYNTAX MmEndpointID
                     MAX-ACCESS read-only
                     STATUS current
                     DESCRIPTION
                        "The H.323 id of this participant as described in ITU-T
		        H.323V2 specification."
                        ::= { mpConferenceGlobalVideoMixTableEntry 2 }
        
        
        -- conformance; stating the mandatory requirements for the MIB
        --
        -- CONFORMANCE
        --
        mpMIBConformance    OBJECT IDENTIFIER ::= { h323MP 3 }
        mpMIBGroups         OBJECT IDENTIFIER ::= { mpMIBConformance 1 }
        
        --
        -- Groups for Conformance
        --
        mpConfigGroup OBJECT-GROUP
            OBJECTS {
                mpConfigMaxAudioMixCount,
                mpConfigMaxVideoMixCount
              }
            STATUS  current
            DESCRIPTION
               "."
            ::= { mpMIBGroups 1 }
        mpConferenceGroup    OBJECT-GROUP
            OBJECTS {
              mpConferenceConferenceId,
              mpConferenceAudioNoiseThreshold,
              mpConferenceLipSyncEnable,
              mpConferenceParticipantsTableIndex,
              mpConferenceParticipantsEndpointId,
              mpConferenceParticipantsTransmitAudioState,
              mpConferenceParticipantsReceiveAudioState,
              mpConferenceParticipantsTransmitVideoState,
              mpConferenceParticipantsReceiveVideoState,
              mpConferenceParticipantsLoudnessMeasurement,
              mpConferenceParticipantsVoiceActivity,
              mpConferenceParticipantsInputAudioGain,
              mpConferenceParticipantsOutputAudioGain,
              mpConferenceParticipantsMaxAudioEncoderPayloadSize,
              mpConferenceParticipantsMaxAudioDecoderPayloadSize,
              mpConferenceParticipantsTotalPacketsTransmitted,
              mpConferenceParticipantsTotalPacketsReceived,
              mpConferenceParticipantsLateAudioPacketsDropped,
              mpConferenceParticipantsReceivedSilencePackets,
              mpConferenceParticipantsSilencePacketsGenerated,
              mpConferenceParticipantsVideoFrameRate,
              mpConferenceParticipantsVideoResolution,
              mpConferenceParticipantsFullPictureCounter,
              mpConferenceGlobalAudioMixTableIndex,
              mpConferenceGlobalAudioMixTerminalIdentifier,
              mpConferenceGlobalVideoMixTableIndex,
              mpConferenceGlobalVideoMixTerminalIdentifier
        
            }
            STATUS  current
            DESCRIPTION
               "."
            ::= { mpMIBGroups 2 }

        mpMIBCompliance        MODULE-COMPLIANCE
            STATUS      current
            DESCRIPTION
                "The set of objects required for compliance."
            MODULE
                MANDATORY-GROUPS { mpConfigGroup, mpConferenceGroup }
            ::= { mpMIBConformance 2 }
        
        END
