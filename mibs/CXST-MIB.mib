CXST-MIB DEFINITIONS ::= BEGIN


IMPORTS
   Counter         FROM RFC1155-SMI
   OBJECT-TYPE     FROM RFC-1212
   cxST            FROM CXProduct-SMI;

--  S/T-Interface Transceiver Driver Configuration Table
--  This table includes:
--  1) The configuration parameters such as the maximum duration allocated
--       for ISDN link synchronization on the NT/TE interface and the Power
--       Source 1 detection option;
--  2) The S/T driver status in particular port status, signal
--       received/transmitted across the S/T reference point, frame
--       synchronization indications;
--  3) Miscellaneous statistics such as the number of activation/deactivation
--       requests received by the I/O card, the number of down-to-up and
--       up-to-down transition transitions that occurred on the I/O card, etc.;
--  4) The controls to clear statistics, power up/down the S/T driver,
--       reinitialize the configuration and other controls.

stTable OBJECT-TYPE
   SYNTAX  SEQUENCE OF StEntry
   ACCESS  not-accessible
   STATUS  mandatory
   DESCRIPTION
"A table containing configuration parameters, controls, status and statistics
 for the S/T Interface Transceiver Driver."
   ::= { cxST 10 }


stEntry OBJECT-TYPE
   SYNTAX  StEntry
   ACCESS  not-accessible
   STATUS  mandatory
   DESCRIPTION
"The entry index in the ISDN S/T Interface Transceiver Driver table."
   INDEX { stSlotNumberIndex }
   ::= { stTable 1 }



StEntry ::=
      SEQUENCE {
         stSlotNumberIndex      INTEGER,
         stRowStatus       		INTEGER,
-- Parameters
         stPS1Detection         INTEGER,
         stTimer1               INTEGER,
         stTimer3               INTEGER,
         stTest                 INTEGER,
-- Status
         stPortStatus           INTEGER,
         stRxInfoState          INTEGER,
         stTxInfoState          INTEGER,
         stErrorIndicator       INTEGER,
         stFrameSync            INTEGER,
         stPortMode            	INTEGER,
-- Statistics           
         stActivation           Counter,
         stDeactivation         Counter,
         stTransition           Counter,
         stNbErrors             Counter,
         stFrameSyncLost        Counter,
         stMissingAMIViolation  INTEGER,
         stUnbalancedFrame      INTEGER,
-- Control
         stClearStat            INTEGER,
         stPortCtrl             INTEGER
      }


stSlotNumberIndex OBJECT-TYPE
   SYNTAX  INTEGER (1..8)
   ACCESS  read-only
   STATUS  mandatory
   DESCRIPTION
"Indicates the physical slot number of the I/O card in the CX900/CX900 PRO.

Range of Values: 1-6 for CX900, 1-8 for CX900 PRO

Default Value: none"
   ::= { stEntry 1 }


stRowStatus      OBJECT-TYPE
      SYNTAX   INTEGER {
               invalid     (1),
               valid    (2)
               }
      ACCESS   read-write
      STATUS   mandatory
      DESCRIPTION
"Determines whether this entry is to be removed from service 
(i.e. invalidated)  within the ST Driver.

Options:
invalid (1): row is flagged; after next reset values will be disabled and row 
will be deleted from table

valid (2): values are enabled

Default Value: valid

Configuration Changed: administrative "
		DEFVAL { valid }
      ::= { stEntry 2 }


stPS1Detection OBJECT-TYPE
   SYNTAX  INTEGER {    
      disabled    (1),
      enabled     (2)
   }
   ACCESS  read-write
   STATUS  mandatory
   DESCRIPTION
"Indicates whether or not the driver has to wait for the detection 
 of the Power Source 1 before generating an activation request at 
 system power-up.

Options:
disabled (1):  Power source 1 detection is not performed.
enabled (2):   Power source 1 detection is performed.

Default Value: disabled (1)"
   DEFVAL { disabled }
   ::= { stEntry 10 }   


stTimer1 OBJECT-TYPE
   SYNTAX  INTEGER
   ACCESS  read-write
   STATUS  mandatory
   DESCRIPTION
"Indicates the maximum duration (in seconds) allocated for ISDN
 link synchronization at the NT interface as specified in the
 I.430 standard.

Default Value: 15"
   DEFVAL { 15 }
   ::= { stEntry 11 }


stTimer3 OBJECT-TYPE
   SYNTAX  INTEGER (0..30)
   ACCESS  read-write
   STATUS  mandatory
   DESCRIPTION
"Indicates the maximum duration (in seconds) allocated for ISDN
 link synchronization at the TE interface as specified in the
 I.430 standard.

Default Value: 10"
   DEFVAL { 10 }
   ::= { stEntry 12 }


stTest OBJECT-TYPE
   SYNTAX  INTEGER {    
      disabled        (1),
      internal2B1D    (2),
      internal2B      (3),
      external        (4),
      stLpbk          (5),
      testSignal      (6)
   }
   ACCESS  read-write
   STATUS  mandatory
   DESCRIPTION
"Indicates if the driver needs to configure the S/T Interface in a test mode.

Options:
disabled     (1): Test mode is disabled
internal2B1D (2): The B1, B2 and D channel data received from the CPU are sent back unchanged.
internal2B   (3): The B1 and B2 channel data received from the CPU are sent back unchanged.
external     (4): An 'analog' loopback is performed if the transmit pair is shorted to the received pair.
stLpbk       (5): The B1 and B2 channel data received from the line interface are sent back unchanged.
testSignal   (6): The device transmits a 96 kHz square wave test signal on the line interface.
 
Default Value: disabled (1)"
   DEFVAL { disabled }
   ::= { stEntry 13 }


stPortStatus OBJECT-TYPE
   SYNTAX  INTEGER {
      portDown    (1),
      portUp      (2)
   }
   ACCESS  read-only
   STATUS  mandatory
   DESCRIPTION
"Indicates the status of the port on this I/O card.

Options:
portDown (1):  port is down
portUp (2):    port is up

Default Value: none"
   ::= { stEntry 20 }


stRxInfoState OBJECT-TYPE
   SYNTAX  INTEGER {
      info0     (1),
      info1     (2),
      info2     (3),
      info3     (4),
      info4     (5),
      infoX     (6) 
   }
   ACCESS  read-only
   STATUS  mandatory
   DESCRIPTION
"Indicates the signal that is received across the S/T reference point
 according to I.430 standard, table 4.

Options:
info0: INFO0 signal received from the TE or the NT 
info1: INFO1 signal received from the TE 
info2: INFO2 signal received from the NT
info3: INFO3 signal received from the TE 
info4: INFO4 signal received from the NT
infoX: INFOX signal received from the TE or the NT 

Default Value: none"
   ::= { stEntry 21 }


stTxInfoState OBJECT-TYPE
   SYNTAX  INTEGER {
      info0     (1),
      info1     (2),
      info2     (3),
      info3     (4),
      info4     (5),
      infoX     (6) 
   }
   ACCESS  read-only
   STATUS  mandatory
   DESCRIPTION
"Indicates the signal that is transmitted across the S/T reference point
 according to I.430 standard, table 4.

Options:
info0: INFO0 signal transmitted to the TE or the NT
info1: INFO1 signal transmitted to the NT
info2: INFO2 signal transmitted to the TE
info3: INFO3 signal transmitted to the NT
info4: INFO4 signal transmitted to the TE
infoX: INFOX signal transmitted to the TE or the NT

Default Value: none"
   ::= { stEntry 22 }


stErrorIndicator OBJECT-TYPE
   SYNTAX  INTEGER {
      errorDetected	(1),
      noError		(2)
   }
   ACCESS  read-only
   STATUS  mandatory
   DESCRIPTION
"Indicates if an error condition has been detected by the 
 activation state machine. Error conditions:
	- lost of framing element;
	- invalid info received.

Options:
errorDetected (1):  an error condition has occurred.
noError (2):    	no error condition has occurred.

Default Value: none"
   ::= { stEntry 23 }


stFrameSync OBJECT-TYPE
   SYNTAX  INTEGER {
      noSync   (1),
      sync     (2)
   }
   ACCESS  read-only
   STATUS  mandatory
   DESCRIPTION
"Indicates if the frame synchronization is achieved

Options:
noSync (1): frame synchronization is not achieved
Sync (2):   frame synchronization is achieved

Default Value: none"
   ::= { stEntry 24 }


stPortMode OBJECT-TYPE
   SYNTAX  INTEGER {
      te   		(1),
      nt     	(2)
   }
   ACCESS  read-only
   STATUS  mandatory
   DESCRIPTION
"Indicates in which mode the ST port is functioning.

Options:
te (1):	Terminal Endpoint, port is in user mode
nt (2): Network Termination, port is in network mode.

Default Value: none"
   ::= { stEntry 25 }


stActivation OBJECT-TYPE
   SYNTAX  Counter
   ACCESS  read-only
   STATUS  mandatory
   DESCRIPTION
"Indicates the number of activation requests received by this I/O card.

Range of Values: 0-4294967295

Default Value: none"
   ::= { stEntry 40 }


stDeactivation OBJECT-TYPE
   SYNTAX  Counter
   ACCESS  read-only
   STATUS  mandatory
   DESCRIPTION
"Indicates the number of deactivation requests received by this I/O card.

Range of Values: 0-4294967295

Default Value: none"
   ::= { stEntry 41 }


stTransition OBJECT-TYPE
   SYNTAX  Counter
   ACCESS  read-only
   STATUS  mandatory
   DESCRIPTION
"Indicates the number of down-to-up or up-to-down transitions that have 
 occurred on this I/O card.

Range of Values: 0-4294967295

Default Value: none"
   ::= { stEntry 42 }


stNbErrors OBJECT-TYPE
   SYNTAX  Counter
   ACCESS  read-only
   STATUS  mandatory
   DESCRIPTION
"Indicates the number of times the transceiver has indicated that
 an error condition has been detected by the activation state
 machine as outlined in CCITT I.430, ETSI  ETS 300012 and
 ANSI T1.605 standards.

Range of Values: 0-4294967295

Default Value: none"
   ::= { stEntry 43 }

stFrameSyncLost OBJECT-TYPE
   SYNTAX  Counter
   ACCESS  read-only
   STATUS  mandatory
   DESCRIPTION
"Indicates the number of times the transceiver has lost it's
 frame synchronization.

Range of Values: 0-4294967295

Default Value: none"
   ::= { stEntry 44 }

stMissingAMIViolation OBJECT-TYPE
   SYNTAX  INTEGER
   ACCESS  read-only
   STATUS  mandatory
   DESCRIPTION
"Indicates the number of frames not containing the right number of
 AMI violations.

Range of Values: 0-255

Default Value: none"
   ::= { stEntry 45 }


stUnbalancedFrame OBJECT-TYPE
   SYNTAX  INTEGER
   ACCESS  read-only
   STATUS  mandatory
   DESCRIPTION
"Indicates the number of unbalanced frames.

Range of Values: 0-255

Default Value: none"
   ::= { stEntry 46 }


stClearStat OBJECT-TYPE
   SYNTAX  INTEGER
   ACCESS  write-only
   STATUS  mandatory
   DESCRIPTION
"Clears all S/T driver statistic counters for this I/O card.

Options:

clearStats : clears statistics

Default value: none"
   ::= { stEntry 60}


stPortCtrl OBJECT-TYPE
   SYNTAX  INTEGER {
      portDown    	(1),
      portUp      	(2),
      portReset   	(3),
	  openBChannels (4)
   }
   ACCESS  write-only
   STATUS  mandatory
   DESCRIPTION
"Either brings up/down the port on this I/O card or reset it.

Options:

portDown (1):  		bring port down
portUp (2):    		bring port up
portReset (3): 		port is reset and configuration is saved
openBChannels (4): 	both B channels are opened (for test purpose only).

Default Value: none"
   ::= { stEntry 61}

END
