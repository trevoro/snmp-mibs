-- *****************************************************************************
-- Unisphere-Data-System-Clock-CONF
--
-- SNMP Agent Capabilities definitions for the System Clock MIB.
--
-- Copyright (c) 2002 Unisphere Networks, Inc.  All rights reserved.
-- *****************************************************************************

Unisphere-Data-System-Clock-CONF DEFINITIONS ::= BEGIN

IMPORTS
    MODULE-IDENTITY
        FROM SNMPv2-SMI
    AGENT-CAPABILITIES
        FROM SNMPv2-CONF
    usdSysClockTimeGroup, usdSysClockDstGroup, usdNtpSysClockGroup,
    usdNtpClientGroup, usdNtpServerGroup, usdNtpPeersGroup, usdNtpAccessGroupGroup
        FROM Unisphere-Data-System-Clock-MIB
    usDataAgents
        FROM Unisphere-Data-Agents;

usdSysClockAgent MODULE-IDENTITY
    LAST-UPDATED "200204041847Z"  -- 04-Apr-02 01:47 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the system clock component of
        the SNMP agent in the Unisphere Routing Switch family of products."
    -- Revision History
    REVISION    "200204041847Z"  -- 04-Apr-02 01:47 PM EST  - RX 4.0
    DESCRIPTION
        "The initial release of this management information module."
    ::= { usDataAgents 52 }

usdSysClockAgentV1 AGENT-CAPABILITIES
    PRODUCT-RELEASE
        "Version 1 of the system clock component of the Unisphere Routing Switch
        SNMP agent.  This version of the system clock component is supported in
        the Unisphere RX 4.0 and subsequent system releases."
    STATUS      current
    DESCRIPTION
        "The MIB supported by the SNMP agent for the system clock application in
        the Unisphere Routing Switch."
    SUPPORTS    Unisphere-Data-System-Clock-MIB
        INCLUDES  {
            usdSysClockTimeGroup,
            usdSysClockDstGroup,
            usdNtpSysClockGroup,
            usdNtpClientGroup,
            usdNtpServerGroup,
            usdNtpPeersGroup,
            usdNtpAccessGroupGroup }
    ::= { usdSysClockAgent 1 }

END
