INTEL-AMOD-MIB DEFINITIONS ::= BEGIN

-- Copyright (C) 1997 Intel Corporation. All rights reserved.
--
-- AMOD MIB, 10-06-1997
--
-- Proprietary MIB containing information about async modem.
--
-- Change History:
-- 99-02-09 Initial version
--

IMPORTS
	Counter FROM RFC1155-SMI
    mib2ext                    FROM INTEL-GEN-MIB
    OBJECT-TYPE                FROM RFC-1212
    DisplayString              FROM RFC1213-MIB;

    amod                OBJECT IDENTIFIER ::= { mib2ext 24 }
    amodModem           OBJECT IDENTIFIER ::= { amod 1 }
    amodLink            OBJECT IDENTIFIER ::= { amod 2 }


-- Data Types

ModemState ::= INTEGER {
	     noConfiguration(1),
            noValidModem(2),
            initializingModem(3),
            resettingModem(4),
            waitingForResetAck(5),
            hangingUp(6),
            waitingForHangupAck(7),
            standBy(8),
            acceptingCall(9),
            connected(10),
            reserved(11),
            dialing(12),
            waitingForAnswer(13),
            other(14)
        }


-- Modem

amodModemTable OBJECT-TYPE
    SYNTAX SEQUENCE OF AmodModemEntry
    ACCESS not-accessible
    STATUS mandatory
    DESCRIPTION "This table contains state of the modem. One entry per modem"
    ::= { amodModem 1 }

amodModemEntry OBJECT-TYPE
    SYNTAX AmodModemEntry
    ACCESS not-accessible
    STATUS mandatory
    DESCRIPTION ""
    INDEX { amodModemIfIndex }
    ::= { amodModemTable 1 }

AmodModemEntry ::= SEQUENCE {
                        amodModemIfIndex
                           INTEGER,
                        amodModemState
                           ModemState,
                        amodModemManufactureName
                           DisplayString (SIZE(20)),
                        amodModemProductNameAndVer
                           DisplayString (SIZE(20))
                        }

amodModemIfIndex OBJECT-TYPE
    SYNTAX INTEGER
    ACCESS read-only
    STATUS mandatory
    DESCRIPTION "Async modem Link index. This is a number that uniquely
                 "
    ::= { amodModemEntry 1 }

amodModemState OBJECT-TYPE
    SYNTAX ModemState
    ACCESS read-only
    STATUS mandatory
    DESCRIPTION "The modem state"
    ::= { amodModemEntry 2 }

amodModemManufactureName OBJECT-TYPE
    SYNTAX DisplayString (SIZE(1..20))
    ACCESS read-only
    STATUS mandatory
    DESCRIPTION ""
    ::= { amodModemEntry 3 }

amodModemProductNameAndVer OBJECT-TYPE
    SYNTAX DisplayString (SIZE(1..30))
    ACCESS read-only
    STATUS mandatory
    DESCRIPTION ""
    ::= { amodModemEntry 4 }


-- Link

amodLinkTable OBJECT-TYPE
    SYNTAX SEQUENCE OF AmodLinkEntry
    ACCESS not-accessible
    STATUS mandatory
    DESCRIPTION "This table contains HDLC counters. One entry per link"
    ::= { amodLink 1 }

amodLinkEntry OBJECT-TYPE
    SYNTAX AmodLinkEntry
    ACCESS not-accessible
    STATUS mandatory
    DESCRIPTION ""
    INDEX { amodLinkIfIndex }
    ::= { amodLinkTable 1 }

AmodLinkEntry ::= SEQUENCE {
                        amodLinkIfIndex
                           INTEGER,
                        amodLinkHdlcRxChecksumErrors
                           Counter,
                        amodLinkHdlcRxLong
                           Counter,
                        amodLinkHdlcRxShort
                           Counter,
                        amodLinkHdlcStuffingErrors
                           Counter,
                        amodLinkHdlcLostEndMarkers
                           Counter,
                        amodLinkHdlcRxOverflow
                           Counter,
                        amodLinkTxCalls
                           Counter,
                        amodLinkTxCallsFailed
                           Counter,
                        amodLinkRxCalls
                           Counter
                        }

amodLinkIfIndex OBJECT-TYPE
    SYNTAX INTEGER
    ACCESS read-only
    STATUS mandatory
    DESCRIPTION "Async modem Link index. This is a number that uniquely
                 "
    ::= { amodLinkEntry 1 }

amodLinkHdlcRxChecksumErrors OBJECT-TYPE
    SYNTAX Counter
    ACCESS read-only
    STATUS mandatory
    DESCRIPTION "Number of packest where the checksum is wrong"
    ::= { amodLinkEntry 2 }

amodLinkHdlcRxLong OBJECT-TYPE
    SYNTAX Counter
    ACCESS read-only
    STATUS mandatory
    DESCRIPTION "Number of packets that are too long"
    ::= { amodLinkEntry 3 }

amodLinkHdlcRxShort OBJECT-TYPE
    SYNTAX Counter
    ACCESS read-only
    STATUS mandatory
    DESCRIPTION "Number of packets that are too short"
    ::= { amodLinkEntry 4 }

amodLinkHdlcStuffingErrors OBJECT-TYPE
    SYNTAX Counter
    ACCESS read-only
    STATUS mandatory
    DESCRIPTION "guf 1"
    ::= { amodLinkEntry 5 }

amodLinkHdlcLostEndMarkers OBJECT-TYPE
    SYNTAX Counter
    ACCESS read-only
    STATUS mandatory
    DESCRIPTION "guf 2"
    ::= { amodLinkEntry 6 }

amodLinkHdlcRxOverflow OBJECT-TYPE
    SYNTAX Counter
    ACCESS read-only
    STATUS mandatory
    DESCRIPTION "guf 3"
    ::= { amodLinkEntry 7 }

amodLinkTxCalls OBJECT-TYPE
    SYNTAX Counter
    ACCESS read-only
    STATUS mandatory
    DESCRIPTION ""
    ::= { amodLinkEntry 8 }

amodLinkTxCallsFailed OBJECT-TYPE
    SYNTAX Counter
    ACCESS read-only
    STATUS mandatory
    DESCRIPTION ""
    ::= { amodLinkEntry 9 }

amodLinkRxCalls OBJECT-TYPE
    SYNTAX Counter
    ACCESS read-only
    STATUS mandatory
    DESCRIPTION ""
    ::= { amodLinkEntry 10 }

END
