UsrUserMan-MIB DEFINITIONS ::= BEGIN

	IMPORTS
		Counter, IpAddress
			FROM RFC1155-SMI
		OBJECT-TYPE
			FROM RFC-1212
		DisplayString FROM RFC1213-MIB
		usrUserMan, UsrUserName
			FROM USR-DEFINITIONS-MIB;

	usrUserManGroup	OBJECT IDENTIFIER ::= { usrUserMan 1 }


-- Begin managed object definitions here...

	usrUserManRadiusIP	OBJECT-TYPE
	SYNTAX	IpAddress
	ACCESS	read-write
	STATUS	mandatory
	DESCRIPTION
		"The IP address of the RADIUS server"
	--CONFIGURABLE
	::= { usrUserManGroup 1 }

	usrUserManRadiusAltIP	OBJECT-TYPE
	SYNTAX	IpAddress
	ACCESS	read-write
	STATUS	mandatory
	DESCRIPTION
		"The alternate IP address of the RADIUS server"
	--CONFIGURABLE
	::= { usrUserManGroup 2 }

	usrUserManRadiusAcctIP	OBJECT-TYPE
	SYNTAX	IpAddress
	ACCESS	read-write
	STATUS	mandatory
	DESCRIPTION
		"The IP address of the RADIUS accounting server"
	--CONFIGURABLE
	::= { usrUserManGroup 3 }

	usrUserManRadiusAcctAltIP	OBJECT-TYPE
	SYNTAX	IpAddress
	ACCESS	read-write
	STATUS	mandatory
	DESCRIPTION
		"The IP address of the RADIUS alternate accounting
			server"
	--CONFIGURABLE
	::= { usrUserManGroup 4 }
	
	usrUserManLocalAuthSuccesses	OBJECT-TYPE
	SYNTAX	Counter
	ACCESS	read-only
	STATUS	mandatory
	DESCRIPTION
		"The number of local authentication successes"
	::= { usrUserManGroup 5 }

	usrUserManLocalAuthFails	OBJECT-TYPE
	SYNTAX	Counter
	ACCESS	read-only
	STATUS	mandatory
	DESCRIPTION
		"The number of local authentication failures"
	::= { usrUserManGroup 6 }

	usrUserManRadiusAuthSuccesses	OBJECT-TYPE
	SYNTAX	Counter
	ACCESS	read-only
	STATUS	mandatory
	DESCRIPTION
		"The number of radius authentication successes"
	::= { usrUserManGroup 7 }

	usrUserManRadiusAuthFails	OBJECT-TYPE
	SYNTAX	Counter
	ACCESS	read-only
	STATUS	mandatory
	DESCRIPTION
		"The number of radius authentication failures"
	::= { usrUserManGroup 8 }

	usrUserManLocalUsers	OBJECT-TYPE
	SYNTAX	Counter
	ACCESS	read-only
	STATUS	mandatory
	DESCRIPTION
		"The number of local users"
	::= { usrUserManGroup 9 }

	usrUserManActiveUsers	OBJECT-TYPE
	SYNTAX	Counter
	ACCESS	read-only
	STATUS	mandatory
	DESCRIPTION
		"The number of active users"
	::= { usrUserManGroup 10 }

	usrUserManRetransmissions	OBJECT-TYPE
	SYNTAX	Counter
	ACCESS	read-only
	STATUS	mandatory
	DESCRIPTION
		"The number of udp packet retransmissions"
	::= { usrUserManGroup 11 }

	usrUserManUdpReceives	OBJECT-TYPE
	SYNTAX	Counter
	ACCESS	read-only
	STATUS	mandatory
	DESCRIPTION
		"The number of udp packets received"
	::= { usrUserManGroup 12 }

	usrUserManRadiusRetrans	OBJECT-TYPE
	SYNTAX	INTEGER
	ACCESS	read-write
	STATUS 	mandatory
	DESCRIPTION
		"The maximum number of times a timeout will occur when
			communicating with radius"	
	--CONFIGURABLE
	::= { usrUserManGroup 13 }

	usrUserManRadiusTimeout	OBJECT-TYPE
	SYNTAX	INTEGER
	ACCESS	read-write
	STATUS	mandatory
	DESCRIPTION
		"The maximum amount of time in seconds we will wait
			for a RADIUS response before retransmitting"
	--CONFIGURABLE
	::= { usrUserManGroup 14 }

	usrUserManAcctRetrans	OBJECT-TYPE
	SYNTAX	INTEGER
	ACCESS	read-write
	STATUS 	mandatory
	DESCRIPTION
		"The maximum number of times a timeout will occur when
			communicating with radius accounting server"
	--CONFIGURABLE
	::= { usrUserManGroup 15 }

	usrUserManAcctTimeout	OBJECT-TYPE
	SYNTAX	INTEGER
	ACCESS	read-write
	STATUS	mandatory
	DESCRIPTION
		"The maximum amount of time in seconds we will wait
			for a RADIUS accounting response before retransmitting"
	--CONFIGURABLE
	::= { usrUserManGroup 16 }

	usrUserManLocalAuth	OBJECT-TYPE
	SYNTAX	INTEGER {
			enabled(1),
			disabled(2)
		} 
	ACCESS	read-write
	STATUS	mandatory
	DESCRIPTION
		"Is local authentication on or off"
	--CONFIGURABLE
	::= { usrUserManGroup 17 }

	usrUserManAcct	OBJECT-TYPE
	SYNTAX	INTEGER {
			enabled(1),
			disabled(2)
		} 
	ACCESS	read-write
	STATUS	mandatory
	DESCRIPTION
		"Is accounting on or off"
	--CONFIGURABLE
	::= { usrUserManGroup 18 }

	usrUserManAcctServers	OBJECT-TYPE
	SYNTAX	INTEGER {
			one(1),
			both(2)
		} 
	ACCESS	read-write
	STATUS	mandatory
	DESCRIPTION
		"Do we want to consider both servers specified as primary"
	--CONFIGURABLE
	::= { usrUserManGroup 19 }

	usrUserManRadiusAuth	OBJECT-TYPE
	SYNTAX	INTEGER {
			enabled(1),
			disabled(2)
		}
	ACCESS	read-write
	STATUS	mandatory
	DESCRIPTION
		"Is radius authentication on or off"
	--CONFIGURABLE
	::= { usrUserManGroup 20 }
	
	usrUserManStartAccountTime	OBJECT-TYPE
	SYNTAX	INTEGER	{
			connectionTime(1),
			authenticationTime(2)
			}
	ACCESS	read-write
	STATUS	mandatory
	DESCRIPTION
		"When do we want to account from"
	--CONFIGURABLE
	::= { usrUserManGroup 21 }

	usrUserManSnmpAccess	OBJECT-TYPE
	SYNTAX	INTEGER	{
			enable(1),
			disable(2)
			}
	ACCESS	read-write
	STATUS	mandatory
	DESCRIPTION
		"Do we allow snmp to set our user table"
	--CONFIGURABLE
	::= { usrUserManGroup 22 }

	usrUserManSaveUsers 	OBJECT-TYPE
	SYNTAX	INTEGER	{
			normal(0),
			save(2)
			}
	ACCESS	not-accessible
	STATUS	mandatory
	DESCRIPTION
		"If we hit the save flag the users will be saved to flash"
	::= { usrUserManGroup 23 }

	usrUserManRadiusSecret OBJECT-TYPE
	SYNTAX	OCTET STRING (SIZE (1..15))
	ACCESS	write-only
	STATUS	mandatory
	DESCRIPTION
		"The shared secret between the RADIUS server and pilgrim"
	--CONFIGURABLE
	::= { usrUserManGroup 24 }

-- User managers table definition

	usrUserManTable	OBJECT-TYPE
	SYNTAX SEQUENCE OF UumEntry
	ACCESS	not-accessible
	STATUS	mandatory
	DESCRIPTION
		""
	::= { usrUserManGroup 25 }
 
	uumEntry	OBJECT-TYPE
	SYNTAX	UumEntry
	ACCESS	not-accessible
	STATUS	mandatory
	DESCRIPTION
		""
	INDEX	{ uumUserName }
	::= { usrUserManTable 1 }

	UumEntry ::=
	SEQUENCE {
	uumUserName
		UsrUserName,
	uumStatus
		INTEGER,
	uumUserPassword
		OCTET STRING,
	uumServiceType
		INTEGER,
	uumFramedProtocol
		INTEGER,
	uumFramedIpAddress
		IpAddress,
	uumFramedIpNetmask
		IpAddress,
	uumFramedRouting
		INTEGER,
	uumFilterIdInput
		OCTET STRING,
	uumFramedMtu
		INTEGER,
	uumFramedCompression
		INTEGER,
	uumLoginIpHost
		IpAddress,
	uumLoginService
		INTEGER,
	uumLoginPort
		INTEGER,
	uumReplyMessage
		OCTET STRING,
	uumCallbackNumberOne
		OCTET STRING,
	uumExpiration
		OCTET STRING,
	uumFramedRoute
		OCTET STRING,
	uumFramedIpxNetwork
		OCTET STRING,
	uumSessionTimeout
		INTEGER,
	uumIdleTimeout
		INTEGER,
	uumBearerCapabilities
		INTEGER,
	uumSpeedOfConnection
		INTEGER,
	uumMaxChannels
		INTEGER,
	uumChannelExpansion
		INTEGER,
	uumChannelDecrement
		INTEGER,
	uumExpansionAlgorithm
		INTEGER,
	uumCompressionAlgorithm
		INTEGER,
	uumReceiveAccMap
		INTEGER,
	uumTransmitAccMap
		INTEGER,
	uumWhereCompression
		INTEGER,
	uumCompressionResetMode
		INTEGER,
	uumMinCompressionSize
		INTEGER,
	uumLocationType
		INTEGER,
	uumIp
		INTEGER,
	uumIpx
		INTEGER,
	uumFilterZones
		INTEGER,
	uumFilterIdOutput
		OCTET STRING,
	uumAppletalk
		INTEGER,
	uumBridging
		INTEGER,
	uumSpoofing
		INTEGER,
	uumHostType
		INTEGER,
	uumSendName
		OCTET STRING,
	uumSendPassword
		OCTET STRING,
	uumStartTime
		OCTET STRING,
	uumEndTime
		OCTET STRING,
	uumSendScript1
		OCTET STRING,
	uumReplyScript1
		OCTET STRING,
	uumSendScript2
		OCTET STRING,
	uumReplyScript2
		OCTET STRING,
	uumSendScript3
		OCTET STRING,
	uumReplyScript3
		OCTET STRING,
	uumSendScript4
		OCTET STRING,
	uumReplyScript4
		OCTET STRING,
	uumSendScript5
		OCTET STRING,
	uumReplyScript5
		OCTET STRING,
	uumSendScript6
		OCTET STRING,
	uumReplyScript6
		OCTET STRING,
	uumTerminalType
		OCTET STRING,
	uumAppletalkNetworkRange
		OCTET STRING,
	uumLocalIpAddress
		IpAddress,
	uumRoutingProtocol
		INTEGER,
	uumCallbackNumberTwo
		OCTET STRING,
	uumModemGroup	
		OCTET STRING,
	uumIpxRouting
		INTEGER,
	uumIpxWan
		INTEGER,
	uumIpRipSendDefault
		INTEGER,
	uumIpRipSendRoutes
		INTEGER,
	uumIpRipSendSubnets
		INTEGER,
	uumIpRipAcceptDefault
		INTEGER,
	uumIpRipSplitHorizon
		INTEGER,
	uumIpRipPoisonReverse
		INTEGER,
	uumIpRipFlashUpdate
		INTEGER,
	uumIpRipV1Send
		INTEGER,
	uumIpRipV1Receive
		INTEGER,
	uumIpRipV2Receive
		INTEGER,
	uumIpRipSilent
		INTEGER,
	uumSimpleAuthPassword
		OCTET STRING,
	uumIpDefaultRouteOption
		INTEGER,
	uumIpPatOption
		INTEGER,
	uumATMCategoryOfService	
		INTEGER,
	uumATMVpi	
		INTEGER,
	uumATMVci
		INTEGER,
	uumATMPeakCellRate
		INTEGER,
	uumATMSustainableCellRate
		INTEGER,
	uumATMBurstTolerance
		INTEGER,
	uumPatDefaultPrivAddr
		IpAddress,
        uumIpSrcValidationOption
                INTEGER,
	uumUserDesignation
		INTEGER,
	uumATMVcType
		INTEGER,
	uumOwnership
		INTEGER,
	uumMacEncapsulatedRouting
		INTEGER,
	uumIpIntelligentNat
		INTEGER,
	uumIpDynamicAddrProto
		INTEGER,
	uumMgmtIpAddress
		IpAddress,
	uumMgmtIpNetmask
		IpAddress,
	uumInternalCallToProto
		INTEGER
	}

	uumUserName	OBJECT-TYPE
	SYNTAX	UsrUserName
	ACCESS	not-accessible
	STATUS	mandatory
	DESCRIPTION
		"The users name"
	::= { uumEntry 1 }
		
	uumStatus	OBJECT-TYPE
	SYNTAX	INTEGER {
		delete(1),
		inactive(2),
		active(3),
		enabled(4),
		disabled(5),
		active-disabled(6)
		}
	ACCESS	read-write
	STATUS	mandatory
	DESCRIPTION
		"The status field for delete"
	::= { uumEntry 2 }

	uumUserPassword	OBJECT-TYPE
	SYNTAX	OCTET STRING (SIZE (1..15))
	ACCESS	write-only
	STATUS	mandatory
	DESCRIPTION
		"The users password"
	::= { uumEntry 3 }

	uumServiceType	OBJECT-TYPE
	SYNTAX	INTEGER 
	ACCESS	read-write
	STATUS	mandatory
	DESCRIPTION
		"The bitmap indicating one or more types of user:
	login 0x1, framed 0x2, callback 0x4, dial-out 0x8,
	administrative 0x10"
	::= { uumEntry 4 }

	uumFramedProtocol	OBJECT-TYPE
	SYNTAX	INTEGER {
		ppp(1),
		slip(2),
		arap(3),
		frame-relay(4),
		rfc-1483(5),
		pppllc(6),
		rfc-1490(7),
		pppoe-client(8),
		pppoeClientLLC(9)
		}
	ACCESS	read-write
	STATUS	mandatory
	DESCRIPTION
		"The framed users protocol"
	::= { uumEntry 5 }

	uumFramedIpAddress	OBJECT-TYPE
	SYNTAX	IpAddress
	ACCESS	read-write
	STATUS	mandatory
	DESCRIPTION
		"The IP destination for the framed user"
	::= { uumEntry 6 }

	uumFramedIpNetmask	OBJECT-TYPE
	SYNTAX	IpAddress
	ACCESS	read-write
	STATUS	mandatory
	DESCRIPTION
		"The destinations netmask"
	::= { uumEntry 7 }

	uumFramedRouting	OBJECT-TYPE
	SYNTAX	INTEGER {
		none(0),
		broadcastRoutingPackets(1),
		listenForRoutingPackets(2),
		broadcastAndListen(3)
		}
	ACCESS	read-write
	STATUS	mandatory
	DESCRIPTION
		"The routing defined for a framed user"
	::= { uumEntry 8 }

	uumFilterIdInput	OBJECT-TYPE
	SYNTAX	OCTET STRING (SIZE (1..240))
	ACCESS	read-write
	STATUS	mandatory
	DESCRIPTION
		"The input or output filter defined for the user"
	::= { uumEntry 9 }

	uumFramedMtu	OBJECT-TYPE
	SYNTAX	INTEGER
	ACCESS	read-write
	STATUS	mandatory
	DESCRIPTION
		"The framed maximum transmission unit"
	::= { uumEntry 10 }

	uumFramedCompression	OBJECT-TYPE
	SYNTAX	INTEGER {
		none(0),
		tcpIpCompression(1),
		ipxCompression(2)
		}
	ACCESS	read-write
	STATUS	mandatory
	DESCRIPTION
		"The compression being used for the framed user"
	::= { uumEntry 11 }

	uumLoginIpHost	OBJECT-TYPE
	SYNTAX	IpAddress
	ACCESS	read-write
	STATUS	mandatory
	DESCRIPTION
		"The IP destination for the login user"
	::= { uumEntry 12 }

	uumLoginService	OBJECT-TYPE
	SYNTAX	INTEGER {
		telnet(0),
		rlogin(1),
		tcp(2),
		lat(4)
		}
	ACCESS	read-write
	STATUS	mandatory
	DESCRIPTION
		"The login user's protocol"
	::= { uumEntry 13 }

	uumLoginPort	OBJECT-TYPE
	SYNTAX	INTEGER
	ACCESS	read-write
	STATUS	mandatory
	DESCRIPTION
		"The tcp port the user will use"
	::= { uumEntry 14 }

	uumReplyMessage	OBJECT-TYPE
	SYNTAX	OCTET STRING (SIZE (1..240))
	ACCESS	read-write
	STATUS	mandatory
	DESCRIPTION
		"The message to be displayed to the user"
	::= { uumEntry 15 }

	uumCallbackNumberOne	OBJECT-TYPE
	SYNTAX	OCTET STRING (SIZE (1..240))
	ACCESS	read-write
	STATUS 	mandatory
	DESCRIPTION
		"The first phone number configured for this user"
	::= { uumEntry 16 }

	uumExpiration	OBJECT-TYPE
	SYNTAX	OCTET STRING (SIZE (11))
	ACCESS	read-write
	STATUS	mandatory
	DESCRIPTION
		"The users expiration date"
	::= { uumEntry 17}

	uumFramedRoute	OBJECT-TYPE
	SYNTAX	OCTET STRING (SIZE (0..240))
	ACCESS	read-write
	STATUS	mandatory
	DESCRIPTION 
		"The framed route for the user"
	::= { uumEntry 18 }

	uumFramedIpxNetwork	OBJECT-TYPE
	SYNTAX	OCTET STRING (SIZE (4))
	ACCESS	read-write
	STATUS	mandatory
	DESCRIPTION
		"The ipx network defined for the user"
	::= { uumEntry 19 }

	uumSessionTimeout	OBJECT-TYPE
	SYNTAX	INTEGER
	ACCESS	read-write
	STATUS	mandatory
	DESCRIPTION
		"The amount of time in seconds before time out"
	::= { uumEntry 20 }

	uumIdleTimeout	OBJECT-TYPE
	SYNTAX	INTEGER
	ACCESS	read-write
	STATUS	mandatory
	DESCRIPTION
		"The amount of idle time in seconds before time out"
	::= { uumEntry 21 }

	uumBearerCapabilities	OBJECT-TYPE
	SYNTAX	INTEGER {
		digital(1),
		analog(2)
		}
	ACCESS	not-accessible
	STATUS	mandatory
	DESCRIPTION
		"The type of transmission"
	::= { uumEntry 22 }

	uumSpeedOfConnection	OBJECT-TYPE
	SYNTAX	INTEGER {
		auto(1),
		fifty-six-k(2),
		sixty-four-k(3),
		voice(4)
		}
	ACCESS	read-write
	STATUS	mandatory
	DESCRIPTION
		"The speed of the connection"
	::= { uumEntry 23 }		
		
	uumMaxChannels	OBJECT-TYPE
	SYNTAX	INTEGER
	ACCESS	read-write
	STATUS	mandatory
	DESCRIPTION
		"The maximum number of channels that may be used"
	::= { uumEntry 24 }
 
	uumChannelExpansion	OBJECT-TYPE
	SYNTAX	INTEGER (0..100)
	ACCESS	read-write
	STATUS	mandatory
	DESCRIPTION
		"The percentage for channel expansion"
	::= { uumEntry 25 }

	uumChannelDecrement	OBJECT-TYPE
	SYNTAX	INTEGER (0..100)
	ACCESS	read-write
	STATUS	mandatory
	DESCRIPTION
		"The percentage for channel decrement"
	::= { uumEntry 26 }

	uumExpansionAlgorithm	OBJECT-TYPE
	SYNTAX	INTEGER {
		constant(1),
		linear(2)
		}
	ACCESS	read-write
	STATUS	mandatory
	DESCRIPTION
		"The expansion algorithm being used"
	::= { uumEntry 27 }	
		
	uumCompressionAlgorithm	OBJECT-TYPE
	SYNTAX	INTEGER {
		none(0),
		stac(1),
		ascend(2),
		microsoft(3),
		auto(4)
		}
	ACCESS	read-write
	STATUS	mandatory
	DESCRIPTION
		"The compression algorithm to be used"
	::= { uumEntry 28 }

	uumReceiveAccMap	OBJECT-TYPE
	SYNTAX	INTEGER
	ACCESS	read-write
	STATUS	mandatory
	DESCRIPTION
		"The receive acc mapping"
	::= { uumEntry 29 }

	uumTransmitAccMap	OBJECT-TYPE
	SYNTAX	INTEGER
	ACCESS	read-write
	STATUS	mandatory
	DESCRIPTION
		"The transmit acc mapping"
	::= { uumEntry 30 }
	
	uumWhereCompression	OBJECT-TYPE
	SYNTAX	INTEGER {
		link(1),
		bundle(2)
		}	
	ACCESS	not-accessible
	STATUS	mandatory
	DESCRIPTION
		"The area where compression should be done"
	::= { uumEntry 31 }

	uumCompressionResetMode	OBJECT-TYPE
	SYNTAX	INTEGER {
		auto(1),
		resetEveryPacket(2),
		resetEveryError(3)
		}
	ACCESS	read-write
	STATUS	mandatory
	DESCRIPTION
		"The mode that the compression should be reset in"
	::= { uumEntry 32 }

	uumMinCompressionSize	OBJECT-TYPE
	SYNTAX	INTEGER 
	ACCESS	read-write
	STATUS	mandatory
	DESCRIPTION
		"The minimum size for compression"
	::= { uumEntry 33 }

	uumLocationType	OBJECT-TYPE
	SYNTAX	INTEGER {
		continuous(1),
		onDemand(2),
		manual(3),
		timed(4)
		}
	ACCESS	read-write
	STATUS	mandatory
	DESCRIPTION
		"The type of location user"
	::= { uumEntry 34 }

	uumIp	OBJECT-TYPE
	SYNTAX	INTEGER {
		enabled(1),
		disabled(2)
		}
	ACCESS	read-write
	STATUS	mandatory
	DESCRIPTION
		"Ip enabled or disabled"
	::= { uumEntry 35 }

	uumIpx	OBJECT-TYPE
	SYNTAX	INTEGER {
		enabled(1),
		disabled(2)
		}
	ACCESS	read-write
	STATUS	mandatory
	DESCRIPTION
		"Ipx enabled or disabled"
	::= { uumEntry 36 }

	uumFilterZones	OBJECT-TYPE
	SYNTAX	INTEGER {
		enabled(1),
		disabled(2)
		}
	ACCESS	read-write
	STATUS	mandatory
	DESCRIPTION
		"Arap needed to define filter zones"
	::= { uumEntry 37 }	

	uumFilterIdOutput	OBJECT-TYPE
	SYNTAX	OCTET STRING (SIZE (1..240))
	ACCESS	read-write
	STATUS	mandatory
	DESCRIPTION
		"The output filter defined for the user"
	::= { uumEntry 38 }

	uumAppletalk	OBJECT-TYPE
	SYNTAX	INTEGER {
		enabled(1),
		disabled(2)
		}
	ACCESS	read-write
	STATUS	mandatory
	DESCRIPTION
		"Appletalk enabled or disabled"
	::= { uumEntry 39 }

	uumBridging	OBJECT-TYPE
	SYNTAX	INTEGER {
		enabled(1),
		disabled(2)
		}
	ACCESS	read-write
	STATUS	mandatory
	DESCRIPTION
		"Bridging enabled or disabled"
	::= { uumEntry 40 }

	uumSpoofing	OBJECT-TYPE
	SYNTAX	INTEGER {
		enabled(1),
		disabled(2)
		}
	ACCESS	read-write
	STATUS	mandatory
	DESCRIPTION
		"Ipx spoofing enabled or disabled"
	::= { uumEntry 41 }

	uumHostType	OBJECT-TYPE
	SYNTAX	INTEGER {
		prompt(1),
		default(2),
		specified(3)
		}
	ACCESS	not-accessible
	STATUS	mandatory
	DESCRIPTION
		"The means for specifying a host for this user"
	::= { uumEntry 42 }

	uumSendName	OBJECT-TYPE
	SYNTAX	OCTET STRING (SIZE (1..240))
	ACCESS	read-write
	STATUS	mandatory
	DESCRIPTION
		"Name we use when challenged for authentication"
	::= { uumEntry 43 }

	uumSendPassword	OBJECT-TYPE
	SYNTAX	OCTET STRING (SIZE (1..240))
	ACCESS	read-write
	STATUS	mandatory
	DESCRIPTION
		"Password we use when challenged for authentication"
	::= { uumEntry 44 }
				
	uumStartTime	OBJECT-TYPE
	SYNTAX	OCTET STRING (SIZE (11))
	ACCESS	read-write
	STATUS	mandatory
	DESCRIPTION
		"Daily time we start timed location"
	::= { uumEntry 45 }

	uumEndTime	OBJECT-TYPE
	SYNTAX	OCTET STRING (SIZE (11))
	ACCESS	read-write
	STATUS	mandatory
	DESCRIPTION
		"Daily time we stop timed location"
	::= { uumEntry 46 }

	uumSendScript1	OBJECT-TYPE
	SYNTAX	OCTET STRING (SIZE (1..240))
	ACCESS	read-write
	STATUS	mandatory
	DESCRIPTION
		"The first send script for this dial-out user"
	::= { uumEntry 47 }

	uumReplyScript1	OBJECT-TYPE
	SYNTAX	OCTET STRING (SIZE (1..240))
	ACCESS	read-write
	STATUS	mandatory
	DESCRIPTION
		"The first reply script for this dial-out user"
	::= { uumEntry 48 }

	uumSendScript2	OBJECT-TYPE
	SYNTAX	OCTET STRING (SIZE (1..240))
	ACCESS	read-write
	STATUS	mandatory
	DESCRIPTION
		"The second send script for this dial-out user"
	::= { uumEntry 49 }

	uumReplyScript2	OBJECT-TYPE
	SYNTAX	OCTET STRING (SIZE (1..240))
	ACCESS	read-write
	STATUS	mandatory
	DESCRIPTION
		"The second reply script for this dial-out user"
	::= { uumEntry 50 }

	uumSendScript3	OBJECT-TYPE
	SYNTAX	OCTET STRING (SIZE (1..240))
	ACCESS	read-write
	STATUS	mandatory
	DESCRIPTION
		"The third send script for this dial-out user"
	::= { uumEntry 51 }

	uumReplyScript3	OBJECT-TYPE
	SYNTAX	OCTET STRING (SIZE (1..240))
	ACCESS	read-write
	STATUS	mandatory
	DESCRIPTION
		"The third reply script for this dial-out user"
	::= { uumEntry 52 }

	uumSendScript4	OBJECT-TYPE
	SYNTAX	OCTET STRING (SIZE (1..240))
	ACCESS	read-write
	STATUS	mandatory
	DESCRIPTION
		"The fourth send script for this dial-out user"
	::= { uumEntry 53 }

	uumReplyScript4	OBJECT-TYPE
	SYNTAX	OCTET STRING (SIZE (1..240))
	ACCESS	read-write
	STATUS	mandatory
	DESCRIPTION
		"The fourth reply script for this dial-out user"
	::= { uumEntry 54 }

	uumSendScript5	OBJECT-TYPE
	SYNTAX	OCTET STRING (SIZE (1..240))
	ACCESS	read-write
	STATUS	mandatory
	DESCRIPTION
		"The fifth send script for this dial-out user"
	::= { uumEntry 55 }

	uumReplyScript5	OBJECT-TYPE
	SYNTAX	OCTET STRING (SIZE (1..240))
	ACCESS	read-write
	STATUS	mandatory
	DESCRIPTION
		"The fifth reply script for this dial-out user"
	::= { uumEntry 56 }

	uumSendScript6	OBJECT-TYPE
	SYNTAX	OCTET STRING (SIZE (1..240))
	ACCESS	read-write
	STATUS	mandatory
	DESCRIPTION
		"The sixth send script for this dial-out user"
	::= { uumEntry 57 }

	uumReplyScript6	OBJECT-TYPE
	SYNTAX	OCTET STRING (SIZE (1..240))
	ACCESS	read-write
	STATUS	mandatory
	DESCRIPTION
		"The sixth reply script for this dial-out user"
	::= { uumEntry 58 }

	uumTerminalType	OBJECT-TYPE
	SYNTAX	OCTET STRING (SIZE (1..240))
	ACCESS	read-write
	STATUS	mandatory
	DESCRIPTION
		"The terminal type for the user"
	::= { uumEntry 59 }

	uumAppletalkNetworkRange	OBJECT-TYPE
	SYNTAX	OCTET STRING (SIZE (4))
	ACCESS	read-write
	STATUS	mandatory
	DESCRIPTION
		"The appletalk network range for the user"
	::= { uumEntry 60 }

	uumLocalIpAddress	OBJECT-TYPE
	SYNTAX	IpAddress
	ACCESS	read-write
	STATUS	mandatory
	DESCRIPTION
		"The local ip address configured for a dial-out user"
	::= { uumEntry 61 }

	uumRoutingProtocol	OBJECT-TYPE
	SYNTAX	INTEGER {
		rip1(1),
		rip2(2)
		}
	ACCESS	read-write
	STATUS	mandatory
	DESCRIPTION
		"The routing protocol configured for a user"
	::= { uumEntry 62 }
	
	uumCallbackNumberTwo	OBJECT-TYPE
	SYNTAX	OCTET STRING (SIZE (1..240))
	ACCESS	read-write
	STATUS 	mandatory
	DESCRIPTION
		"The first phone number configured for this user"
	::= { uumEntry 63 }
	
	uumModemGroup	OBJECT-TYPE
	SYNTAX	OCTET STRING (SIZE (1..240))
	ACCESS	read-write
	STATUS	mandatory
	DESCRIPTION
		"The modem group string for the user"
	::= { uumEntry 64 }

	uumIpxRouting	OBJECT-TYPE
	SYNTAX	INTEGER {
		none(0),
		send(1),
		listen(2),
		respond(3),
		all(4)
		}
	ACCESS	read-write
	STATUS	mandatory
	DESCRIPTION
		"The ipx routing defined for a framed user"
	::= { uumEntry 65 }

	uumIpxWan	OBJECT-TYPE
	SYNTAX	INTEGER {
		enable(1),
		disable(2)
		}
	ACCESS	read-write
	STATUS	mandatory
	DESCRIPTION
		"Is ipx wan enabled or disabled for the user"
	::= { uumEntry 66 }

	uumIpRipSendDefault	OBJECT-TYPE
	SYNTAX	INTEGER {
		enable(1),
		disable(2)
		}
	ACCESS	read-write
	STATUS	mandatory
	DESCRIPTION
		"IP RIP flag"
	::= { uumEntry 67 }

	uumIpRipSendRoutes	OBJECT-TYPE
	SYNTAX	INTEGER {
		enable(1),
		disable(2)
		}
	ACCESS	read-write
	STATUS	mandatory
	DESCRIPTION
		"IP RIP flag"
	::= { uumEntry 68 }

	uumIpRipSendSubnets	OBJECT-TYPE
	SYNTAX	INTEGER {
		enable(1),
		disable(2)
		}
	ACCESS	read-write
	STATUS	mandatory
	DESCRIPTION
		"IP RIP flag"
	::= { uumEntry 69 }

	uumIpRipAcceptDefault	OBJECT-TYPE
	SYNTAX	INTEGER {
		enable(1),
		disable(2)
		}
	ACCESS	read-write
	STATUS	mandatory
	DESCRIPTION
		"IP RIP flag"
	::= { uumEntry 70 }

	uumIpRipSplitHorizon	OBJECT-TYPE
	SYNTAX	INTEGER {
		enable(1),
		disable(2)
		}
	ACCESS	read-write
	STATUS	mandatory
	DESCRIPTION
		"IP RIP flag"
	::= { uumEntry 71 }
	
	uumIpRipPoisonReverse	OBJECT-TYPE
	SYNTAX	INTEGER {
		enable(1),
		disable(2)
		}
	ACCESS	read-write
	STATUS	mandatory
	DESCRIPTION
		"IP RIP flag"
	::= { uumEntry 72 }

	uumIpRipFlashUpdate	OBJECT-TYPE
	SYNTAX	INTEGER {
		enable(1),
		disable(2)
		}
	ACCESS	read-write
	STATUS	mandatory
	DESCRIPTION
		"IP RIP flag"
	::= { uumEntry 73 }

	uumIpRipSimpleAuth	OBJECT-TYPE
	SYNTAX	INTEGER {
		enable(1),
		disable(2)
		}
	ACCESS	read-only
	STATUS	mandatory
	DESCRIPTION
		"IP RIP flag"
	::= { uumEntry 74 }

	uumIpRipV1Send	OBJECT-TYPE
	SYNTAX	INTEGER {
		enable(1),
		disable(2)
		}
	ACCESS	read-write
	STATUS	mandatory
	DESCRIPTION
		"IP RIP flag"
	::= { uumEntry 75 }

	uumIpRipV1Receive	OBJECT-TYPE
	SYNTAX	INTEGER {
		enable(1),
		disable(2)
		}
	ACCESS	read-write
	STATUS	mandatory
	DESCRIPTION
		"IP RIP flag"
	::= { uumEntry 76 }

	uumIpRipV2Receive	OBJECT-TYPE
	SYNTAX	INTEGER {
		enable(1),
		disable(2)
		}
	ACCESS	read-write
	STATUS	mandatory
	DESCRIPTION
		"IP RIP flag"
	::= { uumEntry 77 }

	uumIpRipSilent	OBJECT-TYPE
	SYNTAX	INTEGER {
		enable(1),
		disable(2)
		}
	ACCESS	read-write
	STATUS	mandatory
	DESCRIPTION
		"IP RIP flag"
	::= { uumEntry 78 }

	uumSimpleAuthPassword	OBJECT-TYPE
	SYNTAX	OCTET STRING (SIZE (1..64))
	ACCESS	read-write
	STATUS	mandatory
	DESCRIPTION
		"The IP RIP simple authentication password"
	::= { uumEntry 79 }

	uumIpDefaultRouteOption	OBJECT-TYPE
	SYNTAX	INTEGER {
		enable(1),
		disable(2)
		}
	ACCESS	read-write
	STATUS	mandatory
	DESCRIPTION
		"If enable (1) a default route will be created using
                 the remote users IP address.  If disable (2) no such
                 route is created."
	::= { uumEntry 80 }

	uumIpPatOption	OBJECT-TYPE
	SYNTAX	INTEGER {
		pat(1),
                nat(2),
		disable(3)
		}
	ACCESS	read-write
	STATUS	mandatory
	DESCRIPTION
                "Network Address Translation (NAT) option field.  When NAT is enabled, 
                 the local LAN addresses are replaced with public recoginzed addresses
                 when the frame traverses a WAN interface.  A mapping between the public and 
                 private addresses is maintained while a connection/session remains active. 
                 Once the connection goes inactive or idle, the mapping is relinquished and 
                 the public address or port can be reused.  Two types of NAT are supported,
                 Port Address Translation (PAT) and the standard NAT (RFC 1631).  With PAT, 
                 the mapping is maintained by the TCP and UDP port number.   The private 
                 address is replaced with the public WAN interface address and the port number 
                 is replaced with a dynamically assigned public port number.  With the standard
                 NAT (RFC 1631), the private address is replaced with dynamically allocated 
                 public addresses taken from a configured address pool.  Both PAT and NAT can 
                 be configured with static assignments. "
	::= { uumEntry 81 }

	uumATMCategoryOfService	OBJECT-TYPE
	SYNTAX	INTEGER {
		unspecified-bit-rate(1),
		variable-bit-rate(2),
		constant-bit-rate(3)
		}
	ACCESS	read-write
	STATUS	mandatory
	DESCRIPTION
		"The ATM category of service"
	::= { uumEntry 82 }		

	uumATMVpi	OBJECT-TYPE
	SYNTAX	INTEGER
	ACCESS	read-write
	STATUS	mandatory
	DESCRIPTION
		"The ATM Virtual Path Id"
	::= { uumEntry 83 }

	uumATMVci	OBJECT-TYPE
	SYNTAX	INTEGER
	ACCESS	read-write
	STATUS	mandatory
	DESCRIPTION
		"The ATM Virtual Channel Id"
	::= { uumEntry 84 }

	uumATMPeakCellRate	OBJECT-TYPE
	SYNTAX	INTEGER
	ACCESS	read-write
	STATUS	mandatory
	DESCRIPTION
		"The ATM Peak Cell Rate"
	::= { uumEntry 85 }

	uumATMSustainableCellRate	OBJECT-TYPE
	SYNTAX	INTEGER
	ACCESS	read-write
	STATUS	mandatory
	DESCRIPTION
		"The ATM Sustainable Cell Rate"
	::= { uumEntry 86 }

	uumATMBurstTolerance	OBJECT-TYPE
	SYNTAX	INTEGER
	ACCESS	read-write
	STATUS	mandatory
	DESCRIPTION
		"The ATM Burst Tolerance"
	::= { uumEntry 87 }

        uumPatDefaultPrivAddr   OBJECT-TYPE
        SYNTAX  IpAddress
        ACCESS  read-write
        STATUS  mandatory
        DESCRIPTION
                "When the NatOption is configured for PAT and a frame
                 is received from the Public Net on a port which does not 
                 have a private address mapping, the frame will be  
                 mapped to the PatDefaultPrivAddr if it is configured. If 
                 the PatDefaultPrivAddr is not configured, 0.0.0.0, the 
                 frame will be discarded."
        ::= { uumEntry 88 }

        uumIpSrcValidationOption OBJECT-TYPE
        SYNTAX  INTEGER {
                enable(1),
                disable(2)
                }
        ACCESS  read-write
        STATUS  mandatory
        DESCRIPTION
                "If enabled, the source address on incoming frames will be 
                 validated.  If a route does not exist for the source 
                 address on the same interface on which the packet was 
                 received, the frame will be silently discarded. The default 
                 for this option is disabled."
        ::= { uumEntry 89 }

	uumUserDesignation	OBJECT-TYPE
	SYNTAX	INTEGER {
		unknown(1),
		internet(2),
		telecommuter(3)
		}
	ACCESS	read-write
	STATUS	mandatory
	DESCRIPTION
		"The users designated type."
	::= { uumEntry 90 }

	uumATMVcType	OBJECT-TYPE
	SYNTAX	INTEGER {
		pvc(1),
		svc(2)
		}
	ACCESS	read-write
	STATUS	mandatory
	DESCRIPTION
		"The type of vc (permanent or switched)."
	::= { uumEntry 91 }		

	uumOwnership OBJECT-TYPE
	SYNTAX	INTEGER {
		autoProvision(1),
		notAutoProvision(2)
		}
	ACCESS	read-write
	STATUS	mandatory
	DESCRIPTION
		"To identify the VC created by auto provisionsing process or some other processes"
	::= { uumEntry 92 }		

	uumMacEncapsulatedRouting OBJECT-TYPE
	SYNTAX	INTEGER {
		enabled(1),
		disabled(2)
		}
	ACCESS	read-write
	STATUS	mandatory
	DESCRIPTION
		"To identify that routed frames will be transmitted out the WAN ports 
		 prepended with a MAC header."
	::= { uumEntry 93 }		

	uumIpIntelligentNat OBJECT-TYPE
	SYNTAX	INTEGER {
		enabled(1),
		disabled(2)
		}
	ACCESS	read-write
	STATUS	mandatory
	DESCRIPTION
		"Only applicable when uumIpPatOption is set to pat. When enabled and processing 
		 an incoming frame without an existing translation mapping, the client with the
		 last access to the remote host will be chosen.  If not found, the 
		 uumPatDefaultPrivAddr will be used."
	::= { uumEntry 94 }		

	uumIpDynamicAddrProto OBJECT-TYPE
	SYNTAX	INTEGER {
		disabled(1),
		dhcp(2),
		invarp(3)
		}
	ACCESS	read-write
	STATUS	mandatory
	DESCRIPTION
		"Protocol used to dynamically learn the IP configuration when the network service is
		 NOT PPP.  Current options are DHCP and Inverse ARP."
	::= { uumEntry 95 }		

	uumMgmtIpAddress	OBJECT-TYPE
	SYNTAX	IpAddress
	ACCESS	read-write
	STATUS	mandatory
	DESCRIPTION
		"Management IP address.   When configured, this address can be used to access the device
		 and will be used as the source address by internal services."
	::= { uumEntry 96 }

	uumMgmtIpNetmask	OBJECT-TYPE
	SYNTAX	IpAddress
	ACCESS	read-write
	STATUS	mandatory
	DESCRIPTION
		"The netmask of the Management Network, associated with the uumMgmtIpAddress"
	::= { uumEntry 97 }

	uumInternalCallToProto OBJECT-TYPE
	SYNTAX	INTEGER {
		vatm(1),
		udp(2),
		l2tp(3)
		}
	ACCESS	read-write
	STATUS	mandatory
	DESCRIPTION
		"Internal field used to specify which Protocol Handler CIP should call for
		 this profile. VATM is the default."
	::= { uumEntry 98 }		


	usrUserManCfmFileName	OBJECT-TYPE
	SYNTAX	DisplayString (SIZE (1..32))
	ACCESS	read-only
	STATUS 	mandatory
	DESCRIPTION
		"The name of the configuration file"
	::= { usrUserManGroup 26 }

	usrUserManCfmSaveFlag	OBJECT-TYPE
	SYNTAX	INTEGER	{
			normal(1),
			save(2),
			saving(3), 
			load(4),
			loading(5)
			}
	ACCESS	read-write
	STATUS	mandatory
	DESCRIPTION
		"The Configuration File Manager Flag for saving user management scalars"
	::= { usrUserManGroup 27 }

	usrUserManRadiusPort	OBJECT-TYPE
	SYNTAX	INTEGER	
	ACCESS	read-write
	STATUS	mandatory
	DESCRIPTION
		"The udp port the primary radius server listens at"
	--CONFIGURABLE
	::= { usrUserManGroup 28 }

	usrUserManRadiusAltPort	OBJECT-TYPE
	SYNTAX	INTEGER	
	ACCESS	read-write
	STATUS	mandatory
	DESCRIPTION
		"The udp port the alternate radius server listens at"
	--CONFIGURABLE
	::= { usrUserManGroup 29 }

	usrUserManRadiusAltSecret	OBJECT-TYPE
	SYNTAX	OCTET STRING	(SIZE (1..15))
	ACCESS	write-only
	STATUS	mandatory
	DESCRIPTION
		"The shared secret between the alternate RADIUS server and pilgrim"
	--CONFIGURABLE
	::= { usrUserManGroup 30 }

-- User managers framed route table definition

	usrUserManFramedRouteTable	OBJECT-TYPE
	SYNTAX	SEQUENCE OF UumFramedRouteEntry
	ACCESS	not-accessible
	STATUS	mandatory
	DESCRIPTION
		""
	::= { usrUserManGroup 31 }

	uumFramedRouteEntry	OBJECT-TYPE
	SYNTAX	UumFramedRouteEntry
	ACCESS	not-accessible
	STATUS	mandatory
	DESCRIPTION
		""
	INDEX	{ uumFramedRouteUserName, uumFramedRouteIpAddress }
	::= { usrUserManFramedRouteTable 1 }

	UumFramedRouteEntry ::= 
	SEQUENCE {
	uumFramedRouteUserName
		UsrUserName,
	uumFramedRouteIpAddress
		IpAddress,
	uumFramedRouteStatus
		INTEGER,
	uumFramedRouteIpMask
		IpAddress,
	uumFramedRouteIpGateway
		IpAddress,
	uumFramedRouteIpMetric
		INTEGER
	}

	uumFramedRouteUserName	OBJECT-TYPE
	SYNTAX	UsrUserName
	ACCESS	not-accessible
	STATUS	mandatory
	DESCRIPTION
		"The users name"
	::= { uumFramedRouteEntry 1 }

	uumFramedRouteIpAddress	OBJECT-TYPE
	SYNTAX	IpAddress
	ACCESS	not-accessible
	STATUS	mandatory
	DESCRIPTION
		"The framed routing ip address for the user"
	::= { uumFramedRouteEntry 2 }
	
	uumFramedRouteStatus	OBJECT-TYPE
	SYNTAX	INTEGER {
		delete(1),
		add(2)
		}
	ACCESS	read-write
	STATUS	mandatory
	DESCRIPTION	
		"The status field for the framed route"
	::= { uumFramedRouteEntry 3 }

	uumFramedRouteIpMask	OBJECT-TYPE
	SYNTAX	IpAddress
	ACCESS	read-write
	STATUS	mandatory
	DESCRIPTION
		"The framed routing ip mask for the user"
	::= { uumFramedRouteEntry 4 }	
		
	uumFramedRouteIpGateway	OBJECT-TYPE
	SYNTAX	IpAddress
	ACCESS	read-write
	STATUS	mandatory
	DESCRIPTION
		"The framed routing ip gateway for the user"
	::= { uumFramedRouteEntry 5 }

	uumFramedRouteIpMetric	OBJECT-TYPE
	SYNTAX	INTEGER 
	ACCESS	read-write
	STATUS	mandatory
	DESCRIPTION	
		"The framed routing ip metric for the user"
	::= { uumFramedRouteEntry 6 }

     --
     -- PAT Static IP UDP Port Translation Entries
     --
     usrUserManPatUdpTable OBJECT-TYPE
         SYNTAX  SEQUENCE OF UumPatUdpPortEntry
         ACCESS  not-accessible
         STATUS  mandatory
         DESCRIPTION
            "Static entries that map a UDP port number to a local/private IP
             address/port.  Each entry defines a service and the corresponding
             private Server."
     ::= { usrUserManGroup 32 }
 
 
     uumPatUdpPortEntry OBJECT-TYPE
         SYNTAX  UumPatUdpPortEntry
         ACCESS  not-accessible
         STATUS  mandatory
         DESCRIPTION
            "A static entry that map a UDP port number to a local/private IP
             address/port.  Defines a service and the corresponding
              private Server."
         INDEX   { uumPatUdpPortName, uumPatUdpPublicPort }
     ::= { usrUserManPatUdpTable 1 }
 
     UumPatUdpPortEntry ::=
        SEQUENCE {
            uumPatUdpPortName
               UsrUserName,
            uumPatUdpStatus
               INTEGER,
            uumPatUdpPublicPort
               INTEGER,
            uumPatUdpPrivAddr
               IpAddress,
            uumPatUdpPrivPort
               INTEGER
     }

     uumPatUdpPortName  OBJECT-TYPE
         SYNTAX  UsrUserName
         ACCESS  not-accessible
         STATUS  mandatory
         DESCRIPTION
                 "The users name"
     ::= { uumPatUdpPortEntry 1 }

     uumPatUdpStatus   OBJECT-TYPE
         SYNTAX  INTEGER {
                 delete(1),
                 add(2)
                 }
         ACCESS  read-write
         STATUS  mandatory
         DESCRIPTION
                "The status field for the UDP Port Entry"
     ::= { uumPatUdpPortEntry 2 }

     uumPatUdpPublicPort  OBJECT-TYPE
        SYNTAX INTEGER
        ACCESS read-write
        STATUS mandatory
        DESCRIPTION
            "Public Port corresponding to a Private Address/Port."
     ::= { uumPatUdpPortEntry 3 }

     uumPatUdpPrivAddr  OBJECT-TYPE
        SYNTAX IpAddress
        ACCESS read-write
        STATUS mandatory
        DESCRIPTION
            "Private Address corresponding to a Public Port number."
     ::= { uumPatUdpPortEntry 4 }
 
     uumPatUdpPrivPort  OBJECT-TYPE
        SYNTAX INTEGER
        ACCESS read-write
        STATUS mandatory
        DESCRIPTION
            "Private Port corresponding to a Public Port number."
     ::= { uumPatUdpPortEntry 5 }

     --
     -- PAT Static IP TCP Port Translation Entries
     --
     usrUserManPatTcpTable OBJECT-TYPE
         SYNTAX  SEQUENCE OF UumPatTcpPortEntry
         ACCESS  not-accessible
         STATUS  mandatory
         DESCRIPTION
            "Static entries that map a TCP port number to a local/private IP
             address/port.  Each entry defines a service and the corresponding
             private Server."
     ::= { usrUserManGroup 33 }
 
 
     uumPatTcpPortEntry OBJECT-TYPE
         SYNTAX  UumPatTcpPortEntry
         ACCESS  not-accessible
         STATUS  mandatory
         DESCRIPTION
            "A static entry that map a TCP port number to a local/private IP
             address/port.  Defines a service and the corresponding
             private Server."
         INDEX   { uumPatTcpPortName, uumPatTcpPublicPort }
     ::= { usrUserManPatTcpTable 1 }
 
     UumPatTcpPortEntry ::=
        SEQUENCE {
            uumPatTcpPortName
               UsrUserName,
            uumPatTcpStatus
               INTEGER,
            uumPatTcpPublicPort
               INTEGER,
            uumPatTcpPrivAddr
               IpAddress,
            uumPatTcpPrivPort
               INTEGER
     }

     uumPatTcpPortName  OBJECT-TYPE
         SYNTAX  UsrUserName
         ACCESS  not-accessible
         STATUS  mandatory
         DESCRIPTION
                 "The users name"
     ::= { uumPatTcpPortEntry 1 }

     uumPatTcpStatus   OBJECT-TYPE
         SYNTAX  INTEGER {
                 delete(1),
                 add(2)
                 }
         ACCESS  read-write
         STATUS  mandatory
         DESCRIPTION
                "The status field for the TCP Port Entry"
     ::= { uumPatTcpPortEntry 2 }

     uumPatTcpPublicPort  OBJECT-TYPE
        SYNTAX INTEGER
        ACCESS read-write
        STATUS mandatory
        DESCRIPTION
            "Public TCP Port corresponding to a Private Address/Port."
     ::= { uumPatTcpPortEntry 3 }

     uumPatTcpPrivAddr  OBJECT-TYPE
        SYNTAX IpAddress
        ACCESS read-write
        STATUS mandatory
        DESCRIPTION
            "Private Address corresponding to a Public Port number."
     ::= { uumPatTcpPortEntry 4 }
 
     uumPatTcpPrivPort  OBJECT-TYPE
        SYNTAX INTEGER
        ACCESS read-write
        STATUS mandatory
        DESCRIPTION
            "Private Port corresponding to a Public Port number."
     ::= { uumPatTcpPortEntry 5 }

     --
     -- NAT Static IP Address Translation Entries
     --
     uumNatStatAddrTable OBJECT-TYPE
         SYNTAX  SEQUENCE OF UumNatStatAddrEntry
         ACCESS  not-accessible
         STATUS  mandatory
         DESCRIPTION
            "The static IP addresses map a Public IP address to a local/
             non-public address.   No port translation is done for static
             defined addresses. "
     ::= { usrUserManGroup 34 }
 
     uumNatStatAddrEntry OBJECT-TYPE
         SYNTAX  UumNatStatAddrEntry
         ACCESS  not-accessible
         STATUS  mandatory
         DESCRIPTION
            "The static IP addresses map a Public IP address to a local/
             non-public address.   No port translation is done for static
             defined addresses. "
         INDEX   { uumNatStatAddrName, uumNatStatPublicAddr }
     ::= { uumNatStatAddrTable 1 }
 
     UumNatStatAddrEntry ::=
         SEQUENCE {
             uumNatStatAddrName
                UsrUserName,
            uumNatStatStatus
                INTEGER,
             uumNatStatPublicAddr
                IpAddress,
             uumNatStatPrivAddr
                IpAddress
         }
 
         uumNatStatAddrName OBJECT-TYPE
             SYNTAX      UsrUserName
             ACCESS      read-write
             STATUS      mandatory
             DESCRIPTION
                "The name of a NAT translation entry.  When NAT is enabled for
                 a user profile, the profile will contain a name which matches
                 the NAT translation entry name. "
         ::= { uumNatStatAddrEntry 1 }

         uumNatStatStatus   OBJECT-TYPE
             SYNTAX  INTEGER {
                     delete(1),
                     add(2)
                     }
             ACCESS  read-write
             STATUS  mandatory
             DESCRIPTION
                "The status field for the NAT Static Entry"
         ::= { uumNatStatAddrEntry 2 }
 
         uumNatStatPublicAddr  OBJECT-TYPE
             SYNTAX IpAddress
             ACCESS read-write
             STATUS mandatory
             DESCRIPTION
                "Public Address corresponding to a Private Address."
         ::= { uumNatStatAddrEntry 3}
 
         uumNatStatPrivAddr  OBJECT-TYPE
            SYNTAX IpAddress
            ACCESS read-write
            STATUS mandatory
            DESCRIPTION
                "Private Address corresponding to a Public Address."
         ::= { uumNatStatAddrEntry 4}

     --
     -- NAT Dynamic IP Address Pool Entries
     --
     uumNatDynAddrTable OBJECT-TYPE
         SYNTAX  SEQUENCE OF UumNatDynAddrEntry
         ACCESS  not-accessible
         STATUS  mandatory
         DESCRIPTION
            "A table of public address pools.  A public address is allocated
             from the pool when a frame traverses a WAN interface with NAT 
             enabled. The public address remains mapped to the private address
             while there are TCP and UDP connections/conversations that are 
             active. " 
     ::= { usrUserManGroup 35 }
 
     uumNatDynAddrEntry OBJECT-TYPE
         SYNTAX  UumNatDynAddrEntry
         ACCESS  not-accessible
         STATUS  mandatory
         DESCRIPTION
            "An entry for a public address pool.  A public address is allocated
             from the pool when a frame traverses a WAN interface with NAT 
             enabled. The public address remains mapped to the private address
             while there are TCP and UDP connections/conversations that are 
             active.  The pool is specified with a start address and the number of 
             addresses in the pool"
         INDEX   { uumNatDynAddrName, uumNatDynPoolAddr }
     ::= { uumNatDynAddrTable 1 }
 
     UumNatDynAddrEntry ::=
         SEQUENCE {
             uumNatDynAddrName
                UsrUserName,
             uumNatDynStatus
                INTEGER,
             uumNatDynPoolAddr
                IpAddress,
             uumNatDynPoolCount
                INTEGER, 
             uumNatDynPoolMask
                IpAddress
         }
 
         uumNatDynAddrName OBJECT-TYPE
             SYNTAX      UsrUserName
             ACCESS      read-write
             STATUS      mandatory
             DESCRIPTION
                "The name of a NAT translation entry.  When NAT is enabled for
                 a user profile, the profile will contain a name which matches
                 the NAT translation entry name. "
         ::= { uumNatDynAddrEntry 1 }

         uumNatDynStatus   OBJECT-TYPE
             SYNTAX  INTEGER {
                     delete(1),
                     add(2)
                     }
             ACCESS  read-write
             STATUS  mandatory
             DESCRIPTION
                "The status field for the NAT Dynamic Entry"
         ::= { uumNatDynAddrEntry 2 }
 
         uumNatDynPoolAddr   OBJECT-TYPE
            SYNTAX IpAddress
            ACCESS read-write
            STATUS mandatory
            DESCRIPTION
               "NAT Dynamic Pool start address." 
         ::= { uumNatDynAddrEntry 3 }

         uumNatDynPoolCount  OBJECT-TYPE
            SYNTAX INTEGER
            ACCESS read-write
            STATUS mandatory
            DESCRIPTION
                "The number of addresses in the NAT Dynamic pool."
         ::= { uumNatDynAddrEntry 4 }

         uumNatDynPoolMask   OBJECT-TYPE
            SYNTAX IpAddress
            ACCESS read-write
            STATUS mandatory
            DESCRIPTION
               "NAT Dynamic Pool ip mask.  Defaults to the IP address class
                (e.g. Class C).  This mask is used in the Routing Messages (RIP)
                to advertise routes for the specified Pool." 
         ::= { uumNatDynAddrEntry 5 }

-- User managers IPX framed route table definition

	usrUserManIPXRouteTable	OBJECT-TYPE
	    SYNTAX	SEQUENCE OF UumIPXRouteEntry
	    ACCESS	not-accessible
	    STATUS	mandatory
	    DESCRIPTION
		""
	::= { usrUserManGroup 36 }

	uumIPXRouteEntry	OBJECT-TYPE
	    SYNTAX	UumIPXRouteEntry
	    ACCESS	not-accessible
	    STATUS	mandatory
	    DESCRIPTION
		""
	    INDEX	{ uumIPXRouteUserName, uumIPXRouteAddress }
	::= { usrUserManIPXRouteTable 1 }

	UumIPXRouteEntry ::= 
	SEQUENCE {
	    uumIPXRouteUserName
		    UsrUserName,
	    uumIPXRouteAddress
		OCTET STRING,
	    uumIPXRouteStatus
		INTEGER,
	    uumIPXRouteMetric
		INTEGER,
	    uumIPXRouteTicks
		INTEGER
	}

	uumIPXRouteUserName	OBJECT-TYPE
	    SYNTAX	UsrUserName
	    ACCESS	not-accessible
	    STATUS	mandatory
	    DESCRIPTION
		"The users name"
	::= { uumIPXRouteEntry 1 }

	uumIPXRouteAddress	OBJECT-TYPE
	    SYNTAX	OCTET STRING (SIZE (4))
	    ACCESS	not-accessible
	    STATUS	mandatory
	    DESCRIPTION
		"The framed routing entry's destination ipx address."
	::= { uumIPXRouteEntry 2 }
	
	uumIPXRouteStatus	OBJECT-TYPE
	    SYNTAX	INTEGER {
		delete(1),
		add(2)
		}
	    ACCESS	read-write
	    STATUS	mandatory
	    DESCRIPTION	
		"The status field for the framed route"
	::= { uumIPXRouteEntry 3 }

	uumIPXRouteMetric	OBJECT-TYPE
	    SYNTAX	INTEGER 
	    ACCESS	read-write
	    STATUS	mandatory
	    DESCRIPTION	
		"The number of router hops necessary to reach the destination."
	::= { uumIPXRouteEntry 4 }

	uumIPXRouteTicks	OBJECT-TYPE
	    SYNTAX	INTEGER 
	    ACCESS	read-write
	    STATUS	mandatory
	    DESCRIPTION	
		"The delay, in ticks, to reach the route's destination."
	::= { uumIPXRouteEntry 5 }


-- User managers IPX Service table definition

	usrUserManIPXServTable	OBJECT-TYPE
	    SYNTAX	SEQUENCE OF UumIpxServEntry
	    ACCESS	not-accessible
	    STATUS	mandatory
	    DESCRIPTION
		""
	::= { usrUserManGroup 37 }

	uumIpxServEntry	OBJECT-TYPE
	    SYNTAX	UumIpxServEntry
	    ACCESS	not-accessible
	    STATUS	mandatory
	    DESCRIPTION
		""
	    INDEX	{ uumIpxServUserName, uumIpxServType, uumIpxServName }
	::= { usrUserManIPXServTable 1 }

	UumIpxServEntry ::= 
	SEQUENCE {
	uumIpxServUserName
		UsrUserName,
        uumIpxServName
                OCTET STRING,
        uumIpxServType
                INTEGER,
        uumIpxServStatus
                INTEGER,
        uumIpxServNetNum
                OCTET STRING,
        uumIpxServNode
                OCTET STRING,
        uumIpxServSocket
                INTEGER,
        uumIpxServHopCount
                INTEGER
	}

	uumIpxServUserName OBJECT-TYPE
	    SYNTAX	UsrUserName
	    ACCESS	not-accessible
	    STATUS	mandatory
	    DESCRIPTION
		"The users name"
	::= {uumIpxServEntry 1}

        uumIpxServName OBJECT-TYPE
            SYNTAX      OCTET STRING (SIZE(1..48))
            ACCESS      read-write
            STATUS      mandatory
            DESCRIPTION "The service name."
          --CONFIGURABLE
        ::= {uumIpxServEntry 2}
 
        uumIpxServType OBJECT-TYPE
            SYNTAX      INTEGER 
            ACCESS      read-write
            STATUS      mandatory
            DESCRIPTION "The service type(e.g. FileServer = 4)."
          --CONFIGURABLE
        ::= {uumIpxServEntry 3}

        uumIpxServStatus  OBJECT-TYPE
            SYNTAX  INTEGER {
                delete(1),
                add(2)
                }
            ACCESS  read-write
            STATUS  mandatory
            DESCRIPTION
                "The status field for the framed route"
        ::= {uumIpxServEntry 4}

        uumIpxServNetNum OBJECT-TYPE
            SYNTAX      OCTET STRING (SIZE (4))
            ACCESS      read-write
            STATUS      mandatory
            DESCRIPTION "The IPX network number portion of the IPX address of the
                       service."
          --CONFIGURABLE
        ::= {uumIpxServEntry 5}
 
        uumIpxServNode OBJECT-TYPE
            SYNTAX      OCTET STRING (SIZE(6))
            ACCESS      read-write
            STATUS      mandatory
            DESCRIPTION "The node portion of the IPX address of the service."
          --CONFIGURABLE
        ::= {uumIpxServEntry 6}
 
        uumIpxServSocket OBJECT-TYPE
            SYNTAX      INTEGER 
            ACCESS      read-write
            STATUS      mandatory
            DESCRIPTION "The socket portion of the IPX address of the service."
          --CONFIGURABLE
        ::= {uumIpxServEntry 7}
 
        uumIpxServHopCount OBJECT-TYPE
            SYNTAX      INTEGER
            ACCESS      read-write
            STATUS      mandatory
            DESCRIPTION "The number of router hops to the server on which the service resides."
          --CONFIGURABLE
        ::= {uumIpxServEntry 8}
 
END
