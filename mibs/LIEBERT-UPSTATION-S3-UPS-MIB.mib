--  Title:    LIEB_S3.MIB
--  Version:  v2.1
--  Date:     05/30/95 10:45am
--
--  Copyright @ 1994-95 Liebert Corporation.  All rights reserved worldwide.
--
--  This MIB defines objects for the Liebert UpstationS3 SNMP Agents.
--

LIEBERT-UPSTATION-S3-UPS-MIB DEFINITIONS ::= BEGIN

          IMPORTS
	      enterprises, Counter,
	      TimeTicks, Gauge                FROM RFC1155-SMI
              OBJECT-TYPE                     FROM RFC-1212
              sysUpTime, DisplayString		  FROM RFC1213-MIB
	      TRAP-TYPE                           FROM RFC-1215;

	  emerson OBJECT IDENTIFIER ::= { enterprises 476 }

--
-- Divisions of Emerson
--

         liebertCorp OBJECT IDENTIFIER ::= { emerson 1 }

--
--  Areas of Liebert Corporation
--
         liebertUps OBJECT IDENTIFIER ::= { liebertCorp 1 }

--
-- UPS
--
	luExtensions OBJECT IDENTIFIER ::= { liebertUps 1 }

	luExperimental OBJECT IDENTIFIER ::= { liebertUps 2 }

	luPrivate OBJECT IDENTIFIER ::= { liebertUps 3 }

--
-- UPS Extensions
--

	luCore OBJECT IDENTIFIER ::= { luExtensions 1 }

          --
          -- The Device Identification group.
          --      All objects in this group are determined at device
	  --      initialization and remain static.
          --

          lcUpsIdent        OBJECT IDENTIFIER ::= { luCore 1 }

          lcUpsIdentManufacturer OBJECT-TYPE
              SYNTAX DisplayString (SIZE (255))
              ACCESS read-only
              STATUS optional
              DESCRIPTION
                      "The UPS manufacturer."
              ::= { lcUpsIdent 1 }

          lcUpsIdentModel OBJECT-TYPE
              SYNTAX DisplayString (SIZE (255))
              ACCESS read-write
              STATUS optional
              DESCRIPTION
                      "The UPS Model designation."
              ::= { lcUpsIdent 2 }

          lcUpsIdentSoftwareVersion OBJECT-TYPE
              SYNTAX DisplayString (SIZE (255))
              ACCESS read-only
              STATUS optional
              DESCRIPTION
                      "The UPS SNMP Agent software version."
              ::= { lcUpsIdent 3 }

          lcUpsIdentSpecific OBJECT-TYPE
              SYNTAX OBJECT IDENTIFIER
              ACCESS read-only
              STATUS optional
              DESCRIPTION
                      "A reference to MIB definitions specific to the
                      particular UPS being managed. This object is
                      used to locate the product-specific MIB for this
                      device.

                      If this information is not present, its value
                      should be the OBJECT IDENTIFIER { 0 0 },
                      which is a syntactically valid object identifier,
                      and any conformant implementation of ASN.1 and BER
                      must be able to generate and recognize this
                      value."
              ::= { lcUpsIdent 4 }

          --
          -- The Battery group.
          --

          lcUpsBattery      OBJECT IDENTIFIER ::= { luCore 2 }

          lcUpsBatTimeRemaining OBJECT-TYPE
              SYNTAX INTEGER (0..65535)
              ACCESS read-only
              STATUS optional
              DESCRIPTION
                      "The estimated time to depletion of battery charge.
                      (Unit of measure: Minute)"
              ::= { lcUpsBattery 1 }

          lcUpsBatTemperature OBJECT-TYPE
              SYNTAX INTEGER (-32768..32767)
              ACCESS read-only
              STATUS optional
              DESCRIPTION
                      "The battery temperature. (Unit of measure:
                      Degree, Centigrade)"
              ::= { lcUpsBattery 2 }

          lcUpsBatVoltage OBJECT-TYPE
              SYNTAX INTEGER (-32768..32767)
              ACCESS read-only
              STATUS optional
              DESCRIPTION
                      "The current battery voltage. (Unit of measure:
                      volt)"
              ::= { lcUpsBattery 3 }

          lcUpsBatCurrent OBJECT-TYPE
              SYNTAX INTEGER (-32768..32767)
              ACCESS read-only
              STATUS optional
              DESCRIPTION
                      "The current battery discharging/charging current.
                      (Unit of measure: Amp)"
              ::= { lcUpsBattery 4 }

          --
          -- The Input group.
          --

          lcUpsInput        OBJECT IDENTIFIER ::= { luCore 3 }

          lcUpsInputFrequency OBJECT-TYPE
              SYNTAX INTEGER (0..65536)
              ACCESS read-only
              STATUS optional
              DESCRIPTION
                      "The current input frequency. (Unit of measure:
                      Hertz)"
              ::= { lcUpsInput 1 }

          lcUpsInputBrownOuts OBJECT-TYPE
              SYNTAX Counter
              ACCESS read-only
              STATUS optional
              DESCRIPTION
                      "The number of brown-out conditions the UPS has
                       experienced."
              ::= { lcUpsInput 2 }

          lcUpsInputBlackOuts OBJECT-TYPE
              SYNTAX Counter
              ACCESS read-only
              STATUS optional
              DESCRIPTION
                      "The number of black-out conditions the UPS has
		       experienced."
              ::= { lcUpsInput 3 }

          lcUpsInputTransients OBJECT-TYPE
              SYNTAX Counter
              ACCESS read-only
              STATUS optional
              DESCRIPTION
                      "The number of transient (surge and spike)
                      conditions the UPS has experienced."
              ::= { lcUpsInput 4 }

          lcUpsInputNumLines OBJECT-TYPE
              SYNTAX INTEGER (1..3)
              ACCESS read-only
              STATUS optional
              DESCRIPTION
                      "The number of input lines utilized in this
                      device. This entry indicates the number of rows in
                      the input table."
              ::= { lcUpsInput 5 }

          lcUpsInputTable OBJECT-TYPE
              SYNTAX SEQUENCE OF LcUpsInputEntry
              ACCESS not-accessible
              STATUS optional
              ::= { lcUpsInput 6 }

          lcUpsInputEntry OBJECT-TYPE
              SYNTAX LcUpsInputEntry
              ACCESS not-accessible
              STATUS optional
              INDEX { lcUpsInputLine }
              ::= { lcUpsInputTable 1 }

          LcUpsInputEntry ::= SEQUENCE {
              lcUpsInputLine       INTEGER,
              lcUpsInputVoltage     INTEGER,
              lcUpsInputCurrent     INTEGER,
              lcUpsInputVA          INTEGER
          }

          lcUpsInputLine OBJECT-TYPE
              SYNTAX INTEGER (1..3)
              ACCESS read-only
              STATUS optional
              DESCRIPTION
                      "The input Line."
              ::= { lcUpsInputEntry 1 }

          lcUpsInputVoltage OBJECT-TYPE
              SYNTAX INTEGER (0..65536)
              ACCESS read-only
              STATUS optional
              DESCRIPTION
                      "The input voltage. (Unit of measure: Volt)"
              ::= { lcUpsInputEntry 2 }

          lcUpsInputCurrent OBJECT-TYPE
              SYNTAX INTEGER (0..65536)
              ACCESS read-only
              STATUS optional
              DESCRIPTION
                      "The input current. (Unit of measure: Amp)"
              ::= { lcUpsInputEntry 3 }

          lcUpsInputVA OBJECT-TYPE
              SYNTAX INTEGER (0..2147483647)
              ACCESS read-only
              STATUS optional
              DESCRIPTION
                      "The input volt-amps."
              ::= { lcUpsInputEntry 4 }

          --
          -- The Output group.
          --

          lcUpsOutput       OBJECT IDENTIFIER ::= { luCore 4 }

          lcUpsOutputFrequency OBJECT-TYPE
              SYNTAX INTEGER (0..65536)
              ACCESS read-only
              STATUS optional
              DESCRIPTION
                      "The current output frequency. (Unit of measure:
                      Hertz)"
              ::= { lcUpsOutput 1 }

          lcUpsOutputLoad OBJECT-TYPE
              SYNTAX INTEGER (0..100)
              ACCESS read-only
              STATUS optional
              DESCRIPTION
                      "The current output load percentage."
              ::= { lcUpsOutput 2 }

          lcUpsOutputNumLines OBJECT-TYPE
              SYNTAX INTEGER (1..3)
              ACCESS read-only
              STATUS optional
              DESCRIPTION
                      "The number of output lines utilized in this
                      device. This entry indicates the number of rows in
                      the output table."
              ::= { lcUpsOutput 3 }

          lcUpsOutputTable OBJECT-TYPE
              SYNTAX SEQUENCE OF LcUpsOutputEntry
              ACCESS not-accessible
              STATUS optional
              ::= { lcUpsOutput 4 }

          lcUpsOutputEntry OBJECT-TYPE
              SYNTAX LcUpsOutputEntry
              ACCESS not-accessible
              STATUS optional
              INDEX { lcUpsOutputLine }
              ::= { lcUpsOutputTable 1 }

          LcUpsOutputEntry ::= SEQUENCE {
              lcUpsOutputLine               INTEGER,
              lcUpsOutputVoltage             INTEGER,
              lcUpsOutputCurrent             INTEGER,
              lcUpsOutputVA                  INTEGER
          }

          lcUpsOutputLine OBJECT-TYPE
              SYNTAX INTEGER (1..3)
              ACCESS read-only
              STATUS optional
              DESCRIPTION
                      "The output Line."
              ::= { lcUpsOutputEntry 1 }

          lcUpsOutputVoltage OBJECT-TYPE
              SYNTAX INTEGER (0..65536)
              ACCESS read-only
              STATUS optional
              DESCRIPTION
                      "The output voltage. (Unit of measure: Volt)"
              ::= { lcUpsOutputEntry 2 }

          lcUpsOutputCurrent OBJECT-TYPE
              SYNTAX INTEGER (0..65536)
              ACCESS read-only
              STATUS optional
              DESCRIPTION
                      "The output current. (Unit of measure: Amp)"
              ::= { lcUpsOutputEntry 3 }

          lcUpsOutputVA OBJECT-TYPE
              SYNTAX INTEGER (0..2147483647)
              ACCESS read-only
              STATUS optional
              DESCRIPTION
                      "The output volt-amps."
              ::= { lcUpsOutputEntry 4 }

          --
          -- The Inverter group.
          --

          lcUpsInverter  OBJECT IDENTIFIER ::= { luCore 5 }

          lcUpsInverterStatus OBJECT-TYPE
              SYNTAX INTEGER {
			unknown (1),
			on      (2),
			off     (3)
			}
              ACCESS read-only
              STATUS optional
              DESCRIPTION
                      "The state of the inverter.  Unknown is returned if
		       the state can not be determined."
              ::= { lcUpsInverter 1 }

          lcUpsInverterTemp OBJECT-TYPE
              SYNTAX INTEGER (-32768..32767)
              ACCESS read-only
              STATUS optional
              DESCRIPTION
                      "The temperature of the inverter. (Unit of
                      measure: degree, Centigrade)"
              ::= { lcUpsInverter 2 }

          --
          -- The Alarm group.
          --

          lcUpsAlarm        OBJECT IDENTIFIER ::= { luCore 6 }

          lcUpsAlarms OBJECT-TYPE
              SYNTAX Gauge
              ACCESS read-only
              STATUS optional
              DESCRIPTION
                      "The current number of alarm conditions."
              ::= { lcUpsAlarm 1 }

          lcUpsAlarmTable OBJECT-TYPE
              SYNTAX SEQUENCE OF LcUpsAlarmEntry
              ACCESS not-accessible
              STATUS optional
              ::= { lcUpsAlarm 2 }

          lcUpsAlarmEntry OBJECT-TYPE
              SYNTAX LcUpsAlarmEntry
              ACCESS not-accessible
              STATUS optional
              INDEX { lcUpsAlarmId }
              ::= { lcUpsAlarmTable 1 }

          LcUpsAlarmEntry ::= SEQUENCE {
              lcUpsAlarmId              INTEGER,
              lcUpsAlarmDescr           OBJECT IDENTIFIER,
              lcUpsAlarmTime            TimeTicks
          }

          lcUpsAlarmId OBJECT-TYPE
              SYNTAX INTEGER (0..2147483647)
              ACCESS read-only
              STATUS optional
              DESCRIPTION
                      "A unique identifier for an alarm condition. This
                      value must remain constant between agent
		      initializations."
              ::= { lcUpsAlarmEntry 1 }

          lcUpsAlarmDescr OBJECT-TYPE
              SYNTAX OBJECT IDENTIFIER
              ACCESS read-only
              STATUS optional
              DESCRIPTION
                      "A reference to an alarm description object. The
                      object referenced should not be accessible, but
                      rather be used to provide a unique description of
                      the alarm condition."
              ::= { lcUpsAlarmEntry 2 }

          lcUpsAlarmTime OBJECT-TYPE
              SYNTAX TimeTicks
              ACCESS read-only
              STATUS optional
              DESCRIPTION
                      "The value of sysUpTime when the alarm condition
                      occured."
              ::= { lcUpsAlarmEntry 3 }

          --
          -- Well known alarm condtions.
          --

          lcUpsAlarmConditions      OBJECT IDENTIFIER ::= { lcUpsAlarm 3 }

          lcUpsAlarmLowBatteryWarning      OBJECT IDENTIFIER
		::= { lcUpsAlarmConditions 1 }
	  -- Battery capacity is low.

          lcUpsAlarmLowBatteryShutdown      OBJECT IDENTIFIER
		::= { lcUpsAlarmConditions 2 }
	  -- Battery capacity is low and has caused the UPS to shutdown.

          lcUpsAlarmUtilFailed        OBJECT IDENTIFIER
		::= { lcUpsAlarmConditions 3 }
	  -- Input line has lost power

          lcUpsAlarmOverTempWarning  OBJECT IDENTIFIER
		::= { lcUpsAlarmConditions 4 }
	  -- An excessive temperature condition has been detected.

          lcUpsAlarmOutputOverloadWarning  OBJECT IDENTIFIER
		::= { lcUpsAlarmConditions 6 }
	  -- An overload condition on the output has been detected.

          lcUpsAlarmInputOverVoltage  OBJECT IDENTIFIER
		::= { lcUpsAlarmConditions 8 }
	  -- An voltage above nominal limits has been detected on an Input
	  -- line.

          lcUpsAlarmBatteryBad      OBJECT IDENTIFIER
		::= { lcUpsAlarmConditions 9 }
	  -- The UPS has detected that the battery is bad.

          lcUpsAlarmOnBattery       OBJECT IDENTIFIER
		::= { lcUpsAlarmConditions 10 }
	  -- The UPS is running on battery.

          lcUpsAlarmUpsOff          OBJECT IDENTIFIER
		::= { lcUpsAlarmConditions 12 }
	  -- The UPS Inverter and bypass are both off.

          --
          -- The Test group
          --      testXYZ        - Initiates test of the XYZ function.
          --      testXYZStatus  - An enumerated value indicating test results
          --
          --

          lcUpsTest OBJECT IDENTIFIER ::= { luCore 7 }

          lcUpsTestBattery OBJECT-TYPE
              SYNTAX INTEGER { unknown (1), start (2), abort (3) }
              ACCESS read-write
              STATUS optional
              DESCRIPTION
                      "Setting this variable to 'start' will initiate
                      the battery test. Setting this variable to 'abort'
                      will stop the battery test if the test is in-
                      progress, otherwise it has no effect. Setting this
		      variable to 'unknown' has no effect.  Reading this
                      variable will always result in a return value of
		      'unknown'. If 'lcUpsTestBatteryStatus' is 'failed'
		      the test may not be performed again and the status
		      will remain in the failure state."
              ::= { lcUpsTest 1 }

          lcUpsTestBatteryStatus OBJECT-TYPE
              SYNTAX  INTEGER {
                  unknown(1),
                  passed(2),
                  failed(3),
                  inProgress(4),
                  sysFailure(5),
                  notSupported(6),
                  inhibited(7)
              }
              ACCESS read-only
              STATUS optional
              DESCRIPTION
                      "The status of the battery test."
              ::= { lcUpsTest 2 }

          lcUpsTestDiag OBJECT-TYPE
              SYNTAX INTEGER { unknown (1), start (2), abort (3) }
              ACCESS read-write
              STATUS optional
              DESCRIPTION
                      "Setting this variable to 'start' will initiate
                      the diagnostics test. Setting this variable to
                      'abort' will stop the diagnostics test if the test
                      is in-progress, otherwise it has no effect.  Setting
		      this variable to 'unknown' has no effect.  Reading this
		      variable will always result in a return value of
		      'unknown'."
              ::= { lcUpsTest 3 }

          lcUpsTestDiagStatus OBJECT-TYPE
              SYNTAX  INTEGER {
                  unknown(1),
                  passed(2),
                  failed(3),
                  inProgress(4),
                  sysFailure(5),
                  notSupported(6),
                  inhibited(7)
              }
              ACCESS read-only
              STATUS optional
              DESCRIPTION
                      "The status of the diagnostics test."
              ::= { lcUpsTest 4 }

          --
          -- The Control group.
          --

          lcUpsControl OBJECT IDENTIFIER ::= { luCore 8 }

          lcUpsControlOutputOffDelay OBJECT-TYPE
              SYNTAX INTEGER (0..2147483647)
              ACCESS read-write
              STATUS optional
              DESCRIPTION
                      "Setting this object causes the agent to instruct
		       the UPS to turn off the output after the indicated
		       number of seconds.  The agent counts down the number
		       of seconds until the event will take place.  The
		       agent issues an lcUpsOutputOffTrap when the countdown
		       finishes.  Note that different models have different
	  	       clock resolutions, usually greater than 1 second.  As
		       a result, the command will only be accurate to the
		       resolution of the UPS's clock.

		       The command can be cancelled by setting
		       lcUpsControlCancelCommand to the value cancel."
              ::= { lcUpsControl 1 }

          lcUpsControlOutputOnDelay OBJECT-TYPE
              SYNTAX INTEGER (0..2147483647)
              ACCESS read-write
              STATUS optional
              DESCRIPTION
                      "Setting this object causes the agent to instruct
		       the UPS to turn on the output after the indicated
		       number of seconds.  The agent counts down the number
		       of seconds until the event will take place.  The
		       agent issues an lcUpsOutputOnTrap when the countdown
		       finishes.  Note that different models have different
	  	       clock resolutions, usually greater than 1 second.  As
		       a result, the command will only be accurate to the
		       resolution of the UPS's clock.

		       The command can be cancelled by setting
		       lcUpsControlCancelCommand to the value cancel."
              ::= { lcUpsControl 2 }

          lcUpsControlOutputOffTrapDelay OBJECT-TYPE
              SYNTAX INTEGER (0..2147483647)
              ACCESS read-write
              STATUS optional
              DESCRIPTION
                      "When 'lcUpsControlOutputOffDelay' reaches a value
                      less than or equal to this object's value, an
		      lcUpsOutputOffWarningTrap will be produced and this
		      object will be reset to 0."
              ::= { lcUpsControl 3 }

          lcUpsControlOutputOnTrapDelay OBJECT-TYPE
              SYNTAX INTEGER (0..2147483647)
              ACCESS read-write
              STATUS optional
              DESCRIPTION
                      "When 'lcUpsControlOutputOnDelay' reaches a value
                      less than or equal to this object's value, an
		      lcUpsOutputOnWarningTrap will be produced and this
		      object will be reset to 0."
              ::= { lcUpsControl 4 }

          lcUpsControlUnixShutdownDelay OBJECT-TYPE
              SYNTAX INTEGER (0..2147483647)
              ACCESS read-write
              STATUS optional
              DESCRIPTION
                      "Setting this object causes the agent to instruct
		       the UPS to perform a UNIX Shutdown in the indicated
		       number of seconds.  The agent counts down the number
		       of seconds until the event will take place.  A Unix
		       shutdown is only valid if the UPS is on Battery.
		       During a UNIX Shutdown, the UPS will turn off the
		       output even if the Utility comes back on line before
		       the shutdown time arrives.  Note that different models
		       have different clock resolutions, usually greater
		       than 1 second.  As a result, the command will only
		       be accurate to the resolution of the UPS's clock.

		       The command can be cancelled by setting
		       lcUpsControlCancelCommand to the value 'cancel'."
              ::= { lcUpsControl 5 }

          lcUpsControlUnixShutdownTrapDelay OBJECT-TYPE
              SYNTAX INTEGER (0..2147483647)
              ACCESS read-write
              STATUS optional
              DESCRIPTION
                      "When 'lcUpsControlUnixShutdownDelay' reaches a value
                      less than or equal to this object's value, an
		      lcUpsUnixShutdownWarningTrap will be produced and
		      this object will be reset to 0."
              ::= { lcUpsControl 6 }

          lcUpsControlCancelCommands OBJECT-TYPE
              SYNTAX INTEGER { unknown (1), cancel (2) }
              ACCESS read-write
              STATUS optional
              DESCRIPTION
                      "Setting this variable to 'cancel' will cause the
		       agent to issue instructions to the UPS to cancel all
		       outstanding commands, such as lcUpsControlOutputOff,
		       lcUpsControlOutputOn, lcUpsControlUnixShutdown."
              ::= { lcUpsControl 7 }

          lcUpsControlRebootAgentDelay OBJECT-TYPE
              SYNTAX INTEGER (0..2147483647)
              ACCESS read-write
              STATUS optional
              DESCRIPTION
                      "Setting this object causes the agent to reboot after
		       the indicated number of seconds have expired.  The
		       value will count down until the event takes place.

		       The command can be cancelled by setting
		       lcUpsControlCancleCommand to the value cancel."
              ::= { lcUpsControl 8 }

          --
          -- The Nominal group.
          --

          lcUpsNominal  OBJECT IDENTIFIER ::= { luCore 9 }

          lcUpsNominalOutputVoltage OBJECT-TYPE
              SYNTAX INTEGER (0..65536)
              ACCESS read-write
              STATUS optional
              DESCRIPTION
                      "The nominal output voltage. (Unit of measure:
                      volt)"
              ::= { lcUpsNominal 1 }

          lcUpsNominalInputVoltage OBJECT-TYPE
              SYNTAX INTEGER (0..65536)
              ACCESS read-write
              STATUS optional
              DESCRIPTION
                      "The nominal input voltage. (Unit of measure:
                      volt)"
              ::= { lcUpsNominal 2 }

          lcUpsNominalOutputVA OBJECT-TYPE
              SYNTAX INTEGER (0..65536)
              ACCESS read-write
              STATUS optional
              DESCRIPTION
                      "The nominal Volt-Amp rating."
              ::= { lcUpsNominal 3 }

          lcUpsNominalOutputWatts OBJECT-TYPE
              SYNTAX INTEGER (0..65536)
              ACCESS read-write
              STATUS optional
              DESCRIPTION
                      "The nominal power rating. (Unit of measure:
                      watt)"
              ::= { lcUpsNominal 4 }

          lcUpsNominalOutputFreq OBJECT-TYPE
              SYNTAX INTEGER (0..65536)
              ACCESS read-write
              STATUS optional
              DESCRIPTION
                      "The nominal output frequency. (Unit of measure:
                      Hertz)"
              ::= { lcUpsNominal 5 }

          lcUpsNominalInputFreq OBJECT-TYPE
              SYNTAX INTEGER (0..65536)
              ACCESS read-write
              STATUS optional
              DESCRIPTION
                      "The nominal input frequency. (Unit of measure:
                      Hertz)"
              ::= { lcUpsNominal 6 }

---
---  UPS Switched Receptacle Group
---

	lcUpsSwitchedReceptacles OBJECT IDENTIFIER ::= { luCore 12 }

	lcUpsSwitchedReceptMaxNum OBJECT-TYPE
	      SYNTAX INTEGER (0..255)
	      ACCESS read-only
	      STATUS optional
 	      DESCRIPTION
		      "The maximum number of switched receptacles supported by the Ups."
	      ::= { lcUpsSwitchedReceptacles 1 }

	lcUpsSwitchedReceptTable OBJECT-TYPE
		SYNTAX SEQUENCE OF LcUpsSwitchedReceptEntry ACCESS not-accessible
		STATUS optional
		::= { lcUpsSwitchedReceptacles 2 }
	
	LcUpsSwitchedReceptEntry ::= SEQUENCE {
		lcUpsSwitchedReceptIndex        INTEGER,
		lcUpsSwitchedReceptOnDelay      INTEGER,
		lcUpsSwitchedReceptOnTrapDelay  INTEGER,
		lcUpsSwitchedReceptOffDelay     INTEGER,
		lcUpsSwitchedReceptOffTrapDelay INTEGER,
		lcUpsSwitchedReceptStatus       INTEGER,
		lcUpsSwitchedReceptLabel	DisplayString
	}
	
	lcUpsSwitchedReceptEntry OBJECT-TYPE
		SYNTAX LcUpsSwitchedReceptEntry
		ACCESS not-accessible
		STATUS optional
		INDEX { lcUpsSwitchedReceptIndex }
		::= { lcUpsSwitchedReceptTable 1 }
	
	lcUpsSwitchedReceptIndex OBJECT-TYPE
		SYNTAX INTEGER
		ACCESS read-only
		STATUS optional
		::= { lcUpsSwitchedReceptEntry 1 }
	
	lcUpsSwitchedReceptOnDelay OBJECT-TYPE
		SYNTAX INTEGER (0..2147483647)
		ACCESS read-write
		STATUS optional
		DESCRIPTION
		    "Setting this object causes the agent to instruct
		     the UPS to turn on a receptacle after the indicated number
		     of seconds.  The agent counts down the number of seconds
		     until the event will take place.  The agent issues an
		     lcUpsReceptOnTrap when the countdown finishes.
		     Note that different models have different clock
		     resolutions, usually greater than 1 second.  As a result,
		     the command will only be accurate to the resolution of the
		     UPS's clock.
	
		     The command can be cancelled by setting
		     lcUpsSwitchedCancelCommand to the value cancel."
		::= { lcUpsSwitchedReceptEntry 2 }
	
	lcUpsSwitchedReceptOnTrapDelay OBJECT-TYPE
		SYNTAX INTEGER (0..2147483647)
		ACCESS read-write
		STATUS optional
		DESCRIPTION
		    "When 'lcUpsSwitchedReceptOnDelay' reaches a value less
		    than or equal to this object's value, an
		    lcUpsReceptOnWarningTrap will be produced and this object
		    will be reset to 0."
		::= { lcUpsSwitchedReceptEntry 3 }
	
	lcUpsSwitchedReceptOffDelay OBJECT-TYPE
		SYNTAX INTEGER (0..2147483647)
		ACCESS read-write
		STATUS optional
		DESCRIPTION
		    "Setting this object causes the agent to instruct the UPS
		     to turn off a receptacle after the indicated number of
		     seconds.  The agent counts down the number of seconds
		     until the event will take place.  The agent issues an
		     lcUpsReceptOffTrap when the countdown finishes.  Note that
		     different models have different clock resolutions, usually
		     greater than 1 second.  As a result, the command will only
		     be accurate to the resolution of the UPS's clock.
	
		     The command can be cancelled by setting
		     lcUpsSwitchedCancelCommand to the value cancel."
		::= { lcUpsSwitchedReceptEntry 4 }
	
	lcUpsSwitchedReceptOffTrapDelay OBJECT-TYPE
		SYNTAX INTEGER (0..2147483647)
		ACCESS read-write
		STATUS optional
		DESCRIPTION
		    "When 'lcUpsSwitchedReceptOffDelay' reaches a value less
		    than or equal to this object's value, an
		    lcUpsReceptOffWarningTrap will be produced and this object
		    will be reset to 0."
		::= { lcUpsSwitchedReceptEntry 5 }
	
	lcUpsSwitchedReceptStatus OBJECT-TYPE
		SYNTAX INTEGER { on(1),off(2) }
		ACCESS read-only
		STATUS optional
		DESCRIPTION
		    "The status of the device receptacle. Note that some
		     devices may support Switched of device receptacles as a
		     group only (by using lcUpsSwitchedOutputOffDelay
		     and lcUpsSwitchedOutputOnDelay)."
		::= { lcUpsSwitchedReceptEntry 6 }
	
	lcUpsSwitchedReceptLabel OBJECT-TYPE
		    SYNTAX DisplayString (SIZE (32))
		    ACCESS read-write
		    STATUS optional
		DESCRIPTION
			"A user-defined text string associated with a switched
			 receptacle.   This may be used to describe the load
		         powered from the receptacle.  The text string is
			 stored in non-volatile memory."
		::= { lcUpsSwitchedReceptEntry 7 }

--
--  The Core Liebert UPS traps
--
          lcUpsTraps        OBJECT IDENTIFIER ::= { luCore 11 }

lcUpsOverloadWarningTrap	TRAP-TYPE
			ENTERPRISE	lcUpsTraps
			VARIABLES  	{ sysUpTime }
			DESCRIPTION
			"An lcUpsOverloadWarningTrap signifies that the UPS
			 has detected an Overload condition where the output
			 load has exceeded the UPS's rated capacity."

			::= 1

lcUpsOnBatteryTrap      TRAP-TYPE
			ENTERPRISE	lcUpsTraps
			VARIABLES   	{ sysUpTime }
			DESCRIPTION
			"An lcUpsOnBatteryTrap signifies that the
 			 UPS is currently on Battery Power."

			::= 3

lcUpsLowBatteryWarningTrap     TRAP-TYPE
			ENTERPRISE	lcUpsTraps
			VARIABLES   	{ sysUpTime }
			DESCRIPTION
			"An lcUpsLowBatteryWarningTrap signifies that the
 			 UPS has entered a Low Battery state."

			::= 4

lcUpsUtilPowerFailedTrap  TRAP-TYPE
			ENTERPRISE	lcUpsTraps
			VARIABLES   	{ sysUpTime }
			DESCRIPTION
			"An lcUpsUtilPowerFailedTrap signifies that the
 			 utility power input to the UPS has been lost."

			::= 6

lcUpsUtilPowerRestoredTrap  TRAP-TYPE
			ENTERPRISE	lcUpsTraps
			VARIABLES   	{ sysUpTime }
			DESCRIPTION
			"An lcUpsUtilPowerRestoredTrap signifies that the
 			 utility power has been restored to the UPS."

			::= 7

lcUpsInputOverVoltageTrap  TRAP-TYPE
			ENTERPRISE	lcUpsTraps
			VARIABLES   	{ sysUpTime }
			DESCRIPTION
			"An lcUpsInputOverVoltageTrap signifies that the
 			 UPS has detected a high input voltage condition."

			::= 8

lcUpsOverTempWarningTrap       TRAP-TYPE
			ENTERPRISE	lcUpsTraps
			VARIABLES   	{ sysUpTime  }
			DESCRIPTION
			"An lcUpsOverTempWarningTrap signifies that the
			 UPS has detected a excessive temperature condition."

			::= 9

lcUpsAlarmTrap		TRAP-TYPE
			ENTERPRISE 	lcUpsTraps
			VARIABLES	{ sysUpTime }
			DESCRIPTION
			"An Alarm condition has occurred and is being reported
			 in the lcUpsAlarmTable."

			::= 11

lcUpsOutputOffTrap      TRAP-TYPE
			ENTERPRISE	lcUpsTraps
			VARIABLES   	{ sysUpTime  }
			DESCRIPTION
			"An lcUpsOutputOffTrap is sent when the UPS
			 turns all of its output off, either at the
			 inverter or via a relay."

			::= 12

lcUpsOutputOffWarningTrap   TRAP-TYPE
			ENTERPRISE	lcUpsTraps
			VARIABLES   	{ sysUpTime }
			DESCRIPTION
			"An lcUpsOutputOffWarningTrap is sent when the
			 lcUpsControlOutputOffDelay reaches the value of
			 lcUpsControlOutputOffTrapDelay."

			::= 13

lcUpsOutputOnTrap       TRAP-TYPE
			ENTERPRISE	lcUpsTraps
			VARIABLES   	{ sysUpTime  }
			DESCRIPTION
			"An lcUpsOutputOnTrap is sent when the UPS
			 turns all of its output back on, either at the
			 inverter or via a relay."

			::= 14

lcUpsOutputOnWarningTrap   TRAP-TYPE
			ENTERPRISE	lcUpsTraps
			VARIABLES   	{ sysUpTime }
			DESCRIPTION
			"An lcUpsOutputOnWarningTrap is sent when the
			 lcUpsControlOutputOnDelay reaches the value of
			 lcUpsControlOutputOnTrapDelay."

			::= 15

lcUpsUnixShutdownTrap      TRAP-TYPE
			ENTERPRISE	lcUpsTraps
			VARIABLES   	{ sysUpTime  }
			DESCRIPTION
			"An lcUpsUnixShutodwnTrap is sent 2 seconds before
 			 the UPS is scheduled to perform a Unix Shutdown."

			::= 16

lcUpsUnixShutdownWarningTrap   TRAP-TYPE
			ENTERPRISE	lcUpsTraps
			VARIABLES   	{ sysUpTime }
			DESCRIPTION
			"An lcUpsUnixShutdownWarningTrap is sent when the
			 lcUpsControlUnixShudownDelay reaches the value of
			 lcUpsControlUnixShutdownTrapDelay."

			::= 17

---
---  UPS Switched Receptacle Traps
---

lcUpsReceptOffTrap      TRAP-TYPE
		ENTERPRISE      lcUpsTraps
		VARIABLES       { sysUpTime, lcUpsSwitchedReceptIndex }
		DESCRIPTION
		"An lcUpsReceptOffTrap is sent when the UPS
		turns an output receptacle off."

		::= 18

lcUpsReceptOffWarningTrap   TRAP-TYPE
		ENTERPRISE      lcUpsTraps
		VARIABLES       { sysUpTime, lcUpsSwitchedReceptIndex }
		DESCRIPTION
		"An lcUpsReceptOffWarningTrap is sent when the
		lcUpsSwitchedReceptOffDelay reaches the value of
		lcUpsSwitchedReceptOffTrapDelay."

		::= 19

lcUpsReceptOnTrap       TRAP-TYPE
		ENTERPRISE      lcUpsTraps
		VARIABLES       { sysUpTime, lcUpsSwitchedReceptIndex  }
		DESCRIPTION
		"An lcUpsReceptOnTrap is sent when the UPS
		turns an output receptacle on."

		::= 20

lcUpsReceptOnWarningTrap   TRAP-TYPE
		ENTERPRISE      lcUpsTraps
		VARIABLES       { sysUpTime, lcUpsSwitchedReceptIndex }
		DESCRIPTION
		"An lcUpsReceptOnWarningTrap is sent when the
		lcUpsSwitchedReceptOnDelay reaches the value of
		lcUpsSwitchedReceptOnTrapDelay."

		::= 21

--
-- The UPStation S Extension
--
	luUPStationS OBJECT IDENTIFIER ::= { luExtensions 2 }

--
-- The Liebert Irvtec UPS Ident group.
--

          lsUpsIdent       OBJECT IDENTIFIER ::= { luUPStationS 1 }

          lsUpsIdentFirmwareVersion OBJECT-TYPE
              SYNTAX DisplayString (SIZE (255))
              ACCESS read-only
              STATUS optional
              DESCRIPTION
                      "The firmware revision level of the UPS."
              ::= { lsUpsIdent 1 }

--
-- The Liebert Irvtec UPS Alarm group
--

          lsUpsAlarm        OBJECT IDENTIFIER ::= { luUPStationS 6 }

          lsUpsAlarmConditions      OBJECT IDENTIFIER ::= { lsUpsAlarm 1 }

          lsUpsAlarmCheckAirFilter  OBJECT IDENTIFIER
	        ::= { lsUpsAlarmConditions 1 }
          -- The air filter is due to be checked.

--
--  The Liebert Irvtec UPS traps
--
	lsUpsTraps        OBJECT IDENTIFIER ::= { luUPStationS 11 }

lsUpsCheckAirFilterTrap   TRAP-TYPE
        	ENTERPRISE      lsUpsTraps
		VARIABLES       { sysUpTime  }
		DESCRIPTION
		"An lsUpsCheckAirFilterTrap signifies that the programmed time
		interval for checking the air filter has passed and it is time to
		check the air filter."

		::= 1

--
-- The Liebert Irvtec UPS Configuration group.
--

          lsUpsConfig       OBJECT IDENTIFIER ::= { luUPStationS 12 }

          lsUpsConfigBypassInstalled OBJECT-TYPE
              SYNTAX INTEGER {
			unknown (1),
			yes     (2),
			no      (3)
		     }
              ACCESS read-only
              STATUS optional
              DESCRIPTION
                      "Indicates if a bypass is installed in the UPS."
              ::= { lsUpsConfig 1 }

--
-- The Liebert Irvtec UPS Bypass group.
--

          lsUpsBypass       OBJECT IDENTIFIER ::= { luUPStationS 13 }

          lsUpsOnBypass OBJECT-TYPE
              SYNTAX INTEGER {
			unknown (1),
			yes     (2),
			no      (3)
		     }
              ACCESS read-only
              STATUS optional
              DESCRIPTION
                      "Indicates that the UPS is currently on bypass."
              ::= { lsUpsBypass 1 }

          lsUpsBypassFrequency OBJECT-TYPE
              SYNTAX INTEGER (0..65536)
              ACCESS read-only
              STATUS optional
              DESCRIPTION
                      "The current bypass frequency. (Unit of measure:
                      Hertz)"
              ::= { lsUpsBypass 2 }

          lsUpsBypassNumLines OBJECT-TYPE
              SYNTAX INTEGER (1..3)
              ACCESS read-only
              STATUS optional
              DESCRIPTION
                      "The number of bypass lines utilized in this
                      device. This entry indicates the number of rows in
                      the bypass table."
              ::= { lsUpsBypass 3 }

          lsUpsBypassTable OBJECT-TYPE
              SYNTAX SEQUENCE OF LsUpsBypassEntry
              ACCESS not-accessible
              STATUS optional
              ::= { lsUpsBypass 4 }

          lsUpsBypassEntry OBJECT-TYPE
              SYNTAX LsUpsBypassEntry
              ACCESS not-accessible
              STATUS optional
              INDEX { lsUpsBypassLine }
              ::= { lsUpsBypassTable 1 }

          LsUpsBypassEntry ::= SEQUENCE {
              lsUpsBypassLine              INTEGER,
              lsUpsBypassVoltage            INTEGER,
              lsUpsBypassCurrent            INTEGER
          }

          lsUpsBypassLine OBJECT-TYPE
              SYNTAX INTEGER (1..3)
              ACCESS read-only
              STATUS optional
              DESCRIPTION
                      "The bypass Line."
              ::= { lsUpsBypassEntry 1 }

          lsUpsBypassVoltage OBJECT-TYPE
              SYNTAX INTEGER (0..65536)
              ACCESS read-only
              STATUS optional
              DESCRIPTION
                      "The bypass voltage. (Unit of measure: Volt)"
              ::= { lsUpsBypassEntry 2 }

          lsUpsBypassCurrent OBJECT-TYPE
              SYNTAX INTEGER (0..65536)
              ACCESS read-only
              STATUS optional
              DESCRIPTION
                      "The bypass current. (Unit of measure: Amp)"
              ::= { lsUpsBypassEntry 3 }

--
-- The UPStation S3 Extension
--
	luUPStationS3 OBJECT IDENTIFIER ::= { luExtensions 7 }

END
