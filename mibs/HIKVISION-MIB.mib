HIKVISION-MIB DEFINITIONS ::= BEGIN

        IMPORTS
                Counter
                        FROM RFC1155-SMI
                enterprises, OBJECT-TYPE, NetworkAddress
                        FROM SNMPv2-SMI
					DisplayString FROM SNMPv2-TC	
							;
                        
	hikvision	OBJECT IDENTIFIER ::= { enterprises 50001 }


	hikEntity		OBJECT IDENTIFIER ::= { hikvision 1 }

-- hikvision persistent property

hikIp   OBJECT-TYPE
    SYNTAX  NetworkAddress
    ACCESS  read-only
    STATUS  mandatory
    DESCRIPTION
            "hikvision device valid ip address"
    ::= { hikEntity 1 }

hikPort   OBJECT-TYPE
    SYNTAX  INTEGER(1..65535)
    ACCESS  read-only
    STATUS  mandatory
    DESCRIPTION
            "hikvision device valid manager port,default is 8000"
    ::= { hikEntity 2 }

hikEntityIndex   OBJECT-TYPE
    SYNTAX  DisplayString (SIZE (0..128))
    ACCESS  read-only
    STATUS  mandatory
    DESCRIPTION
            "hikvision device unique index, for DVR this is serial NO."
    ::= { hikEntity 3 }   
    
    hikEntityType OBJECT IDENTIFIER ::= { hikEntity 100 } 

hikEntityType OBJECT-TYPE
    SYNTAX  INTEGER {
                dvr(1),
                nvr(2),
                ipc(3),
                unknown(255)
            }
    ACCESS  read-only
    STATUS  mandatory
    DESCRIPTION
            "hikvision products type"
    ::= { hikEntity 100 }


hikEntitySubType OBJECT-TYPE
    SYNTAX  INTEGER {
                dvr-70xx(1),
                dvr-71xx(2),
                dvr-80xx(20),
                dvr-81xx(21),
                dvr-90xx(40),
                dvr-91xx(41),
                nvr(200),
                ipc(400),
                unknown(65535)
            }
    ACCESS  read-only
    STATUS  mandatory
    DESCRIPTION
            "hikvision product sub type"
    ::= { hikEntity 101 }
    
hikOnline OBJECT-TYPE
    SYNTAX  INTEGER {
                online(1),
                absent(2),
                unknown(255)
            }
    ACCESS  read-only
    STATUS  mandatory
    DESCRIPTION
            "display hikvision product online status"
    ::= { hikEntity 102 }
 
hikService OBJECT-TYPE
    SYNTAX  INTEGER {
                unknown(255)
            }
    ACCESS  read-only
    STATUS  mandatory
    DESCRIPTION
            "display hikvision product service type, now dvr will return Unknown"
    ::= { hikEntity 103 }

hikCMSDefType OBJECT-TYPE
    SYNTAX  INTEGER {
                unknown(255)
            }
    ACCESS  read-only
    STATUS  mandatory
    DESCRIPTION
            "display hikvision product defined CMS type, now dvr will return Unknown"
    ::= { hikEntity 104 }

hikObjectID OBJECT-TYPE
    SYNTAX  INTEGER
    ACCESS  read-only
    STATUS  mandatory
    DESCRIPTION
            "display hikvision product object ID, now dvr do not need this will return 0"
    ::= { hikEntity 105 }

hikObjectName OBJECT-TYPE
    SYNTAX  DisplayString (SIZE (0..128))
    ACCESS  read-only
    STATUS  mandatory
    DESCRIPTION
            "display hikvision product object Name, now dvr do not need this will return nothing"
    ::= { hikEntity 106 }

hikTrapHostIp1 OBJECT-TYPE
    SYNTAX  DisplayString (SIZE (0..128))
    ACCESS  read-only
    STATUS  mandatory
    DESCRIPTION
            "display hikvision product 1st trap host ip address "
    ::= { hikEntity 110}
    
    
    
    
--hik cpu info
hikCPUNum OBJECT-TYPE
    SYNTAX  INTEGER(1..512)
    ACCESS  read-only
    STATUS  mandatory
    DESCRIPTION
            "the number of hikvision product's cpu "
    ::= { hikEntity 200}

hikCPUFrequency OBJECT-TYPE
    SYNTAX  DisplayString (SIZE (0..32))
    ACCESS  read-only
    STATUS  mandatory
    DESCRIPTION
            "the frequency of hikvision product's cpu, format like “2000MHZ” "
    ::= { hikEntity 201}

--hik memery info
hikMemoryCapability OBJECT-TYPE
    SYNTAX  INTEGER
    ACCESS  read-only
    STATUS  mandatory
    DESCRIPTION
            "the size of Memory"
    ::= { hikEntity 220}    
    
hikMemoryUsage OBJECT-TYPE
    SYNTAX  INTEGER(0..100)
    ACCESS  read-only
    STATUS  mandatory
    DESCRIPTION
            "the Usage of hikvision product's Memory, value scope  is (0-100)"
    ::= { hikEntity 221}       
    
hikDeviceStatus OBJECT-TYPE
    SYNTAX  INTEGER{
                    online(1),
                    absent(2),
                    unknown(255)
                }
    ACCESS  read-only
    STATUS  mandatory
    DESCRIPTION
            "display hikvision product status"
    ::= { hikEntity 230}

hikDeviceLanguage OBJECT-TYPE
    SYNTAX  INTEGER{
                    english(1),
                    simple-chinese(2),
                    traditional-chinese(3),
                    japanese(4),
                    korea(5),
                    unknown(255)
                }
    ACCESS  read-only
    STATUS  mandatory
    DESCRIPTION
            "display hikvision product language"
    ::= { hikEntity 231}

-- hikvision disk info --

hikDiskNum OBJECT-TYPE
    SYNTAX  INTEGER
    ACCESS  read-only
    STATUS  mandatory
    DESCRIPTION
            "the number of hikvision device local disks"
    ::= { hikEntity 240}
-- the disk table

hikDiskTable OBJECT-TYPE
    SYNTAX  SEQUENCE OF HikDiskEntry
    ACCESS  not-accessible
    STATUS  mandatory
    DESCRIPTION
            "A list of disk entries.  The number of
            entries is given by the value of hikDiskNum."
    ::= { hikEntity 241 }
    
hikDiskEntry OBJECT-TYPE
    SYNTAX  HikDiskEntry
    ACCESS  not-accessible
    STATUS  mandatory
    DESCRIPTION
            "A disk entry containing objects at local disk status."
    INDEX   { hikDiskIndex }
    ::= { hikDiskTable 1 }

HikDiskEntry ::=
    SEQUENCE {
        hikDiskIndex
            INTEGER,
        hikDiskVolume
            DisplayString,
        hikDiskStatus
            INTEGER,
        hikDiskFreeSpace
            INTEGER,
        hikDiskCapability
            INTEGER
    }

hikDiskIndex OBJECT-TYPE
    SYNTAX  INTEGER
    ACCESS  read-only
    STATUS  mandatory
    DESCRIPTION
            "An unique value for each local disk entry.  Its value
            ranges between 1 and the value of ifNumber."
    ::= { hikDiskEntry 1 }

hikDiskVolume OBJECT-TYPE
    SYNTAX  DisplayString(SIZE (0..32))
    ACCESS  read-only
    STATUS  mandatory
    DESCRIPTION
            "A textual string containing information about local
            disk"
    ::= { hikDiskEntry 2 }

hikDiskStatus OBJECT-TYPE
    SYNTAX  INTEGER{
                normal(0),
                unformatted(1),
                abnormal(2),
                smartfailed(3),
                mismatch(4),
                idle(5),
                notonline(6),
				reparing(10),
				formatting(11)
                }
    ACCESS  read-only
    STATUS  mandatory
    DESCRIPTION
            "local disk status"
    ::= { hikDiskEntry 3 }

hikDiskFreeSpace OBJECT-TYPE
    SYNTAX  INTEGER
    ACCESS  read-only
    STATUS  mandatory
    DESCRIPTION
            "the size of local disk entry free space,
             if we get 100, means free space is 100M"
    ::= { hikDiskEntry 4 }

hikDiskCapability OBJECT-TYPE
    SYNTAX  INTEGER
    ACCESS  read-only
    STATUS  mandatory
    DESCRIPTION
            "the size of local disk entry all space,
             if we get 100, means all space is 100M"
    ::= { hikDiskEntry 5 }


-- hikvisoin trap define  
    
	--power status trap
	power-PowerOn TRAP-TYPE
		ENTERPRISE hikvision
		DESCRIPTION
			"hikvision device power on"
		::= 1

	power-PowerOff TRAP-TYPE
		ENTERPRISE hikvision
		DESCRIPTION
			"hikvision device shut down"
		::= 2

	power-ReBoot TRAP-TYPE
		ENTERPRISE hikvision
		DESCRIPTION
			"hikvision device reboot"
		::= 3		


        
END
