-- *****************************************************************
--
-- stn-if.mib:  
--      Spring Tide Networks Interface MIB file.
--
--
--      Copyright (c) 1999, 2000 by Spring Tide Networks, Inc.
--                      ALL RIGHTS RESERVED       
--
-- *****************************************************************

-- MIB Object definitions for Spring Tide Network Interfaces 

STN-IF-MIB DEFINITIONS ::= BEGIN

    IMPORTS
        MODULE-IDENTITY,
        OBJECT-TYPE,
        NOTIFICATION-TYPE,
        Integer32
                FROM SNMPv2-SMI

        TEXTUAL-CONVENTION,
        DisplayString
                FROM SNMPv2-TC

        MODULE-COMPLIANCE, 
        OBJECT-GROUP
                FROM SNMPv2-CONF

        InterfaceIndex
                FROM IF-MIB

        stnSystems,
        stnNotification
                FROM SPRING-TIDE-NETWORKS-SMI;


    stnIfMIB       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION
                "STN Interface MIB."
        ::= { stnSystems 3 }


    --
    -- Top Level STN Interface MIB Objects
    --
    stnInterfaces       OBJECT IDENTIFIER ::= { stnIfMIB 1 }
    stnIfMibConformance OBJECT IDENTIFIER ::= { stnIfMIB 2 }

    stnIf           OBJECT IDENTIFIER ::= { stnInterfaces 1 }


    --
    -- STN Interface MIB Textual Conventions
    --
    StnInterfaceType ::= TEXTUAL-CONVENTION
        STATUS          current
        DESCRIPTION     "Interface type."
        SYNTAX          INTEGER {    
                            unknown(1),     -- not applicable or other
                            ethernet(2),
                            sonet(3),   
                            epif(4),
                            ds3(5)     
                        }

    StnIfOperStatus ::= TEXTUAL-CONVENTION
        STATUS          current
        DESCRIPTION     "Interface operational status."
        SYNTAX          INTEGER {    
                            unknown(1),            -- none of the following
                            up-non-redundant(2),   -- 
                            up-redundant(3),       -- 
                            down-non-redundant(4), -- 
                            down-redundant(5)      -- 
                        }


    StnIfDuplexType ::= TEXTUAL-CONVENTION
        STATUS          current
        DESCRIPTION     "Interface duplex type."
        SYNTAX          INTEGER {    
                            unknown(1),		-- none of the following
                            half(2),
                            full(3)
                        }


    --
    -- STN Interface Table
    --
    stnIfTable OBJECT-TYPE
        SYNTAX        SEQUENCE OF StnIfEntry
        MAX-ACCESS    not-accessible
        STATUS        current
        DESCRIPTION   "A list of interface entries."
        ::= { stnIf 1 }
 
    stnIfEntry OBJECT-TYPE
        SYNTAX          StnIfEntry
        MAX-ACCESS      not-accessible
        STATUS          current
        DESCRIPTION     "Entry contains information about a particular interface."
        INDEX           { stnIfIndex }
        ::= { stnIfTable 1 }

     StnIfEntry ::= SEQUENCE {
                stnIfIndex          InterfaceIndex,
                stnIfSlot           Integer32,
                stnIfPort           Integer32,
                stnIfEngine1        Integer32,
                stnIfEngine2        Integer32,
                stnIfInternalPort   Integer32,
                stnIfType           StnInterfaceType,
                stnIfOperStatus     StnIfOperStatus,
                stnIfDescr          DisplayString,
                stnIfDuplex         StnIfDuplexType
                }

    stnIfIndex OBJECT-TYPE
        SYNTAX          InterfaceIndex
        MAX-ACCESS      read-only
        STATUS          current
        DESCRIPTION     "A sequence number that identifies a particular 
                        interface in the chassis."
        ::= { stnIfEntry 1 }

    stnIfSlot OBJECT-TYPE
        SYNTAX          Integer32
        MAX-ACCESS      read-only
        STATUS          current
        DESCRIPTION     "The physical slot in which the interface exists."
        ::= { stnIfEntry 2 }

    stnIfPort OBJECT-TYPE
        SYNTAX          Integer32
        MAX-ACCESS      read-only
        STATUS          current
        DESCRIPTION     "The physical port in which the interface exists."
        ::= { stnIfEntry 3 }

    stnIfEngine1 OBJECT-TYPE
        SYNTAX          Integer32
        MAX-ACCESS      read-only
        STATUS          current
        DESCRIPTION     "The first physical engine ID associated with this interface."
        ::= { stnIfEntry 4 }

    stnIfEngine2 OBJECT-TYPE
        SYNTAX          Integer32
        MAX-ACCESS      read-only
        STATUS          current
        DESCRIPTION     "The second physical engine ID associated with this interface."
        ::= { stnIfEntry 5 }

    stnIfInternalPort OBJECT-TYPE
        SYNTAX          Integer32
        MAX-ACCESS      read-only
        STATUS          current
        DESCRIPTION     "The physical internal port ID for this interface."
        ::= { stnIfEntry 6 }

    stnIfType OBJECT-TYPE     
        SYNTAX          StnInterfaceType
        MAX-ACCESS      read-only
        STATUS          current
        DESCRIPTION     "The type of interface."
        ::= { stnIfEntry  7 }

    stnIfOperStatus   OBJECT-TYPE
        SYNTAX          StnIfOperStatus
        MAX-ACCESS      read-only
        STATUS          current
        DESCRIPTION     "Operational status of the interface."
        ::= { stnIfEntry  8 }

    stnIfDescr OBJECT-TYPE
        SYNTAX          DisplayString
        MAX-ACCESS      read-only
        STATUS          current
        DESCRIPTION     "A descriptive string used to describe the interface."
        ::= { stnIfEntry  9 }

    stnIfDuplex OBJECT-TYPE
        SYNTAX          StnIfDuplexType
        MAX-ACCESS      read-only
        STATUS          current
        DESCRIPTION     "The duplex type of the interface."
        ::= { stnIfEntry  10 }


    --
    -- STN Traps & Notifications 
    --
    stnInterfaceUp NOTIFICATION-TYPE
        OBJECTS         { stnIfIndex, stnIfSlot, stnIfPort,  
                          stnIfEngine1, stnIfEngine2, stnIfInternalPort,
                          stnIfType, stnIfOperStatus, stnIfDescr }
        STATUS          current
        DESCRIPTION
                "A stnInterfaceUp trap signifies that the agent entity has
                detected that the stnIfOperStatus object in the 
                STN-IF-MIB has transitioned from any disfunctional state, 
                down-non-redundant(4) or down-redundant(5) to any 
                functional state, up-non-redundant(2) or up-redundant(3).
                The generation of this trap can be controlled by the
                InterfaceUpTraps configuration object."
        ::= { stnNotification 13 }

    stnInterfaceDown NOTIFICATION-TYPE
        OBJECTS         { stnIfIndex, stnIfSlot, stnIfPort,  
                          stnIfEngine1, stnIfEngine2, stnIfInternalPort,
                          stnIfType, stnIfOperStatus, stnIfDescr }
        STATUS          current
        DESCRIPTION
                "A stnInterfaceDown trap signifies that the agent entity has
                detected that the stnIfOperStatus object in the 
                STN-IF-MIB has transitioned from any functional state, 
                up-non-redundant(2) or up-redundant(3), to any disfunctional 
                state, down-non-redundant(4) or down-redundant(5).
                The generation of this trap can be controlled by the
                InterfaceDownTraps configuration object."
        ::= { stnNotification 14 }


    --
    -- Conformance information
    --
    stnIfMibCompliances OBJECT IDENTIFIER ::= { stnIfMibConformance 1 }
    stnIfMibGroups      OBJECT IDENTIFIER ::= { stnIfMibConformance 2 }


    --
    -- Compliance statements
    --

    stnIfMibComplianceRev1 MODULE-COMPLIANCE
        STATUS  current 
        DESCRIPTION
                "The compliance statement for entities which implement
                the Spring Tide Networks Interface MIB."
        MODULE  -- this module
                MANDATORY-GROUPS { stnIfMibGroup }
        ::= { stnIfMibCompliances 1 }


    --
    -- Conformance Units
    --

    stnIfMibGroup OBJECT-GROUP
        OBJECTS {
                stnIfIndex,
                stnIfSlot,
                stnIfPort,
                stnIfEngine1,
                stnIfEngine2,
                stnIfInternalPort,
                stnIfType,
                stnIfOperStatus,
                stnIfDescr,      
                stnIfDuplex       
        }
        STATUS current
        DESCRIPTION 
            "A collection of STN objects providing interface information."
        ::= { stnIfMibGroups 1 }

   
END
