--			Ascend mibsparing MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSPARING-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    miblimSparingConfigProfile  OBJECT IDENTIFIER ::= { configuration 12}
    mibifSparingConfigProfile  OBJECT IDENTIFIER ::= { configuration 119}
    miblimSparingStatusProfile  OBJECT IDENTIFIER ::= { configuration 120}

	-- The miblimSparingConfigProfile table
	--
	-- This table contains parameters for the miblimSparingConfigProfile profile
	--

    miblimSparingConfigProfileTable	OBJECT-TYPE
	SYNTAX		SEQUENCE OF MiblimSparingConfigProfileEntry
	ACCESS		not-accessible
	STATUS		mandatory
	DESCRIPTION	"A list of miblimSparingConfigProfile profile entries."
	::= { miblimSparingConfigProfile 1 }

    miblimSparingConfigProfileEntry	OBJECT-TYPE
	SYNTAX		MiblimSparingConfigProfileEntry
	ACCESS		not-accessible
	STATUS		mandatory
	DESCRIPTION	"A miblimSparingConfigProfile entry containing objects that
			 maps to the parameters of miblimSparingConfigProfile profile."
	INDEX		{ limSparingConfigProfile-Shelf-o, limSparingConfigProfile-Slot-o, limSparingConfigProfile-Item-o }
	::= { miblimSparingConfigProfileTable 1 }

    MiblimSparingConfigProfileEntry ::=
	SEQUENCE {
	    limSparingConfigProfile-Shelf-o
		INTEGER,
	    limSparingConfigProfile-Slot-o
		INTEGER,
	    limSparingConfigProfile-Item-o
		INTEGER,
	    limSparingConfigProfile-PhysicalAddress-Shelf
		INTEGER,
	    limSparingConfigProfile-PhysicalAddress-Slot
		INTEGER,
	    limSparingConfigProfile-PhysicalAddress-ItemNumber
		INTEGER,
	    limSparingConfigProfile-SpareSlotType
		INTEGER,
	    limSparingConfigProfile-SparingMode
		INTEGER,
	    limSparingConfigProfile-SpareSlotNumber
		INTEGER,
	    limSparingConfigProfile-ManuallySparedSlotNumber
		INTEGER,
	    limSparingConfigProfile-Action-o
		INTEGER
	}

    limSparingConfigProfile-Shelf-o	OBJECT-TYPE
	SYNTAX	INTEGER
	ACCESS	read-only
	STATUS	mandatory
	DESCRIPTION	""
	::= { miblimSparingConfigProfileEntry 6 }

    limSparingConfigProfile-Slot-o	OBJECT-TYPE
	SYNTAX	INTEGER
	ACCESS	read-only
	STATUS	mandatory
	DESCRIPTION	""
	::= { miblimSparingConfigProfileEntry 7 }

    limSparingConfigProfile-Item-o	OBJECT-TYPE
	SYNTAX	INTEGER
	ACCESS	read-only
	STATUS	mandatory
	DESCRIPTION	""
	::= { miblimSparingConfigProfileEntry 8 }

    limSparingConfigProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miblimSparingConfigProfileEntry 9 }

    limSparingConfigProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miblimSparingConfigProfileEntry 10 }

    limSparingConfigProfile-PhysicalAddress-ItemNumber	OBJECT-TYPE
	SYNTAX	INTEGER
	ACCESS	read-write
	STATUS	mandatory
	DESCRIPTION	"A number that specifies an addressable entity within the context of shelf and slot."
	::= { miblimSparingConfigProfileEntry 11 }

    limSparingConfigProfile-SpareSlotType	OBJECT-TYPE
	SYNTAX	INTEGER {
		    none (1),
		    unknown (2),
		    cm (3),
		    routerCard (4),
		    n-8t1Card (5),
		    n-8e1Card (6),
		    n-48modemCard (7),
		    hdlcCard (8),
		    n-4etherCard (9),
		    n-4swanCard (10),
		    hssiCard (11),
		    n-10UnchanT1Card (12),
		    obsoleteAnalogModemCard (13),
		    t3Card (14),
		    n-48modem56kCard (15),
		    shelfForward (16),
		    sdslCard (17),
		    capadslCard (18),
		    dmtadslCard (19),
		    modemController (20),
		    n-32idslCard (21),
		    n-10UnchanE1Card (22),
		    analogModem2Card (23),
		    csmxCard (24),
		    uds3Card (25),
		    ds3AtmCard (26),
		    n-4ether2Card (27),
		    hdlc2Card (28),
		    n-24sdslDataCard (29),
		    maddCard (30),
		    n-24sdslVoiceCard (31),
		    oc3AtmTrunkDaughterCard (32),
		    oc3AtmCard (33),
		    ether3Card (34),
		    srsEtherCard (35),
		    sdslAtmCard (36),
		    alDmtadslAtmCard (37),
		    csm3vCard (38),
		    hdlc2ecCard (39),
		    ds3AtmTrunkDaughterCard (40),
		    etherDualCard (41),
		    stm0Card (43),
		    sdslAtmV2Card (44),
		    terminatorCard (48),
		    dadslAtm24Card (49),
		    pctfitCard (50),
		    pctfieCard (51),
		    gliteAtm48Card (52),
		    ds3Atm2Card (53),
		    e3AtmCard (54),
		    ima24t1Card (55),
		    madd2Card (56),
		    hdsl2Card (57),
		    stngr32IdslCard (58),
		    annexbDadslAtmCard (59),
		    ima24E1Card (60),
		    annexcDadslAtmCard (61),
		    ether3ndCard (62),
		    clpmtCard (63),
		    clpmeCard (64),
		    e3AtmTrunkDaughterCard (65),
		    ima8T1Card (66),
		    ima8E1Card (67),
		    stngr48aAdslCard (68),
		    stngr48bAdslCard (69),
		    stngr48cAdslCard (70),
		    stngr40aAdslCard (71),
		    oc3Atm2Card (72),
		    n-4swan2Card (73),
		    cds3Lim (74),
		    r7000Card (75),
		    vpnCard (76),
		    hseCard (77),
		    madd3Card (78),
		    cmV2 (79),
		    coc3Lim (80),
		    shdsl72Card (81),
		    n-2oc34ds3AtmTrunkDaughterCard (82),
		    stngr72AdslCard (83),
		    mrt36AdslCard (84),
		    n-24t1Card (85),
		    n-24e1Card (86),
		    mrtCm (87),
		    cstm1Lim (88),
		    madd3240Card (89),
		    dsntscCard (90),
		    n-2ds3Card (91),
		    n-2stm14e3AtmTrunkDaughterCard (92),
		    oc3AtmTrunkDaughterCardVer2 (93),
		    enetHseCard (94),
		    ds3AtmHseCard (95),
		    oc3AtmHseCard (96),
		    gigeHseCard (97),
		    aslam32 (98),
		    vdslCard (99),
		    stngr72cAdslCard (100),
		    madd3Voip480Card (101),
		    trunkModule (102),
		    n-16oc3AtmTrunkDaughterCard (103),
		    ima8t1TrunkDaughterCard (104),
		    ima8e1TrunkDaughterCard (105),
		    n-3ds3Card (106),
		    clnCard (107),
		    alpmtCard (108),
		    ipServicesModule (110),
		    alpmeCard (111),
		    stngr72GsAdslCard (112),
		    eagleXdslCard (113),
		    oc12AtmTrunkDaughterCard (116),
		    apxenetCard (117)
		}
	ACCESS	read-write
	STATUS	mandatory
	DESCRIPTION	"The type of slot card currently present in the spare slot."
	::= { miblimSparingConfigProfileEntry 12 }

    limSparingConfigProfile-SparingMode	OBJECT-TYPE
	SYNTAX	INTEGER {
		    inactive (1),
		    manual (2),
		    automatic (3)
		}
	ACCESS	read-write
	STATUS	mandatory
	DESCRIPTION	"LIM sparing mode defines the operational mode of the sparing function."
	::= { miblimSparingConfigProfileEntry 2 }

    limSparingConfigProfile-SpareSlotNumber	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The slot-number of the spare LIM."
	::= { miblimSparingConfigProfileEntry 3 }

    limSparingConfigProfile-ManuallySparedSlotNumber	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The slot-number of the manually spared LIM."
	::= { miblimSparingConfigProfileEntry 4 }

    limSparingConfigProfile-Action-o	OBJECT-TYPE
	SYNTAX	INTEGER {
		    noAction (1),
		    createProfile (2),
		    deleteProfile (3)
		}
	ACCESS	read-write
	STATUS	mandatory
	DESCRIPTION	""
	::= { miblimSparingConfigProfileEntry 5 }


	-- The miblimSparingConfigProfile__auto_lim_sparing_config__lim_sparing_config table
	--
	-- This table contains parameters for the miblimSparingConfigProfile__auto_lim_sparing_config__lim_sparing_config profile
	--

    miblimSparingConfigProfile-AutoLimSparingConfig-LimSparingConfigTable	OBJECT-TYPE
	SYNTAX		SEQUENCE OF MiblimSparingConfigProfile-AutoLimSparingConfig-LimSparingConfigEntry
	ACCESS		not-accessible
	STATUS		mandatory
	DESCRIPTION	"A list of miblimSparingConfigProfile__auto_lim_sparing_config__lim_sparing_config profile entries."
	::= { miblimSparingConfigProfile 2 }

    miblimSparingConfigProfile-AutoLimSparingConfig-LimSparingConfigEntry	OBJECT-TYPE
	SYNTAX		MiblimSparingConfigProfile-AutoLimSparingConfig-LimSparingConfigEntry
	ACCESS		not-accessible
	STATUS		mandatory
	DESCRIPTION	"A miblimSparingConfigProfile__auto_lim_sparing_config__lim_sparing_config entry containing objects that
			 maps to the parameters of miblimSparingConfigProfile__auto_lim_sparing_config__lim_sparing_config profile."
	INDEX		{ limSparingConfigProfile-AutoLimSparingConfig-LimSparingConfig-Shelf-o, limSparingConfigProfile-AutoLimSparingConfig-LimSparingConfig-Slot-o, limSparingConfigProfile-AutoLimSparingConfig-LimSparingConfig-Item-o, limSparingConfigProfile-AutoLimSparingConfig-LimSparingConfig-Index-o }
	::= { miblimSparingConfigProfile-AutoLimSparingConfig-LimSparingConfigTable 1 }

    MiblimSparingConfigProfile-AutoLimSparingConfig-LimSparingConfigEntry ::=
	SEQUENCE {
	    limSparingConfigProfile-AutoLimSparingConfig-LimSparingConfig-Shelf-o
		INTEGER,
	    limSparingConfigProfile-AutoLimSparingConfig-LimSparingConfig-Slot-o
		INTEGER,
	    limSparingConfigProfile-AutoLimSparingConfig-LimSparingConfig-Item-o
		INTEGER,
	    limSparingConfigProfile-AutoLimSparingConfig-LimSparingConfig-Index-o
		INTEGER,
	    limSparingConfigProfile-AutoLimSparingConfig-LimSparingConfig-Active
		INTEGER,
	    limSparingConfigProfile-AutoLimSparingConfig-LimSparingConfig-ErrorAveragingPeriod
		INTEGER,
	    limSparingConfigProfile-AutoLimSparingConfig-LimSparingConfig-ErrorThreshold
		INTEGER,
	    limSparingConfigProfile-AutoLimSparingConfig-LimSparingConfig-UpDownThreshold
		INTEGER,
	    limSparingConfigProfile-AutoLimSparingConfig-LimSparingConfig-PortFailureThreshold
		INTEGER
	}

    limSparingConfigProfile-AutoLimSparingConfig-LimSparingConfig-Shelf-o	OBJECT-TYPE
	SYNTAX	INTEGER
	ACCESS	read-only
	STATUS	mandatory
	DESCRIPTION	""
	::= { miblimSparingConfigProfile-AutoLimSparingConfig-LimSparingConfigEntry 1 }

    limSparingConfigProfile-AutoLimSparingConfig-LimSparingConfig-Slot-o	OBJECT-TYPE
	SYNTAX	INTEGER
	ACCESS	read-only
	STATUS	mandatory
	DESCRIPTION	""
	::= { miblimSparingConfigProfile-AutoLimSparingConfig-LimSparingConfigEntry 2 }

    limSparingConfigProfile-AutoLimSparingConfig-LimSparingConfig-Item-o	OBJECT-TYPE
	SYNTAX	INTEGER
	ACCESS	read-only
	STATUS	mandatory
	DESCRIPTION	""
	::= { miblimSparingConfigProfile-AutoLimSparingConfig-LimSparingConfigEntry 3 }

    limSparingConfigProfile-AutoLimSparingConfig-LimSparingConfig-Index-o	OBJECT-TYPE
	SYNTAX	INTEGER
	ACCESS	read-only
	STATUS	mandatory
	DESCRIPTION	""
	::= { miblimSparingConfigProfile-AutoLimSparingConfig-LimSparingConfigEntry 4 }

    limSparingConfigProfile-AutoLimSparingConfig-LimSparingConfig-Active	OBJECT-TYPE
	SYNTAX	INTEGER {
		    no (1),
		    yes (2)
		}
	ACCESS	read-write
	STATUS	mandatory
	DESCRIPTION	"enabled / disabled sparing for this LIM by setting this field to yes / no."
	::= { miblimSparingConfigProfile-AutoLimSparingConfig-LimSparingConfigEntry 5 }

    limSparingConfigProfile-AutoLimSparingConfig-LimSparingConfig-ErrorAveragingPeriod	OBJECT-TYPE
	SYNTAX	INTEGER
	ACCESS	read-write
	STATUS	mandatory
	DESCRIPTION	"The time period used for calculation of the error moving average."
	::= { miblimSparingConfigProfile-AutoLimSparingConfig-LimSparingConfigEntry 6 }

    limSparingConfigProfile-AutoLimSparingConfig-LimSparingConfig-ErrorThreshold	OBJECT-TYPE
	SYNTAX	INTEGER
	ACCESS	read-write
	STATUS	mandatory
	DESCRIPTION	"The moving average error threshold that would initiate sparing."
	::= { miblimSparingConfigProfile-AutoLimSparingConfig-LimSparingConfigEntry 7 }

    limSparingConfigProfile-AutoLimSparingConfig-LimSparingConfig-UpDownThreshold	OBJECT-TYPE
	SYNTAX	INTEGER
	ACCESS	read-write
	STATUS	mandatory
	DESCRIPTION	"The line up-down count threshold that would initiate sparing."
	::= { miblimSparingConfigProfile-AutoLimSparingConfig-LimSparingConfigEntry 8 }

    limSparingConfigProfile-AutoLimSparingConfig-LimSparingConfig-PortFailureThreshold	OBJECT-TYPE
	SYNTAX	INTEGER
	ACCESS	read-write
	STATUS	mandatory
	DESCRIPTION	"The port failure threshold that would initiate LIM sparing."
	::= { miblimSparingConfigProfile-AutoLimSparingConfig-LimSparingConfigEntry 10 }


	-- The mibifSparingConfigProfile table
	--
	-- This table contains parameters for the mibifSparingConfigProfile profile
	--

    mibifSparingConfigProfileTable	OBJECT-TYPE
	SYNTAX		SEQUENCE OF MibifSparingConfigProfileEntry
	ACCESS		not-accessible
	STATUS		mandatory
	DESCRIPTION	"A list of mibifSparingConfigProfile profile entries."
	::= { mibifSparingConfigProfile 1 }

    mibifSparingConfigProfileEntry	OBJECT-TYPE
	SYNTAX		MibifSparingConfigProfileEntry
	ACCESS		not-accessible
	STATUS		mandatory
	DESCRIPTION	"A mibifSparingConfigProfile entry containing objects that
			 maps to the parameters of mibifSparingConfigProfile profile."
	INDEX		{ ifSparingConfigProfile-Index-o }
	::= { mibifSparingConfigProfileTable 1 }

    MibifSparingConfigProfileEntry ::=
	SEQUENCE {
	    ifSparingConfigProfile-Index-o
		INTEGER,
	    ifSparingConfigProfile-Action-o
		INTEGER
	}

    ifSparingConfigProfile-Index-o	OBJECT-TYPE
	SYNTAX	INTEGER
	ACCESS	read-only
	STATUS	mandatory
	DESCRIPTION	""
	::= { mibifSparingConfigProfileEntry 1 }

    ifSparingConfigProfile-Action-o	OBJECT-TYPE
	SYNTAX	INTEGER {
		    noAction (1),
		    createProfile (2),
		    deleteProfile (3)
		}
	ACCESS	read-write
	STATUS	mandatory
	DESCRIPTION	""
	::= { mibifSparingConfigProfileEntry 2 }


	-- The miblimSparingStatusProfile table
	--
	-- This table contains parameters for the miblimSparingStatusProfile profile
	--

    miblimSparingStatusProfileTable	OBJECT-TYPE
	SYNTAX		SEQUENCE OF MiblimSparingStatusProfileEntry
	ACCESS		not-accessible
	STATUS		mandatory
	DESCRIPTION	"A list of miblimSparingStatusProfile profile entries."
	::= { miblimSparingStatusProfile 1 }

    miblimSparingStatusProfileEntry	OBJECT-TYPE
	SYNTAX		MiblimSparingStatusProfileEntry
	ACCESS		not-accessible
	STATUS		mandatory
	DESCRIPTION	"A miblimSparingStatusProfile entry containing objects that
			 maps to the parameters of miblimSparingStatusProfile profile."
	INDEX		{ limSparingStatusProfile-Index-o }
	::= { miblimSparingStatusProfileTable 1 }

    MiblimSparingStatusProfileEntry ::=
	SEQUENCE {
	    limSparingStatusProfile-Index-o
		INTEGER,
	    limSparingStatusProfile-SpareSlotType
		INTEGER,
	    limSparingStatusProfile-SparingMode
		INTEGER,
	    limSparingStatusProfile-SpareSlotNumber
		INTEGER,
	    limSparingStatusProfile-SparedSlotNumber
		INTEGER,
	    limSparingStatusProfile-SparingChangeReason
		INTEGER,
	    limSparingStatusProfile-SparingChangeTime
		INTEGER,
	    limSparingStatusProfile-SparingChangeCounter
		INTEGER,
	    limSparingStatusProfile-Action-o
		INTEGER
	}

    limSparingStatusProfile-Index-o	OBJECT-TYPE
	SYNTAX	INTEGER
	ACCESS	read-only
	STATUS	mandatory
	DESCRIPTION	""
	::= { miblimSparingStatusProfileEntry 1 }

    limSparingStatusProfile-SpareSlotType	OBJECT-TYPE
	SYNTAX	INTEGER {
		    none (1),
		    unknown (2),
		    cm (3),
		    routerCard (4),
		    n-8t1Card (5),
		    n-8e1Card (6),
		    n-48modemCard (7),
		    hdlcCard (8),
		    n-4etherCard (9),
		    n-4swanCard (10),
		    hssiCard (11),
		    n-10UnchanT1Card (12),
		    obsoleteAnalogModemCard (13),
		    t3Card (14),
		    n-48modem56kCard (15),
		    shelfForward (16),
		    sdslCard (17),
		    capadslCard (18),
		    dmtadslCard (19),
		    modemController (20),
		    n-32idslCard (21),
		    n-10UnchanE1Card (22),
		    analogModem2Card (23),
		    csmxCard (24),
		    uds3Card (25),
		    ds3AtmCard (26),
		    n-4ether2Card (27),
		    hdlc2Card (28),
		    n-24sdslDataCard (29),
		    maddCard (30),
		    n-24sdslVoiceCard (31),
		    oc3AtmTrunkDaughterCard (32),
		    oc3AtmCard (33),
		    ether3Card (34),
		    srsEtherCard (35),
		    sdslAtmCard (36),
		    alDmtadslAtmCard (37),
		    csm3vCard (38),
		    hdlc2ecCard (39),
		    ds3AtmTrunkDaughterCard (40),
		    etherDualCard (41),
		    stm0Card (43),
		    sdslAtmV2Card (44),
		    terminatorCard (48),
		    dadslAtm24Card (49),
		    pctfitCard (50),
		    pctfieCard (51),
		    gliteAtm48Card (52),
		    ds3Atm2Card (53),
		    e3AtmCard (54),
		    ima24t1Card (55),
		    madd2Card (56),
		    hdsl2Card (57),
		    stngr32IdslCard (58),
		    annexbDadslAtmCard (59),
		    ima24E1Card (60),
		    annexcDadslAtmCard (61),
		    ether3ndCard (62),
		    clpmtCard (63),
		    clpmeCard (64),
		    e3AtmTrunkDaughterCard (65),
		    ima8T1Card (66),
		    ima8E1Card (67),
		    stngr48aAdslCard (68),
		    stngr48bAdslCard (69),
		    stngr48cAdslCard (70),
		    stngr40aAdslCard (71),
		    oc3Atm2Card (72),
		    n-4swan2Card (73),
		    cds3Lim (74),
		    r7000Card (75),
		    vpnCard (76),
		    hseCard (77),
		    madd3Card (78),
		    cmV2 (79),
		    coc3Lim (80),
		    shdsl72Card (81),
		    n-2oc34ds3AtmTrunkDaughterCard (82),
		    stngr72AdslCard (83),
		    mrt36AdslCard (84),
		    n-24t1Card (85),
		    n-24e1Card (86),
		    mrtCm (87),
		    cstm1Lim (88),
		    madd3240Card (89),
		    dsntscCard (90),
		    n-2ds3Card (91),
		    n-2stm14e3AtmTrunkDaughterCard (92),
		    oc3AtmTrunkDaughterCardVer2 (93),
		    enetHseCard (94),
		    ds3AtmHseCard (95),
		    oc3AtmHseCard (96),
		    gigeHseCard (97),
		    aslam32 (98),
		    vdslCard (99),
		    stngr72cAdslCard (100),
		    madd3Voip480Card (101),
		    trunkModule (102),
		    n-16oc3AtmTrunkDaughterCard (103),
		    ima8t1TrunkDaughterCard (104),
		    ima8e1TrunkDaughterCard (105),
		    n-3ds3Card (106),
		    clnCard (107),
		    alpmtCard (108),
		    ipServicesModule (110),
		    alpmeCard (111),
		    stngr72GsAdslCard (112),
		    eagleXdslCard (113),
		    oc12AtmTrunkDaughterCard (116),
		    apxenetCard (117)
		}
	ACCESS	read-only
	STATUS	mandatory
	DESCRIPTION	"The type of slot card currently being spared."
	::= { miblimSparingStatusProfileEntry 2 }

    limSparingStatusProfile-SparingMode	OBJECT-TYPE
	SYNTAX	INTEGER {
		    inactive (1),
		    manual (2),
		    automatic (3)
		}
	ACCESS	read-only
	STATUS	mandatory
	DESCRIPTION	"LIM sparing mode defines the operational mode of the sparing function."
	::= { miblimSparingStatusProfileEntry 3 }

    limSparingStatusProfile-SpareSlotNumber	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-only
	STATUS	mandatory
	DESCRIPTION	"The slot-number of the spare card."
	::= { miblimSparingStatusProfileEntry 4 }

    limSparingStatusProfile-SparedSlotNumber	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-only
	STATUS	mandatory
	DESCRIPTION	"The slot-number of the spared card."
	::= { miblimSparingStatusProfileEntry 5 }

    limSparingStatusProfile-SparingChangeReason	OBJECT-TYPE
	SYNTAX	INTEGER {
		    unknown (1),
		    manual (2),
		    automatic (3),
		    test (4)
		}
	ACCESS	read-only
	STATUS	mandatory
	DESCRIPTION	"The reson for the last sparing state change."
	::= { miblimSparingStatusProfileEntry 6 }

    limSparingStatusProfile-SparingChangeTime	OBJECT-TYPE
	SYNTAX	INTEGER
	ACCESS	read-only
	STATUS	mandatory
	DESCRIPTION	"The time of the last sparing state change."
	::= { miblimSparingStatusProfileEntry 7 }

    limSparingStatusProfile-SparingChangeCounter	OBJECT-TYPE
	SYNTAX	INTEGER
	ACCESS	read-only
	STATUS	mandatory
	DESCRIPTION	"The number of sparing state changes."
	::= { miblimSparingStatusProfileEntry 8 }

    limSparingStatusProfile-Action-o	OBJECT-TYPE
	SYNTAX	INTEGER {
		    noAction (1),
		    createProfile (2),
		    deleteProfile (3)
		}
	ACCESS	read-write
	STATUS	mandatory
	DESCRIPTION	""
	::= { miblimSparingStatusProfileEntry 9 }


	-- The miblimSparingStatusProfile__lim_sparing_status table
	--
	-- This table contains parameters for the miblimSparingStatusProfile__lim_sparing_status profile
	--

    miblimSparingStatusProfile-LimSparingStatusTable	OBJECT-TYPE
	SYNTAX		SEQUENCE OF MiblimSparingStatusProfile-LimSparingStatusEntry
	ACCESS		not-accessible
	STATUS		mandatory
	DESCRIPTION	"A list of miblimSparingStatusProfile__lim_sparing_status profile entries."
	::= { miblimSparingStatusProfile 2 }

    miblimSparingStatusProfile-LimSparingStatusEntry	OBJECT-TYPE
	SYNTAX		MiblimSparingStatusProfile-LimSparingStatusEntry
	ACCESS		not-accessible
	STATUS		mandatory
	DESCRIPTION	"A miblimSparingStatusProfile__lim_sparing_status entry containing objects that
			 maps to the parameters of miblimSparingStatusProfile__lim_sparing_status profile."
	INDEX		{ limSparingStatusProfile-LimSparingStatus-Index-o, limSparingStatusProfile-LimSparingStatus-Index1-o }
	::= { miblimSparingStatusProfile-LimSparingStatusTable 1 }

    MiblimSparingStatusProfile-LimSparingStatusEntry ::=
	SEQUENCE {
	    limSparingStatusProfile-LimSparingStatus-Index-o
		INTEGER,
	    limSparingStatusProfile-LimSparingStatus-Index1-o
		INTEGER,
	    limSparingStatusProfile-LimSparingStatus-Active
		INTEGER,
	    limSparingStatusProfile-LimSparingStatus-LimStatusOk
		INTEGER,
	    limSparingStatusProfile-LimSparingStatus-SparingState
		INTEGER
	}

    limSparingStatusProfile-LimSparingStatus-Index-o	OBJECT-TYPE
	SYNTAX	INTEGER
	ACCESS	read-only
	STATUS	mandatory
	DESCRIPTION	""
	::= { miblimSparingStatusProfile-LimSparingStatusEntry 1 }

    limSparingStatusProfile-LimSparingStatus-Index1-o	OBJECT-TYPE
	SYNTAX	INTEGER
	ACCESS	read-only
	STATUS	mandatory
	DESCRIPTION	""
	::= { miblimSparingStatusProfile-LimSparingStatusEntry 2 }

    limSparingStatusProfile-LimSparingStatus-Active	OBJECT-TYPE
	SYNTAX	INTEGER {
		    no (1),
		    yes (2)
		}
	ACCESS	read-only
	STATUS	mandatory
	DESCRIPTION	"The sparing active state for this LIM."
	::= { miblimSparingStatusProfile-LimSparingStatusEntry 3 }

    limSparingStatusProfile-LimSparingStatus-LimStatusOk	OBJECT-TYPE
	SYNTAX	INTEGER {
		    no (1),
		    yes (2)
		}
	ACCESS	read-only
	STATUS	mandatory
	DESCRIPTION	"Is the LIM status OK."
	::= { miblimSparingStatusProfile-LimSparingStatusEntry 4 }

    limSparingStatusProfile-LimSparingStatus-SparingState	OBJECT-TYPE
	SYNTAX	INTEGER {
		    sparingNone (1),
		    primaryActive (2),
		    primaryInactive (3),
		    secondaryActive (4),
		    secondaryInactive (5),
		    notApplicable (6)
		}
	ACCESS	read-only
	STATUS	mandatory
	DESCRIPTION	"The sparing state of the line interface module ( LIM )."
	::= { miblimSparingStatusProfile-LimSparingStatusEntry 5 }

END
