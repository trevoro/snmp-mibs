HIPATH-WIRELESS-HIGUARD-MIB DEFINITIONS ::= BEGIN

IMPORTS
        enterprises,
        MODULE-IDENTITY,
        OBJECT-TYPE,
        NOTIFICATION-TYPE,
        Integer32,IpAddress
                FROM SNMPv2-SMI
        hiPathWirelessHWM			
		FROM HIPATH-WIRELESS-SMI;

-- 1.3.6.1.4.1.4329.15.6.1
hiPathWirelessHiGuardMib MODULE-IDENTITY
        LAST-UPDATED "201010211500Z"    -- October 21, 2010 03:00:00 PM
        ORGANIZATION 
		"Siemens Enterprise Networks, Inc."
        CONTACT-INFO
		"Behrouz Sultan
		 Enterasys Networks, Inc.
				
		 55 Commerce Valley Drive, Suite 400
		 Thornhill ON, L3T 7V9
				
		 Email: bsultani@enterasys.com
		 Phone: 289-695-3241"

        DESCRIPTION
		"Definitions for parsing events sent by HiGuard Server"
        REVISION "201010211500Z"        -- October 21, 2010 03:00:00 PM
        DESCRIPTION
                "Initial version."
     ::= { hiPathWirelessHWM 1 }

--
-- Node definitions
--

-- 1.3.6.1.4.1.4329.15.6.1.1
eventSeverityLevel OBJECT-TYPE
        SYNTAX INTEGER {
            high(1),
            medium(2),
            low(3)
        }
        MAX-ACCESS read-only
        STATUS current
        DESCRIPTION "Event Severity level"
     ::= { hiPathWirelessHiGuardMib 1 }

-- 1.3.6.1.4.1.4329.15.6.1.2
senderComponentId OBJECT-TYPE
        SYNTAX OCTET STRING (SIZE (1..300))
        MAX-ACCESS read-only
        STATUS current
        DESCRIPTION "Sender Component ID"
     ::= { hiPathWirelessHiGuardMib 2 }

-- 1.3.6.1.4.1.4329.15.6.1.3
senderIPaddress OBJECT-TYPE
        SYNTAX IpAddress
        MAX-ACCESS read-only
        STATUS current
        DESCRIPTION "Sender IP Address"
     ::= { hiPathWirelessHiGuardMib 3 }

-- 1.3.6.1.4.1.4329.15.6.1.4
eventSummaryDescription OBJECT-TYPE
        SYNTAX OCTET STRING (SIZE (1..300))
        MAX-ACCESS read-only
        STATUS current
        DESCRIPTION "Event Summary Description"
     ::= { hiPathWirelessHiGuardMib 4 }

-- 1.3.6.1.4.1.4329.15.6.1.5
hiGuardEvent NOTIFICATION-TYPE
        OBJECTS {
             eventSeverityLevel,
             senderComponentId,
             senderIPaddress,    
	     eventSummaryDescription
        }
        STATUS current
        DESCRIPTION "SpectraGuard Enterprise Event"
     ::= { hiPathWirelessHiGuardMib 5 }

END
