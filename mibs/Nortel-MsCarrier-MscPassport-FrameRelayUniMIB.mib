Nortel-MsCarrier-MscPassport-FrameRelayUniMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      Hex,
      NonReplicated,
      FixedPoint3,
      HexString,
      EnterpriseDateAndTime,
      PassportCounter64,
      Link,
      DigitString,
      Unsigned64
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayUni Enterprise MIB."

frameRelayUniMIB OBJECT IDENTIFIER ::= { mscPassportMIBs 24 }










-- FrameRelayUni/n
-- This component defines an instance of the Frame Relay UNI 
-- service. The component instance value n is a unique positive integer 
-- within a module. Framer is created whenever the FrUni is added. 
-- Users who need VirtualFramer should delete the Framer first, then 
-- add the VirtualFramer.

mscFrUni OBJECT IDENTIFIER ::= { mscComponents 71 }



mscFrUniRowStatusTable OBJECT-TYPE
   SYNTAX     SEQUENCE OF MscFrUniRowStatusEntry
   ACCESS     not-accessible
   STATUS     mandatory
   DESCRIPTION
     "This entry controls the addition and deletion of 
      mscFrUni components."
::= { mscFrUni 1 }

mscFrUniRowStatusEntry OBJECT-TYPE
   SYNTAX     MscFrUniRowStatusEntry
   ACCESS     not-accessible
   STATUS     mandatory
   DESCRIPTION
     "A single entry in the table represents a single 
      mscFrUni component."
   INDEX {
      mscFrUniIndex }
::= { mscFrUniRowStatusTable 1 }

MscFrUniRowStatusEntry ::= SEQUENCE {
   mscFrUniRowStatus
      RowStatus,
   mscFrUniComponentName
      DisplayString,
   mscFrUniStorageType
      StorageType,
   mscFrUniIndex
      Integer32 }

mscFrUniRowStatus OBJECT-TYPE
   SYNTAX     RowStatus 
   ACCESS     read-write
   STATUS     mandatory
   DESCRIPTION
     "This variable is used as the basis for SNMP naming of
      mscFrUni components.
      These components can be added and deleted."
::= { mscFrUniRowStatusEntry 1 }

mscFrUniComponentName OBJECT-TYPE
   SYNTAX     DisplayString 
   ACCESS     read-only
   STATUS     mandatory
   DESCRIPTION
     "This variable provides the component's string name for
      use with the ASCII Console Interface"
::= { mscFrUniRowStatusEntry 2 }

mscFrUniStorageType OBJECT-TYPE
   SYNTAX     StorageType 
   ACCESS     read-only
   STATUS     mandatory
   DESCRIPTION
     "This variable represents the storage type value for the
      mscFrUni tables."
::= { mscFrUniRowStatusEntry 4 }

mscFrUniIndex OBJECT-TYPE
   SYNTAX     Integer32 (1..65535)
   ACCESS     not-accessible
   STATUS     mandatory
   DESCRIPTION
     "This variable represents the index for the mscFrUni tables."
::= { mscFrUniRowStatusEntry 10 }

mscFrUniCidDataTable OBJECT-TYPE
   SYNTAX     SEQUENCE OF MscFrUniCidDataEntry
   ACCESS     not-accessible
   STATUS     mandatory
   DESCRIPTION
     "This group contains the attribute for a component's Customer 
      Identifier (CID). Refer to the attribute description for a detailed 
      explanation of CIDs."
::= { mscFrUni 10 }

mscFrUniCidDataEntry OBJECT-TYPE
   SYNTAX     MscFrUniCidDataEntry
   ACCESS     not-accessible
   STATUS     mandatory
   DESCRIPTION
     "An entry in the mscFrUniCidDataTable."
   INDEX {
      mscFrUniIndex }
::= { mscFrUniCidDataTable 1 }

MscFrUniCidDataEntry ::= SEQUENCE {
   mscFrUniCustomerIdentifier
      Unsigned32 }

mscFrUniCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscFrUniCidDataEntry 1 }

mscFrUniStateTable OBJECT-TYPE
   SYNTAX     SEQUENCE OF MscFrUniStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFrUni 11 }

mscFrUniStateEntry OBJECT-TYPE
   SYNTAX     MscFrUniStateEntry
   ACCESS     not-accessible
   STATUS     mandatory
   DESCRIPTION
     "An entry in the mscFrUniStateTable."
   INDEX {
      mscFrUniIndex }
::= { mscFrUniStateTable 1 }

MscFrUniStateEntry ::= SEQUENCE {
   mscFrUniAdminState
      INTEGER,
   mscFrUniOperationalState
      INTEGER,
   mscFrUniUsageState
      INTEGER,
   mscFrUniAvailabilityStatus
      OCTET STRING,
   mscFrUniProceduralStatus
      OCTET STRING,
   mscFrUniControlStatus
      OCTET STRING,
   mscFrUniAlarmStatus
      OCTET STRING,
   mscFrUniStandbyStatus
      INTEGER,
   mscFrUniUnknownStatus
      INTEGER }

mscFrUniAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFrUniStateEntry 1 }

mscFrUniOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFrUniStateEntry 2 }

mscFrUniUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFrUniStateEntry 3 }

mscFrUniAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFrUniStateEntry 4 }

mscFrUniProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFrUniStateEntry 5 }

mscFrUniControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFrUniStateEntry 6 }

mscFrUniAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFrUniStateEntry 7 }

mscFrUniStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFrUniStateEntry 8 }

mscFrUniUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFrUniStateEntry 9 }

mscFrUniStatsTable OBJECT-TYPE
   SYNTAX     SEQUENCE OF MscFrUniStatsEntry
   ACCESS     not-accessible
   STATUS     mandatory
   DESCRIPTION
     "FrUni/n Statistics
      This group contains the statistics about the operational behavior of 
      the service at the interface level."
::= { mscFrUni 12 }

mscFrUniStatsEntry OBJECT-TYPE
   SYNTAX     MscFrUniStatsEntry
   ACCESS     not-accessible
   STATUS     mandatory
   DESCRIPTION
     "An entry in the mscFrUniStatsTable."
   INDEX {
      mscFrUniIndex }
::= { mscFrUniStatsTable 1 }

MscFrUniStatsEntry ::= SEQUENCE {
   mscFrUniLastUnknownDlci
      Unsigned32,
   mscFrUniUnknownDlciFramesFromIf
      Counter32,
   mscFrUniInvalidHeaderFramesFromIf
      Counter32 }

mscFrUniLastUnknownDlci OBJECT-TYPE
   SYNTAX     Unsigned32 (0..1023)
   ACCESS     read-only
   STATUS     mandatory
   DESCRIPTION
     "This attribute identifies the most recent DLCI which user frames 
      were received on for which a DLCI has not been provisioned on the 
      port."
   DEFVAL     { 0 }
::= { mscFrUniStatsEntry 1 }

mscFrUniUnknownDlciFramesFromIf OBJECT-TYPE
   SYNTAX     Counter32 
   ACCESS     read-only
   STATUS     mandatory
   DESCRIPTION
     "This attribute contains a count of the number of frames received 
      from the interface with an unknown DLCI (DLCI which is not 
      provisioned). When the maximum is reached the count wraps to 
      zero."
::= { mscFrUniStatsEntry 2 }

mscFrUniInvalidHeaderFramesFromIf OBJECT-TYPE
   SYNTAX     Counter32 
   ACCESS     read-only
   STATUS     mandatory
   DESCRIPTION
     "This attribute counts the number of frames received from the 
      interface with an invalid header format. When the maximum is 
      reached the count wraps to zero."
::= { mscFrUniStatsEntry 3 }

mscFrUniIfEntryTable OBJECT-TYPE
   SYNTAX     SEQUENCE OF MscFrUniIfEntryEntry
   ACCESS     not-accessible
   STATUS     mandatory
   DESCRIPTION
     "This group contains the provisionable attributes for the ifEntry."
::= { mscFrUni 13 }

mscFrUniIfEntryEntry OBJECT-TYPE
   SYNTAX     MscFrUniIfEntryEntry
   ACCESS     not-accessible
   STATUS     mandatory
   DESCRIPTION
     "An entry in the mscFrUniIfEntryTable."
   INDEX {
      mscFrUniIndex }
::= { mscFrUniIfEntryTable 1 }

MscFrUniIfEntryEntry ::= SEQUENCE {
   mscFrUniIfAdminStatus
      INTEGER,
   mscFrUniIfIndex
      InterfaceIndex }

mscFrUniIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscFrUniIfEntryEntry 1 }

mscFrUniIfIndex OBJECT-TYPE
   SYNTAX     InterfaceIndex (1..65535)
   ACCESS     read-only
   STATUS     mandatory
   DESCRIPTION
     "This is the index for the IfEntry. Its value is automatically initialized 
      during the provisioning process."
::= { mscFrUniIfEntryEntry 2 }

mscFrUniOperStatusTable OBJECT-TYPE
   SYNTAX     SEQUENCE OF MscFrUniOperStatusEntry
   ACCESS     not-accessible
   STATUS     mandatory
   DESCRIPTION
     "This group includes the Operational Status attribute. This attribute 
      defines the current operational state of this component."
::= { mscFrUni 14 }

mscFrUniOperStatusEntry OBJECT-TYPE
   SYNTAX     MscFrUniOperStatusEntry
   ACCESS     not-accessible
   STATUS     mandatory
   DESCRIPTION
     "An entry in the mscFrUniOperStatusTable."
   INDEX {
      mscFrUniIndex }
::= { mscFrUniOperStatusTable 1 }

MscFrUniOperStatusEntry ::= SEQUENCE {
   mscFrUniSnmpOperStatus
      INTEGER }

mscFrUniSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscFrUniOperStatusEntry 1 }

mscFrUniEmissionPriorityQsTable OBJECT-TYPE
   SYNTAX     SEQUENCE OF MscFrUniEmissionPriorityQsEntry
   ACCESS     not-accessible
   STATUS     mandatory
   DESCRIPTION
     "This group contains the provisionable attribute to specifie the 
      number of Frame Relay egress emission priority queues to be used 
      on that Frame Relay Interface"
::= { mscFrUni 15 }

mscFrUniEmissionPriorityQsEntry OBJECT-TYPE
   SYNTAX     MscFrUniEmissionPriorityQsEntry
   ACCESS     not-accessible
   STATUS     mandatory
   DESCRIPTION
     "An entry in the mscFrUniEmissionPriorityQsTable."
   INDEX {
      mscFrUniIndex }
::= { mscFrUniEmissionPriorityQsTable 1 }

MscFrUniEmissionPriorityQsEntry ::= SEQUENCE {
   mscFrUniNumberOfEmissionQs
      Unsigned32 }

mscFrUniNumberOfEmissionQs OBJECT-TYPE
   SYNTAX     Unsigned32 (2 | 4)
   ACCESS     read-write
   STATUS     mandatory
   DESCRIPTION
     "This attribute specifies the number of egress emission priority 
      queues that will be used for that Frame Relay interface. The 
      possible values of this attribute are 2 or 4:
      For V.35, V.11, HSSI, E1, DS1, E3, DS3 or 8pDS1 the possible 
      values are: 2 (in which case they are hardware queues), or 4 (in 
      which case they are software queues).
      For DS1C, E1C or DS3C the possible values are 2, 4 (in all cases 
      they are software queues)."
   DEFVAL     { 2 }
::= { mscFrUniEmissionPriorityQsEntry 1 }

mscFrUniFrmToIfByQueueTable OBJECT-TYPE
   SYNTAX     SEQUENCE OF MscFrUniFrmToIfByQueueEntry
   ACCESS     not-accessible
   STATUS     mandatory
   DESCRIPTION
     "This attribute counts the total number of frames transmitted to the 
      interface per egress emission priority queue since the component 
      has been activated. There is potientially a maximum of 4 emission 
      priority queues. The number of available egress queues varies 
      according to the value of the provisionable attribute 
      numberOfEmissionQs. Egress queue 0 has the lowest priority, while 
      egress queue 3 has the highest priority. The queue values
      are only indicated when the numberOfEmissionQs is set to 4 
      queues."
::= { mscFrUni 341 }

mscFrUniFrmToIfByQueueEntry OBJECT-TYPE
   SYNTAX     MscFrUniFrmToIfByQueueEntry
   ACCESS     not-accessible
   STATUS     mandatory
   DESCRIPTION
     "An entry in the mscFrUniFrmToIfByQueueTable."
   INDEX {
      mscFrUniIndex,
      mscFrUniFrmToIfByQueueIndex }
::= { mscFrUniFrmToIfByQueueTable 1 }

MscFrUniFrmToIfByQueueEntry ::= SEQUENCE {
   mscFrUniFrmToIfByQueueIndex
      Integer32,
   mscFrUniFrmToIfByQueueValue
      Unsigned32 }

mscFrUniFrmToIfByQueueIndex OBJECT-TYPE
   SYNTAX     Integer32 (0..3)
   ACCESS     not-accessible
   STATUS     mandatory
   DESCRIPTION
     "This variable represents the index for the mscFrUniFrmToIfByQueueTable."
::= { mscFrUniFrmToIfByQueueEntry 1 }

mscFrUniFrmToIfByQueueValue OBJECT-TYPE
   SYNTAX     Unsigned32 (0..4294967295)
   ACCESS     read-only
   STATUS     mandatory
   DESCRIPTION
     "This variable represents an individual value for the
      mscFrUniFrmToIfByQueueTable."
::= { mscFrUniFrmToIfByQueueEntry 2 }

mscFrUniOctetToIfByQueueTable OBJECT-TYPE
   SYNTAX     SEQUENCE OF MscFrUniOctetToIfByQueueEntry
   ACCESS     not-accessible
   STATUS     mandatory
   DESCRIPTION
     "This attribute counts the total number of octets transmitted from the 
      service to the interface per emission priority queue since the 
      component has been activated. There is potientially a maximum of 
      4 emission priority queues. The number of available egress queues 
      varies according to the value of the provisionable attribute 
      numberOfEmissionQs. Egress queue 0 has the lowest priority, while 
      egress queue 3 has the highest priority."
::= { mscFrUni 342 }

mscFrUniOctetToIfByQueueEntry OBJECT-TYPE
   SYNTAX     MscFrUniOctetToIfByQueueEntry
   ACCESS     not-accessible
   STATUS     mandatory
   DESCRIPTION
     "An entry in the mscFrUniOctetToIfByQueueTable."
   INDEX {
      mscFrUniIndex,
      mscFrUniOctetToIfByQueueIndex }
::= { mscFrUniOctetToIfByQueueTable 1 }

MscFrUniOctetToIfByQueueEntry ::= SEQUENCE {
   mscFrUniOctetToIfByQueueIndex
      Integer32,
   mscFrUniOctetToIfByQueueValue
      Unsigned32 }

mscFrUniOctetToIfByQueueIndex OBJECT-TYPE
   SYNTAX     Integer32 (0..3)
   ACCESS     not-accessible
   STATUS     mandatory
   DESCRIPTION
     "This variable represents the index for the mscFrUniOctetToIfByQueueTable."
::= { mscFrUniOctetToIfByQueueEntry 1 }

mscFrUniOctetToIfByQueueValue OBJECT-TYPE
   SYNTAX     Unsigned32 (0..4294967295)
   ACCESS     read-only
   STATUS     mandatory
   DESCRIPTION
     "This variable represents an individual value for the
      mscFrUniOctetToIfByQueueTable."
::= { mscFrUniOctetToIfByQueueEntry 2 }


-- This group contains a superset of all attributes which may apply to a 
-- VC. Particular applications will typically offer only a subset of 
-- these attributes by providing a definition of their own DNA 
-- subcomponent. 

mscFrUniDna OBJECT IDENTIFIER ::= { mscFrUni 2 }



mscFrUniDnaRowStatusTable OBJECT-TYPE
   SYNTAX     SEQUENCE OF MscFrUniDnaRowStatusEntry
   ACCESS     not-accessible
   STATUS     mandatory
   DESCRIPTION
     "This entry controls the addition and deletion of 
      mscFrUniDna components."
::= { mscFrUniDna 1 }

mscFrUniDnaRowStatusEntry OBJECT-TYPE
   SYNTAX     MscFrUniDnaRowStatusEntry
   ACCESS     not-accessible
   STATUS     mandatory
   DESCRIPTION
     "A single entry in the table represents a single 
      mscFrUniDna component."
   INDEX {
      mscFrUniIndex,
      mscFrUniDnaIndex }
::= { mscFrUniDnaRowStatusTable 1 }

MscFrUniDnaRowStatusEntry ::= SEQUENCE {
   mscFrUniDnaRowStatus
      RowStatus,
   mscFrUniDnaComponentName
      DisplayString,
   mscFrUniDnaStorageType
      StorageType,
   mscFrUniDnaIndex
      NonReplicated }

mscFrUniDnaRowStatus OBJECT-TYPE
   SYNTAX     RowStatus 
   ACCESS     read-only
   STATUS     mandatory
   DESCRIPTION
     "This variable is used as the basis for SNMP naming of
      mscFrUniDna components.
      These components cannot be added nor deleted."
::= { mscFrUniDnaRowStatusEntry 1 }

mscFrUniDnaComponentName OBJECT-TYPE
   SYNTAX     DisplayString 
   ACCESS     read-only
   STATUS     mandatory
   DESCRIPTION
     "This variable provides the component's string name for
      use with the ASCII Console Interface"
::= { mscFrUniDnaRowStatusEntry 2 }

mscFrUniDnaStorageType OBJECT-TYPE
   SYNTAX     StorageType 
   ACCESS     read-only
   STATUS     mandatory
   DESCRIPTION
     "This variable represents the storage type value for the
      mscFrUniDna tables."
::= { mscFrUniDnaRowStatusEntry 4 }

mscFrUniDnaIndex OBJECT-TYPE
   SYNTAX     NonReplicated 
   ACCESS     not-accessible
   STATUS     mandatory
   DESCRIPTION
     "This variable represents the index for the mscFrUniDna tables."
::= { mscFrUniDnaRowStatusEntry 10 }

mscFrUniDnaAddressTable OBJECT-TYPE
   SYNTAX     SEQUENCE OF MscFrUniDnaAddressEntry
   ACCESS     not-accessible
   STATUS     mandatory
   DESCRIPTION
     "This group contains attributes common to all DNAs. Every DNA 
      used in the network is defined with this group of 2 attributes."
::= { mscFrUniDna 10 }

mscFrUniDnaAddressEntry OBJECT-TYPE
   SYNTAX     MscFrUniDnaAddressEntry
   ACCESS     not-accessible
   STATUS     mandatory
   DESCRIPTION
     "An entry in the mscFrUniDnaAddressTable."
   INDEX {
      mscFrUniIndex,
      mscFrUniDnaIndex }
::= { mscFrUniDnaAddressTable 1 }

MscFrUniDnaAddressEntry ::= SEQUENCE {
   mscFrUniDnaNumberingPlanIndicator
      INTEGER,
   mscFrUniDnaDataNetworkAddress
      DigitString }

mscFrUniDnaNumberingPlanIndicator OBJECT-TYPE
   SYNTAX     INTEGER  {
                 x121(0),
                 e164(1) }
   ACCESS     read-write
   STATUS     mandatory
   DESCRIPTION
     "This attribute indicates the Numbering Plan Indicator (NPI) of the 
      DNA that is entered. Address may belong to X.121 or E.164 plans. 
      X.121 is used in packet switched data networks."
   DEFVAL     { x121 }
::= { mscFrUniDnaAddressEntry 1 }

mscFrUniDnaDataNetworkAddress OBJECT-TYPE
   SYNTAX     DigitString (SIZE (1..15))
   ACCESS     read-write
   STATUS     mandatory
   DESCRIPTION
     "This attribute indicates the customer's unique identifier. It is the 
      equivalent of the telephone number in the telephone network."
::= { mscFrUniDnaAddressEntry 2 }

mscFrUniDnaOutgoingOptionsTable OBJECT-TYPE
   SYNTAX     SEQUENCE OF MscFrUniDnaOutgoingOptionsEntry
   ACCESS     not-accessible
   STATUS     mandatory
   DESCRIPTION
     "This group defines DNA call options for calls made from the 
      interface. These options are not used for calls arriving to the 
      interface represented by this DNA."
::= { mscFrUniDna 11 }

mscFrUniDnaOutgoingOptionsEntry OBJECT-TYPE
   SYNTAX     MscFrUniDnaOutgoingOptionsEntry
   ACCESS     not-accessible
   STATUS     mandatory
   DESCRIPTION
     "An entry in the mscFrUniDnaOutgoingOptionsTable."
   INDEX {
      mscFrUniIndex,
      mscFrUniDnaIndex }
::= { mscFrUniDnaOutgoingOptionsTable 1 }

MscFrUniDnaOutgoingOptionsEntry ::= SEQUENCE {
   mscFrUniDnaOutDefaultPriority
      INTEGER,
   mscFrUniDnaOutDefaultPathSensitivity
      INTEGER,
   mscFrUniDnaOutPathSensitivityOverRide
      INTEGER,
   mscFrUniDnaOutDefaultPathReliability
      INTEGER,
   mscFrUniDnaOutAccess
      INTEGER,
   mscFrUniDnaDefaultTransferPriority
      INTEGER,
   mscFrUniDnaTransferPriorityOverRide
      INTEGER }

mscFrUniDnaOutDefaultPriority OBJECT-TYPE
   SYNTAX     INTEGER  {
                 normal(0),
                 high(1) }
   ACCESS     read-write
   STATUS     mandatory
   DESCRIPTION
     "This attribute indicates the default priority of outgoing calls from 
      the DTE to the network.
      
      It can be overridden by the discardPriority under DLCI Direct Call 
      subcomponent.
      
      This option can be also included in X.25 signalling, in such case it 
      will be overruled."
   DEFVAL     { normal }
::= { mscFrUniDnaOutgoingOptionsEntry 7 }

mscFrUniDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls that use this DNA. The chosen default 
      class of path sensitivity applies to all outgoing calls established 
      using this DNA. 
      
      This attribute, if set to throughput, indicates that the default class is 
      throughput sensitive. If set to delay, then the default class is delay 
      sensitive. The default of outDefaultPathSensitivity is throughput."
   DEFVAL     { throughput }
::= { mscFrUniDnaOutgoingOptionsEntry 11 }

mscFrUniDnaOutPathSensitivityOverRide OBJECT-TYPE
   SYNTAX     INTEGER  {
                 no(0),
                 yes(1) }
   ACCESS     read-write
   STATUS     obsolete
   DESCRIPTION
     "If this attribute is set to yes in the call request, the called end will 
      use the calling end provisioning data on path sensitivity to override 
      its own provisioning data.
      
      The default of outPathSensitivityOverRide is yes."
   DEFVAL     { yes }
::= { mscFrUniDnaOutgoingOptionsEntry 12 }

mscFrUniDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular DNA. The chosen default class of routing applies to 
      all outgoing calls established using this DNA, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the 
      VC handles the duplication and disordering to ensure that packets 
      are delivered to the DTE properly.
      For the Frame Relay service, duplication of packets is not desired, 
      in which case, normal reliability may be chosen as the preferred 
      class of routing."
   DEFVAL     { normal }
::= { mscFrUniDnaOutgoingOptionsEntry 14 }

mscFrUniDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTEs 
      that have Incoming Access capabilities. If set to a value of 
      disallowed, then such calls cannot be made using this DNA. Such 
      calls will be cleared by the local DCE.
      This attribute corresponds to the CCITT 'Closed User Group with 
      Outgoing Access' feature for DNAs in that outgoing access is 
      granted if this attribute is set to a value of allowed."
   DEFVAL     { disallowed }
::= { mscFrUniDnaOutgoingOptionsEntry 17 }

mscFrUniDnaDefaultTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15) }
   ACCESS     read-write
   STATUS     mandatory
   DESCRIPTION
     "This attribute specifies the default transfer priority for all outgoing 
      calls using this particular DNA. It can be overridden by the 
      transferPriority provisioned in the Dlci DirectCall sub-component.
      
      The transfer priority is a preference configured for an application 
      according to its delay-sensitivity requirement. Frames with higher 
      transfer priority are served by the network before the frames with 
      lower priority. The transfer priority standard is defined to have 16 
      levels from 0 to 15.
      
      Each transfer priority n, where n indicates the transfer priority 
      index, contains a default setting for routing class of service 
      (multimedia, delay or throughput) and frame relay egress queue 
      (depending on the number of supported egress queues on the remote 
      end interface) specified by the routingClassOfService and 
      emissionPriority attributes provisioned in the Mod Frs DprsNet 
      Tpm/n component. The default mapping can be altered by a user if 
      required.
      
      The default defaultTransferPriority is 0."
   DEFVAL     { n0 }
::= { mscFrUniDnaOutgoingOptionsEntry 18 }

mscFrUniDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end 
      will use its own provisioning data on transfer priority.
      
      This attribute is not applicable for Frame Relay SVCs.
      
      For more information about transfer priority, please refer to the 
      previous attribute defaultTransferPriority.
      
      The default of transferPriorityOverRide is yes."
   DEFVAL     { yes }
::= { mscFrUniDnaOutgoingOptionsEntry 19 }

mscFrUniDnaIncomingOptionsTable OBJECT-TYPE
   SYNTAX     SEQUENCE OF MscFrUniDnaIncomingOptionsEntry
   ACCESS     not-accessible
   STATUS     mandatory
   DESCRIPTION
     "This group defines options for incoming calls. These options are 
      used for calls arriving to the interface represented by this DNA. For 
      calls originated from the interface, IncomingOptions attributes are 
      not used."
::= { mscFrUniDna 12 }

mscFrUniDnaIncomingOptionsEntry OBJECT-TYPE
   SYNTAX     MscFrUniDnaIncomingOptionsEntry
   ACCESS     not-accessible
   STATUS     mandatory
   DESCRIPTION
     "An entry in the mscFrUniDnaIncomingOptionsTable."
   INDEX {
      mscFrUniIndex,
      mscFrUniDnaIndex }
::= { mscFrUniDnaIncomingOptionsTable 1 }

MscFrUniDnaIncomingOptionsEntry ::= SEQUENCE {
   mscFrUniDnaIncAccess
      INTEGER }

mscFrUniDnaIncAccess OBJECT-TYPE
   SYNTAX     INTEGER  {
                 disallowed(0),
                 allowed(1) }
   ACCESS     read-write
   STATUS     mandatory
   DESCRIPTION
     "This attribute, if set to a value of allowed specifies that incoming 
      calls (from the network to the DTE) from the open (non-CUG) part 
      of the network are permitted. It also permits incoming calls from 
      DTEs that have outgoing access capabilities. If set to a value of 
      disallowed, such calls cannot be made to this DNA. They will be 
      cleared by the local DCE.
      This attribute corresponds to the CCITT 'Closed User Group with 
      Incoming Access' feature for DNAs in that incoming access is 
      granted if this attribute is set to a value of allowed."
   DEFVAL     { disallowed }
::= { mscFrUniDnaIncomingOptionsEntry 9 }

mscFrUniDnaCallOptionsTable OBJECT-TYPE
   SYNTAX     SEQUENCE OF MscFrUniDnaCallOptionsEntry
   ACCESS     not-accessible
   STATUS     mandatory
   DESCRIPTION
     "This group defines additional all options for not related to direction 
      of the call."
::= { mscFrUniDna 13 }

mscFrUniDnaCallOptionsEntry OBJECT-TYPE
   SYNTAX     MscFrUniDnaCallOptionsEntry
   ACCESS     not-accessible
   STATUS     mandatory
   DESCRIPTION
     "An entry in the mscFrUniDnaCallOptionsTable."
   INDEX {
      mscFrUniIndex,
      mscFrUniDnaIndex }
::= { mscFrUniDnaCallOptionsTable 1 }

MscFrUniDnaCallOptionsEntry ::= SEQUENCE {
   mscFrUniDnaAccountClass
      Unsigned32,
   mscFrUniDnaAccountCollection
      OCTET STRING,
   mscFrUniDnaServiceExchange
      Unsigned32,
   mscFrUniDnaEgressAccounting
      INTEGER,
   mscFrUniDnaDataPath
      INTEGER }

mscFrUniDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls that are set up using this particular DNA."
   DEFVAL     { 0 }
::= { mscFrUniDnaCallOptionsEntry 10 }

mscFrUniDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. The 
      force option is available for X.75 Gateways only. If none of these 
      reasons are set, then accounting will be suppressed.
      To set a specific accounting collection reason, the reason is entered 
      and the corresponding bit in the structure is set to a value of 1. To 
      turn off a specific accounting collection reason, the reason is 
      entered preceded with the '~' character, and the corresponding bit in 
      the structure is set to a value of 0.
      The bit placement for the accounting collection reasons is as 
      follows:
      Bit 0  - Bill
      Bit 1  - Test
      Bit 2  - Study
      Bit 3  - Audit
      Bit 4  - Force

      Description of bits:
      bill(0)
      test(1)
      study(2)
      audit(3)
      force(4)"
   DEFVAL     { '80'H }
::= { mscFrUniDnaCallOptionsEntry 11 }

mscFrUniDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { mscFrUniDnaCallOptionsEntry 12 }

mscFrUniDnaEgressAccounting OBJECT-TYPE
   SYNTAX     INTEGER  {
                 no(0),
                 yes(1) }
   ACCESS     read-write
   STATUS     mandatory
   DESCRIPTION
     "This attribute specifies if egress accounting is enabled by the frame 
      relay service. If egress accounting is disabled, only segment counts 
      are collected by the VC. No frame relay counts appear in the 
      accounting records for the frame relay service. If egress accounting 
      is enabled, the accounting records for the frame relay service will 
      contain frame relay specific counts."
   DEFVAL     { no }
::= { mscFrUniDnaCallOptionsEntry 13 }

mscFrUniDnaDataPath OBJECT-TYPE
   SYNTAX     INTEGER  {
                 dprsOnly(0),
                 dprsMcsOnly(1),
                 dprsMcsFirst(2) }
   ACCESS     read-write
   STATUS     mandatory
   DESCRIPTION
     "This attribute specifies the data path to be used by Virtual Circuits 
      on this interface. If the connection has a DirectCall component then 
      the value can be overridden by the dataPath attribute of the 
      DirectCall component.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used."
   DEFVAL     { dprsOnly }
::= { mscFrUniDnaCallOptionsEntry 21 }


-- 
-- FrUni/n Dna ClosedUserGroup
-- This group defines options associated with national or international 
-- CUG Identifier. Other DNAs in the network can have CUGs defined 
-- which groups these DNAs by CUG interlockCode. If DNAs are 
-- defined with CUGs, calls from DNAs which do not have the same 
-- interlockCode defined are refused. Attributes incAccess and 
-- outAccess can override this rule.
-- 
-- A CUG is provisioned by default as a SELECTABLE CUG. If a 
-- SELECTABLE CUG is provisioned, the DTE can include a CUG 
-- facility in the call request. If it does, the DTE selects a specific 
-- CUG by signaling the CUG's index. A DTE can subscribe to as 
-- many as 256 SELECTABLE CUGs.
-- 
-- A SIMPLE CUG is provisioned by setting a SELECTABLE CUG's 
-- preferential attribute to the value yes. There are two prerequisites: a 
-- single SELECTABLE CUG must exist; its attributes incCalls and 
-- outCalls must both be set to allowed. If a SIMPLE CUG is 
-- provisioned, it is the default CUG used to establish a call when the 
-- call request sent by the DTE does not include any CUG facility. If 
-- the DTE includes any CUG facility in the call request, the call is 
-- cleared. A DTE subscribing to a SIMPLE CUG cannot subscribe to 
-- any other CUG.

mscFrUniDnaCug OBJECT IDENTIFIER ::= { mscFrUniDna 2 }



mscFrUniDnaCugRowStatusTable OBJECT-TYPE
   SYNTAX     SEQUENCE OF MscFrUniDnaCugRowStatusEntry
   ACCESS     not-accessible
   STATUS     mandatory
   DESCRIPTION
     "This entry controls the addition and deletion of 
      mscFrUniDnaCug components."
::= { mscFrUniDnaCug 1 }

mscFrUniDnaCugRowStatusEntry OBJECT-TYPE
   SYNTAX     MscFrUniDnaCugRowStatusEntry
   ACCESS     not-accessible
   STATUS     mandatory
   DESCRIPTION
     "A single entry in the table represents a single 
      mscFrUniDnaCug component."
   INDEX {
      mscFrUniIndex,
      mscFrUniDnaIndex,
      mscFrUniDnaCugIndex }
::= { mscFrUniDnaCugRowStatusTable 1 }

MscFrUniDnaCugRowStatusEntry ::= SEQUENCE {
   mscFrUniDnaCugRowStatus
      RowStatus,
   mscFrUniDnaCugComponentName
      DisplayString,
   mscFrUniDnaCugStorageType
      StorageType,
   mscFrUniDnaCugIndex
      Integer32 }

mscFrUniDnaCugRowStatus OBJECT-TYPE
   SYNTAX     RowStatus 
   ACCESS     read-write
   STATUS     mandatory
   DESCRIPTION
     "This variable is used as the basis for SNMP naming of
      mscFrUniDnaCug components.
      These components can be added and deleted."
::= { mscFrUniDnaCugRowStatusEntry 1 }

mscFrUniDnaCugComponentName OBJECT-TYPE
   SYNTAX     DisplayString 
   ACCESS     read-only
   STATUS     mandatory
   DESCRIPTION
     "This variable provides the component's string name for
      use with the ASCII Console Interface"
::= { mscFrUniDnaCugRowStatusEntry 2 }

mscFrUniDnaCugStorageType OBJECT-TYPE
   SYNTAX     StorageType 
   ACCESS     read-only
   STATUS     mandatory
   DESCRIPTION
     "This variable represents the storage type value for the
      mscFrUniDnaCug tables."
::= { mscFrUniDnaCugRowStatusEntry 4 }

mscFrUniDnaCugIndex OBJECT-TYPE
   SYNTAX     Integer32 (0..255)
   ACCESS     not-accessible
   STATUS     mandatory
   DESCRIPTION
     "This variable represents the index for the mscFrUniDnaCug tables."
::= { mscFrUniDnaCugRowStatusEntry 10 }

mscFrUniDnaCugCugOptionsTable OBJECT-TYPE
   SYNTAX     SEQUENCE OF MscFrUniDnaCugCugOptionsEntry
   ACCESS     not-accessible
   STATUS     mandatory
   DESCRIPTION
     "Attributes in this group define ClosedUserGroup options associated 
      with interlockCode. DNA's with the same CUG (interlockCode) can 
      make calls within this group. Various combinations which permit or 
      prevent calls in the same CUG group are defined here."
::= { mscFrUniDnaCug 10 }

mscFrUniDnaCugCugOptionsEntry OBJECT-TYPE
   SYNTAX     MscFrUniDnaCugCugOptionsEntry
   ACCESS     not-accessible
   STATUS     mandatory
   DESCRIPTION
     "An entry in the mscFrUniDnaCugCugOptionsTable."
   INDEX {
      mscFrUniIndex,
      mscFrUniDnaIndex,
      mscFrUniDnaCugIndex }
::= { mscFrUniDnaCugCugOptionsTable 1 }

MscFrUniDnaCugCugOptionsEntry ::= SEQUENCE {
   mscFrUniDnaCugType
      INTEGER,
   mscFrUniDnaCugDnic
      DigitString,
   mscFrUniDnaCugInterlockCode
      Unsigned32,
   mscFrUniDnaCugPreferential
      INTEGER,
   mscFrUniDnaCugOutCalls
      INTEGER,
   mscFrUniDnaCugIncCalls
      INTEGER }

mscFrUniDnaCugType OBJECT-TYPE
   SYNTAX     INTEGER  {
                 national(0),
                 international(1) }
   ACCESS     read-write
   STATUS     mandatory
   DESCRIPTION
     "This attribute specifies the CUG type - the CUG is either a national 
      CUG, or an international CUG. International closed user groups are 
      usually established between DTEs for which there is an X.75 
      Gateway between; whereas national closed user groups are usually 
      established between DTEs for which there is no X.75 Gateway 
      between. (National CUGs cannot normally traverse an X.75 
      Gateway).
      If this attribute is set to national, then the CUG is a national CUG, 
      in which case, the dnic should be left at its default value since it is 
      not part of a national CUG. If this attribute is set to international, 
      then the CUG is an international CUG, in which case, the dnic 
      should be set appropriately as part of the CUG interlockCode."
   DEFVAL     { national }
::= { mscFrUniDnaCugCugOptionsEntry 1 }

mscFrUniDnaCugDnic OBJECT-TYPE
   SYNTAX     DigitString (SIZE (4))
   ACCESS     read-write
   STATUS     mandatory
   DESCRIPTION
     "This attribute specifies the dnic (Data Network ID Code) of the 
      CUG by which packet networks are identified. This attribute is not 
      applicable if the CUG is a national CUG, as specified by the CUG 
      type attribute. There are usually 1 or 2 dnics assigned per country, 
      for public networks. The U.S. is an exception where each BOC has 
      a dnic. Also, a group of private networks can have its own dnic.
      
      dnic value is not an arbitrary number. It is assigned by international 
      agreement and controlled by CCITT."
   DEFVAL     { '30303030'H }  -- "0000"
::= { mscFrUniDnaCugCugOptionsEntry 2 }

mscFrUniDnaCugInterlockCode OBJECT-TYPE
   SYNTAX     Unsigned32 (0..65535)
   ACCESS     read-write
   STATUS     mandatory
   DESCRIPTION
     "This attribute specifies the CUG identifier of a national or 
      international CUG call. It is an arbitrary number and it also can be 
      called CUG in some descriptions. Interfaces (DNA's) defined with 
      this number can make calls to DNA's with the same interlockCode."
   DEFVAL     { 65535 }
::= { mscFrUniDnaCugCugOptionsEntry 3 }

mscFrUniDnaCugPreferential OBJECT-TYPE
   SYNTAX     INTEGER  {
                 no(0),
                 yes(1) }
   ACCESS     read-write
   STATUS     mandatory
   DESCRIPTION
     "The attribute 'preferential', if set to yes indicates that this CUG is 
      the SIMPLE CUG (as defined in ITU X.36 [10/96]), in which case 
      it will be used during the call establishment phase if the DTE has 
      not explicitly specified a CUG index in the call request packet. If set 
      to no, then this CUG is not the SIMPLE CUG, but an instance of 
      the SELECTABLE CUG.
      
      The attribute 'preferential' is set to no by CAS when a CUG 
      instance is created. If only one CUG instance exists under a DNA, 
      and if this CUG's attributes 'incCalls' and 'outCall' are both set to 
      allowed, then this CUG instance can be changed to a SIMPLE CUG 
      by setting the attribute 'preferential' to yes. If more than one CUG 
      instances exist under a DNA, none of the CUGs can be set by the 
      user as 'preferential'. Essentially, the attribute 'preferential' 
      distinguishes a SIMPLE CUG from a SELECTABLE CUG.
      
      In the case of a FRUNI DNA with a single CUG instance, the CUG 
      can be a SIMPLE CUG (preferential = yes) or the only instance of a 
      SELECTABLE CUG (preferential = no)."
   DEFVAL     { no }
::= { mscFrUniDnaCugCugOptionsEntry 4 }

mscFrUniDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) can be made using this particular CUG. 
      If set to a value of disallowed, then outgoing calls cannot be made 
      using this CUG - such calls will be cleared by the local DCE.
      This attribute corresponds to the CCITT 'Outgoing Calls Barred' 
      feature for CUGs in that outgoing calls are barred if this attribute is 
      set to a value of disallowed."
   DEFVAL     { allowed }
::= { mscFrUniDnaCugCugOptionsEntry 5 }

mscFrUniDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular CUG. If 
      set to disallowed, then incoming calls cannot be made using this 
      CUG - such calls will be cleared by the local DCE.
      This attribute corresponds to the CCITT 'Incoming Calls Barred' 
      feature for CUGs in that incoming calls are barred if this attribute is 
      set to a value of disallowed."
   DEFVAL     { allowed }
::= { mscFrUniDnaCugCugOptionsEntry 6 }


-- FrUni/n Dna HuntGroupMember
-- This component specifies the interaction of this DNA with one or 
-- more hunt groups to which it is expected to belong.
-- Note that is not possible to automatically verify the consistency of 
-- the hunt group membership specified under this component with the 
-- hunt group provisioning on the DPN Hunt Group Server(s).

mscFrUniDnaHgM OBJECT IDENTIFIER ::= { mscFrUniDna 3 }



mscFrUniDnaHgMRowStatusTable OBJECT-TYPE
   SYNTAX     SEQUENCE OF MscFrUniDnaHgMRowStatusEntry
   ACCESS     not-accessible
   STATUS     mandatory
   DESCRIPTION
     "This entry controls the addition and deletion of 
      mscFrUniDnaHgM components."
::= { mscFrUniDnaHgM 1 }

mscFrUniDnaHgMRowStatusEntry OBJECT-TYPE
   SYNTAX     MscFrUniDnaHgMRowStatusEntry
   ACCESS     not-accessible
   STATUS     mandatory
   DESCRIPTION
     "A single entry in the table represents a single 
      mscFrUniDnaHgM component."
   INDEX {
      mscFrUniIndex,
      mscFrUniDnaIndex,
      mscFrUniDnaHgMIndex }
::= { mscFrUniDnaHgMRowStatusTable 1 }

MscFrUniDnaHgMRowStatusEntry ::= SEQUENCE {
   mscFrUniDnaHgMRowStatus
      RowStatus,
   mscFrUniDnaHgMComponentName
      DisplayString,
   mscFrUniDnaHgMStorageType
      StorageType,
   mscFrUniDnaHgMIndex
      NonReplicated }

mscFrUniDnaHgMRowStatus OBJECT-TYPE
   SYNTAX     RowStatus 
   ACCESS     read-write
   STATUS     mandatory
   DESCRIPTION
     "This variable is used as the basis for SNMP naming of
      mscFrUniDnaHgM components.
      These components can be added and deleted."
::= { mscFrUniDnaHgMRowStatusEntry 1 }

mscFrUniDnaHgMComponentName OBJECT-TYPE
   SYNTAX     DisplayString 
   ACCESS     read-only
   STATUS     mandatory
   DESCRIPTION
     "This variable provides the component's string name for
      use with the ASCII Console Interface"
::= { mscFrUniDnaHgMRowStatusEntry 2 }

mscFrUniDnaHgMStorageType OBJECT-TYPE
   SYNTAX     StorageType 
   ACCESS     read-only
   STATUS     mandatory
   DESCRIPTION
     "This variable represents the storage type value for the
      mscFrUniDnaHgM tables."
::= { mscFrUniDnaHgMRowStatusEntry 4 }

mscFrUniDnaHgMIndex OBJECT-TYPE
   SYNTAX     NonReplicated 
   ACCESS     not-accessible
   STATUS     mandatory
   DESCRIPTION
     "This variable represents the index for the mscFrUniDnaHgM tables."
::= { mscFrUniDnaHgMRowStatusEntry 10 }

mscFrUniDnaHgMIfTable OBJECT-TYPE
   SYNTAX     SEQUENCE OF MscFrUniDnaHgMIfEntry
   ACCESS     not-accessible
   STATUS     mandatory
   DESCRIPTION
     "This group contains the interface parameters between the 
      HuntGroupMember and the hunt group server."
::= { mscFrUniDnaHgM 10 }

mscFrUniDnaHgMIfEntry OBJECT-TYPE
   SYNTAX     MscFrUniDnaHgMIfEntry
   ACCESS     not-accessible
   STATUS     mandatory
   DESCRIPTION
     "An entry in the mscFrUniDnaHgMIfTable."
   INDEX {
      mscFrUniIndex,
      mscFrUniDnaIndex,
      mscFrUniDnaHgMIndex }
::= { mscFrUniDnaHgMIfTable 1 }

MscFrUniDnaHgMIfEntry ::= SEQUENCE {
   mscFrUniDnaHgMAvailabilityUpdateThreshold
      Unsigned32 }

mscFrUniDnaHgMAvailabilityUpdateThreshold OBJECT-TYPE
   SYNTAX     Unsigned32 (2048..16777216)
   ACCESS     read-write
   STATUS     mandatory
   DESCRIPTION
     "This attribute specifies how much availableAggregateCIR can 
      change before an Availability Message Packet (AMP) is sent to the 
      hunt group server informing it of the change.
      If the value specified is not a multiple of 2048, the value actually 
      used as the threshold will be the next higher multiple of 2048."
   DEFVAL     { 8192 }
::= { mscFrUniDnaHgMIfEntry 1 }

mscFrUniDnaHgMOpTable OBJECT-TYPE
   SYNTAX     SEQUENCE OF MscFrUniDnaHgMOpEntry
   ACCESS     not-accessible
   STATUS     mandatory
   DESCRIPTION
     "This group contains the operational attributes of the 
      HuntGroupMember component."
::= { mscFrUniDnaHgM 11 }

mscFrUniDnaHgMOpEntry OBJECT-TYPE
   SYNTAX     MscFrUniDnaHgMOpEntry
   ACCESS     not-accessible
   STATUS     mandatory
   DESCRIPTION
     "An entry in the mscFrUniDnaHgMOpTable."
   INDEX {
      mscFrUniIndex,
      mscFrUniDnaIndex,
      mscFrUniDnaHgMIndex }
::= { mscFrUniDnaHgMOpTable 1 }

MscFrUniDnaHgMOpEntry ::= SEQUENCE {
   mscFrUniDnaHgMMaximumAvailableAggregateCir
      Unsigned32,
   mscFrUniDnaHgMAvailableAggregateCir
      Unsigned32,
   mscFrUniDnaHgMAvailabilityDelta
      INTEGER,
   mscFrUniDnaHgMAvailableDlcis
      Unsigned32 }

mscFrUniDnaHgMMaximumAvailableAggregateCir OBJECT-TYPE
   SYNTAX     Unsigned32 (0..4294967295)
   ACCESS     read-only
   STATUS     mandatory
   DESCRIPTION
     "This attribute indicates the maximum available bandwidth for this 
      hunt group member. This value represents the total sum of the 
      sixteen egress bandwidth pools. It is the sum of the sixteen indices 
      of the FrUni Ca egressBandwidthPool attribute multiplied by the 
      link speed."
::= { mscFrUniDnaHgMOpEntry 1 }

mscFrUniDnaHgMAvailableAggregateCir OBJECT-TYPE
   SYNTAX     Unsigned32 (0..4294967295)
   ACCESS     read-only
   STATUS     mandatory
   DESCRIPTION
     "This attribute indicates the current total available bandwidth 
      reported to the hunt group server in the Availability Message Packet 
      (AMP). This value represents the sum of the sixteen currently 
      available egress bandwidth pools. It is the sum of the sixteen indices 
      of the FrUni Ca egressPoolAvailableBandwidth attribute. 
      It increments when a connection is released. 
      It decrements when a connection is accepted.
      Both this attribute and the availableDlcis attribute must be non zero 
      for this interface to receive calls on a hunt group."
::= { mscFrUniDnaHgMOpEntry 2 }

mscFrUniDnaHgMAvailabilityDelta OBJECT-TYPE
   SYNTAX     INTEGER (-16777216..16777215)
   ACCESS     read-only
   STATUS     mandatory
   DESCRIPTION
     "This attribute indicates the net change in the available aggregate 
      CIR since the last Availability Message Packet (AMP) was sent to 
      the Hunt Group. Once the absolute value of this attribute reaches 
      the availabilityUpdateThreshold an AMP is sent to the hunt group 
      server(s) and the availabilityDelta is re-computed."
::= { mscFrUniDnaHgMOpEntry 3 }

mscFrUniDnaHgMAvailableDlcis OBJECT-TYPE
   SYNTAX     Unsigned32 (0..4096)
   ACCESS     read-only
   STATUS     mandatory
   DESCRIPTION
     "This attribute indicates the number of DLCIs available for SVCs on 
      the interface associated with this DNA. If this value reaches 0, an 
      AMP with zero availability is sent to the hunt group server(s).
      Both this attribute and the availableAggregateCir attribute must be 
      non zero for this DNA to receive calls on the hunt group."
::= { mscFrUniDnaHgMOpEntry 5 }


-- FrUni/n Dna HgM HuntGroupAddress/n
-- This component specifies a hunt group address to which this 
-- member belongs. A hunt group member belongs to at least one hunt 
-- group.

mscFrUniDnaHgMHgAddr OBJECT IDENTIFIER ::= { mscFrUniDnaHgM 2 }



mscFrUniDnaHgMHgAddrRowStatusTable OBJECT-TYPE
   SYNTAX     SEQUENCE OF MscFrUniDnaHgMHgAddrRowStatusEntry
   ACCESS     not-accessible
   STATUS     mandatory
   DESCRIPTION
     "This entry controls the addition and deletion of 
      mscFrUniDnaHgMHgAddr components."
::= { mscFrUniDnaHgMHgAddr 1 }

mscFrUniDnaHgMHgAddrRowStatusEntry OBJECT-TYPE
   SYNTAX     MscFrUniDnaHgMHgAddrRowStatusEntry
   ACCESS     not-accessible
   STATUS     mandatory
   DESCRIPTION
     "A single entry in the table represents a single 
      mscFrUniDnaHgMHgAddr component."
   INDEX {
      mscFrUniIndex,
      mscFrUniDnaIndex,
      mscFrUniDnaHgMIndex,
      mscFrUniDnaHgMHgAddrIndex }
::= { mscFrUniDnaHgMHgAddrRowStatusTable 1 }

MscFrUniDnaHgMHgAddrRowStatusEntry ::= SEQUENCE {
   mscFrUniDnaHgMHgAddrRowStatus
      RowStatus,
   mscFrUniDnaHgMHgAddrComponentName
      DisplayString,
   mscFrUniDnaHgMHgAddrStorageType
      StorageType,
   mscFrUniDnaHgMHgAddrIndex
      Integer32 }

mscFrUniDnaHgMHgAddrRowStatus OBJECT-TYPE
   SYNTAX     RowStatus 
   ACCESS     read-write
   STATUS     mandatory
   DESCRIPTION
     "This variable is used as the basis for SNMP naming of
      mscFrUniDnaHgMHgAddr components.
      These components can be added and deleted."
::= { mscFrUniDnaHgMHgAddrRowStatusEntry 1 }

mscFrUniDnaHgMHgAddrComponentName OBJECT-TYPE
   SYNTAX     DisplayString 
   ACCESS     read-only
   STATUS     mandatory
   DESCRIPTION
     "This variable provides the component's string name for
      use with the ASCII Console Interface"
::= { mscFrUniDnaHgMHgAddrRowStatusEntry 2 }

mscFrUniDnaHgMHgAddrStorageType OBJECT-TYPE
   SYNTAX     StorageType 
   ACCESS     read-only
   STATUS     mandatory
   DESCRIPTION
     "This variable represents the storage type value for the
      mscFrUniDnaHgMHgAddr tables."
::= { mscFrUniDnaHgMHgAddrRowStatusEntry 4 }

mscFrUniDnaHgMHgAddrIndex OBJECT-TYPE
   SYNTAX     Integer32 (0..1)
   ACCESS     not-accessible
   STATUS     mandatory
   DESCRIPTION
     "This variable represents the index for the mscFrUniDnaHgMHgAddr tables."
::= { mscFrUniDnaHgMHgAddrRowStatusEntry 10 }

mscFrUniDnaHgMHgAddrAddrTable OBJECT-TYPE
   SYNTAX     SEQUENCE OF MscFrUniDnaHgMHgAddrAddrEntry
   ACCESS     not-accessible
   STATUS     mandatory
   DESCRIPTION
     "This group contains attributes common to all DNAs. Every DNA 
      used in the network is defined with this group of 2 attributes."
::= { mscFrUniDnaHgMHgAddr 10 }

mscFrUniDnaHgMHgAddrAddrEntry OBJECT-TYPE
   SYNTAX     MscFrUniDnaHgMHgAddrAddrEntry
   ACCESS     not-accessible
   STATUS     mandatory
   DESCRIPTION
     "An entry in the mscFrUniDnaHgMHgAddrAddrTable."
   INDEX {
      mscFrUniIndex,
      mscFrUniDnaIndex,
      mscFrUniDnaHgMIndex,
      mscFrUniDnaHgMHgAddrIndex }
::= { mscFrUniDnaHgMHgAddrAddrTable 1 }

MscFrUniDnaHgMHgAddrAddrEntry ::= SEQUENCE {
   mscFrUniDnaHgMHgAddrNumberingPlanIndicator
      INTEGER,
   mscFrUniDnaHgMHgAddrDataNetworkAddress
      DigitString }

mscFrUniDnaHgMHgAddrNumberingPlanIndicator OBJECT-TYPE
   SYNTAX     INTEGER  {
                 x121(0),
                 e164(1) }
   ACCESS     read-write
   STATUS     mandatory
   DESCRIPTION
     "This attribute indicates the Numbering Plan Indicator (NPI) of the 
      DNA. The address may belong to X.121 or E.164 plans."
   DEFVAL     { x121 }
::= { mscFrUniDnaHgMHgAddrAddrEntry 1 }

mscFrUniDnaHgMHgAddrDataNetworkAddress OBJECT-TYPE
   SYNTAX     DigitString (SIZE (1..15))
   ACCESS     read-write
   STATUS     mandatory
   DESCRIPTION
     "This attribute contains digits which form the unique identifier of the 
      customer interface. It can be compared (approximation only) to a 
      telephone number where the phone number identifies a unique 
      telephone set. DNA digits are selected and assigned by network 
      operators."
::= { mscFrUniDnaHgMHgAddrAddrEntry 2 }


-- FrUni/n Framer
-- FrNni/n Framer
-- FrAtm/n Framer
-- This component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscFrUniFramer OBJECT IDENTIFIER ::= { mscFrUni 3 }



mscFrUniFramerRowStatusTable OBJECT-TYPE
   SYNTAX     SEQUENCE OF MscFrUniFramerRowStatusEntry
   ACCESS     not-accessible
   STATUS     mandatory
   DESCRIPTION
     "This entry controls the addition and deletion of 
      mscFrUniFramer components."
::= { mscFrUniFramer 1 }

mscFrUniFramerRowStatusEntry OBJECT-TYPE
   SYNTAX     MscFrUniFramerRowStatusEntry
   ACCESS     not-accessible
   STATUS     mandatory
   DESCRIPTION
     "A single entry in the table represents a single 
      mscFrUniFramer component."
   INDEX {
      mscFrUniIndex,
      mscFrUniFramerIndex }
::= { mscFrUniFramerRowStatusTable 1 }

MscFrUniFramerRowStatusEntry ::= SEQUENCE {
   mscFrUniFramerRowStatus
      RowStatus,
   mscFrUniFramerComponentName
      DisplayString,
   mscFrUniFramerStorageType
      StorageType,
   mscFrUniFramerIndex
      NonReplicated }

mscFrUniFramerRowStatus OBJECT-TYPE
   SYNTAX     RowStatus 
   ACCESS     read-write
   STATUS     mandatory
   DESCRIPTION
     "This variable is used as the basis for SNMP naming of
      mscFrUniFramer components.
      These components can be added and deleted."
::= { mscFrUniFramerRowStatusEntry 1 }

mscFrUniFramerComponentName OBJECT-TYPE
   SYNTAX     DisplayString 
   ACCESS     read-only
   STATUS     mandatory
   DESCRIPTION
     "This variable provides the component's string name for
      use with the ASCII Console Interface"
::= { mscFrUniFramerRowStatusEntry 2 }

mscFrUniFramerStorageType OBJECT-TYPE
   SYNTAX     StorageType 
   ACCESS     read-only
   STATUS     mandatory
   DESCRIPTION
     "This variable represents the storage type value for the
      mscFrUniFramer tables."
::= { mscFrUniFramerRowStatusEntry 4 }

mscFrUniFramerIndex OBJECT-TYPE
   SYNTAX     NonReplicated 
   ACCESS     not-accessible
   STATUS     mandatory
   DESCRIPTION
     "This variable represents the index for the mscFrUniFramer tables."
::= { mscFrUniFramerRowStatusEntry 10 }

mscFrUniFramerProvTable OBJECT-TYPE
   SYNTAX     SEQUENCE OF MscFrUniFramerProvEntry
   ACCESS     not-accessible
   STATUS     mandatory
   DESCRIPTION
     "This group contains the base provisioning data for the Framer 
      component. Application or hardware interface specific provisioning 
      data is contained in other provisionable Framer groups."
::= { mscFrUniFramer 10 }

mscFrUniFramerProvEntry OBJECT-TYPE
   SYNTAX     MscFrUniFramerProvEntry
   ACCESS     not-accessible
   STATUS     mandatory
   DESCRIPTION
     "An entry in the mscFrUniFramerProvTable."
   INDEX {
      mscFrUniIndex,
      mscFrUniFramerIndex }
::= { mscFrUniFramerProvTable 1 }

MscFrUniFramerProvEntry ::= SEQUENCE {
   mscFrUniFramerInterfaceName
      Link }

mscFrUniFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscFrUniFramerProvEntry 1 }

mscFrUniFramerLinkTable OBJECT-TYPE
   SYNTAX     SEQUENCE OF MscFrUniFramerLinkEntry
   ACCESS     not-accessible
   STATUS     mandatory
   DESCRIPTION
     "This group contains attributes defining the framing of data on the 
      link interface."
::= { mscFrUniFramer 11 }

mscFrUniFramerLinkEntry OBJECT-TYPE
   SYNTAX     MscFrUniFramerLinkEntry
   ACCESS     not-accessible
   STATUS     mandatory
   DESCRIPTION
     "An entry in the mscFrUniFramerLinkTable."
   INDEX {
      mscFrUniIndex,
      mscFrUniFramerIndex }
::= { mscFrUniFramerLinkTable 1 }

MscFrUniFramerLinkEntry ::= SEQUENCE {
   mscFrUniFramerDataInversion
      INTEGER,
   mscFrUniFramerFrameCrcType
      INTEGER,
   mscFrUniFramerFlagsBetweenFrames
      Unsigned32 }

mscFrUniFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted.
      
      This attribute may only take its default value for non-MSA cards."
   DEFVAL     { off }
::= { mscFrUniFramerLinkEntry 2 }

mscFrUniFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used.
      
      This attribute may take only its default value for non-MSA cards."
   DEFVAL     { crc16 }
::= { mscFrUniFramerLinkEntry 3 }

mscFrUniFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscFrUniFramerLinkEntry 4 }

mscFrUniFramerStateTable OBJECT-TYPE
   SYNTAX     SEQUENCE OF MscFrUniFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrUniFramer 12 }

mscFrUniFramerStateEntry OBJECT-TYPE
   SYNTAX     MscFrUniFramerStateEntry
   ACCESS     not-accessible
   STATUS     mandatory
   DESCRIPTION
     "An entry in the mscFrUniFramerStateTable."
   INDEX {
      mscFrUniIndex,
      mscFrUniFramerIndex }
::= { mscFrUniFramerStateTable 1 }

MscFrUniFramerStateEntry ::= SEQUENCE {
   mscFrUniFramerAdminState
      INTEGER,
   mscFrUniFramerOperationalState
      INTEGER,
   mscFrUniFramerUsageState
      INTEGER }

mscFrUniFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrUniFramerStateEntry 1 }

mscFrUniFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrUniFramerStateEntry 2 }

mscFrUniFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrUniFramerStateEntry 3 }

mscFrUniFramerStatsTable OBJECT-TYPE
   SYNTAX     SEQUENCE OF MscFrUniFramerStatsEntry
   ACCESS     not-accessible
   STATUS     mandatory
   DESCRIPTION
     "This group contains the operational statistics data for a Framer 
      component."
::= { mscFrUniFramer 13 }

mscFrUniFramerStatsEntry OBJECT-TYPE
   SYNTAX     MscFrUniFramerStatsEntry
   ACCESS     not-accessible
   STATUS     mandatory
   DESCRIPTION
     "An entry in the mscFrUniFramerStatsTable."
   INDEX {
      mscFrUniIndex,
      mscFrUniFramerIndex }
::= { mscFrUniFramerStatsTable 1 }

MscFrUniFramerStatsEntry ::= SEQUENCE {
   mscFrUniFramerFrmToIf
      Counter32,
   mscFrUniFramerFrmFromIf
      Counter32,
   mscFrUniFramerOctetFromIf
      Counter32,
   mscFrUniFramerAborts
      Counter32,
   mscFrUniFramerCrcErrors
      Counter32,
   mscFrUniFramerLrcErrors
      Counter32,
   mscFrUniFramerNonOctetErrors
      Counter32,
   mscFrUniFramerOverruns
      Counter32,
   mscFrUniFramerUnderruns
      Counter32,
   mscFrUniFramerLargeFrmErrors
      Counter32,
   mscFrUniFramerFrmModeErrors
      Counter32,
   mscFrUniFramerFrmToIf64
      PassportCounter64,
   mscFrUniFramerFrmFromIf64
      PassportCounter64,
   mscFrUniFramerOctetFromIf64
      PassportCounter64 }

mscFrUniFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscFrUniFramerStatsEntry 1 }

mscFrUniFramerFrmFromIf OBJECT-TYPE
   SYNTAX     Counter32 
   ACCESS     read-only
   STATUS     obsolete
   DESCRIPTION
     "The number of frames received from the link interface by Framer."
::= { mscFrUniFramerStatsEntry 2 }

mscFrUniFramerOctetFromIf OBJECT-TYPE
   SYNTAX     Counter32 
   ACCESS     read-only
   STATUS     obsolete
   DESCRIPTION
     "The number of bytes received from the link interface by Framer."
::= { mscFrUniFramerStatsEntry 3 }

mscFrUniFramerAborts OBJECT-TYPE
   SYNTAX     Counter32 
   ACCESS     read-only
   STATUS     mandatory
   DESCRIPTION
     "This attribute is the total number of aborts received."
::= { mscFrUniFramerStatsEntry 4 }

mscFrUniFramerCrcErrors OBJECT-TYPE
   SYNTAX     Counter32 
   ACCESS     read-only
   STATUS     mandatory
   DESCRIPTION
     "This attribute is the total number of frames with CRC errors, 
      occurring in the receive direction from the link."
::= { mscFrUniFramerStatsEntry 5 }

mscFrUniFramerLrcErrors OBJECT-TYPE
   SYNTAX     Counter32 
   ACCESS     read-only
   STATUS     mandatory
   DESCRIPTION
     "This attribute is the total number of frames with LRC errors, 
      occurring in the Tx link prior to transmission onto the link."
::= { mscFrUniFramerStatsEntry 6 }

mscFrUniFramerNonOctetErrors OBJECT-TYPE
   SYNTAX     Counter32 
   ACCESS     read-only
   STATUS     mandatory
   DESCRIPTION
     "This attribute is the total number of frames that were non octet 
      aligned."
::= { mscFrUniFramerStatsEntry 7 }

mscFrUniFramerOverruns OBJECT-TYPE
   SYNTAX     Counter32 
   ACCESS     read-only
   STATUS     mandatory
   DESCRIPTION
     "This attribute is the total number of frames received from the link 
      for which overruns occurred."
::= { mscFrUniFramerStatsEntry 8 }

mscFrUniFramerUnderruns OBJECT-TYPE
   SYNTAX     Counter32 
   ACCESS     read-only
   STATUS     mandatory
   DESCRIPTION
     "This attribute is the total number of frames transmitted to the link 
      for which underruns occurred."
::= { mscFrUniFramerStatsEntry 9 }

mscFrUniFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscFrUniFramerStatsEntry 10 }

mscFrUniFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscFrUniFramerStatsEntry 11 }

mscFrUniFramerFrmToIf64 OBJECT-TYPE
   SYNTAX     PassportCounter64 
   ACCESS     read-only
   STATUS     mandatory
   DESCRIPTION
     "The number of frames transmitted to the link interface by Framer.
      
      Note: This does not include the number of frames transmitted 
      directly to the hardware queue, thus bypassing the Framer 
      component."
::= { mscFrUniFramerStatsEntry 14 }

mscFrUniFramerFrmFromIf64 OBJECT-TYPE
   SYNTAX     PassportCounter64 
   ACCESS     read-only
   STATUS     mandatory
   DESCRIPTION
     "The number of frames received from the link interface by Framer."
::= { mscFrUniFramerStatsEntry 15 }

mscFrUniFramerOctetFromIf64 OBJECT-TYPE
   SYNTAX     PassportCounter64 
   ACCESS     read-only
   STATUS     mandatory
   DESCRIPTION
     "The number of bytes received from the link interface by Framer."
::= { mscFrUniFramerStatsEntry 16 }

mscFrUniFramerUtilTable OBJECT-TYPE
   SYNTAX     SEQUENCE OF MscFrUniFramerUtilEntry
   ACCESS     not-accessible
   STATUS     mandatory
   DESCRIPTION
     "This group contains the link utilizaiton operational data for a 
      Framer component."
::= { mscFrUniFramer 14 }

mscFrUniFramerUtilEntry OBJECT-TYPE
   SYNTAX     MscFrUniFramerUtilEntry
   ACCESS     not-accessible
   STATUS     mandatory
   DESCRIPTION
     "An entry in the mscFrUniFramerUtilTable."
   INDEX {
      mscFrUniIndex,
      mscFrUniFramerIndex }
::= { mscFrUniFramerUtilTable 1 }

MscFrUniFramerUtilEntry ::= SEQUENCE {
   mscFrUniFramerNormPrioLinkUtilToIf
      Gauge32,
   mscFrUniFramerNormPrioLinkUtilFromIf
      Gauge32 }

mscFrUniFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this indluces traffic with 
      Transfer Priorities (TP) of 0, 6 and 9 and/or Emission Priority of 2 
      and 3. The utilization is the average for the last minute."
   DEFVAL     { 0 }
::= { mscFrUniFramerUtilEntry 1 }

mscFrUniFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscFrUniFramerUtilEntry 3 }


-- FrUni/n LocalManagementInterface
-- FrNni/n LocalManagementInterface
-- FrAtm/n LocalManagementInterface
-- This component defines the parameters for implementing the Local 
-- Management Interface protocol.

mscFrUniLmi OBJECT IDENTIFIER ::= { mscFrUni 4 }



mscFrUniLmiRowStatusTable OBJECT-TYPE
   SYNTAX     SEQUENCE OF MscFrUniLmiRowStatusEntry
   ACCESS     not-accessible
   STATUS     mandatory
   DESCRIPTION
     "This entry controls the addition and deletion of 
      mscFrUniLmi components."
::= { mscFrUniLmi 1 }

mscFrUniLmiRowStatusEntry OBJECT-TYPE
   SYNTAX     MscFrUniLmiRowStatusEntry
   ACCESS     not-accessible
   STATUS     mandatory
   DESCRIPTION
     "A single entry in the table represents a single 
      mscFrUniLmi component."
   INDEX {
      mscFrUniIndex,
      mscFrUniLmiIndex }
::= { mscFrUniLmiRowStatusTable 1 }

MscFrUniLmiRowStatusEntry ::= SEQUENCE {
   mscFrUniLmiRowStatus
      RowStatus,
   mscFrUniLmiComponentName
      DisplayString,
   mscFrUniLmiStorageType
      StorageType,
   mscFrUniLmiIndex
      NonReplicated }

mscFrUniLmiRowStatus OBJECT-TYPE
   SYNTAX     RowStatus 
   ACCESS     read-only
   STATUS     mandatory
   DESCRIPTION
     "This variable is used as the basis for SNMP naming of
      mscFrUniLmi components.
      These components cannot be added nor deleted."
::= { mscFrUniLmiRowStatusEntry 1 }

mscFrUniLmiComponentName OBJECT-TYPE
   SYNTAX     DisplayString 
   ACCESS     read-only
   STATUS     mandatory
   DESCRIPTION
     "This variable provides the component's string name for
      use with the ASCII Console Interface"
::= { mscFrUniLmiRowStatusEntry 2 }

mscFrUniLmiStorageType OBJECT-TYPE
   SYNTAX     StorageType 
   ACCESS     read-only
   STATUS     mandatory
   DESCRIPTION
     "This variable represents the storage type value for the
      mscFrUniLmi tables."
::= { mscFrUniLmiRowStatusEntry 4 }

mscFrUniLmiIndex OBJECT-TYPE
   SYNTAX     NonReplicated 
   ACCESS     not-accessible
   STATUS     mandatory
   DESCRIPTION
     "This variable represents the index for the mscFrUniLmi tables."
::= { mscFrUniLmiRowStatusEntry 10 }

mscFrUniLmiParmsTable OBJECT-TYPE
   SYNTAX     SEQUENCE OF MscFrUniLmiParmsEntry
   ACCESS     not-accessible
   STATUS     mandatory
   DESCRIPTION
     "This group contains the provisionable attributes of the LMI 
      component."
::= { mscFrUniLmi 10 }

mscFrUniLmiParmsEntry OBJECT-TYPE
   SYNTAX     MscFrUniLmiParmsEntry
   ACCESS     not-accessible
   STATUS     mandatory
   DESCRIPTION
     "An entry in the mscFrUniLmiParmsTable."
   INDEX {
      mscFrUniIndex,
      mscFrUniLmiIndex }
::= { mscFrUniLmiParmsTable 1 }

MscFrUniLmiParmsEntry ::= SEQUENCE {
   mscFrUniLmiProcedures
      INTEGER,
   mscFrUniLmiAsyncStatusReport
      INTEGER,
   mscFrUniLmiErrorEventThreshold
      Unsigned32,
   mscFrUniLmiEventCount
      Unsigned32,
   mscFrUniLmiCheckPointTimer
      Unsigned32,
   mscFrUniLmiMessageCountTimer
      Unsigned32,
   mscFrUniLmiIgnoreActiveBit
      INTEGER,
   mscFrUniLmiSide
      INTEGER,
   mscFrUniLmiPvcConfigParmsInFsr
      INTEGER }

mscFrUniLmiProcedures OBJECT-TYPE
   SYNTAX     INTEGER  {
                 none(0),
                 vendorForum(1),
                 ansi(2),
                 itu(3),
                 autoConfigure(4) }
   ACCESS     read-write
   STATUS     mandatory
   DESCRIPTION
     "This attribute selects the procedures to be used for the Local 
      Management Interface. The following procedures are supported:
      
      none: no Local Management Interface procedures are running on 
      this interface. This accommodates Frame Relay user equipment that 
      has not implemented any LMI procedures. The remaining attributes 
      of this group are ignored.
      
      vendorForum: Local Management Interface procedures from the 
      Vendor Forum specification are supported on this interface. DLCI 
      1023 is used for the LMI protocol. This value cannot be used if the 
      side attribute is both.
      
      ansi: Local Management Interface procedures from the ANSI 
      specification are supported. DLCI 0 is used for the LMI protocol.
      
      itu: Local Management Interface procedures from the ITU-T 
      specification are supported. DLCI 0 is used for the LMI protocol. 
      Was previously ccitt.
      
      autoConfigure: The interface determines automatically which 
      Local Management Interface procedures to use. This value cannot 
      be used if the side attribute is user.
      
      The procedures currently in use can be seen in the operational 
      attribute opProcedures."
   DEFVAL     { autoConfigure }
::= { mscFrUniLmiParmsEntry 1 }

mscFrUniLmiAsyncStatusReport OBJECT-TYPE
   SYNTAX     INTEGER  {
                 off(0),
                 on(1) }
   ACCESS     read-write
   STATUS     mandatory
   DESCRIPTION
     "This attribute selects the use of asynchronous PVC status report 
      procedures as specified in ANSI, CCITT, and Vendor Forum. 
      
      This attribute can be set to on or off. If procedures is set to none, 
      this attribute is ignored."
   DEFVAL     { off }
::= { mscFrUniLmiParmsEntry 2 }

mscFrUniLmiErrorEventThreshold OBJECT-TYPE
   SYNTAX     Unsigned32 (1..10)
   ACCESS     read-write
   STATUS     mandatory
   DESCRIPTION
     "An event is defined as follows: (1) receipt of a STATUS ENQUIRY 
      message; or (2) expiration of timer T392. An error event is (1) 
      nonreceipt of STATUS ENQUIRY in T392 seconds; (2) invalid 
      contents of a LMI message; (3) invalid receive sequence number. 
      This attribute specifies the number of error events which, if they 
      occur within eventCount events, cause a protocol error condition. 
      The condition is cleared after eventCount sequential correct events 
      occur. This attribute corresponds to the nN2 parameter described in 
      the Vendor Forum Specification. 
      
      It must be less than or equal to eventCount."
   DEFVAL     { 3 }
::= { mscFrUniLmiParmsEntry 3 }

mscFrUniLmiEventCount OBJECT-TYPE
   SYNTAX     Unsigned32 (1..10)
   ACCESS     read-write
   STATUS     mandatory
   DESCRIPTION
     "This attribute specifies the number of contiguous events within 
      which no more than eventErrorThreshold error events are allowed. 
      This attribute corresponds to the nN3 parameter described in the 
      Vendor Forum Specification. 
      
      It must be greater than or equal to errorEventThreshold."
   DEFVAL     { 4 }
::= { mscFrUniLmiParmsEntry 4 }

mscFrUniLmiCheckPointTimer OBJECT-TYPE
   SYNTAX     Unsigned32 (5 | 10 | 15 | 20 | 25 | 30)
   ACCESS     read-write
   STATUS     mandatory
   DESCRIPTION
     "This attribute selects the time (in seconds) within which a STATUS 
      ENQUIRY message is expected. This attribute corresponds to the 
      nT2 parameter described in the Vendor Forum Specification.
      
      It must be less than messageCountTimer."
   DEFVAL     { 15 }
::= { mscFrUniLmiParmsEntry 5 }

mscFrUniLmiMessageCountTimer OBJECT-TYPE
   SYNTAX     Unsigned32 (5 | 10 | 15 | 20 | 25 | 30)
   ACCESS     read-write
   STATUS     mandatory
   DESCRIPTION
     "This attribute selects the time (in seconds) within which at most five 
      (this is a fixed value and corresponds to maximum message count in 
      VendorForum) STATUS ENQUIRY messages are expected. This 
      attribute applies only when the lmiProcedures is set to 
      vendorForum.
      
      messageCountTimer must always be greater than checkPointTimer."
   DEFVAL     { 20 }
::= { mscFrUniLmiParmsEntry 6 }

mscFrUniLmiIgnoreActiveBit OBJECT-TYPE
   SYNTAX     INTEGER  {
                 no(0),
                 yes(1) }
   ACCESS     read-write
   STATUS     mandatory
   DESCRIPTION
     "This attribute specifies whether the Frame Relay LMI Active Bit 
      (A-bit) has a bearing on the transfer of user data across this Frame 
      Relay interface for both directions of traffic flow.
      
      When this attribute is set to yes, the A-bit status of a user DLCI 
      connection does not affect data transfer.
      
      When this attribute is set to no, data received from the local 
      interface will be discarded if an A-bit =0 condition exists towards 
      the local user. Data being sent to the local interface is discarded if 
      an A-bit = 0 condition exists towards the subnet."
   DEFVAL     { no }
::= { mscFrUniLmiParmsEntry 7 }

mscFrUniLmiSide OBJECT-TYPE
   SYNTAX     INTEGER  {
                 network(0),
                 user(1),
                 both(2) }
   ACCESS     read-write
   STATUS     mandatory
   DESCRIPTION
     "This attribute can be set to user, network, or both. 
      
      When this attribute is set to user, USP LMI procedures are running. 
      When this attribute is set to network, NSP LMI procedures are 
      running. When this attribute is set to both, USPNSP LMI 
      procedures are running.
      When the value is both, the procedures attribute must not be set to 
      vendorForum. 
      Setting the value to user when the procedures attribute is set to 
      autoConfigure is disallowed semantically."
   DEFVAL     { network }
::= { mscFrUniLmiParmsEntry 8 }

mscFrUniLmiPvcConfigParmsInFsr OBJECT-TYPE
   SYNTAX     INTEGER  {
                 no(0),
                 yes(1) }
   ACCESS     read-write
   STATUS     mandatory
   DESCRIPTION
     "When this attribute is set to yes, additional Q.933 information 
      elements are included in the LMI Full Status message to facilitate 
      CPE PVC parameter configuring.
      
      When set to yes, the Check Prov command fails if the Lmi side is 
      not set to network.
      
      When set to yes, Check Prov fails if the number of DLCIs on the 
      FrUni is greater than 300.
      
      If the service is not a FrUni this attribute is ignored."
   DEFVAL     { no }
::= { mscFrUniLmiParmsEntry 9 }

mscFrUniLmiStateTable OBJECT-TYPE
   SYNTAX     SEQUENCE OF MscFrUniLmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrUniLmi 11 }

mscFrUniLmiStateEntry OBJECT-TYPE
   SYNTAX     MscFrUniLmiStateEntry
   ACCESS     not-accessible
   STATUS     mandatory
   DESCRIPTION
     "An entry in the mscFrUniLmiStateTable."
   INDEX {
      mscFrUniIndex,
      mscFrUniLmiIndex }
::= { mscFrUniLmiStateTable 1 }

MscFrUniLmiStateEntry ::= SEQUENCE {
   mscFrUniLmiAdminState
      INTEGER,
   mscFrUniLmiOperationalState
      INTEGER,
   mscFrUniLmiUsageState
      INTEGER }

mscFrUniLmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrUniLmiStateEntry 1 }

mscFrUniLmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrUniLmiStateEntry 2 }

mscFrUniLmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrUniLmiStateEntry 3 }

mscFrUniLmiPsiTable OBJECT-TYPE
   SYNTAX     SEQUENCE OF MscFrUniLmiPsiEntry
   ACCESS     not-accessible
   STATUS     mandatory
   DESCRIPTION
     "This group provides the protocol status of the Local Management 
      Interface."
::= { mscFrUniLmi 12 }

mscFrUniLmiPsiEntry OBJECT-TYPE
   SYNTAX     MscFrUniLmiPsiEntry
   ACCESS     not-accessible
   STATUS     mandatory
   DESCRIPTION
     "An entry in the mscFrUniLmiPsiTable."
   INDEX {
      mscFrUniIndex,
      mscFrUniLmiIndex }
::= { mscFrUniLmiPsiTable 1 }

MscFrUniLmiPsiEntry ::= SEQUENCE {
   mscFrUniLmiProtocolStatus
      INTEGER,
   mscFrUniLmiOpProcedures
      INTEGER }

mscFrUniLmiProtocolStatus OBJECT-TYPE
   SYNTAX     INTEGER  {
                 errorCondition(0),
                 normalCondition(1),
                 configuring(2) }
   ACCESS     read-only
   STATUS     mandatory
   DESCRIPTION
     "This attribute indicates whether the LMI is in an error condition or 
      whether the LMI procedures are behaving normally. When 
      operating with no LMI protocol, this attribute is always set to 
      normalCondition. When operating with LMI procedures, this 
      attribute is set to errorCondition after n392 of the last n393 events 
      are in error. The consequence of an errorCondition is that all 
      DLCIs on this interface will become inactive in both directions. The 
      errorCondition is cleared and a normalCondition is indicated when 
      a sufficient number of events have occurred without error. In ANSI, 
      this occurs when n393 consecutive good events take place.
      
      If the procedures attribute is set to autoConfigure, this attribute is 
      set to configuring while adaptive LMI determines which LMI 
      procedures are running on the link. A single LMI error event during 
      auto configuration causes the attribute value to change to 
      errorCondition. If during configuring no LMI message is received, 
      an LMI errorCondition is raised after n392 x t392 seconds."
::= { mscFrUniLmiPsiEntry 1 }

mscFrUniLmiOpProcedures OBJECT-TYPE
   SYNTAX     INTEGER  {
                 none(0),
                 vendorForum(1),
                 ansi(2),
                 itu(3),
                 unknown(4) }
   ACCESS     read-only
   STATUS     mandatory
   DESCRIPTION
     "The opProcedures attribute indicates the procedures being used for 
      the Local Management Interface. This attribute should be ignored if 
      protocolStatus is not normalCondition. The following procedures 
      are supported:
      
      none: Local Management Interface procedures are not running on 
      this interface. This accommodates Frame Relay user equipment that 
      has not implemented any LMI procedures.
      
      vendorForum: Local Management Interface procedures from the 
      Vendor Forum specification are running on this interface. DLCI 
      1023 is used for the LMI protocol.
      
      ansi: Local Management Interface procedures from the ANSI 
      specification are running. DLCI 0 is used for the LMI protocol.
      
      itu: Local Management Interface procedures from the ITU-T 
      specification are running. DLCI 0 is used for the LMI protocol. Was 
      previously ccitt.
      
      unknown: Local Management Interface procedures have yet to be 
      determined by Adaptive LMI."
::= { mscFrUniLmiPsiEntry 2 }

mscFrUniLmiStatsTable OBJECT-TYPE
   SYNTAX     SEQUENCE OF MscFrUniLmiStatsEntry
   ACCESS     not-accessible
   STATUS     mandatory
   DESCRIPTION
     "This group contains the operational statistics for the Frame Relay 
      Local Management Interface."
::= { mscFrUniLmi 13 }

mscFrUniLmiStatsEntry OBJECT-TYPE
   SYNTAX     MscFrUniLmiStatsEntry
   ACCESS     not-accessible
   STATUS     mandatory
   DESCRIPTION
     "An entry in the mscFrUniLmiStatsTable."
   INDEX {
      mscFrUniIndex,
      mscFrUniLmiIndex }
::= { mscFrUniLmiStatsTable 1 }

MscFrUniLmiStatsEntry ::= SEQUENCE {
   mscFrUniLmiKeepAliveStatusToIf
      Counter32,
   mscFrUniLmiFullStatusToIf
      Counter32,
   mscFrUniLmiKeepAliveStatusEnqFromIf
      Counter32,
   mscFrUniLmiFullStatusEnqFromIf
      Counter32,
   mscFrUniLmiNetworkSideEventHistory
      AsciiString,
   mscFrUniLmiProtocolErrors
      Counter32,
   mscFrUniLmiUnexpectedIes
      Counter32,
   mscFrUniLmiSequenceErrors
      Counter32,
   mscFrUniLmiUnexpectedReports
      Counter32,
   mscFrUniLmiPollingVerifTimeouts
      Counter32,
   mscFrUniLmiKeepAliveEnqToIf
      Counter32,
   mscFrUniLmiFullStatusEnqToIf
      Counter32,
   mscFrUniLmiUserSideEventHistory
      AsciiString,
   mscFrUniLmiStatusSequenceErrors
      Counter32,
   mscFrUniLmiNoStatusReportCount
      Counter32 }

mscFrUniLmiKeepAliveStatusToIf OBJECT-TYPE
   SYNTAX     Counter32 
   ACCESS     read-only
   STATUS     mandatory
   DESCRIPTION
     "This attribute counts the number of Local Management Interface 
      keep alive status messages sent to the external user device in 
      response to a status enquiry for keep alive status. When the 
      maximum count is exceeded it wraps to zero."
::= { mscFrUniLmiStatsEntry 1 }

mscFrUniLmiFullStatusToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { mscFrUniLmiStatsEntry 2 }

mscFrUniLmiKeepAliveStatusEnqFromIf OBJECT-TYPE
   SYNTAX     Counter32 
   ACCESS     read-only
   STATUS     mandatory
   DESCRIPTION
     "This attribute counts the number of Local Management Interface 
      valid keep alive status enquiry messages received from the external 
      user device. When the maximum count is reached it wraps to zero."
::= { mscFrUniLmiStatsEntry 3 }

mscFrUniLmiFullStatusEnqFromIf OBJECT-TYPE
   SYNTAX     Counter32 
   ACCESS     read-only
   STATUS     mandatory
   DESCRIPTION
     "This attribute counts the number of Local Management Interface 
      valid full status enquiry messages received from the external user 
      device. When the maximum count is reached it wraps to zero."
::= { mscFrUniLmiStatsEntry 4 }

mscFrUniLmiNetworkSideEventHistory OBJECT-TYPE
   SYNTAX     AsciiString (SIZE (1..10))
   ACCESS     read-only
   STATUS     mandatory
   DESCRIPTION
     "This attribute displays the Local Management Interface network 
      side procedure event history in order of occurrence. An event is 
      represented by a single symbol. A '+' symbol indicates a good 
      event. An 'X' symbol indicates a protocol error event. The leftmost 
      event is the most recent to occur. The provisioned eventCount (nN3/
      N393) dictates the maximum number of events displayed. A good 
      event is triggered by receipt of a valid status enquiry message. An 
      error event is one of three possibilities, either a nT2/T392 timer 
      expiry, receipt of a status enquiry message with bad sequence 
      numbers, or when lmiProcedures is provisioned to vendorForum 
      and we receive more than nN4 status enquiry messages within the 
      provisioned messageCountTimer (nT3)."
::= { mscFrUniLmiStatsEntry 5 }

mscFrUniLmiProtocolErrors OBJECT-TYPE
   SYNTAX     Counter32 
   ACCESS     read-only
   STATUS     mandatory
   DESCRIPTION
     "This attribute counts the number of Local Management Interface 
      protocol errors. It is the sum of the sequence (sequenceErrors), 
      timeout (pollingVerifTimeouts) and too many status enquiry 
      messages received within the messageCountTimer (nT3) errors. The 
      too many status enquiries error only applies when lmiProcedures is 
      set to vendorForum. When the maximum count is exceeded it 
      wraps to zero."
::= { mscFrUniLmiStatsEntry 6 }

mscFrUniLmiUnexpectedIes OBJECT-TYPE
   SYNTAX     Counter32 
   ACCESS     read-only
   STATUS     mandatory
   DESCRIPTION
     "This attribute counts the number of Local Management Interface 
      frames received with an Information Element identifier that is 
      unknown or unexpected. An unexpected Information Element is not 
      a protocol error. When the maximum count is reached, this counter 
      wraps to zero."
::= { mscFrUniLmiStatsEntry 7 }

mscFrUniLmiSequenceErrors OBJECT-TYPE
   SYNTAX     Counter32 
   ACCESS     read-only
   STATUS     mandatory
   DESCRIPTION
     "This attribute counts the number of Local Management Interface 
      Status Enquiry message sequence errors. A sequence error is receipt 
      of a Status Enquiry message with a receive sequence number not 
      equal to the last send sequence number. When the maximum count 
      is reached the counter wraps to zero."
::= { mscFrUniLmiStatsEntry 8 }

mscFrUniLmiUnexpectedReports OBJECT-TYPE
   SYNTAX     Counter32 
   ACCESS     read-only
   STATUS     mandatory
   DESCRIPTION
     "This attribute counts the number of Local Management Interface 
      frames received with an unknown or unexpected report type. An 
      unexpected report type is not a protocol error. When the maximum 
      count is reached the counter wraps to zero."
::= { mscFrUniLmiStatsEntry 9 }

mscFrUniLmiPollingVerifTimeouts OBJECT-TYPE
   SYNTAX     Counter32 
   ACCESS     read-only
   STATUS     mandatory
   DESCRIPTION
     "This attribute counts the number of checkPointTImer (t392) timer 
      expiries occurring on the Local Management Interface. When the 
      maximum count is reached the counter wraps to zero."
::= { mscFrUniLmiStatsEntry 10 }

mscFrUniLmiKeepAliveEnqToIf OBJECT-TYPE
   SYNTAX     Counter32 
   ACCESS     read-only
   STATUS     mandatory
   DESCRIPTION
     "This attribute counts the number of Local Management Interface 
      keep alive enquiry status messages sent to the external user device 
      for keep alive status. When the maximum count is reached it wraps 
      to zero."
::= { mscFrUniLmiStatsEntry 11 }

mscFrUniLmiFullStatusEnqToIf OBJECT-TYPE
   SYNTAX     Counter32 
   ACCESS     read-only
   STATUS     mandatory
   DESCRIPTION
     "This attribute counts the number of Local Management Interface 
      full status messages sent to the external user device in response to a 
      status enquiry for keep alive or full status. When the maximum 
      count is reached it wraps to zero."
::= { mscFrUniLmiStatsEntry 12 }

mscFrUniLmiUserSideEventHistory OBJECT-TYPE
   SYNTAX     AsciiString (SIZE (1..10))
   ACCESS     read-only
   STATUS     mandatory
   DESCRIPTION
     "This attribute displays the Local Management Interface user side 
      procedure event history in order of occurrence. An event is 
      represented by a single symbol. A '+' symbol indicates a good 
      event. An 'X' symbol indicates a protocol error event. The left most 
      event is the most recent to occur. The provisioned eventCount (nN3/
      N393) dictates the maximum number of events displayed. A good 
      event is triggered by receipt of a valid status message. An error 
      event is either a nT1/T391 timer expiry or receipt of a status 
      message with bad sequence numbers."
::= { mscFrUniLmiStatsEntry 13 }

mscFrUniLmiStatusSequenceErrors OBJECT-TYPE
   SYNTAX     Counter32 
   ACCESS     read-only
   STATUS     mandatory
   DESCRIPTION
     "This attribute counts the number of Local Management Interface 
      Status message sequence errors. A sequence error is receipt of a 
      Status message with a receive sequence number not equal to the last 
      send sequence number. When the maximum count is reached the 
      counter wraps to zero."
::= { mscFrUniLmiStatsEntry 14 }

mscFrUniLmiNoStatusReportCount OBJECT-TYPE
   SYNTAX     Counter32 
   ACCESS     read-only
   STATUS     mandatory
   DESCRIPTION
     "This attribute counts the number of times when no status report or 
      an invalid status report comes from the external network. This 
      attribute is incremented in two cases: 
      i) after a status enquiry is sent out and T391 timer expires without 
      having a status report received.
      ii) an invalid status report is received.
      
      When the maximum count is reached it wraps to zero."
::= { mscFrUniLmiStatsEntry 15 }

mscFrUniLmiUspParmsTable OBJECT-TYPE
   SYNTAX     SEQUENCE OF MscFrUniLmiUspParmsEntry
   ACCESS     not-accessible
   STATUS     mandatory
   DESCRIPTION
     "This group contains the provisionable attributes of the Local 
      Management Interface user side procedure."
::= { mscFrUniLmi 14 }

mscFrUniLmiUspParmsEntry OBJECT-TYPE
   SYNTAX     MscFrUniLmiUspParmsEntry
   ACCESS     not-accessible
   STATUS     mandatory
   DESCRIPTION
     "An entry in the mscFrUniLmiUspParmsTable."
   INDEX {
      mscFrUniIndex,
      mscFrUniLmiIndex }
::= { mscFrUniLmiUspParmsTable 1 }

MscFrUniLmiUspParmsEntry ::= SEQUENCE {
   mscFrUniLmiFullStatusPollingCycles
      Unsigned32,
   mscFrUniLmiLinkVerificationTimer
      Unsigned32 }

mscFrUniLmiFullStatusPollingCycles OBJECT-TYPE
   SYNTAX     Unsigned32 (1..255)
   ACCESS     read-write
   STATUS     mandatory
   DESCRIPTION
     "This attribute specifies how frequently the Frame Relay UNI service 
      should initiate a Status Enquiry for a full PVC status report. A 
      polling cycle is a Status Enquiry and Status Report exchange. 
      
      This attribute is used only if the side attribute is either user or both."
   DEFVAL     { 6 }
::= { mscFrUniLmiUspParmsEntry 1 }

mscFrUniLmiLinkVerificationTimer OBJECT-TYPE
   SYNTAX     Unsigned32 (5 | 10 | 15 | 20 | 25 | 30)
   ACCESS     read-write
   STATUS     mandatory
   DESCRIPTION
     "This attribute specifies how frequently the Frame Relay UNI service 
      should initiate a Status Enquiry for link integrity verification. It 
      must be less than checkPointTimer (t392).
      
      When the Lmi side is network, this attribute is ignored."
   DEFVAL     { 10 }
::= { mscFrUniLmiUspParmsEntry 2 }


-- FrUni/n DataLinkConnectionIdentifier/n
-- This component represents a Data Link Connection Identifier. It is 
-- responsible for the Frame Relay U-plane (User-plane) protocol for 
-- the specified instance. There can be many instances of Dlci for each 
-- FrUni. The instance value is used to identify the logical connection, 
-- multiplexed within the physical channel, with which a frame is 
-- associated. All frames carried within a particular physical channel 
-- and having the same DLCI value are associated with the same 
-- logical connection.
-- 
-- A DLCI instance can be a permanent virtual circuit (PVC) or 
-- switched permanent virtual circuit (P-SPVC) added through 
-- provisioning, or a switched virtual circuit (SVC) which is created 
-- dynamically through signaling.
-- 
-- The lock and unlock commands apply to permanent (PVC and P-
-- SPVC) DLCIs. The clear command applies to switched (SVC) 
-- DLCIs.

mscFrUniDlci OBJECT IDENTIFIER ::= { mscFrUni 5 }



mscFrUniDlciRowStatusTable OBJECT-TYPE
   SYNTAX     SEQUENCE OF MscFrUniDlciRowStatusEntry
   ACCESS     not-accessible
   STATUS     mandatory
   DESCRIPTION
     "This entry controls the addition and deletion of 
      mscFrUniDlci components."
::= { mscFrUniDlci 1 }

mscFrUniDlciRowStatusEntry OBJECT-TYPE
   SYNTAX     MscFrUniDlciRowStatusEntry
   ACCESS     not-accessible
   STATUS     mandatory
   DESCRIPTION
     "A single entry in the table represents a single 
      mscFrUniDlci component."
   INDEX {
      mscFrUniIndex,
      mscFrUniDlciIndex }
::= { mscFrUniDlciRowStatusTable 1 }

MscFrUniDlciRowStatusEntry ::= SEQUENCE {
   mscFrUniDlciRowStatus
      RowStatus,
   mscFrUniDlciComponentName
      DisplayString,
   mscFrUniDlciStorageType
      StorageType,
   mscFrUniDlciIndex
      Integer32 }

mscFrUniDlciRowStatus OBJECT-TYPE
   SYNTAX     RowStatus 
   ACCESS     read-write
   STATUS     mandatory
   DESCRIPTION
     "This variable is used as the basis for SNMP naming of
      mscFrUniDlci components.
      These components can be added and deleted."
::= { mscFrUniDlciRowStatusEntry 1 }

mscFrUniDlciComponentName OBJECT-TYPE
   SYNTAX     DisplayString 
   ACCESS     read-only
   STATUS     mandatory
   DESCRIPTION
     "This variable provides the component's string name for
      use with the ASCII Console Interface"
::= { mscFrUniDlciRowStatusEntry 2 }

mscFrUniDlciStorageType OBJECT-TYPE
   SYNTAX     StorageType 
   ACCESS     read-only
   STATUS     mandatory
   DESCRIPTION
     "This variable represents the storage type value for the
      mscFrUniDlci tables."
::= { mscFrUniDlciRowStatusEntry 4 }

mscFrUniDlciIndex OBJECT-TYPE
   SYNTAX     Integer32 (16..1007)
   ACCESS     not-accessible
   STATUS     mandatory
   DESCRIPTION
     "This variable represents the index for the mscFrUniDlci tables."
::= { mscFrUniDlciRowStatusEntry 10 }

mscFrUniDlciStateTable OBJECT-TYPE
   SYNTAX     SEQUENCE OF MscFrUniDlciStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscFrUniDlci 10 }

mscFrUniDlciStateEntry OBJECT-TYPE
   SYNTAX     MscFrUniDlciStateEntry
   ACCESS     not-accessible
   STATUS     mandatory
   DESCRIPTION
     "An entry in the mscFrUniDlciStateTable."
   INDEX {
      mscFrUniIndex,
      mscFrUniDlciIndex }
::= { mscFrUniDlciStateTable 1 }

MscFrUniDlciStateEntry ::= SEQUENCE {
   mscFrUniDlciAdminState
      INTEGER,
   mscFrUniDlciOperationalState
      INTEGER,
   mscFrUniDlciUsageState
      INTEGER,
   mscFrUniDlciAvailabilityStatus
      OCTET STRING,
   mscFrUniDlciProceduralStatus
      OCTET STRING,
   mscFrUniDlciControlStatus
      OCTET STRING,
   mscFrUniDlciAlarmStatus
      OCTET STRING,
   mscFrUniDlciStandbyStatus
      INTEGER,
   mscFrUniDlciUnknownStatus
      INTEGER }

mscFrUniDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscFrUniDlciStateEntry 1 }

mscFrUniDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscFrUniDlciStateEntry 2 }

mscFrUniDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscFrUniDlciStateEntry 3 }

mscFrUniDlciAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscFrUniDlciStateEntry 4 }

mscFrUniDlciProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscFrUniDlciStateEntry 5 }

mscFrUniDlciControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscFrUniDlciStateEntry 6 }

mscFrUniDlciAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscFrUniDlciStateEntry 7 }

mscFrUniDlciStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscFrUniDlciStateEntry 8 }

mscFrUniDlciUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscFrUniDlciStateEntry 9 }

mscFrUniDlciAbitTable OBJECT-TYPE
   SYNTAX     SEQUENCE OF MscFrUniDlciAbitEntry
   ACCESS     not-accessible
   STATUS     mandatory
   DESCRIPTION
     "This group contains the A-Bit status information for this Data Link 
      Connection Identifier."
::= { mscFrUniDlci 12 }

mscFrUniDlciAbitEntry OBJECT-TYPE
   SYNTAX     MscFrUniDlciAbitEntry
   ACCESS     not-accessible
   STATUS     mandatory
   DESCRIPTION
     "An entry in the mscFrUniDlciAbitTable."
   INDEX {
      mscFrUniIndex,
      mscFrUniDlciIndex }
::= { mscFrUniDlciAbitTable 1 }

MscFrUniDlciAbitEntry ::= SEQUENCE {
   mscFrUniDlciABitStatusToIf
      INTEGER,
   mscFrUniDlciABitReasonToIf
      INTEGER,
   mscFrUniDlciABitStatusFromIf
      INTEGER,
   mscFrUniDlciABitReasonFromIf
      INTEGER,
   mscFrUniDlciLoopbackState
      INTEGER }

mscFrUniDlciABitStatusToIf OBJECT-TYPE
   SYNTAX     INTEGER  {
                 inactive(0),
                 active(1),
                 notApplicable(2) }
   ACCESS     read-only
   STATUS     mandatory
   DESCRIPTION
     "This attribute is the most recent A-bit status sent to the interface. 
      The A-bit status is part of the LMI protocol, and indicates 
      willingness to accept data from the local interface.
      
      inactive - the Frame Relay service discards all data offered from the 
      local interface.
      
      active - the Frame Relay service tries to process all data offered 
      from the local interface.
      
      notApplicable - the DLCI is switched, so this attribute is ignored."
   DEFVAL     { inactive }
::= { mscFrUniDlciAbitEntry 1 }

mscFrUniDlciABitReasonToIf OBJECT-TYPE
   SYNTAX     INTEGER  {
                 notApplicable(0),
                 remoteUserSignaled(1),
                 localLmiError(2),
                 remoteLmiError(3),
                 localLinkDown(4),
                 remoteLinkDown(5),
                 pvcSpvcDown(6),
                 userNotAuthorized(8),
                 resourceNotAvailable(9),
                 dlciCollisionAtNni(10) }
   ACCESS     read-only
   STATUS     mandatory
   DESCRIPTION
     "This attribute provides the reason (if any) for an inactive status to 
      be sent to the interface. This reason is notApplicable for an active 
      status."
   DEFVAL     { notApplicable }
::= { mscFrUniDlciAbitEntry 2 }

mscFrUniDlciABitStatusFromIf OBJECT-TYPE
   SYNTAX     INTEGER  {
                 inactive(0),
                 active(1),
                 notApplicable(2) }
   ACCESS     read-only
   STATUS     mandatory
   DESCRIPTION
     "This attribute is the most recent A-Bit status received from the 
      interface.
      
      inactive - the Frame Relay service informs the remote DLCI not to 
      send user data to this interface.
      
      active - the Frame Relay service informs the remote DLCI that it is 
      okay to send user data to this interface.
      
      notApplicable - the DLCI is switched, so this attribute is ignored."
   DEFVAL     { inactive }
::= { mscFrUniDlciAbitEntry 3 }

mscFrUniDlciABitReasonFromIf OBJECT-TYPE
   SYNTAX     INTEGER  {
                 notApplicable(0),
                 remoteUserSignaled(1),
                 localLmiError(2),
                 localLinkDown(4),
                 missingFromLmiReport(7) }
   ACCESS     read-only
   STATUS     mandatory
   DESCRIPTION
     "This attribute provides the reason (if any) for an inactive status to 
      be sent to the subnet. This reason is notApplicable for an active 
      status."
   DEFVAL     { notApplicable }
::= { mscFrUniDlciAbitEntry 4 }

mscFrUniDlciLoopbackState OBJECT-TYPE
   SYNTAX     INTEGER  {
                 off(0),
                 on(1) }
   ACCESS     read-only
   STATUS     mandatory
   DESCRIPTION
     "This attribute has the value on when the DLCI is in loopback mode 
      and off otherwise. The loopback command verbs start and stop are 
      used to initiate and terminate the loopback mode for a DLCI. While 
      loopbackState is on, the local LMI will report to the interface the A-
      bit status as active. Also an active A-bit signal will be reliably 
      propagated across the subnet to the remote DLCI."
   DEFVAL     { off }
::= { mscFrUniDlciAbitEntry 5 }

mscFrUniDlciCalldTable OBJECT-TYPE
   SYNTAX     SEQUENCE OF MscFrUniDlciCalldEntry
   ACCESS     not-accessible
   STATUS     mandatory
   DESCRIPTION
     "This group of attributes describes the characteristics of the call such 
      as call type and call state."
::= { mscFrUniDlci 13 }

mscFrUniDlciCalldEntry OBJECT-TYPE
   SYNTAX     MscFrUniDlciCalldEntry
   ACCESS     not-accessible
   STATUS     mandatory
   DESCRIPTION
     "An entry in the mscFrUniDlciCalldTable."
   INDEX {
      mscFrUniIndex,
      mscFrUniDlciIndex }
::= { mscFrUniDlciCalldTable 1 }

MscFrUniDlciCalldEntry ::= SEQUENCE {
   mscFrUniDlciCallType
      INTEGER,
   mscFrUniDlciQstate
      INTEGER,
   mscFrUniDlciCallref
      Unsigned32 }

mscFrUniDlciCallType OBJECT-TYPE
   SYNTAX     INTEGER  {
                 pvc(0),
                 svc(1),
                 spvc(2) }
   ACCESS     read-only
   STATUS     mandatory
   DESCRIPTION
     "This attribute indicates whether this DLCI is a permancent virtual 
      circuit (PVC), a switched virtual circuit (SVC) or a switched 
      permament virtual circuit (SPVC)."
::= { mscFrUniDlciCalldEntry 1 }

mscFrUniDlciQstate OBJECT-TYPE
   SYNTAX     INTEGER  {
                 null(0),
                 callInitiated(1),
                 callProceedingSent(3),
                 callPresent(6),
                 callProceedingReceived(9),
                 active(10),
                 disconnectRequest(11),
                 disconnectIndication(12),
                 releaseRequest(19),
                 notApplicable(20),
                 restartRequest(61),
                 restart(62) }
   ACCESS     read-only
   STATUS     mandatory
   DESCRIPTION
     "This attribute indicates the FRF.4 state of an SVC call. The value of 
      this attribute for a permanent (PVC and P-SPVC) DLCI is always 
      notApplicable. In the description that follows, 'local' refers to the 
      user who has initiated the SETUP request, and 'remote' refers to 
      the user to whom the local user wishes to connect.
      
      State description:
      In the null state, the network has neither received nor sent call setup 
      requests for this DLCI.
      
      In the callInitiated state, the network has received a SETUP 
      message from the local user.
      
      In the outgoingCallProceeding state, the network has sent a CALL 
      PROCEEDING message to the local user in response to the SETUP 
      message.
      
      In the callPresent state, the network has sent a SETUP message to 
      the remote user.
      
      In the incomingCallProceeding state, the network has received a 
      CALL PROCEEDING message from the remote user in response to 
      a SETUP message.
      
      In the active state, either the network has sent a CONNECT 
      message to the local user, or the network has received a CONNECT 
      from the remote user.
      
      In the disconnectRequest state, the network has received a 
      DISCONNECT message from the local user.
      
      In the disconnectIndication state, the network has sent a 
      DISCONNECT to the local user.
      
      In the releaseRequest state, the network has sent out a RELEASE 
      message to the local user.
      
      In the restartRequest state, the network has sent a RESTART 
      request to the local user and is waiting for an acknowledgement.
      
      In the restart state, the network has received a request for a restart 
      from the local user and the network has not returned an 
      acknowledgement."
::= { mscFrUniDlciCalldEntry 2 }

mscFrUniDlciCallref OBJECT-TYPE
   SYNTAX     Unsigned32 (0..32767)
   ACCESS     read-only
   STATUS     mandatory
   DESCRIPTION
     "This attribute indicates the FRF.4 call reference number associated 
      with this DLCI. The value of this attribute for a provisioned (PVC 
      or P-SPVC) DLCI is always 0."
::= { mscFrUniDlciCalldEntry 3 }

mscFrUniDlciSpOpTable OBJECT-TYPE
   SYNTAX     SEQUENCE OF MscFrUniDlciSpOpEntry
   ACCESS     not-accessible
   STATUS     mandatory
   DESCRIPTION
     "This group defines the service and traffic parameters specific to this 
      instance of DLCI. For permanent (PVC and P-SPVC) DLCIs, the 
      values of attributes with the exception of the measurementInterval 
      should be identical to those in the group 
      FrsDataLinkConnectionProv under the 
      FrsUniServiceParametersProv component. For switched (SVC) 
      DLCIs, the values of attributes may be different from the values 
      provisioned under the FrUni Sig component, if signaling 
      negotiations have ocurred to alter the service parameters."
::= { mscFrUniDlci 14 }

mscFrUniDlciSpOpEntry OBJECT-TYPE
   SYNTAX     MscFrUniDlciSpOpEntry
   ACCESS     not-accessible
   STATUS     mandatory
   DESCRIPTION
     "An entry in the mscFrUniDlciSpOpTable."
   INDEX {
      mscFrUniIndex,
      mscFrUniDlciIndex }
::= { mscFrUniDlciSpOpTable 1 }

MscFrUniDlciSpOpEntry ::= SEQUENCE {
   mscFrUniDlciMaximumFrameSize
      Unsigned32,
   mscFrUniDlciRateEnforcement
      INTEGER,
   mscFrUniDlciCommittedInformationRate
      Unsigned32,
   mscFrUniDlciCommittedBurstSize
      Unsigned32,
   mscFrUniDlciExcessBurstSize
      Unsigned32,
   mscFrUniDlciMeasurementInterval
      Unsigned32,
   mscFrUniDlciRateAdaptation
      INTEGER,
   mscFrUniDlciAccounting
      INTEGER,
   mscFrUniDlciEmissionPriorityToIf
      INTEGER,
   mscFrUniDlciTransferPriToNwk
      Unsigned32,
   mscFrUniDlciTransferPriFromNwk
      Unsigned32 }

mscFrUniDlciMaximumFrameSize OBJECT-TYPE
   SYNTAX     Unsigned32 (1..8187)
   ACCESS     read-only
   STATUS     mandatory
   DESCRIPTION
     "This attribute indicates the maximum number of octets which may 
      be included in the information field. The frame relay header and 
      CRC octets are not included in this definition. This attribute 
      corresponds to the dN1 parameter described in the Vendor Forum 
      Specification."
::= { mscFrUniDlciSpOpEntry 1 }

mscFrUniDlciRateEnforcement OBJECT-TYPE
   SYNTAX     INTEGER  {
                 off(0),
                 on(1) }
   ACCESS     read-only
   STATUS     obsolete
   DESCRIPTION
     "This attribute is obsolete. It provided the information which is now 
      represented by the provisionable attribute rateEnforcement under 
      the ServiceParameters component."
::= { mscFrUniDlciSpOpEntry 2 }

mscFrUniDlciCommittedInformationRate OBJECT-TYPE
   SYNTAX     Unsigned32 (0..50000000)
   ACCESS     read-only
   STATUS     mandatory
   DESCRIPTION
     "This attribute indicates the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute should be ignored when rateEnforcement is off."
::= { mscFrUniDlciSpOpEntry 3 }

mscFrUniDlciCommittedBurstSize OBJECT-TYPE
   SYNTAX     Unsigned32 (0..50000000)
   ACCESS     read-only
   STATUS     mandatory
   DESCRIPTION
     "This attribute indicates the committed burst size (Bc) in bits. bc is 
      the amount of data that a network agrees to transfer under normal 
      conditions over a measurement interval (t). Data marked DE=1 is 
      not accounted for in Bc.
      
      This attribute should be ignored when rateEnforcement is off."
::= { mscFrUniDlciSpOpEntry 4 }

mscFrUniDlciExcessBurstSize OBJECT-TYPE
   SYNTAX     Unsigned32 (0..50000000)
   ACCESS     read-only
   STATUS     mandatory
   DESCRIPTION
     "This attribute indicates the excess burst size (Be) in bits. Be is the 
      amount of uncommitted data that the network will attempt to deliver 
      over measurement interval T. Data marked DE=1 by the user or by 
      the network is accounted for here.
      
      This attribute should be ignored when rateEnforcement is off."
::= { mscFrUniDlciSpOpEntry 5 }

mscFrUniDlciMeasurementInterval OBJECT-TYPE
   SYNTAX     Unsigned32 (0..4294967295)
   ACCESS     read-only
   STATUS     mandatory
   DESCRIPTION
     "This attribute indicates the time interval (in milliseconds) over 
      which rates and burst sizes are measured.
      
      This attribute should be ignored when rateEnforcement is off."
::= { mscFrUniDlciSpOpEntry 6 }

mscFrUniDlciRateAdaptation OBJECT-TYPE
   SYNTAX     INTEGER  {
                 off(0),
                 on(1),
                 eirOnly(2) }
   ACCESS     read-only
   STATUS     obsolete
   DESCRIPTION
     "This attribute is obsolete. It provided the information which is now 
      represented by the provisionable attribute rateAdaptation under the 
      ServiceParameters component."
::= { mscFrUniDlciSpOpEntry 7 }

mscFrUniDlciAccounting OBJECT-TYPE
   SYNTAX     INTEGER  {
                 off(0),
                 on(1) }
   ACCESS     read-only
   STATUS     mandatory
   DESCRIPTION
     "This attribute indicates whether accounting data collection and 
      record generation is turned on at this DLCI. For accounting data 
      collection and record generation to be turned on, the accountingOn 
      bit and at least one of the accountCollection bits in the 
      DataNetworkAddress component must be set to on."
::= { mscFrUniDlciSpOpEntry 8 }

mscFrUniDlciEmissionPriorityToIf OBJECT-TYPE
   SYNTAX     INTEGER (0 | 1 | 2 | 3)
   ACCESS     read-only
   STATUS     mandatory
   DESCRIPTION
     "This attribute indicates the emission priority of frames sent to the 
      interface. A larger value denotes a higher priority."
::= { mscFrUniDlciSpOpEntry 9 }

mscFrUniDlciTransferPriToNwk OBJECT-TYPE
   SYNTAX     Unsigned32 (0..15)
   ACCESS     read-only
   STATUS     mandatory
   DESCRIPTION
     "This attribute indicates the priority at which data is transferred to 
      the network.
      
      The transfer priority is a preference configured for an application 
      according to its delay-sensitivity requirement. Frames with higher 
      transfer priority are served by the network before the frames with 
      lower priority. The transfer priority standard is defined to have 16 
      indices from 0 to 15. 
      
      Each transfer priority n, where n specifies the transfer priority 
      index, contains a default setting for routing class of service 
      (multimedia, delay, or throughput) and frame relay egress queue 
      (depending on the number of supported egress queues on the remote 
      end interface) specified by the routingClassOfService and 
      emissionPriority attributes provisioned in the Mod Frs DprsNet 
      Tpm/n component. The default mapping can be altered by a user if 
      required."
::= { mscFrUniDlciSpOpEntry 10 }

mscFrUniDlciTransferPriFromNwk OBJECT-TYPE
   SYNTAX     Unsigned32 (0..15)
   ACCESS     read-only
   STATUS     mandatory
   DESCRIPTION
     "This attribute indicates the priority at which data is transferred from 
      the network.
      
      The transfer priority is a preference configured for an application 
      according to its delay-sensitivity requirement. Frames with higher 
      transfer priority are served by the network before the frames with 
      lower priority. The transfer priority standard is defined to have 16 
      indices from 0 to 15.
      
      Each transfer priority n, where n specifies the transfer priority 
      index, contains a default setting for routing class of service 
      (multimedia, delay, or throughput) and frame relay egress queue 
      (depending on the number of supported egress queues on the remote 
      end interface) specified by the routingClassOfService and 
      emissionPriority attributes provisioned in the Mod Frs DprsNet 
      Tpm/n component. The default mapping can be altered by a user if 
      required."
::= { mscFrUniDlciSpOpEntry 11 }

mscFrUniDlciStatsTable OBJECT-TYPE
   SYNTAX     SEQUENCE OF MscFrUniDlciStatsEntry
   ACCESS     not-accessible
   STATUS     mandatory
   DESCRIPTION
     "This group contains the operational statistics for the Frame Relay 
      Data Link Connection Identifier."
::= { mscFrUniDlci 15 }

mscFrUniDlciStatsEntry OBJECT-TYPE
   SYNTAX     MscFrUniDlciStatsEntry
   ACCESS     not-accessible
   STATUS     mandatory
   DESCRIPTION
     "An entry in the mscFrUniDlciStatsTable."
   INDEX {
      mscFrUniIndex,
      mscFrUniDlciIndex }
::= { mscFrUniDlciStatsTable 1 }

MscFrUniDlciStatsEntry ::= SEQUENCE {
   mscFrUniDlciFrmToIf
      Unsigned32,
   mscFrUniDlciFecnFrmToIf
      Unsigned32,
   mscFrUniDlciBecnFrmToIf
      Unsigned32,
   mscFrUniDlciBciToSubnet
      Unsigned32,
   mscFrUniDlciDeFrmToIf
      Unsigned32,
   mscFrUniDlciDiscCongestedToIf
      Unsigned32,
   mscFrUniDlciDiscDeCongestedToIf
      Unsigned32,
   mscFrUniDlciFrmFromIf
      Unsigned32,
   mscFrUniDlciFecnFrmFromIf
      Unsigned32,
   mscFrUniDlciBecnFrmFromIf
      Unsigned32,
   mscFrUniDlciFciFromSubnet
      Unsigned32,
   mscFrUniDlciBciFromSubnet
      Unsigned32,
   mscFrUniDlciDeFrmFromIf
      Unsigned32,
   mscFrUniDlciExcessFrmFromIf
      Unsigned32,
   mscFrUniDlciDiscExcessFromIf
      Unsigned32,
   mscFrUniDlciDiscFrameAbit
      Unsigned32,
   mscFrUniDlciDiscCongestedFromIf
      Unsigned32,
   mscFrUniDlciDiscDeCongestedFromIf
      Unsigned32,
   mscFrUniDlciErrorShortFrmFromIf
      Unsigned32,
   mscFrUniDlciErrorLongFrmFromIf
      Unsigned32,
   mscFrUniDlciBecnFrmSetByService
      Unsigned32,
   mscFrUniDlciBytesToIf
      Unsigned32,
   mscFrUniDlciDeBytesToIf
      Unsigned32,
   mscFrUniDlciDiscCongestedToIfBytes
      Unsigned32,
   mscFrUniDlciDiscDeCongestedToIfBytes
      Unsigned32,
   mscFrUniDlciBytesFromIf
      Unsigned32,
   mscFrUniDlciDeBytesFromIf
      Unsigned32,
   mscFrUniDlciExcessBytesFromIf
      Unsigned32,
   mscFrUniDlciDiscExcessFromIfBytes
      Unsigned32,
   mscFrUniDlciDiscByteAbit
      Unsigned32,
   mscFrUniDlciDiscCongestedFromIfBytes
      Unsigned32,
   mscFrUniDlciDiscDeCongestedFromIfBytes
      Unsigned32,
   mscFrUniDlciErrorShortBytesFromIf
      Unsigned32,
   mscFrUniDlciErrorLongBytesFromIf
      Unsigned32,
   mscFrUniDlciRateAdaptReduct
      Unsigned32,
   mscFrUniDlciRateAdaptReductPeriod
      Unsigned32,
   mscFrUniDlciTransferPriorityToNetwork
      INTEGER,
   mscFrUniDlciTransferPriorityFromNetwork
      INTEGER,
   mscFrUniDlciCirPresent
      Unsigned32,
   mscFrUniDlciEirPresent
      Unsigned32 }

mscFrUniDlciFrmToIf OBJECT-TYPE
   SYNTAX     Unsigned32 (0..4294967295)
   ACCESS     read-only
   STATUS     mandatory
   DESCRIPTION
     "This attribute counts the frames sent out the interface. When the 
      maximum count is reached the count wraps to zero."
   DEFVAL     { 0 }
::= { mscFrUniDlciStatsEntry 1 }

mscFrUniDlciFecnFrmToIf OBJECT-TYPE
   SYNTAX     Unsigned32 (0..4294967295)
   ACCESS     read-only
   STATUS     mandatory
   DESCRIPTION
     "This attribute counts the frames sent to the interface with the 
      Forward Explicit Congestion Notification (FECN) bit set. When the 
      count reaches maximum it wraps to zero."
   DEFVAL     { 0 }
::= { mscFrUniDlciStatsEntry 2 }

mscFrUniDlciBecnFrmToIf OBJECT-TYPE
   SYNTAX     Unsigned32 (0..4294967295)
   ACCESS     read-only
   STATUS     mandatory
   DESCRIPTION
     "This attribute counts the frames sent to the interface with the 
      Backward Explicit Congestion Notification (BECN) bit set. When 
      the count reaches maximum it wraps to zero."
   DEFVAL     { 0 }
::= { mscFrUniDlciStatsEntry 3 }

mscFrUniDlciBciToSubnet OBJECT-TYPE
   SYNTAX     Unsigned32 (0..4294967295)
   ACCESS     read-only
   STATUS     mandatory
   DESCRIPTION
     "This attribute counts the frames sent into the local network with the 
      Backward Congestion Indication (BCI) bit set. When the count 
      reaches maximum it wraps to zero."
   DEFVAL     { 0 }
::= { mscFrUniDlciStatsEntry 4 }

mscFrUniDlciDeFrmToIf OBJECT-TYPE
   SYNTAX     Unsigned32 (0..4294967295)
   ACCESS     read-only
   STATUS     mandatory
   DESCRIPTION
     "This attribute counts the frames sent to the interface with the 
      Discard Eligibility (DE) bit set. When the count reaches maximum 
      it wraps to zero."
   DEFVAL     { 0 }
::= { mscFrUniDlciStatsEntry 5 }

mscFrUniDlciDiscCongestedToIf OBJECT-TYPE
   SYNTAX     Unsigned32 (0..4294967295)
   ACCESS     read-only
   STATUS     mandatory
   DESCRIPTION
     "This attribute counts the number of frame discards at the Frame 
      Relay service due to local congestion in the direction toward the 
      interface. When this count reaches maximum, it wraps to zero."
   DEFVAL     { 0 }
::= { mscFrUniDlciStatsEntry 6 }

mscFrUniDlciDiscDeCongestedToIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion in the direction toward the interface. When this 
      count reaches maximum, it wraps to zero."
   DEFVAL     { 0 }
::= { mscFrUniDlciStatsEntry 7 }

mscFrUniDlciFrmFromIf OBJECT-TYPE
   SYNTAX     Unsigned32 (0..4294967295)
   ACCESS     read-only
   STATUS     mandatory
   DESCRIPTION
     "This attribute counts the frames received from the interface. It 
      includes the frames that are discarded due to error or excess. When 
      the maximum count is reached the count wraps to zero."
   DEFVAL     { 0 }
::= { mscFrUniDlciStatsEntry 8 }

mscFrUniDlciFecnFrmFromIf OBJECT-TYPE
   SYNTAX     Unsigned32 (0..4294967295)
   ACCESS     read-only
   STATUS     mandatory
   DESCRIPTION
     "This attribute counts the frames received from the interface with the 
      Forward Explicit Congestion Notification (FECN) bit set. When the 
      count reaches maximum it wraps to zero."
   DEFVAL     { 0 }
::= { mscFrUniDlciStatsEntry 9 }

mscFrUniDlciBecnFrmFromIf OBJECT-TYPE
   SYNTAX     Unsigned32 (0..4294967295)
   ACCESS     read-only
   STATUS     mandatory
   DESCRIPTION
     "This attribute counts the frames received from the interface with the 
      Backward Explicit Congestion Notification (BECN) bit set. When 
      the count reaches maximum it wraps to zero."
   DEFVAL     { 0 }
::= { mscFrUniDlciStatsEntry 10 }

mscFrUniDlciFciFromSubnet OBJECT-TYPE
   SYNTAX     Unsigned32 (0..4294967295)
   ACCESS     read-only
   STATUS     mandatory
   DESCRIPTION
     "This attribute counts the frames received from the network with the 
      Forward Congestion Indication (FCI) bit set. When the count 
      reaches maximum it wraps to zero."
   DEFVAL     { 0 }
::= { mscFrUniDlciStatsEntry 11 }

mscFrUniDlciBciFromSubnet OBJECT-TYPE
   SYNTAX     Unsigned32 (0..4294967295)
   ACCESS     read-only
   STATUS     mandatory
   DESCRIPTION
     "This attribute counts the frames received from the network with the 
      Backward Congestion Indication (BCI) bit set. When the count 
      reaches maximum it wraps to zero."
   DEFVAL     { 0 }
::= { mscFrUniDlciStatsEntry 12 }

mscFrUniDlciDeFrmFromIf OBJECT-TYPE
   SYNTAX     Unsigned32 (0..4294967295)
   ACCESS     read-only
   STATUS     mandatory
   DESCRIPTION
     "This attribute counts the frames received from the interface with the 
      Discard Eligibility (DE) bit set. When the count reaches maximum 
      it wraps to zero."
   DEFVAL     { 0 }
::= { mscFrUniDlciStatsEntry 13 }

mscFrUniDlciExcessFrmFromIf OBJECT-TYPE
   SYNTAX     Unsigned32 (0..4294967295)
   ACCESS     read-only
   STATUS     mandatory
   DESCRIPTION
     "This attribute counts the frames received from the interface with the 
      Discard Eligibility (DE) bit clear, but subsequently set by the 
      network due to rate enforcement. When the count reaches 
      maximum it wraps to zero."
   DEFVAL     { 0 }
::= { mscFrUniDlciStatsEntry 14 }

mscFrUniDlciDiscExcessFromIf OBJECT-TYPE
   SYNTAX     Unsigned32 (0..4294967295)
   ACCESS     read-only
   STATUS     mandatory
   DESCRIPTION
     "This attribute counts the frames which were discarded due to rate 
      enforcement. When the count reaches maximum it wraps to zero."
   DEFVAL     { 0 }
::= { mscFrUniDlciStatsEntry 15 }

mscFrUniDlciDiscFrameAbit OBJECT-TYPE
   SYNTAX     Unsigned32 (0..4294967295)
   ACCESS     read-only
   STATUS     mandatory
   DESCRIPTION
     "This attribute counts the number of frame discards at the Frame 
      Relay Service, due to an inactive PVC status, in the direction 
      toward the local network. When this count reaches maximum, it 
      wraps to zero."
   DEFVAL     { 0 }
::= { mscFrUniDlciStatsEntry 16 }

mscFrUniDlciDiscCongestedFromIf OBJECT-TYPE
   SYNTAX     Unsigned32 (0..4294967295)
   ACCESS     read-only
   STATUS     mandatory
   DESCRIPTION
     "This attribute counts the number of frame discards at the Frame 
      Relay service due to local congestion in the direction toward the 
      network. When this count reaches maximum, it wraps to zero."
   DEFVAL     { 0 }
::= { mscFrUniDlciStatsEntry 17 }

mscFrUniDlciDiscDeCongestedFromIf OBJECT-TYPE
   SYNTAX     Unsigned32 (0..4294967295)
   ACCESS     read-only
   STATUS     mandatory
   DESCRIPTION
     "This attribute counts the number of discarded frames, with the 
      Discard Eligibility (DE) bit set, at the Frame Relay service, due to 
      local congestion, in the direction toward the local network. When 
      this count reaches maximum, it wraps to zero."
   DEFVAL     { 0 }
::= { mscFrUniDlciStatsEntry 18 }

mscFrUniDlciErrorShortFrmFromIf OBJECT-TYPE
   SYNTAX     Unsigned32 (0..4294967295)
   ACCESS     read-only
   STATUS     mandatory
   DESCRIPTION
     "This attribute counts the frames received with 0 octets in the 
      information field. When the count reaches maximum it wraps to 
      zero."
   DEFVAL     { 0 }
::= { mscFrUniDlciStatsEntry 19 }

mscFrUniDlciErrorLongFrmFromIf OBJECT-TYPE
   SYNTAX     Unsigned32 (0..4294967295)
   ACCESS     read-only
   STATUS     mandatory
   DESCRIPTION
     "This attribute counts the frames received with number of octets in 
      the information field greater than the subscribed maximum. When 
      the count reaches maximum it wraps to zero. Frames whose lengths 
      are greater than the hardware receive buffer are ignored by the 
      hardware and are therefore not included in this count."
   DEFVAL     { 0 }
::= { mscFrUniDlciStatsEntry 20 }

mscFrUniDlciBecnFrmSetByService OBJECT-TYPE
   SYNTAX     Unsigned32 (0..4294967295)
   ACCESS     read-only
   STATUS     mandatory
   DESCRIPTION
     "This attribute counts the number of frames with BECN set by the 
      Frame Relay service. It is incremented whenever the Frame Relay 
      service sets BECN on a frame upon detecting local congestion. This 
      count is incremented regardless of whether the frame already bears 
      a set BECN bit since its use is to determine the place of congestion. 
      When the count reaches maximum, it wraps to zero."
   DEFVAL     { 0 }
::= { mscFrUniDlciStatsEntry 21 }

mscFrUniDlciBytesToIf OBJECT-TYPE
   SYNTAX     Unsigned32 (0..4294967295)
   ACCESS     read-only
   STATUS     mandatory
   DESCRIPTION
     "This attribute counts the bytes sent out the interface. When the 
      maximum count is reached the count wraps to zero."
   DEFVAL     { 0 }
::= { mscFrUniDlciStatsEntry 22 }

mscFrUniDlciDeBytesToIf OBJECT-TYPE
   SYNTAX     Unsigned32 (0..4294967295)
   ACCESS     read-only
   STATUS     mandatory
   DESCRIPTION
     "This attribute counts the bytes sent to the interface with the Discard 
      Eligibility (DE) bit set. When the count reaches maximum it wraps 
      to zero."
   DEFVAL     { 0 }
::= { mscFrUniDlciStatsEntry 23 }

mscFrUniDlciDiscCongestedToIfBytes OBJECT-TYPE
   SYNTAX     Unsigned32 (0..4294967295)
   ACCESS     read-only
   STATUS     mandatory
   DESCRIPTION
     "This attribute counts the number of byte discards at the Frame 
      Relay service due to local congestion in the direction toward the 
      link. When this count reaches maximum, it wraps to zero."
   DEFVAL     { 0 }
::= { mscFrUniDlciStatsEntry 24 }

mscFrUniDlciDiscDeCongestedToIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the link. When the maximum count is reached the 
      count wraps to zero."
   DEFVAL     { 0 }
::= { mscFrUniDlciStatsEntry 25 }

mscFrUniDlciBytesFromIf OBJECT-TYPE
   SYNTAX     Unsigned32 (0..4294967295)
   ACCESS     read-only
   STATUS     mandatory
   DESCRIPTION
     "This attribute counts the bytes received from the interface. Bytes 
      that are discarded due to error or excess are not counted. When the 
      maximum count is reached the count wraps to zero."
   DEFVAL     { 0 }
::= { mscFrUniDlciStatsEntry 26 }

mscFrUniDlciDeBytesFromIf OBJECT-TYPE
   SYNTAX     Unsigned32 (0..4294967295)
   ACCESS     read-only
   STATUS     mandatory
   DESCRIPTION
     "This attribute counts the bytes received from the interface with the 
      Discard Eligibility (DE) bit set. When the count reaches maximum 
      it wraps to zero."
   DEFVAL     { 0 }
::= { mscFrUniDlciStatsEntry 27 }

mscFrUniDlciExcessBytesFromIf OBJECT-TYPE
   SYNTAX     Unsigned32 (0..4294967295)
   ACCESS     read-only
   STATUS     mandatory
   DESCRIPTION
     "This attribute counts the bytes received from the interface with the 
      Discard Eligibility (DE) bit clear, but subsequently set by the 
      network due to rate enforcement. When the count reaches 
      maximum it wraps to zero."
   DEFVAL     { 0 }
::= { mscFrUniDlciStatsEntry 28 }

mscFrUniDlciDiscExcessFromIfBytes OBJECT-TYPE
   SYNTAX     Unsigned32 (0..4294967295)
   ACCESS     read-only
   STATUS     mandatory
   DESCRIPTION
     "This attribute counts the bytes which were discarded due to rate 
      enforcement. When the count reaches maximum it wraps to zero."
   DEFVAL     { 0 }
::= { mscFrUniDlciStatsEntry 29 }

mscFrUniDlciDiscByteAbit OBJECT-TYPE
   SYNTAX     Unsigned32 (0..4294967295)
   ACCESS     read-only
   STATUS     mandatory
   DESCRIPTION
     "This attribute counts the bytes which were discarded due to aBit 
      turned off."
   DEFVAL     { 0 }
::= { mscFrUniDlciStatsEntry 30 }

mscFrUniDlciDiscCongestedFromIfBytes OBJECT-TYPE
   SYNTAX     Unsigned32 (0..4294967295)
   ACCESS     read-only
   STATUS     mandatory
   DESCRIPTION
     "This attribute counts the number of byte discards at the Frame 
      Relay service due to local congestion in the direction toward the 
      network. When this count reaches maximum, it wraps to zero."
   DEFVAL     { 0 }
::= { mscFrUniDlciStatsEntry 31 }

mscFrUniDlciDiscDeCongestedFromIfBytes OBJECT-TYPE
   SYNTAX     Unsigned32 (0..4294967295)
   ACCESS     read-only
   STATUS     mandatory
   DESCRIPTION
     "This attribute counts the number of discard eligible (DE=1) byte 
      discards at the Frame Relay service due to local congestion in the 
      direction toward the network. When the maximum count is reached 
      the count wraps to zero."
   DEFVAL     { 0 }
::= { mscFrUniDlciStatsEntry 32 }

mscFrUniDlciErrorShortBytesFromIf OBJECT-TYPE
   SYNTAX     Unsigned32 (0..4294967295)
   ACCESS     read-only
   STATUS     mandatory
   DESCRIPTION
     "This attribute counts the bytes received with 0 octets in the 
      information field. When the count reaches maximum it wraps to 
      zero."
   DEFVAL     { 0 }
::= { mscFrUniDlciStatsEntry 33 }

mscFrUniDlciErrorLongBytesFromIf OBJECT-TYPE
   SYNTAX     Unsigned32 (0..4294967295)
   ACCESS     read-only
   STATUS     mandatory
   DESCRIPTION
     "This attribute counts the bytes received with number of octets in the 
      information field greater than the subscribed maximum. When the 
      count reaches maximum it wraps to zero. Bytes whose lengths are 
      greater than the hardware receive buffer are ignored by the 
      hardware and are therefore not included in this count."
   DEFVAL     { 0 }
::= { mscFrUniDlciStatsEntry 34 }

mscFrUniDlciRateAdaptReduct OBJECT-TYPE
   SYNTAX     Unsigned32 (0..4294967295)
   ACCESS     read-only
   STATUS     mandatory
   DESCRIPTION
     "This attribute counts the number of rate reductions due to rate 
      adaptation. Rate adaptation causes the allowed rate to be reduced in 
      steps. After each reduction, a period of time is awaited before 
      further action is taken. At the end of this period, the allowed rate is 
      further reduced if congestion is still prevalent. When this count 
      reaches maximum, it wraps to zero."
   DEFVAL     { 0 }
::= { mscFrUniDlciStatsEntry 35 }

mscFrUniDlciRateAdaptReductPeriod OBJECT-TYPE
   SYNTAX     Unsigned32 (0..4294967295)
   ACCESS     read-only
   STATUS     mandatory
   DESCRIPTION
     "This attribute provides a cumulative count of the amount of time 
      that rate adaptation procedures have been in effect. When this count 
      reaches maximum, it wraps to zero."
   DEFVAL     { 0 }
::= { mscFrUniDlciStatsEntry 36 }

mscFrUniDlciTransferPriorityToNetwork OBJECT-TYPE
   SYNTAX     INTEGER (0..15)
   ACCESS     read-only
   STATUS     obsolete
   DESCRIPTION
     "This attribute is obsolete. It is replaced by attribute 
      transferPriorityToNetwork under group 
      FrsNniDataLinkConnectionIdentifierServiceParametersOp."
::= { mscFrUniDlciStatsEntry 37 }

mscFrUniDlciTransferPriorityFromNetwork OBJECT-TYPE
   SYNTAX     INTEGER (0..15)
   ACCESS     read-only
   STATUS     obsolete
   DESCRIPTION
     "This attribute is obsolete. It is replaced by attribute 
      transferPriorityFromNetwork under group 
      FrsNniDataLinkConnectionIdentifierServiceParametersOp."
::= { mscFrUniDlciStatsEntry 38 }

mscFrUniDlciCirPresent OBJECT-TYPE
   SYNTAX     Unsigned32 (0..4294967295)
   ACCESS     read-only
   STATUS     mandatory
   DESCRIPTION
     "This attribute provides the actual Committed Information Rate 
      (CIR) enforced for this DLCI. This number is in units of 800 bits/
      sec, since that is the internal resolution of Passport rate 
      enforcement. If rateEnforcement is off, then this number does not 
      have meaning. Normally, this attribute matches the provisioned CIR 
      for the DLCI. But when Rate Adaptation is active, then this number 
      will vary to represent the actual Allowed CIR at the moment that 
      this attribute is collected."
   DEFVAL     { 0 }
::= { mscFrUniDlciStatsEntry 39 }

mscFrUniDlciEirPresent OBJECT-TYPE
   SYNTAX     Unsigned32 (0..4294967295)
   ACCESS     read-only
   STATUS     mandatory
   DESCRIPTION
     "This attribute provides the actual Excess Information Rate (EIR) 
      enforced for this DLCI. This number is in units of 800 bits/sec, 
      since that is the internal resolution of Passport rate enforcement. If 
      rateEnforcement is off, then this number does not have meaning. 
      Normally, this attribute matches the provisioned EIR for the DLCI. 
      But when Rate Adaptation is active, then this number will vary to 
      represent the actual Allowed EIR at the moment that this attribute is 
      collected."
   DEFVAL     { 0 }
::= { mscFrUniDlciStatsEntry 40 }

mscFrUniDlciIntTable OBJECT-TYPE
   SYNTAX     SEQUENCE OF MscFrUniDlciIntEntry
   ACCESS     not-accessible
   STATUS     mandatory
   DESCRIPTION
     "This group contains the operational statistics for the Frame Relay 
      Data Link Connection Identifier interval data (accounting data)."
::= { mscFrUniDlci 16 }

mscFrUniDlciIntEntry OBJECT-TYPE
   SYNTAX     MscFrUniDlciIntEntry
   ACCESS     not-accessible
   STATUS     mandatory
   DESCRIPTION
     "An entry in the mscFrUniDlciIntTable."
   INDEX {
      mscFrUniIndex,
      mscFrUniDlciIndex }
::= { mscFrUniDlciIntTable 1 }

MscFrUniDlciIntEntry ::= SEQUENCE {
   mscFrUniDlciStartTime
      EnterpriseDateAndTime,
   mscFrUniDlciTotalIngressBytes
      Unsigned64,
   mscFrUniDlciTotalEgressBytes
      Unsigned64,
   mscFrUniDlciEirIngressBytes
      Unsigned64,
   mscFrUniDlciEirEgressBytes
      Unsigned64,
   mscFrUniDlciDiscardedBytes
      Unsigned64,
   mscFrUniDlciTotalIngressSegFrm
      Unsigned32,
   mscFrUniDlciTotalEgressSegFrm
      Unsigned32,
   mscFrUniDlciEirIngressSegFrm
      Unsigned32,
   mscFrUniDlciEirEgressSegFrm
      Unsigned32,
   mscFrUniDlciDiscardedSegFrm
      Unsigned32,
   mscFrUniDlciCirPresentObs
      Unsigned32,
   mscFrUniDlciEirPresentObs
      Unsigned32,
   mscFrUniDlciRateEnforcementPresent
      INTEGER,
   mscFrUniDlciRateAdaptationPresent
      INTEGER,
   mscFrUniDlciLocalRateAdaptOccurred
      INTEGER,
   mscFrUniDlciCallReferenceNumber
      Hex,
   mscFrUniDlciElapsedDifference
      Unsigned32,
   mscFrUniDlciCallRefNumber
      Unsigned32 }

mscFrUniDlciStartTime OBJECT-TYPE
   SYNTAX     EnterpriseDateAndTime (SIZE (0 | 19))
   ACCESS     read-only
   STATUS     mandatory
   DESCRIPTION
     "This attribute indicates the start time of this interval period. If Vc 
      spans 12 hour time or time of day change startTime reflects new 
      time as recorded at 12 hour periods or time of day changes. A new 
      interval period is started each time an accounting record is 
      generated."
::= { mscFrUniDlciIntEntry 1 }

mscFrUniDlciTotalIngressBytes OBJECT-TYPE
   SYNTAX     Unsigned64 (SIZE (8))
   ACCESS     read-only
   STATUS     mandatory
   DESCRIPTION
     "This attribute counts the total bytes received from the interface 
      since the start of the interval period. The start of the interval period 
      is captured in the startTime attribute. The count is reset to zero 
      when an accounting record is generated."
::= { mscFrUniDlciIntEntry 2 }

mscFrUniDlciTotalEgressBytes OBJECT-TYPE
   SYNTAX     Unsigned64 (SIZE (8))
   ACCESS     read-only
   STATUS     mandatory
   DESCRIPTION
     "This attribute counts the total bytes sent to the interface since the 
      start of the interval period. The start of the interval period is 
      captured in the startTime attribute. The count is reset to zero when 
      an accounting record is generated."
::= { mscFrUniDlciIntEntry 3 }

mscFrUniDlciEirIngressBytes OBJECT-TYPE
   SYNTAX     Unsigned64 (SIZE (8))
   ACCESS     read-only
   STATUS     mandatory
   DESCRIPTION
     "This attribute counts the total bytes with the Discard Eligibility 
      (DE) bit set sent to the subnet since the start of the interval period. 
      The start of the interval period is captured in the startTime attribute. 
      The count is reset to zero when an accounting record is generated."
::= { mscFrUniDlciIntEntry 4 }

mscFrUniDlciEirEgressBytes OBJECT-TYPE
   SYNTAX     Unsigned64 (SIZE (8))
   ACCESS     read-only
   STATUS     mandatory
   DESCRIPTION
     "This attribute counts the total bytes with the Discard Eligibility 
      (DE) bit set sent to the interface since the start of the interval 
      period. The start of the interval period is captured in the startTime 
      attribute. The count is reset to zero when an accounting record is 
      generated."
::= { mscFrUniDlciIntEntry 5 }

mscFrUniDlciDiscardedBytes OBJECT-TYPE
   SYNTAX     Unsigned64 (SIZE (8))
   ACCESS     read-only
   STATUS     mandatory
   DESCRIPTION
     "This attribute counts the total bytes in invalid frames received from 
      the interface and discarded at the DLCI since the start of the interval 
      period. This count is a sum of octets in frames discarded due to the 
      number of octets in the information field greater than the subscribed 
      maximum or equal to 0, due to aBit turned off, or due to rate 
      enforcement. The start of the interval period is captured in the 
      startTime attribute. The count is reset to zero when an accounting 
      record is generated."
::= { mscFrUniDlciIntEntry 6 }

mscFrUniDlciTotalIngressSegFrm OBJECT-TYPE
   SYNTAX     Unsigned32 (0..4294967295)
   ACCESS     read-only
   STATUS     mandatory
   DESCRIPTION
     "If the value of the unitsCounted attribute in moduleData component 
      is segments, this attribute counts the total number of segments in 
      frames received from the interface since the start of the interval 
      period. If the value of the unitsCounted attribute in moduleData 
      component is frames, this attribute counts the total number of 
      frames received from the interface since the start of the interval 
      period. The start of the interval period is captured in the startTime 
      attribute. The count is reset to zero when an accounting record is 
      generated."
   DEFVAL     { 0 }
::= { mscFrUniDlciIntEntry 7 }

mscFrUniDlciTotalEgressSegFrm OBJECT-TYPE
   SYNTAX     Unsigned32 (0..4294967295)
   ACCESS     read-only
   STATUS     mandatory
   DESCRIPTION
     "If the value of the unitsCounted attribute in moduleData component 
      is segments, this attribute counts the total number of segments in 
      frames sent to the interface since the start of the interval period. If 
      the value of the unitsCounted attribute in moduleData component is 
      frames, this attribute counts the total number of frames sent to the 
      interface since the start of the interval period. The start of the 
      interval period is captured in the startTime attribute. The count is 
      reset to zero when an accounting record is generated."
   DEFVAL     { 0 }
::= { mscFrUniDlciIntEntry 8 }

mscFrUniDlciEirIngressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the subnet since the 
      start of the interval period. If the value of the unitsCounted attribute 
      in moduleData component is frames, this attribute counts the 
      number of frames with the Discard Eligibility (DE) bit set sent to 
      the subnet since the start of the interval period. The start of the 
      interval period is captured in the startTime attribute. The count is 
      reset to zero when an accounting record is generated."
   DEFVAL     { 0 }
::= { mscFrUniDlciIntEntry 9 }

mscFrUniDlciEirEgressSegFrm OBJECT-TYPE
   SYNTAX     Unsigned32 (0..4294967295)
   ACCESS     read-only
   STATUS     mandatory
   DESCRIPTION
     "If the value of the unitsCounted attribute in moduleData component 
      is segments, this attribute counts the number of segments in frames 
      with the Discard Eligibility (DE) bit set sent to the interface since 
      the start of the interval period. If the value of the unitsCounted 
      attribute in moduleData component is frames, this attribute counts 
      the number of frames with the Discard Eligibility (DE) bit set sent 
      to the interface since the start of the interval period. The start of the 
      interval period is captured in the startTime attribute. The count is 
      reset to zero when an accounting record is generated."
   DEFVAL     { 0 }
::= { mscFrUniDlciIntEntry 10 }

mscFrUniDlciDiscardedSegFrm OBJECT-TYPE
   SYNTAX     Unsigned32 (0..4294967295)
   ACCESS     read-only
   STATUS     mandatory
   DESCRIPTION
     "If the value of the unitsCounted attribute in moduleData component 
      is segments, this attribute counts the number of segments in invalid 
      frames received from the interface and discarded at the DLCI. If the 
      value of the unitsCounted attribute in moduleData component is 
      frames, this attribute counts the number of invalid frames received 
      from the interface and discarded at the DLCI. Segments of frames 
      are counted since the start of the interval period. The count is reset 
      to zero when an accounting record is generated. The count is a sum 
      of segments in frames or frames discarded due to the number of 
      octets in the information field greater than the subscribed maximum 
      or equal to 0, due to aBit turned off, or due to rate enforcement."
   DEFVAL     { 0 }
::= { mscFrUniDlciIntEntry 11 }

mscFrUniDlciCirPresentObs OBJECT-TYPE
   SYNTAX     Unsigned32 (0..4294967295)
   ACCESS     read-only
   STATUS     obsolete
   DESCRIPTION
     "This attribute has moved to the statistics subgroup. See cirPresent.."
   DEFVAL     { 0 }
::= { mscFrUniDlciIntEntry 12 }

mscFrUniDlciEirPresentObs OBJECT-TYPE
   SYNTAX     Unsigned32 (0..4294967295)
   ACCESS     read-only
   STATUS     obsolete
   DESCRIPTION
     "This attribute has moved to the statistics subgroup. See eirPresent."
   DEFVAL     { 0 }
::= { mscFrUniDlciIntEntry 13 }

mscFrUniDlciRateEnforcementPresent OBJECT-TYPE
   SYNTAX     INTEGER  {
                 off(0),
                 on(1) }
   ACCESS     read-only
   STATUS     obsolete
   DESCRIPTION
     "This attribute is obsolete. See the provisionable rateEnforcement 
      attribute."
   DEFVAL     { off }
::= { mscFrUniDlciIntEntry 14 }

mscFrUniDlciRateAdaptationPresent OBJECT-TYPE
   SYNTAX     INTEGER  {
                 off(0),
                 on(1) }
   ACCESS     read-only
   STATUS     obsolete
   DESCRIPTION
     "This attribute is obsolete. See the provisionable rateAdaptation 
      attribute."
   DEFVAL     { off }
::= { mscFrUniDlciIntEntry 15 }

mscFrUniDlciLocalRateAdaptOccurred OBJECT-TYPE
   SYNTAX     INTEGER  {
                 no(0),
                 yes(1) }
   ACCESS     read-only
   STATUS     mandatory
   DESCRIPTION
     "This attribute indicates whether rate adaptation has occurred on this 
      user Data Link Connection on this Frame Relay interface. The value 
      is reset to no when an accounting record is generated."
   DEFVAL     { no }
::= { mscFrUniDlciIntEntry 16 }

mscFrUniDlciCallReferenceNumber OBJECT-TYPE
   SYNTAX     Hex (0..16777215)
   ACCESS     read-only
   STATUS     obsolete
   DESCRIPTION
     "This attribute is obsoleted and replaced by callRefNumber."
   DEFVAL     { 0 }
::= { mscFrUniDlciIntEntry 17 }

mscFrUniDlciElapsedDifference OBJECT-TYPE
   SYNTAX     Unsigned32 (0..4294967295)
   ACCESS     read-only
   STATUS     mandatory
   DESCRIPTION
     "This attribute indicates the elapsed time representing the period of 
      this interval data. It is elapsed time in 0.1 second increments since 
      the call started."
   DEFVAL     { 0 }
::= { mscFrUniDlciIntEntry 18 }

mscFrUniDlciCallRefNumber OBJECT-TYPE
   SYNTAX     Unsigned32 (0..4294967295)
   ACCESS     read-only
   STATUS     mandatory
   DESCRIPTION
     "This attribute indicates the call reference number which is a unique 
      number generated by the switch.The same Call Reference Number 
      is stored in the interval data (accounting record) at both ends of the 
      call. It can be used as one of the attributes in matching duplicate 
      records generated at each end of the call."
   DEFVAL     { 0 }
::= { mscFrUniDlciIntEntry 20 }


-- FrUni/n Dlci/n DirectCall 
-- FrNni/n Dlci/n DirectCall 
-- This component defines direct call options for calls issued without 
-- operator intervention. Connection is complete and can be initiated 
-- automatically. Frequency of connection tries is controlled by retry 
-- timer.

mscFrUniDlciDc OBJECT IDENTIFIER ::= { mscFrUniDlci 2 }



mscFrUniDlciDcRowStatusTable OBJECT-TYPE
   SYNTAX     SEQUENCE OF MscFrUniDlciDcRowStatusEntry
   ACCESS     not-accessible
   STATUS     mandatory
   DESCRIPTION
     "This entry controls the addition and deletion of 
      mscFrUniDlciDc components."
::= { mscFrUniDlciDc 1 }

mscFrUniDlciDcRowStatusEntry OBJECT-TYPE
   SYNTAX     MscFrUniDlciDcRowStatusEntry
   ACCESS     not-accessible
   STATUS     mandatory
   DESCRIPTION
     "A single entry in the table represents a single 
      mscFrUniDlciDc component."
   INDEX {
      mscFrUniIndex,
      mscFrUniDlciIndex,
      mscFrUniDlciDcIndex }
::= { mscFrUniDlciDcRowStatusTable 1 }

MscFrUniDlciDcRowStatusEntry ::= SEQUENCE {
   mscFrUniDlciDcRowStatus
      RowStatus,
   mscFrUniDlciDcComponentName
      DisplayString,
   mscFrUniDlciDcStorageType
      StorageType,
   mscFrUniDlciDcIndex
      NonReplicated }

mscFrUniDlciDcRowStatus OBJECT-TYPE
   SYNTAX     RowStatus 
   ACCESS     read-only
   STATUS     mandatory
   DESCRIPTION
     "This variable is used as the basis for SNMP naming of
      mscFrUniDlciDc components.
      These components cannot be added nor deleted."
::= { mscFrUniDlciDcRowStatusEntry 1 }

mscFrUniDlciDcComponentName OBJECT-TYPE
   SYNTAX     DisplayString 
   ACCESS     read-only
   STATUS     mandatory
   DESCRIPTION
     "This variable provides the component's string name for
      use with the ASCII Console Interface"
::= { mscFrUniDlciDcRowStatusEntry 2 }

mscFrUniDlciDcStorageType OBJECT-TYPE
   SYNTAX     StorageType 
   ACCESS     read-only
   STATUS     mandatory
   DESCRIPTION
     "This variable represents the storage type value for the
      mscFrUniDlciDc tables."
::= { mscFrUniDlciDcRowStatusEntry 4 }

mscFrUniDlciDcIndex OBJECT-TYPE
   SYNTAX     NonReplicated 
   ACCESS     not-accessible
   STATUS     mandatory
   DESCRIPTION
     "This variable represents the index for the mscFrUniDlciDc tables."
::= { mscFrUniDlciDcRowStatusEntry 10 }

mscFrUniDlciDcOptionsTable OBJECT-TYPE
   SYNTAX     SEQUENCE OF MscFrUniDlciDcOptionsEntry
   ACCESS     not-accessible
   STATUS     mandatory
   DESCRIPTION
     "This group defines attributes associated with a direct call. It defines 
      connection in terms of path and call option parameters. This 
      connection can be permanent (PVC), switched (SVC), or switched 
      permanent (SPVC). It can have four facilities:
      - 						CCITT Facilities
      - DTE Facilities
      - National Facilities
      - International Facilities
      The total number of bytes of facilities including the facility codes 
      and all of the facility data from all of the four classes of facilities 
      must not exceed 512 bytes."
::= { mscFrUniDlciDc 10 }

mscFrUniDlciDcOptionsEntry OBJECT-TYPE
   SYNTAX     MscFrUniDlciDcOptionsEntry
   ACCESS     not-accessible
   STATUS     mandatory
   DESCRIPTION
     "An entry in the mscFrUniDlciDcOptionsTable."
   INDEX {
      mscFrUniIndex,
      mscFrUniDlciIndex,
      mscFrUniDlciDcIndex }
::= { mscFrUniDlciDcOptionsTable 1 }

MscFrUniDlciDcOptionsEntry ::= SEQUENCE {
   mscFrUniDlciDcRemoteNpi
      INTEGER,
   mscFrUniDlciDcRemoteDna
      DigitString,
   mscFrUniDlciDcRemoteDlci
      Unsigned32,
   mscFrUniDlciDcType
      INTEGER,
   mscFrUniDlciDcTransferPriority
      INTEGER,
   mscFrUniDlciDcDiscardPriority
      INTEGER,
   mscFrUniDlciDcDeDiscardPriority
      INTEGER,
   mscFrUniDlciDcDataPath
      INTEGER,
   mscFrUniDlciDcCugIndex
      Unsigned32,
   mscFrUniDlciDcCugType
      INTEGER,
   mscFrUniDlciDcMapIpCosToFrQos
      INTEGER }

mscFrUniDlciDcRemoteNpi OBJECT-TYPE
   SYNTAX     INTEGER  {
                 x121(0),
                 e164(1) }
   ACCESS     read-write
   STATUS     mandatory
   DESCRIPTION
     "This attribute specifies the Numbering Plan Indicator (NPI) of the 
      remoteDna."
   DEFVAL     { x121 }
::= { mscFrUniDlciDcOptionsEntry 3 }

mscFrUniDlciDcRemoteDna OBJECT-TYPE
   SYNTAX     DigitString (SIZE (1..15))
   ACCESS     read-write
   STATUS     mandatory
   DESCRIPTION
     "This attribute specifies the Data Network Address (DNA) of the 
      service at the remote end of the DLCI. This is the called 
      (destination) DCE address (DNA) of this PVC."
::= { mscFrUniDlciDcOptionsEntry 4 }

mscFrUniDlciDcRemoteDlci OBJECT-TYPE
   SYNTAX     Unsigned32 (16..1007)
   ACCESS     read-write
   STATUS     mandatory
   DESCRIPTION
     "This attribute specifies the remote DLCI of the PVC connection."
::= { mscFrUniDlciDcOptionsEntry 5 }

mscFrUniDlciDcType OBJECT-TYPE
   SYNTAX     INTEGER  {
                 permanentMaster(1),
                 permanentSlave(2),
                 permanentBackupSlave(3),
                 permanentSlaveWithBackup(4),
                 spvcMaster(5),
                 spvcSlave(6),
                 spvcBackupSlave(7),
                 spvcSlaveWithBackup(8) }
   ACCESS     read-write
   STATUS     mandatory
   DESCRIPTION
     "This attribute specifies the type of VC call.
      
      If the value is set to permanentMaster, then a permanent 
      connection will be established between two ends. The remote end 
      must be defined as a permanentSlave, permanentBackupSlave, or 
      permanentSlaveWithBackup. The connection cannot be established 
      if the remote end is defined as anything else. The end defined as 
      permanentMaster always initiates the calls. It attempts to call once 
      per minute.
      
      If the value is set to permanentSlave then a permanent connection 
      will be established between two ends. The remote end must be 
      defined as a permanentMaster. The connection cannot be 
      established if the remote end is defined as anything else. The 
      permanentSlave end attempts to call once per minute.
      
      If the value is set to permanentSlaveWithBackup then a permanent 
      connection will be established between the two ends. The remote 
      end must be defined as a permanentMaster. The connection cannot 
      be established if the remote interface is defined as anything else. 
      The permanentSlaveWithBackup attempts to call once per minute. 
      When type is set to permanentSlaveWithBackup, the connection is 
      cleared if the interface becomes unavailable. This enables a retry of 
      the connection which can be redirected to the 
      permanentBackupSlave.
      
      If the value is set to permanentBackupSlave then a permanent 
      connection is established between the two ends only if the 
      permanentMaster end is disconnected from the 
      permanentSlaveWithBackup end and a backup call is established 
      by the call redirection system. If the permanentSlaveWithBackup 
      interface becomes available again, the permanentBackupSlave end 
      is disconnected and the permanentSlaveWithBackup end is 
      reconnected to the permanentMaster end. The 
      permanentBackupSlave end does not try to establish a call.
      
      If the value is set to spvcMaster, then a permanent connection is 
      established between two ends, with resiliency at the NNI), if the 
      connection transits across two or more networks. The remote end, 
      which may be in the same network, or an external network that is 
      reachable via Frame Relay NNIs, must be defined as either a 
      spvcSlave, spvcBackupSlave or spvcSlaveWithBackup. The 
      connection cannot be established if the remote end is defined as 
      anything else. The end defined as spvcMaster always initiates the 
      call. It attempts to call once per minute. The call is attempted by the 
      spvcMaster and accepted by the remote end only if all of the 
      following conditions are satisfied, at both ends:
      1. The physical layer must be operational.
      2. The LMI procedures must be in normalCondition (that is, no 
      service affecting condition).
      3. If the LMI side attribute is provisioned to both, the A-bit 
      received from the interface must be Active. If the LMI side 
      attribute is not provisioned to both, this condition does not 
      apply.
      
      After a call is cleared, the spvcMaster end attempts to retry the call 
      according to the rule for the clear cause. If the call is cleared or 
      rejected due to the failure of one of the three conditions indicated 
      above, or due to unavailability of resources along any point in the 
      connection path, the call will be retried after 60 seconds. For all 
      other causes, such as loss of service at an NNI, the call will be 
      retried immediately.
      
      If the value is set to spvcSlave then an SPVC connection is 
      established between two ends. The remote end must be defined as 
      an spvcMaster. The connection cannot be established if the remote 
      end is defined as anything else. The spvcSlave end does not attempt 
      to call.
      
      If the value is set to spvcSlaveWithBackup then a SPVC connection 
      is established between the two ends. The remote end must be 
      defined as an spvcMaster. The connection cannot be established if 
      the remote interface end is defined as anything else. Unlike a 
      permanentSlaveWithBackup end, the spvcSlaveWithBackup end 
      does not attempt to call. If the value is set to spvcSlaveWithBackup, 
      the connection is cleared if the interface becomes unavailable. This 
      enables a retry of the connection by the spvcMaster end, which may 
      be redirected to an end that is set to spvcBackupSlave.
      
      If the value is set to spvcBackupSlave then an SPVC connection is 
      established between the two ends only if the spvcMaster end is 
      disconnected from the spvcSlaveWithBackup end, and a backup 
      call is redirected by the call redirection system. Unlike the PVC 
      connection, if the spvcSlaveWithBackup interface becomes 
      available again, the spvcBackupSlave end is not disconnected and 
      the spvcSlaveWithBackup end is not reconnected to the spvcMaster 
      end. Neither the spvcBackupSlave nor the spvcSlaveWithBackup 
      ends try to establish an SPVC call."
   DEFVAL     { permanentMaster }
::= { mscFrUniDlciDcOptionsEntry 6 }

mscFrUniDlciDcTransferPriority OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 useDnaDefTP(255) }
   ACCESS     read-write
   STATUS     mandatory
   DESCRIPTION
     "This attribute specifies the transfer priority to the local network for 
      the outgoing calls using this particular DLCI. It overrides the 
      defaultTransferPriority provisioned in its associated Dna 
      component.
      
      The transfer priority is a preference configured for an application 
      according to its delay-sensitivity requirement. Frames with higher 
      transfer priority are served by the network before the frames with 
      lower priority. The transfer priority standard is defined to have 16 
      levels from 0 to 15.
      
      Each transfer priority n, where n is the transfer priority index, has a 
      default setting for routing class of service (multimedia, delay, or 
      throughput) and Frame Relay egress queue (depending on the 
      number of supported egress queues on the remote end interface).
      These settings are specified by the routingClassOfService and 
      emissionPriority attributes provisioned under the Mod Frs DprsNet 
      Tpm/n component.
      
      Specifying useDnaDefTP means using the value given by 
      defaultTransferPriority in the associated Dna for this DLCI."
   DEFVAL     { useDnaDefTP }
::= { mscFrUniDlciDcOptionsEntry 9 }

mscFrUniDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Under congestion conditions, traffic with 
      normal priority is discarded before traffic with high priority. The 
      Dna default value (provisioned by outDefaultPriority) is taken if 
      this attribute is set to the value useDnaDefPriority."
   DEFVAL     { useDnaDefPriority }
::= { mscFrUniDlciDcOptionsEntry 10 }

mscFrUniDlciDcDeDiscardPriority OBJECT-TYPE
   SYNTAX     INTEGER  {
                 lowest(0),
                 determinedByDiscardPriority(1) }
   ACCESS     read-write
   STATUS     mandatory
   DESCRIPTION
     "This attribute specifies whether the discardPriority applies to DE 
      frames for this DLCI.
      
      When set to determinedByDiscardPriority, traffic with DE bit set 
      will be discarded according to the setting of the discardPriority.
      
      When set to lowest, all traffic with DE bit set is treated the same and 
      is sent to the subnet at the lowest discard priority."
   DEFVAL     { determinedByDiscardPriority }
::= { mscFrUniDlciDcOptionsEntry 11 }

mscFrUniDlciDcDataPath OBJECT-TYPE
   SYNTAX     INTEGER  {
                 dprsOnly(0),
                 dprsMcsOnly(1),
                 dprsMcsFirst(2),
                 useDnaValue(3) }
   ACCESS     read-write
   STATUS     mandatory
   DESCRIPTION
     "This attribute specifies the data path to be used by Virtual Circuits 
      on this interface. The value of the dataPath attribute in the Dna 
      component is overridden by this attribute if the value is not 
      useDnaValue.
      
      This value applies to the connection after data transfer state is 
      reached. All the data and control traffic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - The dynamic packet routing system is used.
      
      dprsMcsOnly - The DPRS Multi-Service Cut-Through Switching 
      path is used.
      
      dprsMcsFirst - The DPRS Multi-Service Cut-Through Switching 
      path is used if it is available. If it is not available, dprsOnly is used.
      
      useDnaValue - The routing system used is based on the value 
      provisioned in the Dna component."
   DEFVAL     { useDnaValue }
::= { mscFrUniDlciDcOptionsEntry 12 }

mscFrUniDlciDcCugIndex OBJECT-TYPE
   SYNTAX     Unsigned32 (0..255)
   ACCESS     read-write
   STATUS     mandatory
   DESCRIPTION
     "This attribute specifies the CUG index which is to be signalled in 
      PVC and SPVC call requests to the remote end.
      
      The type of CUG signalling is defined in attribute cugType in this 
      component."
   DEFVAL     { 0 }
::= { mscFrUniDlciDcOptionsEntry 13 }

mscFrUniDlciDcCugType OBJECT-TYPE
   SYNTAX     INTEGER  {
                 doNotSignal(0),
                 cug(3),
                 cugOa(9) }
   ACCESS     read-write
   STATUS     mandatory
   DESCRIPTION
     "This attribute specifies the type of CUG signalling to be used in 
      PVC and SPVC call requests. Index of CUG to be used is defined in 
      attribute cugIndex in this component.
      
      Possible values are:
      cug - signal CUG
      cugOa - signal CUG with outgoing access
      doNotSignal - no CUG in call request"
   DEFVAL     { doNotSignal }
::= { mscFrUniDlciDcOptionsEntry 14 }

mscFrUniDlciDcMapIpCosToFrQos OBJECT-TYPE
   SYNTAX     INTEGER  {
                 no(0),
                 yes(1) }
   ACCESS     read-write
   STATUS     mandatory
   DESCRIPTION
     "This attribute specifies whether an IP TOS value is mapped to an 
      FR QOS. The mapping used is provisioned in the Mod Frs 
      IpCosToFrQos component.
      
      When this attribute is set to yes, at Frame Relay egress, the IP TOS 
      byte in each frame is checked. The TOS value determines the egress 
      emission queue and the discard priority for that frame.
      
      When this attribute is set to no, FR QOS is determined by the 
      provisioned discard priority and transfer priority."
   DEFVAL     { no }
::= { mscFrUniDlciDcOptionsEntry 15 }

mscFrUniDlciDcNfaTable OBJECT-TYPE
   SYNTAX     SEQUENCE OF MscFrUniDlciDcNfaEntry
   ACCESS     not-accessible
   STATUS     obsolete
   DESCRIPTION
     "This is the i'th National facility required for this direct call. Within 
      the provisioning system, the user specifies the facility code along 
      with the facility parameters. The facility is represented internally as 
      a hexadecimal string following the X.25 ITU-T representation for 
      facility data.
      
      Two explicit attributes discardPriority and pathSensitivity are 
      created to replace H.01 and H.30 in the group 
      VcsDirectCallOptionsProv of this file. The migrate escape here 
      (DcComponent::migrateFaxEscape) propagates the old provisioning 
      data under H.01 and H.30 into discardPriority and transferPriority. 
      
      The rule of the above propagation are: 0 in H.01 is equivalent to 
      discardPriority 0; 1 in H.01 is equivalent to discardPriority 1. And 0 
      in H.30 is equivalent to transferPriority throughput; 1 in H.30 is 
      equivalent to pathSensitivity delay.
      
      Please refer to discardPriority and pathSensitivity for more 
      information on how to use them."
::= { mscFrUniDlciDc 202 }

mscFrUniDlciDcNfaEntry OBJECT-TYPE
   SYNTAX     MscFrUniDlciDcNfaEntry
   ACCESS     not-accessible
   STATUS     obsolete
   DESCRIPTION
     "An entry in the mscFrUniDlciDcNfaTable."
   INDEX {
      mscFrUniIndex,
      mscFrUniDlciIndex,
      mscFrUniDlciDcIndex,
      mscFrUniDlciDcNfaIndex }
::= { mscFrUniDlciDcNfaTable 1 }

MscFrUniDlciDcNfaEntry ::= SEQUENCE {
   mscFrUniDlciDcNfaIndex
      Integer32,
   mscFrUniDlciDcNfaValue
      HexString,
   mscFrUniDlciDcNfaRowStatus
      RowStatus }

mscFrUniDlciDcNfaIndex OBJECT-TYPE
   SYNTAX     Integer32 (1 | 48)
   ACCESS     not-accessible
   STATUS     obsolete
   DESCRIPTION
     "This variable represents the index for the mscFrUniDlciDcNfaTable."
::= { mscFrUniDlciDcNfaEntry 1 }

mscFrUniDlciDcNfaValue OBJECT-TYPE
   SYNTAX     HexString (SIZE (0..128))
   ACCESS     read-write
   STATUS     obsolete
   DESCRIPTION
     "This variable represents an individual value for the
      mscFrUniDlciDcNfaTable."
::= { mscFrUniDlciDcNfaEntry 2 }

mscFrUniDlciDcNfaRowStatus OBJECT-TYPE
   SYNTAX     RowStatus 
   ACCESS     write-only
   STATUS     obsolete
   DESCRIPTION
     "This variable is used to control the addition and deletion 
      of individual values of the mscFrUniDlciDcNfaTable."
::= { mscFrUniDlciDcNfaEntry 3 }


-- This component defines attributes collected by Frame Relay Vc.

mscFrUniDlciVc OBJECT IDENTIFIER ::= { mscFrUniDlci 3 }



mscFrUniDlciVcRowStatusTable OBJECT-TYPE
   SYNTAX     SEQUENCE OF MscFrUniDlciVcRowStatusEntry
   ACCESS     not-accessible
   STATUS     mandatory
   DESCRIPTION
     "This entry controls the addition and deletion of 
      mscFrUniDlciVc components."
::= { mscFrUniDlciVc 1 }

mscFrUniDlciVcRowStatusEntry OBJECT-TYPE
   SYNTAX     MscFrUniDlciVcRowStatusEntry
   ACCESS     not-accessible
   STATUS     mandatory
   DESCRIPTION
     "A single entry in the table represents a single 
      mscFrUniDlciVc component."
   INDEX {
      mscFrUniIndex,
      mscFrUniDlciIndex,
      mscFrUniDlciVcIndex }
::= { mscFrUniDlciVcRowStatusTable 1 }

MscFrUniDlciVcRowStatusEntry ::= SEQUENCE {
   mscFrUniDlciVcRowStatus
      RowStatus,
   mscFrUniDlciVcComponentName
      DisplayString,
   mscFrUniDlciVcStorageType
      StorageType,
   mscFrUniDlciVcIndex
      NonReplicated }

mscFrUniDlciVcRowStatus OBJECT-TYPE
   SYNTAX     RowStatus 
   ACCESS     read-only
   STATUS     mandatory
   DESCRIPTION
     "This variable is used as the basis for SNMP naming of
      mscFrUniDlciVc components.
      These components cannot be added nor deleted."
::= { mscFrUniDlciVcRowStatusEntry 1 }

mscFrUniDlciVcComponentName OBJECT-TYPE
   SYNTAX     DisplayString 
   ACCESS     read-only
   STATUS     mandatory
   DESCRIPTION
     "This variable provides the component's string name for
      use with the ASCII Console Interface"
::= { mscFrUniDlciVcRowStatusEntry 2 }

mscFrUniDlciVcStorageType OBJECT-TYPE
   SYNTAX     StorageType 
   ACCESS     read-only
   STATUS     mandatory
   DESCRIPTION
     "This variable represents the storage type value for the
      mscFrUniDlciVc tables."
::= { mscFrUniDlciVcRowStatusEntry 4 }

mscFrUniDlciVcIndex OBJECT-TYPE
   SYNTAX     NonReplicated 
   ACCESS     not-accessible
   STATUS     mandatory
   DESCRIPTION
     "This variable represents the index for the mscFrUniDlciVc tables."
::= { mscFrUniDlciVcRowStatusEntry 10 }

mscFrUniDlciVcCadTable OBJECT-TYPE
   SYNTAX     SEQUENCE OF MscFrUniDlciVcCadEntry
   ACCESS     not-accessible
   STATUS     mandatory
   DESCRIPTION
     "This group represents operational call data related to Frame Relay 
      Vc. It can be displayed only for Frame Relay Vc which is created by 
      application."
::= { mscFrUniDlciVc 10 }

mscFrUniDlciVcCadEntry OBJECT-TYPE
   SYNTAX     MscFrUniDlciVcCadEntry
   ACCESS     not-accessible
   STATUS     mandatory
   DESCRIPTION
     "An entry in the mscFrUniDlciVcCadTable."
   INDEX {
      mscFrUniIndex,
      mscFrUniDlciIndex,
      mscFrUniDlciVcIndex }
::= { mscFrUniDlciVcCadTable 1 }

MscFrUniDlciVcCadEntry ::= SEQUENCE {
   mscFrUniDlciVcType
      INTEGER,
   mscFrUniDlciVcState
      INTEGER,
   mscFrUniDlciVcPreviousState
      INTEGER,
   mscFrUniDlciVcDiagnosticCode
      Unsigned32,
   mscFrUniDlciVcPreviousDiagnosticCode
      Unsigned32,
   mscFrUniDlciVcCalledNpi
      INTEGER,
   mscFrUniDlciVcCalledDna
      DigitString,
   mscFrUniDlciVcCalledLcn
      Unsigned32,
   mscFrUniDlciVcCallingNpi
      INTEGER,
   mscFrUniDlciVcCallingDna
      DigitString,
   mscFrUniDlciVcCallingLcn
      Unsigned32,
   mscFrUniDlciVcAccountingEnabled
      INTEGER,
   mscFrUniDlciVcFastSelectCall
      INTEGER,
   mscFrUniDlciVcPathReliability
      INTEGER,
   mscFrUniDlciVcAccountingEnd
      INTEGER,
   mscFrUniDlciVcPriority
      INTEGER,
   mscFrUniDlciVcSegmentSize
      Unsigned32,
   mscFrUniDlciVcMaxSubnetPktSize
      Unsigned32,
   mscFrUniDlciVcRcosToNetwork
      INTEGER,
   mscFrUniDlciVcRcosFromNetwork
      INTEGER,
   mscFrUniDlciVcEmissionPriorityToNetwork
      INTEGER,
   mscFrUniDlciVcEmissionPriorityFromNetwork
      INTEGER,
   mscFrUniDlciVcDataPath
      AsciiString }

mscFrUniDlciVcType OBJECT-TYPE
   SYNTAX     INTEGER  {
                 svc(0),
                 pvc(1),
                 spvc(2),
                 frf10spvc(3) }
   ACCESS     read-only
   STATUS     mandatory
   DESCRIPTION
     "This attribute displays the type of call, pvc,svc,spvc or frf10spvc."
::= { mscFrUniDlciVcCadEntry 1 }

mscFrUniDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscFrUniDlciVcCadEntry 2 }

mscFrUniDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscFrUniDlciVcCadEntry 3 }

mscFrUniDlciVcDiagnosticCode OBJECT-TYPE
   SYNTAX     Unsigned32 (0..255)
   ACCESS     read-only
   STATUS     mandatory
   DESCRIPTION
     "This attribute displays the internal substate of call control. It is used 
      to further refine state of call processing."
::= { mscFrUniDlciVcCadEntry 4 }

mscFrUniDlciVcPreviousDiagnosticCode OBJECT-TYPE
   SYNTAX     Unsigned32 (0..255)
   ACCESS     read-only
   STATUS     mandatory
   DESCRIPTION
     "This attribute displays the internal substate of call control. It is used 
      to further refine state of call processing."
::= { mscFrUniDlciVcCadEntry 5 }

mscFrUniDlciVcCalledNpi OBJECT-TYPE
   SYNTAX     INTEGER  {
                 x121(0),
                 e164(1) }
   ACCESS     read-only
   STATUS     mandatory
   DESCRIPTION
     "This attribute displays the Numbering Plan Indicator (NPI) of the 
      called end."
::= { mscFrUniDlciVcCadEntry 6 }

mscFrUniDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscFrUniDlciVcCadEntry 7 }

mscFrUniDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscFrUniDlciVcCadEntry 8 }

mscFrUniDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { mscFrUniDlciVcCadEntry 9 }

mscFrUniDlciVcCallingDna OBJECT-TYPE
   SYNTAX     DigitString (SIZE (1..15))
   ACCESS     read-only
   STATUS     mandatory
   DESCRIPTION
     "This attribute displays the Data Network Address (Dna) of the 
      calling end."
::= { mscFrUniDlciVcCadEntry 10 }

mscFrUniDlciVcCallingLcn OBJECT-TYPE
   SYNTAX     Unsigned32 (1..65535)
   ACCESS     read-only
   STATUS     mandatory
   DESCRIPTION
     "This attribute displays the Logical Channel Number of the calling 
      end."
::= { mscFrUniDlciVcCadEntry 11 }

mscFrUniDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscFrUniDlciVcCadEntry 12 }

mscFrUniDlciVcFastSelectCall OBJECT-TYPE
   SYNTAX     INTEGER  {
                 no(0),
                 yes(1) }
   ACCESS     read-only
   STATUS     mandatory
   DESCRIPTION
     "This attribute displays that this is a fast select call."
::= { mscFrUniDlciVcCadEntry 13 }

mscFrUniDlciVcPathReliability OBJECT-TYPE
   SYNTAX     INTEGER  {
                 high(0),
                 normal(1) }
   ACCESS     read-only
   STATUS     mandatory
   DESCRIPTION
     "This attribute displays the path reliability."
::= { mscFrUniDlciVcCadEntry 19 }

mscFrUniDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscFrUniDlciVcCadEntry 20 }

mscFrUniDlciVcPriority OBJECT-TYPE
   SYNTAX     INTEGER  {
                 normal(0),
                 high(1) }
   ACCESS     read-only
   STATUS     mandatory
   DESCRIPTION
     "This attribute displays whether the call is a normal or a high 
      priority call."
::= { mscFrUniDlciVcCadEntry 21 }

mscFrUniDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscFrUniDlciVcCadEntry 22 }

mscFrUniDlciVcMaxSubnetPktSize OBJECT-TYPE
   SYNTAX     Unsigned32 (0..4096)
   ACCESS     read-only
   STATUS     mandatory
   DESCRIPTION
     "This attribute indicates the maximum packet size allowed on the Vc."
::= { mscFrUniDlciVcCadEntry 27 }

mscFrUniDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscFrUniDlciVcCadEntry 28 }

mscFrUniDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscFrUniDlciVcCadEntry 29 }

mscFrUniDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscFrUniDlciVcCadEntry 30 }

mscFrUniDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscFrUniDlciVcCadEntry 31 }

mscFrUniDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscFrUniDlciVcCadEntry 32 }

mscFrUniDlciVcIntdTable OBJECT-TYPE
   SYNTAX     SEQUENCE OF MscFrUniDlciVcIntdEntry
   ACCESS     not-accessible
   STATUS     mandatory
   DESCRIPTION
     "This group defines display of interval data collected by Vc. Data in 
      this group is variable and may depend on time when this display 
      command is issued."
::= { mscFrUniDlciVc 11 }

mscFrUniDlciVcIntdEntry OBJECT-TYPE
   SYNTAX     MscFrUniDlciVcIntdEntry
   ACCESS     not-accessible
   STATUS     mandatory
   DESCRIPTION
     "An entry in the mscFrUniDlciVcIntdTable."
   INDEX {
      mscFrUniIndex,
      mscFrUniDlciIndex,
      mscFrUniDlciVcIndex }
::= { mscFrUniDlciVcIntdTable 1 }

MscFrUniDlciVcIntdEntry ::= SEQUENCE {
   mscFrUniDlciVcCallReferenceNumber
      Hex,
   mscFrUniDlciVcElapsedTimeTillNow
      Unsigned32,
   mscFrUniDlciVcSegmentsRx
      Unsigned32,
   mscFrUniDlciVcSegmentsSent
      Unsigned32,
   mscFrUniDlciVcStartTime
      EnterpriseDateAndTime,
   mscFrUniDlciVcCallReferenceNumberDecimal
      Unsigned32 }

mscFrUniDlciVcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscFrUniDlciVcIntdEntry 1 }

mscFrUniDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscFrUniDlciVcIntdEntry 2 }

mscFrUniDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscFrUniDlciVcIntdEntry 3 }

mscFrUniDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscFrUniDlciVcIntdEntry 4 }

mscFrUniDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscFrUniDlciVcIntdEntry 5 }

mscFrUniDlciVcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscFrUniDlciVcIntdEntry 7 }

mscFrUniDlciVcFrdTable OBJECT-TYPE
   SYNTAX     SEQUENCE OF MscFrUniDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscFrUniDlciVc 12 }

mscFrUniDlciVcFrdEntry OBJECT-TYPE
   SYNTAX     MscFrUniDlciVcFrdEntry
   ACCESS     not-accessible
   STATUS     mandatory
   DESCRIPTION
     "An entry in the mscFrUniDlciVcFrdTable."
   INDEX {
      mscFrUniIndex,
      mscFrUniDlciIndex,
      mscFrUniDlciVcIndex }
::= { mscFrUniDlciVcFrdTable 1 }

MscFrUniDlciVcFrdEntry ::= SEQUENCE {
   mscFrUniDlciVcFrmCongestedToSubnet
      Unsigned32,
   mscFrUniDlciVcCannotForwardToSubnet
      Unsigned32,
   mscFrUniDlciVcNotDataXferToSubnet
      Unsigned32,
   mscFrUniDlciVcOutOfRangeFrmFromSubnet
      Unsigned32,
   mscFrUniDlciVcCombErrorsFromSubnet
      Unsigned32,
   mscFrUniDlciVcDuplicatesFromSubnet
      Unsigned32,
   mscFrUniDlciVcNotDataXferFromSubnet
      Unsigned32,
   mscFrUniDlciVcFrmLossTimeouts
      Unsigned32,
   mscFrUniDlciVcOoSeqByteCntExceeded
      Unsigned32,
   mscFrUniDlciVcPeakOoSeqPktCount
      Unsigned32,
   mscFrUniDlciVcPeakOoSeqFrmForwarded
      Unsigned32,
   mscFrUniDlciVcSendSequenceNumber
      Unsigned32,
   mscFrUniDlciVcPktRetryTimeouts
      Unsigned32,
   mscFrUniDlciVcPeakRetryQueueSize
      Unsigned32,
   mscFrUniDlciVcSubnetRecoveries
      Unsigned32,
   mscFrUniDlciVcOoSeqPktCntExceeded
      Unsigned32,
   mscFrUniDlciVcPeakOoSeqByteCount
      Unsigned32 }

mscFrUniDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscFrUniDlciVcFrdEntry 2 }

mscFrUniDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscFrUniDlciVcFrdEntry 3 }

mscFrUniDlciVcNotDataXferToSubnet OBJECT-TYPE
   SYNTAX     Unsigned32 (0..5000)
   ACCESS     read-only
   STATUS     mandatory
   DESCRIPTION
     "This attribute records the number of frames from link discarded 
      when the Vc tries to recover from internal path failure."
::= { mscFrUniDlciVcFrdEntry 4 }

mscFrUniDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscFrUniDlciVcFrdEntry 5 }

mscFrUniDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscFrUniDlciVcFrdEntry 6 }

mscFrUniDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscFrUniDlciVcFrdEntry 7 }

mscFrUniDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { mscFrUniDlciVcFrdEntry 8 }

mscFrUniDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscFrUniDlciVcFrdEntry 9 }

mscFrUniDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscFrUniDlciVcFrdEntry 10 }

mscFrUniDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscFrUniDlciVcFrdEntry 11 }

mscFrUniDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscFrUniDlciVcFrdEntry 12 }

mscFrUniDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscFrUniDlciVcFrdEntry 13 }

mscFrUniDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscFrUniDlciVcFrdEntry 15 }

mscFrUniDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscFrUniDlciVcFrdEntry 16 }

mscFrUniDlciVcSubnetRecoveries OBJECT-TYPE
   SYNTAX     Unsigned32 (0..5000)
   ACCESS     read-only
   STATUS     mandatory
   DESCRIPTION
     "This attribute displays the number of successful Vc recovery 
      attempts."
::= { mscFrUniDlciVcFrdEntry 17 }

mscFrUniDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscFrUniDlciVcFrdEntry 19 }

mscFrUniDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscFrUniDlciVcFrdEntry 20 }

mscFrUniDlciVcDmepTable OBJECT-TYPE
   SYNTAX     SEQUENCE OF MscFrUniDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscFrUniDlciVc 417 }

mscFrUniDlciVcDmepEntry OBJECT-TYPE
   SYNTAX     MscFrUniDlciVcDmepEntry
   ACCESS     not-accessible
   STATUS     mandatory
   DESCRIPTION
     "An entry in the mscFrUniDlciVcDmepTable."
   INDEX {
      mscFrUniIndex,
      mscFrUniDlciIndex,
      mscFrUniDlciVcIndex,
      mscFrUniDlciVcDmepValue }
::= { mscFrUniDlciVcDmepTable 1 }

MscFrUniDlciVcDmepEntry ::= SEQUENCE {
   mscFrUniDlciVcDmepValue
      RowPointer }

mscFrUniDlciVcDmepValue OBJECT-TYPE
   SYNTAX     RowPointer 
   ACCESS     read-only
   STATUS     mandatory
   DESCRIPTION
     "This variable represents both the value and the index for the
      mscFrUniDlciVcDmepTable."
::= { mscFrUniDlciVcDmepEntry 1 }


-- FrUni/n Dlci/n ServiceParametersProv
-- This component contains the provisionable traffic control attributes 
-- for its parent Dlci component.

mscFrUniDlciSp OBJECT IDENTIFIER ::= { mscFrUniDlci 4 }



mscFrUniDlciSpRowStatusTable OBJECT-TYPE
   SYNTAX     SEQUENCE OF MscFrUniDlciSpRowStatusEntry
   ACCESS     not-accessible
   STATUS     mandatory
   DESCRIPTION
     "This entry controls the addition and deletion of 
      mscFrUniDlciSp components."
::= { mscFrUniDlciSp 1 }

mscFrUniDlciSpRowStatusEntry OBJECT-TYPE
   SYNTAX     MscFrUniDlciSpRowStatusEntry
   ACCESS     not-accessible
   STATUS     mandatory
   DESCRIPTION
     "A single entry in the table represents a single 
      mscFrUniDlciSp component."
   INDEX {
      mscFrUniIndex,
      mscFrUniDlciIndex,
      mscFrUniDlciSpIndex }
::= { mscFrUniDlciSpRowStatusTable 1 }

MscFrUniDlciSpRowStatusEntry ::= SEQUENCE {
   mscFrUniDlciSpRowStatus
      RowStatus,
   mscFrUniDlciSpComponentName
      DisplayString,
   mscFrUniDlciSpStorageType
      StorageType,
   mscFrUniDlciSpIndex
      NonReplicated }

mscFrUniDlciSpRowStatus OBJECT-TYPE
   SYNTAX     RowStatus 
   ACCESS     read-only
   STATUS     mandatory
   DESCRIPTION
     "This variable is used as the basis for SNMP naming of
      mscFrUniDlciSp components.
      These components cannot be added nor deleted."
::= { mscFrUniDlciSpRowStatusEntry 1 }

mscFrUniDlciSpComponentName OBJECT-TYPE
   SYNTAX     DisplayString 
   ACCESS     read-only
   STATUS     mandatory
   DESCRIPTION
     "This variable provides the component's string name for
      use with the ASCII Console Interface"
::= { mscFrUniDlciSpRowStatusEntry 2 }

mscFrUniDlciSpStorageType OBJECT-TYPE
   SYNTAX     StorageType 
   ACCESS     read-only
   STATUS     mandatory
   DESCRIPTION
     "This variable represents the storage type value for the
      mscFrUniDlciSp tables."
::= { mscFrUniDlciSpRowStatusEntry 4 }

mscFrUniDlciSpIndex OBJECT-TYPE
   SYNTAX     NonReplicated 
   ACCESS     not-accessible
   STATUS     mandatory
   DESCRIPTION
     "This variable represents the index for the mscFrUniDlciSp tables."
::= { mscFrUniDlciSpRowStatusEntry 10 }

mscFrUniDlciSpParmsTable OBJECT-TYPE
   SYNTAX     SEQUENCE OF MscFrUniDlciSpParmsEntry
   ACCESS     not-accessible
   STATUS     mandatory
   DESCRIPTION
     "This group contains the provisionable attributes for the Data Link 
      Connection Identifier. These attributes reflect the service parameters 
      specific to this instance of DLCI. The congestion control attributes 
      in this group are defined in T1.606 Addendum 1."
::= { mscFrUniDlciSp 11 }

mscFrUniDlciSpParmsEntry OBJECT-TYPE
   SYNTAX     MscFrUniDlciSpParmsEntry
   ACCESS     not-accessible
   STATUS     mandatory
   DESCRIPTION
     "An entry in the mscFrUniDlciSpParmsTable."
   INDEX {
      mscFrUniIndex,
      mscFrUniDlciIndex,
      mscFrUniDlciSpIndex }
::= { mscFrUniDlciSpParmsTable 1 }

MscFrUniDlciSpParmsEntry ::= SEQUENCE {
   mscFrUniDlciSpMaximumFrameSize
      Unsigned32,
   mscFrUniDlciSpRateEnforcement
      INTEGER,
   mscFrUniDlciSpCommittedInformationRate
      Gauge32,
   mscFrUniDlciSpCommittedBurstSize
      Gauge32,
   mscFrUniDlciSpExcessBurstSize
      Gauge32,
   mscFrUniDlciSpMeasurementInterval
      Unsigned32,
   mscFrUniDlciSpRateAdaptation
      INTEGER,
   mscFrUniDlciSpAccounting
      INTEGER,
   mscFrUniDlciSpRaSensitivity
      Unsigned32,
   mscFrUniDlciSpUpdateBCI
      INTEGER }

mscFrUniDlciSpMaximumFrameSize OBJECT-TYPE
   SYNTAX     Unsigned32 (1..8187)
   ACCESS     read-write
   STATUS     mandatory
   DESCRIPTION
     "This attribute specifies the maximum number of octets which may 
      be included in the information field. The frame relay header and 
      CRC octets are not included in this definition. This attribute 
      corresponds to the dN1 parameter described in the Vendor Forum 
      Specification."
   DEFVAL     { 2100 }
::= { mscFrUniDlciSpParmsEntry 1 }

mscFrUniDlciSpRateEnforcement OBJECT-TYPE
   SYNTAX     INTEGER  {
                 off(0),
                 on(1) }
   ACCESS     read-write
   STATUS     mandatory
   DESCRIPTION
     "This attribute specifies whether rate enforcement is in effect for this 
      user Data Link Connection on this Frame Relay interface. Turning 
      on rate enforcement means that CIR and DE=1 traffic will be 
      measured and enforced. Turning off rate enforcement means that all 
      frames from the user will be accepted and no modifications to the 
      frame with respect to the DE bit will be made."
   DEFVAL     { on }
::= { mscFrUniDlciSpParmsEntry 2 }

mscFrUniDlciSpCommittedInformationRate OBJECT-TYPE
   SYNTAX     Gauge32 (0..50000000)
   ACCESS     read-write
   STATUS     mandatory
   DESCRIPTION
     "This attribute specifies the committed information rate (CIR) in bits 
      per second (bit/s). When rateEnforcement is set to on, cir is the rate 
      at which the network agrees to transfer information under normal 
      conditions. This rate is measured over a measurement interval (t) 
      that is determined internally based on CIR and the committed burst 
      size (Bc). An exception to this occurs when CIR is provisioned to 
      be zero, in which case the measurement interval (t) must be 
      provisioned explicitly.
      
      This attribute is ignored when rateEnforcement is off. If 
      rateEnforcement is on and this attribute is 0, Bc must also be 0."
   DEFVAL     { 64000 }
::= { mscFrUniDlciSpParmsEntry 3 }

mscFrUniDlciSpCommittedBurstSize OBJECT-TYPE
   SYNTAX     Gauge32 (0..50000000)
   ACCESS     read-write
   STATUS     mandatory
   DESCRIPTION
     "This attribute specifies the committed burst size (Bc) in bits. bc is 
      the amount of data that a network agrees to transfer under normal 
      conditions over a measurement interval (t). Data marked DE=1 is 
      not accounted for in Bc.
      
      This attribute is ignored when rateEnforcement is off. If 
      rateEnforcement is on and this attribute is 0, cir must also be 0."
   DEFVAL     { 64000 }
::= { mscFrUniDlciSpParmsEntry 4 }

mscFrUniDlciSpExcessBurstSize OBJECT-TYPE
   SYNTAX     Gauge32 (0..50000000)
   ACCESS     read-write
   STATUS     mandatory
   DESCRIPTION
     "This attribute specifies the excess burst size (Be) in bits. Be is the 
      amount of uncommitted data that the network will attempt to deliver 
      over measurement interval T. Data marked DE=1 by the user or by 
      the network is accounted for here.
      
      CIR, Bc, and Be cannot all be zero when rateEnforcement is on."
   DEFVAL     { 0 }
::= { mscFrUniDlciSpParmsEntry 5 }

mscFrUniDlciSpMeasurementInterval OBJECT-TYPE
   SYNTAX     Unsigned32 (0..25500)
   ACCESS     read-write
   STATUS     mandatory
   DESCRIPTION
     "When cir and bc are zero and rateEnforcement is on, this attribute 
      must be provisioned to specify the time interval (in milliseconds) 
      over which rates and burst sizes are measured.
      
      When cir and bc are non-zero, the time interval is internally 
      calculated and is not shown. In that situation, this field is ignored, 
      and is not representative of the time interval.
      
      This attribute is ignored when rateEnforcement is off, or when cir 
      and bc are non-zero. If rateEnforcement is on and both cir and bc 
      are zero, this field must be non-zero."
   DEFVAL     { 0 }
::= { mscFrUniDlciSpParmsEntry 6 }

mscFrUniDlciSpRateAdaptation OBJECT-TYPE
   SYNTAX     INTEGER  {
                 off(0),
                 on(1),
                 eirOnly(2),
                 cirProportionate(3) }
   ACCESS     read-write
   STATUS     mandatory
   DESCRIPTION
     "This attribute specifies whether rate adaptation is in effect for this 
      user Data Link Connection on this Frame Relay interface. Rate 
      adaptation is a feature that, in periods of congestion, adapts the rate 
      at which the user is allowed to send data into the network to that 
      which the network is able to handle at that time. This pro-active 
      measure of handling congestion optimizes network resources by 
      causing the ingress to discard frames that would otherwise be 
      discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be set to on eirOnly or cirProportionate if 
      rateEnforcement is turned on."
   DEFVAL     { off }
::= { mscFrUniDlciSpParmsEntry 7 }

mscFrUniDlciSpAccounting OBJECT-TYPE
   SYNTAX     INTEGER  {
                 off(0),
                 on(1) }
   ACCESS     read-write
   STATUS     mandatory
   DESCRIPTION
     "This attribute specifies whether accounting data collection and 
      record generation is turned on at this DLCI. For accounting data 
      collection and record generation to be turned on, the accountingOn 
      bit and at least one of the accountCollection bits in the 
      DataNetworkAddress component must be set to on."
   DEFVAL     { on }
::= { mscFrUniDlciSpParmsEntry 8 }

mscFrUniDlciSpRaSensitivity OBJECT-TYPE
   SYNTAX     Unsigned32 (1..20)
   ACCESS     read-write
   STATUS     mandatory
   DESCRIPTION
     "This attribute specifies the sensitivity of the rate adaptation system. 
      A higher number indicates a higher sensitivity and therefore a 
      quicker reaction time to network conditions. A quicker reaction 
      time allows the network to discard frames at the access and protect 
      network resources, but can lead to false alarms and a greater 
      fluctuation of the allowed rate. A higher setting therefore tends to 
      favour the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on.
      
      This attribute is ignored if rateAdaptation is turned off."
   DEFVAL     { 7 }
::= { mscFrUniDlciSpParmsEntry 9 }

mscFrUniDlciSpUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updatBCI is set to off, then 
      incoming BECN bits will have no effect.
      
      Setting updateBCI on for a DLCI means that the remote end of the 
      DLCI, which is specified by the remotedna and remotedlci attributes 
      of the dc component of the dlci, may perform Rate Adaptation 
      using the flow of incoming BECN bits, in addition to internal 
      Passport congestion management systems.
      
      If the rateAdaptation attribute of the remote dlci is provisioned as 
      eirOnly, cirProportionate, or on, then congestion from another 
      network connected to a Passport network may trigger dynamic 
      congestion management. If the rateAdaptation attribute of the 
      remote dlci is provisioned to off, then the setting of updateBCI 
      attribute here will have no effect.."
   DEFVAL     { off }
::= { mscFrUniDlciSpParmsEntry 10 }


-- FrUni/n Dlci/n LoopBack	
-- FrNni/n Dlci/n LoopBack		
-- This component is the data loopback tool for the parent DLCI.

mscFrUniDlciLb OBJECT IDENTIFIER ::= { mscFrUniDlci 5 }



mscFrUniDlciLbRowStatusTable OBJECT-TYPE
   SYNTAX     SEQUENCE OF MscFrUniDlciLbRowStatusEntry
   ACCESS     not-accessible
   STATUS     mandatory
   DESCRIPTION
     "This entry controls the addition and deletion of 
      mscFrUniDlciLb components."
::= { mscFrUniDlciLb 1 }

mscFrUniDlciLbRowStatusEntry OBJECT-TYPE
   SYNTAX     MscFrUniDlciLbRowStatusEntry
   ACCESS     not-accessible
   STATUS     mandatory
   DESCRIPTION
     "A single entry in the table represents a single 
      mscFrUniDlciLb component."
   INDEX {
      mscFrUniIndex,
      mscFrUniDlciIndex,
      mscFrUniDlciLbIndex }
::= { mscFrUniDlciLbRowStatusTable 1 }

MscFrUniDlciLbRowStatusEntry ::= SEQUENCE {
   mscFrUniDlciLbRowStatus
      RowStatus,
   mscFrUniDlciLbComponentName
      DisplayString,
   mscFrUniDlciLbStorageType
      StorageType,
   mscFrUniDlciLbIndex
      NonReplicated }

mscFrUniDlciLbRowStatus OBJECT-TYPE
   SYNTAX     RowStatus 
   ACCESS     read-only
   STATUS     mandatory
   DESCRIPTION
     "This variable is used as the basis for SNMP naming of
      mscFrUniDlciLb components.
      These components cannot be added nor deleted."
::= { mscFrUniDlciLbRowStatusEntry 1 }

mscFrUniDlciLbComponentName OBJECT-TYPE
   SYNTAX     DisplayString 
   ACCESS     read-only
   STATUS     mandatory
   DESCRIPTION
     "This variable provides the component's string name for
      use with the ASCII Console Interface"
::= { mscFrUniDlciLbRowStatusEntry 2 }

mscFrUniDlciLbStorageType OBJECT-TYPE
   SYNTAX     StorageType 
   ACCESS     read-only
   STATUS     mandatory
   DESCRIPTION
     "This variable represents the storage type value for the
      mscFrUniDlciLb tables."
::= { mscFrUniDlciLbRowStatusEntry 4 }

mscFrUniDlciLbIndex OBJECT-TYPE
   SYNTAX     NonReplicated 
   ACCESS     not-accessible
   STATUS     mandatory
   DESCRIPTION
     "This variable represents the index for the mscFrUniDlciLb tables."
::= { mscFrUniDlciLbRowStatusEntry 10 }

mscFrUniDlciLbStatsTable OBJECT-TYPE
   SYNTAX     SEQUENCE OF MscFrUniDlciLbStatsEntry
   ACCESS     not-accessible
   STATUS     mandatory
   DESCRIPTION
     "This group contains all the statistics for the data loopback tool."
::= { mscFrUniDlciLb 10 }

mscFrUniDlciLbStatsEntry OBJECT-TYPE
   SYNTAX     MscFrUniDlciLbStatsEntry
   ACCESS     not-accessible
   STATUS     mandatory
   DESCRIPTION
     "An entry in the mscFrUniDlciLbStatsTable."
   INDEX {
      mscFrUniIndex,
      mscFrUniDlciIndex,
      mscFrUniDlciLbIndex }
::= { mscFrUniDlciLbStatsTable 1 }

MscFrUniDlciLbStatsEntry ::= SEQUENCE {
   mscFrUniDlciLbLocalTotalFrm
      Unsigned32,
   mscFrUniDlciLbLocalTotalBytes
      Unsigned32,
   mscFrUniDlciLbLocalFecnFrm
      Unsigned32,
   mscFrUniDlciLbLocalBecnFrm
      Unsigned32,
   mscFrUniDlciLbLocalDeFrm
      Unsigned32,
   mscFrUniDlciLbLocalDeBytes
      Unsigned32,
   mscFrUniDlciLbRemoteTotalFrm
      Unsigned32,
   mscFrUniDlciLbRemoteTotalBytes
      Unsigned32,
   mscFrUniDlciLbRemoteFecnFrm
      Unsigned32,
   mscFrUniDlciLbRemoteBecnFrm
      Unsigned32,
   mscFrUniDlciLbRemoteDeFrm
      Unsigned32,
   mscFrUniDlciLbRemoteDeBytes
      Unsigned32 }

mscFrUniDlciLbLocalTotalFrm OBJECT-TYPE
   SYNTAX     Unsigned32 (0..4294967295)
   ACCESS     read-only
   STATUS     mandatory
   DESCRIPTION
     "This attribute records the number of frames looped back to the link 
      since loopback was last started."
   DEFVAL     { 0 }
::= { mscFrUniDlciLbStatsEntry 1 }

mscFrUniDlciLbLocalTotalBytes OBJECT-TYPE
   SYNTAX     Unsigned32 (0..4294967295)
   ACCESS     read-only
   STATUS     mandatory
   DESCRIPTION
     "This attribute records the number of bytes looped back to the link 
      since loopback mode was started."
   DEFVAL     { 0 }
::= { mscFrUniDlciLbStatsEntry 2 }

mscFrUniDlciLbLocalFecnFrm OBJECT-TYPE
   SYNTAX     Unsigned32 (0..4294967295)
   ACCESS     read-only
   STATUS     mandatory
   DESCRIPTION
     "This attribute records the number of frames with the Forward 
      Explicit Congestion Notification (FECN) bit set, looped back to the 
      link since the loopback mode was started."
   DEFVAL     { 0 }
::= { mscFrUniDlciLbStatsEntry 3 }

mscFrUniDlciLbLocalBecnFrm OBJECT-TYPE
   SYNTAX     Unsigned32 (0..4294967295)
   ACCESS     read-only
   STATUS     mandatory
   DESCRIPTION
     "This attribute records the number of frames with the Backward 
      Explicit Congestion Notification (BECN) bit set, looped back to the 
      link since the loopback mode was started."
   DEFVAL     { 0 }
::= { mscFrUniDlciLbStatsEntry 4 }

mscFrUniDlciLbLocalDeFrm OBJECT-TYPE
   SYNTAX     Unsigned32 (0..4294967295)
   ACCESS     read-only
   STATUS     mandatory
   DESCRIPTION
     "This attribute records the number of frames with the Discard 
      Eligibility (DE) bit set, looped back to the link since the loopback 
      mode was started."
   DEFVAL     { 0 }
::= { mscFrUniDlciLbStatsEntry 5 }

mscFrUniDlciLbLocalDeBytes OBJECT-TYPE
   SYNTAX     Unsigned32 (0..4294967295)
   ACCESS     read-only
   STATUS     mandatory
   DESCRIPTION
     "This attribute records the number of bytes in frames with the 
      Discard Eligibility (DE) bit set, looped back to the link since the 
      loopback mode was started."
   DEFVAL     { 0 }
::= { mscFrUniDlciLbStatsEntry 6 }

mscFrUniDlciLbRemoteTotalFrm OBJECT-TYPE
   SYNTAX     Unsigned32 (0..4294967295)
   ACCESS     read-only
   STATUS     mandatory
   DESCRIPTION
     "This attribute records the number of frames looped back to the 
      subnet since loopback was last started."
   DEFVAL     { 0 }
::= { mscFrUniDlciLbStatsEntry 7 }

mscFrUniDlciLbRemoteTotalBytes OBJECT-TYPE
   SYNTAX     Unsigned32 (0..4294967295)
   ACCESS     read-only
   STATUS     mandatory
   DESCRIPTION
     "This attribute records the number of bytes looped back to the subnet 
      since loopback was last started."
   DEFVAL     { 0 }
::= { mscFrUniDlciLbStatsEntry 8 }

mscFrUniDlciLbRemoteFecnFrm OBJECT-TYPE
   SYNTAX     Unsigned32 (0..4294967295)
   ACCESS     read-only
   STATUS     mandatory
   DESCRIPTION
     "This attribute records the number of frames with the Forward 
      Explicit Congestion Notification (FECN) bit set, looped back to the 
      subnet since the loopback mode was started."
   DEFVAL     { 0 }
::= { mscFrUniDlciLbStatsEntry 9 }

mscFrUniDlciLbRemoteBecnFrm OBJECT-TYPE
   SYNTAX     Unsigned32 (0..4294967295)
   ACCESS     read-only
   STATUS     mandatory
   DESCRIPTION
     "This attribute records the number of frames with the Backward 
      Explicit Congestion Notification (BECN) bit set, looped back to the 
      subnet since the loopback mode was started."
   DEFVAL     { 0 }
::= { mscFrUniDlciLbStatsEntry 10 }

mscFrUniDlciLbRemoteDeFrm OBJECT-TYPE
   SYNTAX     Unsigned32 (0..4294967295)
   ACCESS     read-only
   STATUS     mandatory
   DESCRIPTION
     "This attribute records the number of frames with the Discard 
      Eligibility (DE) bit set, looped back to the subnet since the 
      loopback mode was started."
   DEFVAL     { 0 }
::= { mscFrUniDlciLbStatsEntry 13 }

mscFrUniDlciLbRemoteDeBytes OBJECT-TYPE
   SYNTAX     Unsigned32 (0..4294967295)
   ACCESS     read-only
   STATUS     mandatory
   DESCRIPTION
     "This attribute records the number of bytes in frames with the 
      Discard Eligibility (DE) bit set, looped back to the subnet since the 
      loopback mode was started."
   DEFVAL     { 0 }
::= { mscFrUniDlciLbStatsEntry 14 }


-- FrNni/n Dlci/n EgressServiceParameters
-- This component contains the provisionable attributes of the egress 
-- direction for the parent Dlci component.

mscFrUniDlciEgressSp OBJECT IDENTIFIER ::= { mscFrUniDlci 6 }



mscFrUniDlciEgressSpRowStatusTable OBJECT-TYPE
   SYNTAX     SEQUENCE OF MscFrUniDlciEgressSpRowStatusEntry
   ACCESS     not-accessible
   STATUS     mandatory
   DESCRIPTION
     "This entry controls the addition and deletion of 
      mscFrUniDlciEgressSp components."
::= { mscFrUniDlciEgressSp 1 }

mscFrUniDlciEgressSpRowStatusEntry OBJECT-TYPE
   SYNTAX     MscFrUniDlciEgressSpRowStatusEntry
   ACCESS     not-accessible
   STATUS     mandatory
   DESCRIPTION
     "A single entry in the table represents a single 
      mscFrUniDlciEgressSp component."
   INDEX {
      mscFrUniIndex,
      mscFrUniDlciIndex,
      mscFrUniDlciEgressSpIndex }
::= { mscFrUniDlciEgressSpRowStatusTable 1 }

MscFrUniDlciEgressSpRowStatusEntry ::= SEQUENCE {
   mscFrUniDlciEgressSpRowStatus
      RowStatus,
   mscFrUniDlciEgressSpComponentName
      DisplayString,
   mscFrUniDlciEgressSpStorageType
      StorageType,
   mscFrUniDlciEgressSpIndex
      NonReplicated }

mscFrUniDlciEgressSpRowStatus OBJECT-TYPE
   SYNTAX     RowStatus 
   ACCESS     read-only
   STATUS     mandatory
   DESCRIPTION
     "This variable is used as the basis for SNMP naming of
      mscFrUniDlciEgressSp components.
      These components cannot be added nor deleted."
::= { mscFrUniDlciEgressSpRowStatusEntry 1 }

mscFrUniDlciEgressSpComponentName OBJECT-TYPE
   SYNTAX     DisplayString 
   ACCESS     read-only
   STATUS     mandatory
   DESCRIPTION
     "This variable provides the component's string name for
      use with the ASCII Console Interface"
::= { mscFrUniDlciEgressSpRowStatusEntry 2 }

mscFrUniDlciEgressSpStorageType OBJECT-TYPE
   SYNTAX     StorageType 
   ACCESS     read-only
   STATUS     mandatory
   DESCRIPTION
     "This variable represents the storage type value for the
      mscFrUniDlciEgressSp tables."
::= { mscFrUniDlciEgressSpRowStatusEntry 4 }

mscFrUniDlciEgressSpIndex OBJECT-TYPE
   SYNTAX     NonReplicated 
   ACCESS     not-accessible
   STATUS     mandatory
   DESCRIPTION
     "This variable represents the index for the mscFrUniDlciEgressSp tables."
::= { mscFrUniDlciEgressSpRowStatusEntry 10 }

mscFrUniDlciEgressSpProvTable OBJECT-TYPE
   SYNTAX     SEQUENCE OF MscFrUniDlciEgressSpProvEntry
   ACCESS     not-accessible
   STATUS     mandatory
   DESCRIPTION
     "This group contains the provisionable attributes for this component."
::= { mscFrUniDlciEgressSp 10 }

mscFrUniDlciEgressSpProvEntry OBJECT-TYPE
   SYNTAX     MscFrUniDlciEgressSpProvEntry
   ACCESS     not-accessible
   STATUS     mandatory
   DESCRIPTION
     "An entry in the mscFrUniDlciEgressSpProvTable."
   INDEX {
      mscFrUniIndex,
      mscFrUniDlciIndex,
      mscFrUniDlciEgressSpIndex }
::= { mscFrUniDlciEgressSpProvTable 1 }

MscFrUniDlciEgressSpProvEntry ::= SEQUENCE {
   mscFrUniDlciEgressSpCommittedInformationRate
      Unsigned32,
   mscFrUniDlciEgressSpCommittedBurstSize
      Unsigned32,
   mscFrUniDlciEgressSpExcessBurstSize
      Unsigned32,
   mscFrUniDlciEgressSpMeasurementInterval
      Unsigned32 }

mscFrUniDlciEgressSpCommittedInformationRate OBJECT-TYPE
   SYNTAX     Unsigned32 (0..50000000 | 50000001)
   ACCESS     read-write
   STATUS     mandatory
   DESCRIPTION
     "This attribute specifies the committed information rate (CIR) for the 
      egress direction. It is used for Call Admission Control (CAC) at the 
      egress link.
      If the value is set to sameAsSp, the value of this attribute is the 
      same as the committedInformationRate attribute under the 
      ServiceParameters component.

      VALUES (

      50000001 = sameAsServiceParameters

      )"
   DEFVAL     { 50000001 }
::= { mscFrUniDlciEgressSpProvEntry 1 }

mscFrUniDlciEgressSpCommittedBurstSize OBJECT-TYPE
   SYNTAX     Unsigned32 (0..50000000 | 50000001)
   ACCESS     read-write
   STATUS     mandatory
   DESCRIPTION
     "This attribute specifies the committed burst size (Bc) for the egress 
      direction. It is used for performing Call Admission Control (CAC) 
      at the egress link.
      If the value is set to sameAsSp, the value of this attribute is the 
      same as the committedBurstSize attribute under the 
      ServiceParameters component.

      VALUES (

      50000001 = sameAsServiceParameters

      )"
   DEFVAL     { 50000001 }
::= { mscFrUniDlciEgressSpProvEntry 2 }

mscFrUniDlciEgressSpExcessBurstSize OBJECT-TYPE
   SYNTAX     Unsigned32 (0..50000000 | 50000001)
   ACCESS     read-write
   STATUS     mandatory
   DESCRIPTION
     "This attribute specifies the excess burst size (Be) for the egress 
      direction. It is used for Call Admission Control (CAC) function 
      towards the egress link.
      If the value is set to sameAsSp, the value of this attribute is the 
      same as the excessBurstSize attribute under the ServiceParameters 
      component.

      VALUES (

      50000001 = sameAsServiceParameters

      )"
   DEFVAL     { 50000001 }
::= { mscFrUniDlciEgressSpProvEntry 3 }

mscFrUniDlciEgressSpMeasurementInterval OBJECT-TYPE
   SYNTAX     Unsigned32 (0..25500 | 25501)
   ACCESS     read-write
   STATUS     mandatory
   DESCRIPTION
     "This attribute specifies the time interval over which rates and burst 
      sizes are measured in the egress direction. It is used for bandwidth 
      reservation for Call Admission Control (CAC) towards the egress 
      link.
      If the value is set to sameAsSp, the value of this attribute is the 
      same as the measurementInterval attribute under the 
      ServiceParameters component.

      VALUES (

      25501 = sameAsServiceParameters

      )"
   DEFVAL     { 25501 }
::= { mscFrUniDlciEgressSpProvEntry 4 }


-- 
-- FrUni/n Signaling
-- This component defines the FRF.4 and Q.922 (LAPF) parameters 
-- for Frame Relay switched virtual circuits at the User-Network 
-- interface. This component must be provisioned for the FrUni 
-- interface to support switched connections.

mscFrUniSig OBJECT IDENTIFIER ::= { mscFrUni 6 }



mscFrUniSigRowStatusTable OBJECT-TYPE
   SYNTAX     SEQUENCE OF MscFrUniSigRowStatusEntry
   ACCESS     not-accessible
   STATUS     mandatory
   DESCRIPTION
     "This entry controls the addition and deletion of 
      mscFrUniSig components."
::= { mscFrUniSig 1 }

mscFrUniSigRowStatusEntry OBJECT-TYPE
   SYNTAX     MscFrUniSigRowStatusEntry
   ACCESS     not-accessible
   STATUS     mandatory
   DESCRIPTION
     "A single entry in the table represents a single 
      mscFrUniSig component."
   INDEX {
      mscFrUniIndex,
      mscFrUniSigIndex }
::= { mscFrUniSigRowStatusTable 1 }

MscFrUniSigRowStatusEntry ::= SEQUENCE {
   mscFrUniSigRowStatus
      RowStatus,
   mscFrUniSigComponentName
      DisplayString,
   mscFrUniSigStorageType
      StorageType,
   mscFrUniSigIndex
      NonReplicated }

mscFrUniSigRowStatus OBJECT-TYPE
   SYNTAX     RowStatus 
   ACCESS     read-write
   STATUS     mandatory
   DESCRIPTION
     "This variable is used as the basis for SNMP naming of
      mscFrUniSig components.
      These components can be added and deleted."
::= { mscFrUniSigRowStatusEntry 1 }

mscFrUniSigComponentName OBJECT-TYPE
   SYNTAX     DisplayString 
   ACCESS     read-only
   STATUS     mandatory
   DESCRIPTION
     "This variable provides the component's string name for
      use with the ASCII Console Interface"
::= { mscFrUniSigRowStatusEntry 2 }

mscFrUniSigStorageType OBJECT-TYPE
   SYNTAX     StorageType 
   ACCESS     read-only
   STATUS     mandatory
   DESCRIPTION
     "This variable represents the storage type value for the
      mscFrUniSig tables."
::= { mscFrUniSigRowStatusEntry 4 }

mscFrUniSigIndex OBJECT-TYPE
   SYNTAX     NonReplicated 
   ACCESS     not-accessible
   STATUS     mandatory
   DESCRIPTION
     "This variable represents the index for the mscFrUniSig tables."
::= { mscFrUniSigRowStatusEntry 10 }

mscFrUniSigRangeTable OBJECT-TYPE
   SYNTAX     SEQUENCE OF MscFrUniSigRangeEntry
   ACCESS     not-accessible
   STATUS     mandatory
   DESCRIPTION
     "This group contains the provisionable attribute to define the range 
      of DLCIs for PVCs and SVCs. The purpose of this range is to 
      prevent DLCI collisions between the provisioned PVCs and the 
      dynamic SVCs."
::= { mscFrUniSig 11 }

mscFrUniSigRangeEntry OBJECT-TYPE
   SYNTAX     MscFrUniSigRangeEntry
   ACCESS     not-accessible
   STATUS     mandatory
   DESCRIPTION
     "An entry in the mscFrUniSigRangeTable."
   INDEX {
      mscFrUniIndex,
      mscFrUniSigIndex }
::= { mscFrUniSigRangeTable 1 }

MscFrUniSigRangeEntry ::= SEQUENCE {
   mscFrUniSigHighestPvcDlci
      Unsigned32,
   mscFrUniSigHighestPermanentDlci
      Unsigned32,
   mscFrUniSigHighestFriPvcDlci
      Unsigned32 }

mscFrUniSigHighestPvcDlci OBJECT-TYPE
   SYNTAX     Unsigned32 (0 | 16..1007)
   ACCESS     read-write
   STATUS     obsolete
   DESCRIPTION
     "This attribute specifies the highest DLCI value that can be 
      provisioned for a PVC. It partitions the DLCI space into PVC and 
      SVC. PVC DLCI numbers higher than this value are rejected. The 
      value 0 is used to indicate that no PVCs are allowed on the 
      interface. The value 1007 indicates that no SVCs are allowed on the 
      interface."
   DEFVAL     { 500 }
::= { mscFrUniSigRangeEntry 1 }

mscFrUniSigHighestPermanentDlci OBJECT-TYPE
   SYNTAX     Unsigned32 (0 | 16..1007)
   ACCESS     read-write
   STATUS     obsolete
   DESCRIPTION
     "This attribute specifies the highest DLCI value that can be 
      provisioned for a permanent connection. It partitions the DLCI 
      space into permanent and switched connections. Permanent DLCI 
      numbers higher than this value cannot be provisioned. The value 0 
      is used to indicate that no permanent connections are allowed on 
      this interface. The value 1007 indicates that no switched 
      connections are allowed on this interface."
   DEFVAL     { 500 }
::= { mscFrUniSigRangeEntry 4 }

mscFrUniSigHighestFriPvcDlci OBJECT-TYPE
   SYNTAX     Unsigned32 (0 | 16..1007)
   ACCESS     read-write
   STATUS     mandatory
   DESCRIPTION
     "This attribute specifies the highest DLCI value that can be 
      provisioned for a permanent connection. It partitions the DLCI 
      space into permanent and switched connections. Permanent DLCI 
      numbers higher than this value cannot be provisioned. The value 0 
      is used to indicate that no permanent connections are allowed on 
      this interface. The value 1007 indicates that no switched 
      connections are allowed on this interface."
   DEFVAL     { 500 }
::= { mscFrUniSigRangeEntry 5 }

mscFrUniSigServParmsTable OBJECT-TYPE
   SYNTAX     SEQUENCE OF MscFrUniSigServParmsEntry
   ACCESS     not-accessible
   STATUS     mandatory
   DESCRIPTION
     "This group contains the provisionable FRF.4 service parameters."
::= { mscFrUniSig 12 }

mscFrUniSigServParmsEntry OBJECT-TYPE
   SYNTAX     MscFrUniSigServParmsEntry
   ACCESS     not-accessible
   STATUS     mandatory
   DESCRIPTION
     "An entry in the mscFrUniSigServParmsTable."
   INDEX {
      mscFrUniIndex,
      mscFrUniSigIndex }
::= { mscFrUniSigServParmsTable 1 }

MscFrUniSigServParmsEntry ::= SEQUENCE {
   mscFrUniSigMaximumAggregateSvcCir
      Unsigned32,
   mscFrUniSigMaximumAggregateSvcEir
      Unsigned32,
   mscFrUniSigMaximumFrameSize
      Unsigned32,
   mscFrUniSigDefaultMaximumFrameSize
      Unsigned32,
   mscFrUniSigDefaultCommittedInformationRate
      Unsigned32,
   mscFrUniSigDefaultCommittedBurstSize
      Unsigned32,
   mscFrUniSigDefaultExcessBurstSize
      Unsigned32,
   mscFrUniSigUnlimitedAggregateEir
      INTEGER,
   mscFrUniSigRateEnforcement
      INTEGER,
   mscFrUniSigRateAdaptation
      INTEGER,
   mscFrUniSigMaximumAggregateSvcCirNormalQ
      Unsigned32,
   mscFrUniSigMaximumAggregateSvcCirHighQ
      Unsigned32,
   mscFrUniSigMaximumAggregateSvcCirInterruptQ
      Unsigned32,
   mscFrUniSigMaximumAggregateSvcEirNormalQ
      Unsigned32,
   mscFrUniSigMaximumAggregateSvcEirHighQ
      Unsigned32,
   mscFrUniSigMaximumAggregateSvcEirInterruptQ
      Unsigned32,
   mscFrUniSigX213IeHandling
      INTEGER,
   mscFrUniSigRaSensitivity
      Unsigned32,
   mscFrUniSigUpdateBCI
      INTEGER,
   mscFrUniSigDefaultLocCheck
      INTEGER }

mscFrUniSigMaximumAggregateSvcCir OBJECT-TYPE
   SYNTAX     Unsigned32 (0..10000)
   ACCESS     read-write
   STATUS     obsolete
   DESCRIPTION
     "This attribute specifies the maximum aggregate user to network 
      direction CIR allowed for SVCs on the interface. It is provisioned 
      as a percentage of the access link speed. This attribute is used to 
      limit the amount of guaranteed SVC throughput allowed into the 
      network at this interface.
      This attribute is obsoleted, during the migration, the value of this 
      attribute will be transfered to maximumAggregateSvcCirNormalQ 
      or maximumAggregateSvcCirHighQ depending on the value of the 
      attribute outDefaultPathSensitivity under DNA component."
   DEFVAL     { 1000 }
::= { mscFrUniSigServParmsEntry 1 }

mscFrUniSigMaximumAggregateSvcEir OBJECT-TYPE
   SYNTAX     Unsigned32 (0..4294967295)
   ACCESS     read-write
   STATUS     obsolete
   DESCRIPTION
     "This attribute specifies the maximum aggregate user to network 
      direction EIR allowed for SVCs on the interface. It is provisioned as 
      a percentage of the access link speed. This attribute is ignored if 
      unlimitedAggregateEir, another attribute under the same group, is 
      set to yes. This attribute is used to limit the amount of excess SVC 
      throughput allowed into the network at this interface.
      This attribute is obsoleted, during the migration, the value of this 
      attribute will be transfered to maximumAggregateSvcEirNormalQ 
      or maximumAggregateSvcEirHighQ depending on the value of the 
      attribute outDefaultPathSensitivity under DNA component."
   DEFVAL     { 10000 }
::= { mscFrUniSigServParmsEntry 2 }

mscFrUniSigMaximumFrameSize OBJECT-TYPE
   SYNTAX     Unsigned32 (1..8187)
   ACCESS     read-write
   STATUS     mandatory
   DESCRIPTION
     "This attribute specifies the maximum number of octets that may be 
      included in the information field of the user DLCI of any switched 
      connections using this interface. Its value must not be smaller than 
      the value of defaultMaximumFrameSize."
   DEFVAL     { 4096 }
::= { mscFrUniSigServParmsEntry 3 }

mscFrUniSigDefaultMaximumFrameSize OBJECT-TYPE
   SYNTAX     Unsigned32 (1..8187)
   ACCESS     read-write
   STATUS     mandatory
   DESCRIPTION
     "This attribute specifies the default maximum number of octets that 
      may be included in the information field of the user DLCI assigned 
      for any switched connections using this interface. This value is used 
      during call parameter negotiation for switched calls on this interface 
      when the maximum frame size is not specified in the user's SETUP 
      message. The value of this attribute must not exceed the value of the 
      maximumFrameSize attribute."
   DEFVAL     { 2100 }
::= { mscFrUniSigServParmsEntry 4 }

mscFrUniSigDefaultCommittedInformationRate OBJECT-TYPE
   SYNTAX     Unsigned32 (0..52000000)
   ACCESS     read-write
   STATUS     mandatory
   DESCRIPTION
     "This attribute specifies the default user to network direction CIR. 
      This value is used during call parameter negotiation for switched 
      calls on this interface when the CIR is not specified in the user's 
      SETUP message."
   DEFVAL     { 64000 }
::= { mscFrUniSigServParmsEntry 5 }

mscFrUniSigDefaultCommittedBurstSize OBJECT-TYPE
   SYNTAX     Unsigned32 (0..52000000)
   ACCESS     read-write
   STATUS     mandatory
   DESCRIPTION
     "This attribute specifies the default user to network direction Bc. 
      This value is used during call parameter negotiation for switched 
      calls on this interface when the Bc is not specified in the user's 
      SETUP message."
   DEFVAL     { 64000 }
::= { mscFrUniSigServParmsEntry 6 }

mscFrUniSigDefaultExcessBurstSize OBJECT-TYPE
   SYNTAX     Unsigned32 (0..52000000)
   ACCESS     read-write
   STATUS     mandatory
   DESCRIPTION
     "This attribute specifies the default user to network direction Be. 
      This value is used during call parameter negotiation for switched 
      calls on this interface when the Be is not specified in the user's 
      SETUP message."
   DEFVAL     { 0 }
::= { mscFrUniSigServParmsEntry 7 }

mscFrUniSigUnlimitedAggregateEir OBJECT-TYPE
   SYNTAX     INTEGER  {
                 no(0),
                 yes(1) }
   ACCESS     read-write
   STATUS     obsolete
   DESCRIPTION
     "This attribute specifies whether the network will enforce aggregate 
      EIR during SVC call establishment. The network keeps track of the 
      sum of user to network EIRs for all the SVC DLCIs at this 
      interface. 
      
      If this attribute is set to no, then the requested EIR for each new 
      SVC call will be adjusted if the resulting aggregate EIR exceeds the 
      value contained in one of the following attributes (depending on the 
      requested Transfer Priority): maximumAggregateSvcEirNormalQ, 
      maximumAggregateSvcEirHighQ or 
      maximumAggregateSvcEirInterruptQ. This may lead to a rejection 
      of the call setup.
      
      If this value is set to yes, then no checks will take place."
   DEFVAL     { yes }
::= { mscFrUniSigServParmsEntry 8 }

mscFrUniSigRateEnforcement OBJECT-TYPE
   SYNTAX     INTEGER  {
                 off(0),
                 on(1) }
   ACCESS     read-write
   STATUS     mandatory
   DESCRIPTION
     "This attribute specifies whether rate enforcement is in effect for 
      SVCs on this interface."
   DEFVAL     { on }
::= { mscFrUniSigServParmsEntry 9 }

mscFrUniSigRateAdaptation OBJECT-TYPE
   SYNTAX     INTEGER  {
                 off(0),
                 on(1),
                 eirOnly(2),
                 cirProportionate(3) }
   ACCESS     read-write
   STATUS     mandatory
   DESCRIPTION
     "This attribute specifies whether closed-loop rate adaptation is in 
      effect for SVCs on this interface. Rate adaptation is a feature that, in 
      periods of congestion, adapts the rate at which the user is allowed to 
      send data into the network to that which the network is able to 
      handle at that time. This proactive measure of handling congestion 
      optimizes network resources by causing the ingress to discard 
      frames that would otherwise be discarded in the network.
      
      If this attribute is set to on, then, at the onset of congestion, the 
      excess information rate (EIR) is reduced to a very low rate. If 
      congestion persists, then the allowed CIR is reduced geometrically 
      by 25% of the current value at that time. The minimum to which 
      CIR can be reduced is 1/16th (6.25%) of the provisioned value. As 
      congestion alleviates, CIR is increased linearly by 6.25% of the 
      provisioned value specified in committedInformationRate.
      
      If set to eirOnly, then rate adaptation will only apply to the excess 
      information rate (EIR). At the onset of congestion, the allowed EIR 
      is reduced by 25% of its provisioned value. If congestion persists, 
      EIR is reduced geometrically by 25% of the current value at that 
      time. As congestion alleviates, EIR is gradually increased linearly 
      by 6.25% of the provisioned EIR.
      
      If set to cirProportionate, then rate adaptation will also only apply 
      to the excess information rate (EIR). At the onset of congestion the 
      initial allowed EIR is set to a multiple of the provisioned CIR. If 
      congestion persists, the allowed EIR is reduced geometrically by 
      25% of the current value at that time. As congestion alleviates, EIR 
      is gradually increased linearly by 6.25% of the provisioned EIR. 
      Note that the allowed EIR may be set higher than the provisioned 
      EIR, since it is calculated initially using another parameter, the 
      provisioned CIR. If the allowed EIR at the moment is higher than 
      the provisioned EIR, then the provisioned EIR is used instead.
      
      This attribute can only be set to on or eirOnly if rateEnforcement is 
      set to on."
   DEFVAL     { off }
::= { mscFrUniSigServParmsEntry 10 }

mscFrUniSigMaximumAggregateSvcCirNormalQ OBJECT-TYPE
   SYNTAX     Unsigned32 (0..10000)
   ACCESS     read-write
   STATUS     obsolete
   DESCRIPTION
     "This attribute specifies the maximum aggregate user to network 
      direction CIR allowed for SVCs on the interface. It is provisioned 
      as a percentage of the access link speed. This attribute is used to 
      limit, at this interface, the amount of guaranteed SVC throughput 
      allowed into the network through the normal priority queue."
   DEFVAL     { 1000 }
::= { mscFrUniSigServParmsEntry 11 }

mscFrUniSigMaximumAggregateSvcCirHighQ OBJECT-TYPE
   SYNTAX     Unsigned32 (0..10000)
   ACCESS     read-write
   STATUS     obsolete
   DESCRIPTION
     "This attribute specifies the maximum aggregate user to network 
      direction CIR allowed for SVCs on the interface. It is provisioned 
      as a percentage of the link access speed. This attribute is used to 
      limit, at this interface, the amount of guaranteed SVC throughput 
      allowed into the network through the high priority queue."
   DEFVAL     { 1000 }
::= { mscFrUniSigServParmsEntry 12 }

mscFrUniSigMaximumAggregateSvcCirInterruptQ OBJECT-TYPE
   SYNTAX     Unsigned32 (0..10000)
   ACCESS     read-write
   STATUS     obsolete
   DESCRIPTION
     "This attribute specifies the maximum aggregate user to network 
      direction CIR allowed for SVCs on the interface. It is provisioned 
      as a percentage of the link access speed. This attribute is used to 
      limit, at this interface, the amount of guaranteed SVC throughput 
      allowed into the network through the interrupting queue."
   DEFVAL     { 1000 }
::= { mscFrUniSigServParmsEntry 13 }

mscFrUniSigMaximumAggregateSvcEirNormalQ OBJECT-TYPE
   SYNTAX     Unsigned32 (0..4294967295)
   ACCESS     read-write
   STATUS     obsolete
   DESCRIPTION
     "This attribute specifies the maximum aggregate user to network 
      direction EIR allowed for SVCs on the interface. It is provisioned as 
      a percentage of the access link speed. This attribute is ignored if 
      unlimitedAggregateEir, another attribute under the same group, is 
      set to yes. This attribute is used to limit, at this interface, the amount 
      of excess SVC throughput allowed into the network through the 
      normal priority queue."
   DEFVAL     { 10000 }
::= { mscFrUniSigServParmsEntry 14 }

mscFrUniSigMaximumAggregateSvcEirHighQ OBJECT-TYPE
   SYNTAX     Unsigned32 (0..4294967295)
   ACCESS     read-write
   STATUS     obsolete
   DESCRIPTION
     "This attribute specifies the maximum aggregate user to network 
      direction EIR allowed for SVCs on the interface. It is provisioned as 
      a percentage of the access link speed. This attribute is ignored if 
      unlimitedAggregateEir, another attribute under the same group, is 
      set to yes. This attribute is used to limit, at this interface, the amount 
      of excess SVC throughput allowed into the network through the 
      high priority queue."
   DEFVAL     { 10000 }
::= { mscFrUniSigServParmsEntry 15 }

mscFrUniSigMaximumAggregateSvcEirInterruptQ OBJECT-TYPE
   SYNTAX     Unsigned32 (0..4294967295)
   ACCESS     read-write
   STATUS     obsolete
   DESCRIPTION
     "This attribute specifies the maximum aggregate user to network 
      direction EIR allowed for SVCs on the interface. It is provisioned as 
      a percentage of the access link speed. This attribute is ignored if 
      unlimitedAggregateEir, another attribute under the same group, is 
      set to yes. This attribute is used to limit, at this interface, the amount 
      of excess SVC throughput allowed into the network through the 
      interrupting queue."
   DEFVAL     { 10000 }
::= { mscFrUniSigServParmsEntry 16 }

mscFrUniSigX213IeHandling OBJECT-TYPE
   SYNTAX     INTEGER  {
                 notSupported(0),
                 proprietary(1) }
   ACCESS     read-write
   STATUS     mandatory
   DESCRIPTION
     "The x213IeHandling attribute specifies how Frame Relay handles 
      the X.213 Priority IE when it is in the FRF.4 setup message. 
      
      When the attribute is set to notSupported, the X.213 Priority IE will 
      not be recognized in the setup message. A FRF.4 status message 
      will be sent to the calling DTE, with the indication that an 
      unrecognized IE was encountered. The call setup then proceeds as 
      normal, and the X.213 Priority IE does not appear in the setup 
      message at the called end.
      
      When the attribute is set to proprietary, and the X.213 Priority IE is 
      present in the FRF.4 setup message, it will be recognized. If there is 
      no Frame Transfer Priority IE in the setup message, the first data 
      byte of the X.213 Priority IE is used to select the transfer and 
      discard priority values for the connection and the X.213 Priority IE 
      is signaled to the called end in the setup message. If the Frame 
      Transfer Priority IE is present in the FRF.4 setup message, its value 
      is used to select the transfer priority, the discard priority is taken 
      from the FRUNI Dna component, and the X.213 Priority IE is 
      ignored.
      
      Refer to the related Application Note for further details before 
      setting the attribute value to proprietary."
   DEFVAL     { notSupported }
::= { mscFrUniSigServParmsEntry 17 }

mscFrUniSigRaSensitivity OBJECT-TYPE
   SYNTAX     Unsigned32 (1..20)
   ACCESS     read-write
   STATUS     mandatory
   DESCRIPTION
     "This attribute specifies the sensitivity of the rate adaptation system 
      for all switched connections on this interface.
      
      A higher number indicates a higher sensitivity and therefore a 
      quicker reaction time to network conditions. A quicker reaction 
      time allows the network to discard frames at the access and protect 
      network resources, but can lead to false alarms and a greater 
      fluctuation of the allowed rate. A higher setting therefore tends to 
      favor the protection of the network over the allowed throughput of 
      the user.
      
      A lower number indicates a lower sensitivity and therefore a slower 
      reaction to network conditions. A slower reaction time results in a 
      greater amount of user traffic allowed into the network, but can lead 
      to a waste of network bandwidth since the traffic may be discarded 
      at the congested resource. A lower setting therefore tends to favour 
      the allowed throughput of the user over the protection of the 
      network.
      
      This attribute is applicable for adapting EIR when rateAdaptation is 
      eirOnly or cirProportionate, or CIR when rateAdaptation is on. 
      
      This attribute is ignored if rateAdaptation is off."
   DEFVAL     { 7 }
::= { mscFrUniSigServParmsEntry 18 }

mscFrUniSigUpdateBCI OBJECT-TYPE
   SYNTAX     INTEGER  {
                 off(0),
                 on(1) }
   ACCESS     read-write
   STATUS     mandatory
   DESCRIPTION
     "This attribute specifies whether internal Backward Congestion 
      Indication (BCI) bits will report congestion external to the Passport 
      network, as communicated through incoming BECN bits.
      
      If updateBCI is set to on, then BCI bits for incoming frames will be 
      set if the BECN on the frame is set. If updateBCI is set to off, then 
      incoming BECN bits has no effect.
      
      Setting updateBCI on for a DLCI means that the remote end of the 
      DLCI, which is specified by the remoteDna and remoteDlci 
      attributes of the Dc component of the Dlci, may perform Rate 
      Adaptation using the flow of incoming BECN bits, in addition to 
      internal Passport congestion management systems.
      
      If the rateAdaptation attribute of the remote DLCI is provisioned as 
      eirOnly, cirProportionate, or on, then congestion from another 
      network connected to a Passport network may trigger dynamic 
      congestion management. If there is no rate adaptation at the other 
      end, then the setting of updateBCI attribute here will have no effect."
   DEFVAL     { off }
::= { mscFrUniSigServParmsEntry 19 }

mscFrUniSigDefaultLocCheck OBJECT-TYPE
   SYNTAX     INTEGER  {
                 off(0),
                 on(1) }
   ACCESS     read-write
   STATUS     mandatory
   DESCRIPTION
     "This attribute specifies whether Passport needs to check the location 
      of Cause IE in a Release or a Disc message issued by local DTE. If 
      this bit is set to on, then Passport will check the location of Cause 
      IE issued by the local DTE and overwrite it by 'user'. If it is set to 
      off, then Passport will not check the location in Cause IE."
   DEFVAL     { on }
::= { mscFrUniSigServParmsEntry 20 }

mscFrUniSigSysParmsTable OBJECT-TYPE
   SYNTAX     SEQUENCE OF MscFrUniSigSysParmsEntry
   ACCESS     not-accessible
   STATUS     mandatory
   DESCRIPTION
     "This group contains the provisionable FRF.4 system parameters."
::= { mscFrUniSig 13 }

mscFrUniSigSysParmsEntry OBJECT-TYPE
   SYNTAX     MscFrUniSigSysParmsEntry
   ACCESS     not-accessible
   STATUS     mandatory
   DESCRIPTION
     "An entry in the mscFrUniSigSysParmsTable."
   INDEX {
      mscFrUniIndex,
      mscFrUniSigIndex }
::= { mscFrUniSigSysParmsTable 1 }

MscFrUniSigSysParmsEntry ::= SEQUENCE {
   mscFrUniSigCallSetupTimer
      Unsigned32,
   mscFrUniSigDisconnectTimer
      Unsigned32,
   mscFrUniSigReleaseTimer
      Unsigned32,
   mscFrUniSigCallProceedingTimer
      Unsigned32,
   mscFrUniSigNetworkType
      INTEGER,
   mscFrUniSigRestartReqTimer
      Unsigned32,
   mscFrUniSigRestartRcvTimer
      Unsigned32,
   mscFrUniSigStatusEnqTimer
      Unsigned32 }

mscFrUniSigCallSetupTimer OBJECT-TYPE
   SYNTAX     Unsigned32 (1..255)
   ACCESS     read-write
   STATUS     mandatory
   DESCRIPTION
     "This attribute specifies the time the network waits for a response to 
      the SETUP message sent to the called user. Upon timer expiry, the 
      SETUP message is retransmitted. The second expiry of this timer 
      causes the call to be cleared."
   DEFVAL     { 4 }
::= { mscFrUniSigSysParmsEntry 1 }

mscFrUniSigDisconnectTimer OBJECT-TYPE
   SYNTAX     Unsigned32 (1..255)
   ACCESS     read-write
   STATUS     mandatory
   DESCRIPTION
     "This attribute specifies the time the network waits for a response to 
      the DISCONNECT message sent to the user. Upon timer expiry, the 
      RELEASE message is sent."
   DEFVAL     { 30 }
::= { mscFrUniSigSysParmsEntry 2 }

mscFrUniSigReleaseTimer OBJECT-TYPE
   SYNTAX     Unsigned32 (1..255)
   ACCESS     read-write
   STATUS     mandatory
   DESCRIPTION
     "This attribute specifies the time the network waits for a response to 
      the RELEASE message sent to the user. Upon timer expiry, the 
      RELEASE message is retransmitted. The second expiry of the timer 
      causes the call to be released."
   DEFVAL     { 4 }
::= { mscFrUniSigSysParmsEntry 3 }

mscFrUniSigCallProceedingTimer OBJECT-TYPE
   SYNTAX     Unsigned32 (1..255)
   ACCESS     read-write
   STATUS     mandatory
   DESCRIPTION
     "This attribute specifies the time the network waits for the 
      CONNECT message from the called user after the network has 
      received the optional CALL PROCEEDING message from the 
      called user. Upon timer expiry, the call is cleared."
   DEFVAL     { 10 }
::= { mscFrUniSigSysParmsEntry 4 }

mscFrUniSigNetworkType OBJECT-TYPE
   SYNTAX     INTEGER  {
                 private(1),
                 public(2) }
   ACCESS     read-write
   STATUS     mandatory
   DESCRIPTION
     "This attribute specifies whether this Frame Relay service is running 
      on a public or a private network. This value is used solely in 
      populating applicable information elements within those FRF.4 
      messages that require a public or private network indication."
   DEFVAL     { private }
::= { mscFrUniSigSysParmsEntry 5 }

mscFrUniSigRestartReqTimer OBJECT-TYPE
   SYNTAX     Unsigned32 (0..255)
   ACCESS     read-write
   STATUS     mandatory
   DESCRIPTION
     "This attribute specifies the time the network waits for the RESTART 
      ACKNOWLEDGE message from the adjacent network after 
      sending a first RESTART message. Upon timer expiry, another 
      RESTART message is sent. After the second expiry, the interface is 
      treated as idle. 
      
      If the restartReqTimer attribute is set to the default value, then the 
      interface is treated as idle when it receives an indication that the 
      link is up and does not send a RESTART message."
   DEFVAL     { 0 }
::= { mscFrUniSigSysParmsEntry 6 }

mscFrUniSigRestartRcvTimer OBJECT-TYPE
   SYNTAX     Unsigned32 (1..255)
   ACCESS     read-write
   STATUS     mandatory
   DESCRIPTION
     "This attribute specifies the time the local network waits for the 
      processing of a RESTART message received by the interface. Upon 
      expiry of this timer, an alarm will be displayed to report the 
      problem. The timer value must be less than the restartReqTimer 
      provisioned value at the adjacent node."
   DEFVAL     { 110 }
::= { mscFrUniSigSysParmsEntry 7 }

mscFrUniSigStatusEnqTimer OBJECT-TYPE
   SYNTAX     Unsigned32 (1..255)
   ACCESS     read-write
   STATUS     mandatory
   DESCRIPTION
     "This attribute specifies the time the network waits for the requested 
      STATUS message from the adjacent network. Upon expiry of this 
      timer, another STATUS ENQUIRY message will be sent."
   DEFVAL     { 4 }
::= { mscFrUniSigSysParmsEntry 8 }

mscFrUniSigLapfSysTable OBJECT-TYPE
   SYNTAX     SEQUENCE OF MscFrUniSigLapfSysEntry
   ACCESS     not-accessible
   STATUS     mandatory
   DESCRIPTION
     "This group contains the provisionable attributes for the SVC data 
      link layer. The data link layer is governed primarily through ITU 
      specification Q.922, and operates over DLCI 0.."
::= { mscFrUniSig 14 }

mscFrUniSigLapfSysEntry OBJECT-TYPE
   SYNTAX     MscFrUniSigLapfSysEntry
   ACCESS     not-accessible
   STATUS     mandatory
   DESCRIPTION
     "An entry in the mscFrUniSigLapfSysTable."
   INDEX {
      mscFrUniIndex,
      mscFrUniSigIndex }
::= { mscFrUniSigLapfSysTable 1 }

MscFrUniSigLapfSysEntry ::= SEQUENCE {
   mscFrUniSigWindowSize
      Unsigned32,
   mscFrUniSigRetransmitLimit
      Unsigned32,
   mscFrUniSigAckTimer
      Unsigned32,
   mscFrUniSigAckDelayTimer
      Unsigned32,
   mscFrUniSigIdleProbeTimer
      Unsigned32 }

mscFrUniSigWindowSize OBJECT-TYPE
   SYNTAX     Unsigned32 (1..127)
   ACCESS     read-write
   STATUS     mandatory
   DESCRIPTION
     "This attribute specifies the window size. This is the maximum 
      number of unacknowledged sequenced frames that may be 
      outstanding from or to this interface at any one time."
   DEFVAL     { 7 }
::= { mscFrUniSigLapfSysEntry 2 }

mscFrUniSigRetransmitLimit OBJECT-TYPE
   SYNTAX     Unsigned32 (0..20)
   ACCESS     read-write
   STATUS     mandatory
   DESCRIPTION
     "This attribute specifies the number of times a frame can be 
      retransmitted by the SVC data link layer before appropriate 
      recovery action is taken."
   DEFVAL     { 3 }
::= { mscFrUniSigLapfSysEntry 3 }

mscFrUniSigAckTimer OBJECT-TYPE
   SYNTAX     Unsigned32 (1000..10000)
   ACCESS     read-write
   STATUS     mandatory
   DESCRIPTION
     "This attribute specifies how long the layer 2 protocol waits for an 
      acknowledgment to a sent frame. The value set for ackTimer must 
      be less than the value set for idleProbeTimer."
   DEFVAL     { 1500 }
::= { mscFrUniSigLapfSysEntry 4 }

mscFrUniSigAckDelayTimer OBJECT-TYPE
   SYNTAX     Unsigned32 (0..10000)
   ACCESS     read-write
   STATUS     mandatory
   DESCRIPTION
     "This attribute specifies how long the network waits before sending 
      an acknowledgment for a received in-sequence I-frame. A value of 
      0 means that every frame is acknowledged and there will be no 
      delay in acknowledgment. A non-zero value means that one 
      acknowledgement is sent for a number of frames."
   DEFVAL     { 0 }
::= { mscFrUniSigLapfSysEntry 5 }

mscFrUniSigIdleProbeTimer OBJECT-TYPE
   SYNTAX     Unsigned32 (1000..65535000)
   ACCESS     read-write
   STATUS     mandatory
   DESCRIPTION
     "This attribute specifies how long the link is permitted to remain idle 
      (that is, no frames are exchanged on the data link). Upon expiry of 
      this timer, the network side's link layer polls its peer for status. The 
      value set for idleProbeTimer must be greater than the value set for 
      ackTimer."
   DEFVAL     { 30000 }
::= { mscFrUniSigLapfSysEntry 6 }

mscFrUniSigStateTable OBJECT-TYPE
   SYNTAX     SEQUENCE OF MscFrUniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrUniSig 15 }

mscFrUniSigStateEntry OBJECT-TYPE
   SYNTAX     MscFrUniSigStateEntry
   ACCESS     not-accessible
   STATUS     mandatory
   DESCRIPTION
     "An entry in the mscFrUniSigStateTable."
   INDEX {
      mscFrUniIndex,
      mscFrUniSigIndex }
::= { mscFrUniSigStateTable 1 }

MscFrUniSigStateEntry ::= SEQUENCE {
   mscFrUniSigAdminState
      INTEGER,
   mscFrUniSigOperationalState
      INTEGER,
   mscFrUniSigUsageState
      INTEGER }

mscFrUniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrUniSigStateEntry 1 }

mscFrUniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrUniSigStateEntry 2 }

mscFrUniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrUniSigStateEntry 3 }

mscFrUniSigStatsTable OBJECT-TYPE
   SYNTAX     SEQUENCE OF MscFrUniSigStatsEntry
   ACCESS     not-accessible
   STATUS     mandatory
   DESCRIPTION
     "This group contains the statistics related to the SVC signaling layer 
      at the interface level."
::= { mscFrUniSig 16 }

mscFrUniSigStatsEntry OBJECT-TYPE
   SYNTAX     MscFrUniSigStatsEntry
   ACCESS     not-accessible
   STATUS     mandatory
   DESCRIPTION
     "An entry in the mscFrUniSigStatsTable."
   INDEX {
      mscFrUniIndex,
      mscFrUniSigIndex }
::= { mscFrUniSigStatsTable 1 }

MscFrUniSigStatsEntry ::= SEQUENCE {
   mscFrUniSigCurrentNumberOfSvcCalls
      Gauge32,
   mscFrUniSigInCalls
      Gauge32,
   mscFrUniSigInCallsRefused
      Counter32,
   mscFrUniSigOutCalls
      Gauge32,
   mscFrUniSigOutCallsFailed
      Counter32,
   mscFrUniSigProtocolErrors
      Counter32,
   mscFrUniSigQualityOfServiceNotAvailable
      Counter32,
   mscFrUniSigSetupTimeout
      Counter32,
   mscFrUniSigLastCauseInStatusMsgReceived
      Unsigned32,
   mscFrUniSigLastStateInStatusMsgReceived
      INTEGER,
   mscFrUniSigLastDlciReceivedStatus
      Unsigned32,
   mscFrUniSigLastStateReceivedStatus
      INTEGER,
   mscFrUniSigLastTimeMsgBlockCongested
      EnterpriseDateAndTime,
   mscFrUniSigLastDlciWithMsgBlockCongestion
      Unsigned32,
   mscFrUniSigCurrentAggregateSvcCirNormalQ
      Unsigned32,
   mscFrUniSigCurrentAggregateSvcCirHighQ
      Unsigned32,
   mscFrUniSigCurrentAggregateSvcCirInterruptQ
      Unsigned32,
   mscFrUniSigCurrentAggregateSvcEirNormalQ
      Unsigned32,
   mscFrUniSigCurrentAggregateSvcEirHighQ
      Unsigned32,
   mscFrUniSigCurrentAggregateSvcEirInterruptQ
      Unsigned32 }

mscFrUniSigCurrentNumberOfSvcCalls OBJECT-TYPE
   SYNTAX     Gauge32 (0..992)
   ACCESS     read-only
   STATUS     mandatory
   DESCRIPTION
     "This attribute indicates the number of Frame Relay SVCs currently 
      existing on this interface."
::= { mscFrUniSigStatsEntry 1 }

mscFrUniSigInCalls OBJECT-TYPE
   SYNTAX     Gauge32 (0..992)
   ACCESS     read-only
   STATUS     mandatory
   DESCRIPTION
     "This attribute indicates the current number of incoming SVCs on 
      this interface (that is, the number of SVCs for which this interface 
      represents the destination end of the call)."
::= { mscFrUniSigStatsEntry 4 }

mscFrUniSigInCallsRefused OBJECT-TYPE
   SYNTAX     Counter32 
   ACCESS     read-only
   STATUS     mandatory
   DESCRIPTION
     "This attribute counts the incoming SVC call requests that are 
      rejected by either this interface or by the called user. When this 
      count exceeds the maximum, it wraps to zero."
::= { mscFrUniSigStatsEntry 5 }

mscFrUniSigOutCalls OBJECT-TYPE
   SYNTAX     Gauge32 (0..992)
   ACCESS     read-only
   STATUS     mandatory
   DESCRIPTION
     "This attribute indicates the current number of outgoing SVCs on 
      this interface (that is, the number of SVCs for which this interface 
      represents the source end of the call)."
::= { mscFrUniSigStatsEntry 6 }

mscFrUniSigOutCallsFailed OBJECT-TYPE
   SYNTAX     Counter32 
   ACCESS     read-only
   STATUS     mandatory
   DESCRIPTION
     "This attribute counts the outgoing SVC call requests that are 
      rejected by either this interface, or by the network side of the 
      destination end, or by the called user. When this count exceeds the 
      maximum, it wraps to zero."
::= { mscFrUniSigStatsEntry 7 }

mscFrUniSigProtocolErrors OBJECT-TYPE
   SYNTAX     Counter32 
   ACCESS     read-only
   STATUS     mandatory
   DESCRIPTION
     "This attribute counts the number of times a FRF.4 protocol error has 
      occurred. Any one of the following events constitutes a protocol 
      error:
      1. In the user-signaled Link Layer Core Parameters IE within the
      SETUP or CONNECT messages, Cir, Bc and Be are all zero;
      2. In the user-signaled Link Layer Core Parameters IE within the
      SETUP or CONNECT messages, Cir is zero but Bc is 
      non-zero, or Bc is zero but Cir is non-zero;
      3. In the user-signaled Link Layer Core Parameters IE within the
      SETUP or CONNECT messages, the Minimum Acceptable CIR
      is greater than Cir;
      4. At the destination end, any of the destination to source direction 
      link layer core parameters has been increased in the 
      CONNECT message from the called user;
      5. At the destination end, the destination to source direction Cir
      in the CONNECT message is smaller than the corresponding 
      minimum acceptable Cir signaled to the called user;
      6. At the source end, any of the source to destination direction 
      link layer core parameters in the CONNECT message from the 
      destination end has been increased;
      7. At the source end, the source to destination direction Cir, after
      negotiation, is smaller than the corresponding minimum
      acceptable Cir;
      8. The network has received a STATUS message from the user
      with an incompatible FRF.4 state.	
      
      When this count reaches maximum, it wraps to zero."
::= { mscFrUniSigStatsEntry 8 }

mscFrUniSigQualityOfServiceNotAvailable OBJECT-TYPE
   SYNTAX     Counter32 
   ACCESS     read-only
   STATUS     mandatory
   DESCRIPTION
     "This attribute counts the number of incoming and outgoing SVCs 
      that are rejected because the quality of service requested cannot be 
      met by the network. When this count reaches maximum, it wraps to 
      zero."
::= { mscFrUniSigStatsEntry 9 }

mscFrUniSigSetupTimeout OBJECT-TYPE
   SYNTAX     Counter32 
   ACCESS     read-only
   STATUS     mandatory
   DESCRIPTION
     "This attribute counts the number of times the T303 setup timer has 
      expired. When this count reaches maximum, it wraps to zero."
::= { mscFrUniSigStatsEntry 10 }

mscFrUniSigLastCauseInStatusMsgReceived OBJECT-TYPE
   SYNTAX     Unsigned32 (0..255)
   ACCESS     read-only
   STATUS     mandatory
   DESCRIPTION
     "This attribute indicates the cause value in the last received user's 
      STATUS message to an existing call. The DLCI to which this 
      STATUS message applies is specified in the lastDlciReceivedStatus 
      attribute.
      
      The initial value of this attribute is 0 which means that no STATUS 
      message has been received for an existing call yet."
   DEFVAL     { 0 }
::= { mscFrUniSigStatsEntry 11 }

mscFrUniSigLastStateInStatusMsgReceived OBJECT-TYPE
   SYNTAX     INTEGER  {
                 null(0),
                 callInitiated(1),
                 n2(2),
                 outgoingCallProceeding(3),
                 n4(4),
                 n5(5),
                 callPresent(6),
                 n7(7),
                 n8(8),
                 incomingCallProceeding(9),
                 active(10),
                 disconnectRequest(11),
                 disconnectIndication(12),
                 n13(13),
                 n14(14),
                 n15(15),
                 n16(16),
                 n17(17),
                 n18(18),
                 releaseRequest(19),
                 notApplicable(20),
                 n21(21),
                 n22(22),
                 n23(23),
                 n24(24),
                 n25(25),
                 n26(26),
                 n27(27),
                 n28(28),
                 n29(29),
                 n30(30),
                 n31(31),
                 n32(32),
                 n33(33),
                 n34(34),
                 n35(35),
                 n36(36),
                 n37(37),
                 n38(38),
                 n39(39),
                 n40(40),
                 n41(41),
                 n42(42),
                 n43(43),
                 n44(44),
                 n45(45),
                 n46(46),
                 n47(47),
                 n48(48),
                 n49(49),
                 n50(50),
                 n51(51),
                 n52(52),
                 n53(53),
                 n54(54),
                 n55(55),
                 n56(56),
                 n57(57),
                 n58(58),
                 n59(59),
                 n60(60),
                 restartRequest(61),
                 restart(62),
                 n63(63) }
   ACCESS     read-only
   STATUS     mandatory
   DESCRIPTION
     "This attribute indicates the state value in the last received user's 
      STATUS message to an existing call. The DLCI to which this 
      STATUS message applies is specified in the lastDlciReceivedStatus 
      attribute.
      
      The initial value of this attribute is notApplicable."
   DEFVAL     { notApplicable }
::= { mscFrUniSigStatsEntry 12 }

mscFrUniSigLastDlciReceivedStatus OBJECT-TYPE
   SYNTAX     Unsigned32 (0 | 16..1007)
   ACCESS     read-only
   STATUS     mandatory
   DESCRIPTION
     "This attribute shows the value of the DLCI that has most recently 
      received a STATUS message from the user.
      
      The initial value of this attribute is 0."
   DEFVAL     { 0 }
::= { mscFrUniSigStatsEntry 13 }

mscFrUniSigLastStateReceivedStatus OBJECT-TYPE
   SYNTAX     INTEGER  {
                 null(0),
                 callInitiated(1),
                 outgoingCallProceeding(3),
                 callPresent(6),
                 incomingCallProceeding(9),
                 active(10),
                 disconnectRequest(11),
                 disconnectIndication(12),
                 releaseRequest(19),
                 notApplicable(20),
                 restartRequest(61),
                 restart(62) }
   ACCESS     read-only
   STATUS     obsolete
   DESCRIPTION
     "This attribute shows the network FRF.4 state of the DLCI that has 
      most recently received a STATUS message from the user. The DLCI 
      to which this STATUS message applies is specified in the 
      lastDlciReceivedStatus attribute.
      
      The initial value of this attribute is notApplicable."
   DEFVAL     { notApplicable }
::= { mscFrUniSigStatsEntry 14 }

mscFrUniSigLastTimeMsgBlockCongested OBJECT-TYPE
   SYNTAX     EnterpriseDateAndTime (SIZE (0 | 16))
   ACCESS     read-only
   STATUS     obsolete
   DESCRIPTION
     "This attribute displays the most recent time that an SVC DLCI has 
      failed to get a message block due to message block congestion. 
      Exceptional behavior can occur due to this. The DLCI that has most 
      recently encountered this is indicated by the 
      lastDlciWithMsgBlockCongestion attribute. However, all SVC 
      DLCIs may be affected.
      
      The initial value of this attribute is 0000-00-00 00:00."
::= { mscFrUniSigStatsEntry 15 }

mscFrUniSigLastDlciWithMsgBlockCongestion OBJECT-TYPE
   SYNTAX     Unsigned32 (0 | 16..1007)
   ACCESS     read-only
   STATUS     obsolete
   DESCRIPTION
     "This attribute shows the value of the DLCI that has most recently 
      failed to get a message block due to message block congestion.
      
      The initial value of this attribute is 0."
   DEFVAL     { 0 }
::= { mscFrUniSigStatsEntry 16 }

mscFrUniSigCurrentAggregateSvcCirNormalQ OBJECT-TYPE
   SYNTAX     Unsigned32 (0..4294967295)
   ACCESS     read-only
   STATUS     obsolete
   DESCRIPTION
     "This attribute shows the aggregate SVC CIR (for traffic transiting in 
      the network through normal priority queue) assigned to existing 
      SVCs on the interface.
      
      The value of currentAggregateSvcCirNormalQ could be greater 
      than the provisionable value of maximumAggregateSvcCiNormalQ 
      if the value of maximumAggregateSvcCirNormalQ has been 
      changed during the service of this FrUni."
::= { mscFrUniSigStatsEntry 17 }

mscFrUniSigCurrentAggregateSvcCirHighQ OBJECT-TYPE
   SYNTAX     Unsigned32 (0..4294967295)
   ACCESS     read-only
   STATUS     obsolete
   DESCRIPTION
     "This attribute shows the aggregate SVC CIR (for traffic transiting in 
      the network through high priority queue) assigned to existing SVCs 
      on the interface.
      
      The value of currentAggregateSvcCirHighQ could be greater than 
      the provisionable value of maximumAggregateSvcCirHighQ if the 
      value of maximumAggregateSvcCirHighQ has been changed during 
      the service of this FrUni."
::= { mscFrUniSigStatsEntry 18 }

mscFrUniSigCurrentAggregateSvcCirInterruptQ OBJECT-TYPE
   SYNTAX     Unsigned32 (0..4294967295)
   ACCESS     read-only
   STATUS     obsolete
   DESCRIPTION
     "This attribute shows the aggregate SVC CIR (for traffic transiting in 
      the network through interrupting queue) assigned to existing SVCs 
      on the interface.
      
      The value of currentAggregateSvcCirInterruptQ could be greater 
      than the provisionable value of 
      maximumAggregateSvcCirInterruptQ if the value of 
      maximumAggregateSvcCirInterruptQ has been changed during the 
      service of this FrUni."
::= { mscFrUniSigStatsEntry 19 }

mscFrUniSigCurrentAggregateSvcEirNormalQ OBJECT-TYPE
   SYNTAX     Unsigned32 (0..4294967295)
   ACCESS     read-only
   STATUS     obsolete
   DESCRIPTION
     "This attribute shows the aggregate SVC EIR (for excess traffic 
      transiting in the network through normal priority queue) assigned to 
      existing SVCs on the interface.
      
      The value of currentAggregateSvcEirNormalQ could be greater 
      than the provisionable value of maximumAggregateSvcEirNormalQ 
      if the value of maximumAggregateSvcEiNormalQ has been changed 
      during the service of this FrUni or unlimitedAggregateEir is set to 
      yes."
::= { mscFrUniSigStatsEntry 20 }

mscFrUniSigCurrentAggregateSvcEirHighQ OBJECT-TYPE
   SYNTAX     Unsigned32 (0..4294967295)
   ACCESS     read-only
   STATUS     obsolete
   DESCRIPTION
     "This attribute shows the aggregate SVC EIR (for excess traffic 
      transiting in the network through high priority queue) assigned to 
      existing SVCs on the interface.
      
      The value of currentAggregateSvcEirHighQ could be greater than 
      the provisionable value of maximumAggregateSvcEirHighQ if the 
      value of maximumAggregateSvcEirHighQ has been changed during 
      the service of this FrUni or unlimitedAggregateEir is set to yes."
::= { mscFrUniSigStatsEntry 21 }

mscFrUniSigCurrentAggregateSvcEirInterruptQ OBJECT-TYPE
   SYNTAX     Unsigned32 (0..4294967295)
   ACCESS     read-only
   STATUS     obsolete
   DESCRIPTION
     "This attribute shows the aggregate SVC EIR (for excess traffic 
      transiting in the network through interrupting queue) assigned to 
      existing SVCs on the interface.
      
      The value of currentAggregateSvcEirInterruptQ could be greater 
      than the provisionable value of 
      maximumAggregateSvcEirInterruptQ if the value of 
      maximumAggregateSvcEirInterruptQ has been changed during the 
      service of this FrUni or unlimitedAggregateEir is set to yes."
::= { mscFrUniSigStatsEntry 22 }

mscFrUniSigLapfStatusTable OBJECT-TYPE
   SYNTAX     SEQUENCE OF MscFrUniSigLapfStatusEntry
   ACCESS     not-accessible
   STATUS     mandatory
   DESCRIPTION
     "This group contains the Q.922 SVC data link layer status."
::= { mscFrUniSig 17 }

mscFrUniSigLapfStatusEntry OBJECT-TYPE
   SYNTAX     MscFrUniSigLapfStatusEntry
   ACCESS     not-accessible
   STATUS     mandatory
   DESCRIPTION
     "An entry in the mscFrUniSigLapfStatusTable."
   INDEX {
      mscFrUniIndex,
      mscFrUniSigIndex }
::= { mscFrUniSigLapfStatusTable 1 }

MscFrUniSigLapfStatusEntry ::= SEQUENCE {
   mscFrUniSigCurrentState
      INTEGER,
   mscFrUniSigLastStateChangeReason
      INTEGER,
   mscFrUniSigFrmrReceive
      HexString,
   mscFrUniSigCurrentQueueSize
      Counter32 }

mscFrUniSigCurrentState OBJECT-TYPE
   SYNTAX     INTEGER  {
                 disconnected(1),
                 linkSetup(2),
                 disconnectRequest(4),
                 informationTransfer(5),
                 waitingAck(7) }
   ACCESS     read-only
   STATUS     mandatory
   DESCRIPTION
     "This attribute shows the current state of the SVC data link layer 
      interface."
::= { mscFrUniSigLapfStatusEntry 1 }

mscFrUniSigLastStateChangeReason OBJECT-TYPE
   SYNTAX     INTEGER  {
                 notStarted(1),
                 abmeEntered(3),
                 abmeReset(5),
                 dmReceived(6),
                 dmSent(7),
                 discReceived(8),
                 discSent(9),
                 frmrReceived(10),
                 n200RetranTimeOut(12),
                 other(13) }
   ACCESS     read-only
   STATUS     mandatory
   DESCRIPTION
     "This attribute shows the reason for the most recent state change.
      notStarted - this is the default state after SVC data link has just 
      been created.
      
      abmeEntered - SVC data link has entered Asynchronous Balanced 
      Mode after SABME or UA has been received.
      abmeReset - the data link has been reset.
      dmReceived - DM response received.
      dmSent - DM sent.
      discReceived - DISC response received.
      discSent - DISC sent.
      frmrReceived - FRMR received.
      n200RetranTimeOut - retransmitLimit has been exceeded.
      other - unspecified state change reasons. The most likely reason for 
      this is the transition from state waitingAck to state 
      informationTransfer."
   DEFVAL     { notStarted }
::= { mscFrUniSigLapfStatusEntry 2 }

mscFrUniSigFrmrReceive OBJECT-TYPE
   SYNTAX     HexString (SIZE (0..8))
   ACCESS     read-only
   STATUS     mandatory
   DESCRIPTION
     "This attribute shows the information field of the Frame Reject 
      (FRMR) most recently received."
::= { mscFrUniSigLapfStatusEntry 3 }

mscFrUniSigCurrentQueueSize OBJECT-TYPE
   SYNTAX     Counter32 
   ACCESS     read-only
   STATUS     mandatory
   DESCRIPTION
     "This attribute shows the current number of frames in the SVC data 
      link layer transmit queue."
::= { mscFrUniSigLapfStatusEntry 4 }

mscFrUniSigLapfStatsTable OBJECT-TYPE
   SYNTAX     SEQUENCE OF MscFrUniSigLapfStatsEntry
   ACCESS     not-accessible
   STATUS     mandatory
   DESCRIPTION
     "This group contains the statistics for the SVC data link layer."
::= { mscFrUniSig 18 }

mscFrUniSigLapfStatsEntry OBJECT-TYPE
   SYNTAX     MscFrUniSigLapfStatsEntry
   ACCESS     not-accessible
   STATUS     mandatory
   DESCRIPTION
     "An entry in the mscFrUniSigLapfStatsTable."
   INDEX {
      mscFrUniIndex,
      mscFrUniSigIndex }
::= { mscFrUniSigLapfStatsTable 1 }

MscFrUniSigLapfStatsEntry ::= SEQUENCE {
   mscFrUniSigStateChange
      Counter32,
   mscFrUniSigRemoteBusy
      Counter32,
   mscFrUniSigReceiveRejectFrame
      Counter32,
   mscFrUniSigAckTimeout
      Counter32,
   mscFrUniSigIFramesTransmitted
      Counter32,
   mscFrUniSigIFramesTxDiscarded
      Counter32,
   mscFrUniSigIFramesReceived
      Counter32,
   mscFrUniSigIFramesRcvdDiscarded
      Counter32 }

mscFrUniSigStateChange OBJECT-TYPE
   SYNTAX     Counter32 
   ACCESS     read-only
   STATUS     mandatory
   DESCRIPTION
     "This attribute counts the number of times the SVC data link layer 
      interface has changed state. While the data link layer is in 
      informationTransfer state, this counter will increment on each 
      expiry of idleProbeTimer as its state goes from 
      informationTransfer to waitingAck and back. When this count 
      exceeds the maximum, it wraps to zero."
::= { mscFrUniSigLapfStatsEntry 1 }

mscFrUniSigRemoteBusy OBJECT-TYPE
   SYNTAX     Counter32 
   ACCESS     read-only
   STATUS     mandatory
   DESCRIPTION
     "This attribute counts the number of times transmission of an I-frame 
      was unsuccessful due to a perceived remote busy condition 
      (window closed or remote busy). When this count reaches 
      maximum, it wraps to zero."
::= { mscFrUniSigLapfStatsEntry 2 }

mscFrUniSigReceiveRejectFrame OBJECT-TYPE
   SYNTAX     Counter32 
   ACCESS     read-only
   STATUS     mandatory
   DESCRIPTION
     "This attribute counts the number of REJ frames received by the 
      interface. When this count reaches maximum, it wraps to zero."
::= { mscFrUniSigLapfStatsEntry 3 }

mscFrUniSigAckTimeout OBJECT-TYPE
   SYNTAX     Counter32 
   ACCESS     read-only
   STATUS     mandatory
   DESCRIPTION
     "This attribute counts the number of times the ackTimer has expired. 
      Frequent increments of this counter indicate a problem at the link or 
      improper values have been chosen for ackTimer and ackDelayTimer 
      between the local and remote sides. When this count reaches 
      maximum, it wraps to zero."
::= { mscFrUniSigLapfStatsEntry 4 }

mscFrUniSigIFramesTransmitted OBJECT-TYPE
   SYNTAX     Counter32 
   ACCESS     read-only
   STATUS     mandatory
   DESCRIPTION
     "This attribute counts the number of SVC I-frames transmitted to the 
      interface on DLCI 0. An I-frame may be counted more than once if 
      there are retransmissions at the SVC data link layer. When this 
      count reaches maximum, it wraps to zero."
::= { mscFrUniSigLapfStatsEntry 5 }

mscFrUniSigIFramesTxDiscarded OBJECT-TYPE
   SYNTAX     Counter32 
   ACCESS     read-only
   STATUS     mandatory
   DESCRIPTION
     "This attribute counts the number of SVC I-frames that are bound for 
      the link but have been discarded. Discard reasons may be one of the 
      following:
      1.	 the frame length is beyond the allowed limit.
      2.	 the SVC data link layer is in disconnected state.
      3. 	the transmit queue has been purged because the queue length 
      has reached the reset threshold.
      4.	 the transmit queue or the queue waiting for acknowledgment
      has been 			purged because the link cannot be re-established.
      
      When this count reaches maximum, it wraps to zero."
::= { mscFrUniSigLapfStatsEntry 6 }

mscFrUniSigIFramesReceived OBJECT-TYPE
   SYNTAX     Counter32 
   ACCESS     read-only
   STATUS     mandatory
   DESCRIPTION
     "This attribute counts the number of SVC I-frames received from the 
      interface. When this count reaches maximum, it wraps to zero."
::= { mscFrUniSigLapfStatsEntry 7 }

mscFrUniSigIFramesRcvdDiscarded OBJECT-TYPE
   SYNTAX     Counter32 
   ACCESS     read-only
   STATUS     mandatory
   DESCRIPTION
     "This attribute counts the number of SVC I-frames received but have 
      been discarded. The discard reasons are:
      1.	 incorrect frame size
      2. frame is out of sequence
      3. frame received while the network side of the SVC data link
      layer is not in the informationTransfer or waitingAck state.
      
      When this count reaches maximum, it wraps to zero."
::= { mscFrUniSigLapfStatsEntry 8 }

mscFrUniSigSvcaccTable OBJECT-TYPE
   SYNTAX     SEQUENCE OF MscFrUniSigSvcaccEntry
   ACCESS     not-accessible
   STATUS     mandatory
   DESCRIPTION
     "This group contains the provisionable attribute which controls 
      accounting for this interface."
::= { mscFrUniSig 19 }

mscFrUniSigSvcaccEntry OBJECT-TYPE
   SYNTAX     MscFrUniSigSvcaccEntry
   ACCESS     not-accessible
   STATUS     mandatory
   DESCRIPTION
     "An entry in the mscFrUniSigSvcaccTable."
   INDEX {
      mscFrUniIndex,
      mscFrUniSigIndex }
::= { mscFrUniSigSvcaccTable 1 }

MscFrUniSigSvcaccEntry ::= SEQUENCE {
   mscFrUniSigDefaultAccounting
      INTEGER }

mscFrUniSigDefaultAccounting OBJECT-TYPE
   SYNTAX     INTEGER  {
                 off(0),
                 on(1) }
   ACCESS     read-write
   STATUS     mandatory
   DESCRIPTION
     "This attribute specifies whether accounting data collection and 
      record generation is turned on for switched connections at this 
      interface. For accounting data collection and record generation to 
      occur, this attribute must be on and at least one of the 
      accountCollection reasons in the Dna component must be present."
   DEFVAL     { on }
::= { mscFrUniSigSvcaccEntry 1 }

mscFrUniSigCodesTable OBJECT-TYPE
   SYNTAX     SEQUENCE OF MscFrUniSigCodesEntry
   ACCESS     not-accessible
   STATUS     mandatory
   DESCRIPTION
     "This group contains the remote data network address, the last SVC 
      clear cause and the last SVC diagnostic code coming from the 
      subnet or the local VC."
::= { mscFrUniSig 20 }

mscFrUniSigCodesEntry OBJECT-TYPE
   SYNTAX     MscFrUniSigCodesEntry
   ACCESS     not-accessible
   STATUS     mandatory
   DESCRIPTION
     "An entry in the mscFrUniSigCodesTable."
   INDEX {
      mscFrUniIndex,
      mscFrUniSigIndex }
::= { mscFrUniSigCodesTable 1 }

MscFrUniSigCodesEntry ::= SEQUENCE {
   mscFrUniSigLastClearRemoteDataNetworkAddress
      DigitString,
   mscFrUniSigLastClearCause
      Unsigned32,
   mscFrUniSigLastDiagnosticCode
      Unsigned32 }

mscFrUniSigLastClearRemoteDataNetworkAddress OBJECT-TYPE
   SYNTAX     DigitString (SIZE (0..15))
   ACCESS     read-only
   STATUS     mandatory
   DESCRIPTION
     "This attribute indicates the Data Network Address (DNA) of the
      remote (the other end of the SVC connection) of the call which 
      cleared last and whose clear and diagnostic codes were recorded."
::= { mscFrUniSigCodesEntry 1 }

mscFrUniSigLastClearCause OBJECT-TYPE
   SYNTAX     Unsigned32 (0..255)
   ACCESS     read-only
   STATUS     mandatory
   DESCRIPTION
     "This attribute indicates the last SVC clear cause signalled at the end 
      of the connection or failure to connect. It is updated only if the clear 
      request comes from the subnet or the call is rejected locally by the 
      VC. The same set of possible values provides the clear cause field 
      in the accounting record."
   DEFVAL     { 0 }
::= { mscFrUniSigCodesEntry 2 }

mscFrUniSigLastDiagnosticCode OBJECT-TYPE
   SYNTAX     Unsigned32 (0..255)
   ACCESS     read-only
   STATUS     mandatory
   DESCRIPTION
     "This attribute indicates the last SVC diagnostic code signalled at the 
      end of the connection or failure to connect. It is updated if the clear 
      request comes from the subnet or the call is rejected locally by the 
      VC. The same set of possible values provides the diagnostic code 
      field in the accounting record."
   DEFVAL     { 0 }
::= { mscFrUniSigCodesEntry 3 }

mscFrUniSigBandwidthNotAvailableTable OBJECT-TYPE
   SYNTAX     SEQUENCE OF MscFrUniSigBandwidthNotAvailableEntry
   ACCESS     not-accessible
   STATUS     mandatory
   DESCRIPTION
     "This attribute counts the number of call failures for each bandwidth 
      pool due to the requested bandwidth not being available."
::= { mscFrUniSig 711 }

mscFrUniSigBandwidthNotAvailableEntry OBJECT-TYPE
   SYNTAX     MscFrUniSigBandwidthNotAvailableEntry
   ACCESS     not-accessible
   STATUS     mandatory
   DESCRIPTION
     "An entry in the mscFrUniSigBandwidthNotAvailableTable."
   INDEX {
      mscFrUniIndex,
      mscFrUniSigIndex,
      mscFrUniSigBandwidthNotAvailableIndex }
::= { mscFrUniSigBandwidthNotAvailableTable 1 }

MscFrUniSigBandwidthNotAvailableEntry ::= SEQUENCE {
   mscFrUniSigBandwidthNotAvailableIndex
      Integer32,
   mscFrUniSigBandwidthNotAvailableValue
      Counter32 }

mscFrUniSigBandwidthNotAvailableIndex OBJECT-TYPE
   SYNTAX     Integer32 (0..15)
   ACCESS     not-accessible
   STATUS     mandatory
   DESCRIPTION
     "This variable represents the mscFrUniSigBandwidthNotAvailableTable
      specific index for the mscFrUniSigBandwidthNotAvailableTable."
::= { mscFrUniSigBandwidthNotAvailableEntry 1 }

mscFrUniSigBandwidthNotAvailableValue OBJECT-TYPE
   SYNTAX     Counter32 
   ACCESS     read-only
   STATUS     mandatory
   DESCRIPTION
     "This variable represents an individual value for the
      mscFrUniSigBandwidthNotAvailableTable."
::= { mscFrUniSigBandwidthNotAvailableEntry 2 }


-- FrUni/n VirtualFramer
-- FrDte/n VirtualFramer
-- The VirtualFramer component binds two services together to 
-- provide data transfer between them. It is mutually exclusive from 
-- Framer component. 

mscFrUniVFramer OBJECT IDENTIFIER ::= { mscFrUni 8 }



mscFrUniVFramerRowStatusTable OBJECT-TYPE
   SYNTAX     SEQUENCE OF MscFrUniVFramerRowStatusEntry
   ACCESS     not-accessible
   STATUS     mandatory
   DESCRIPTION
     "This entry controls the addition and deletion of 
      mscFrUniVFramer components."
::= { mscFrUniVFramer 1 }

mscFrUniVFramerRowStatusEntry OBJECT-TYPE
   SYNTAX     MscFrUniVFramerRowStatusEntry
   ACCESS     not-accessible
   STATUS     mandatory
   DESCRIPTION
     "A single entry in the table represents a single 
      mscFrUniVFramer component."
   INDEX {
      mscFrUniIndex,
      mscFrUniVFramerIndex }
::= { mscFrUniVFramerRowStatusTable 1 }

MscFrUniVFramerRowStatusEntry ::= SEQUENCE {
   mscFrUniVFramerRowStatus
      RowStatus,
   mscFrUniVFramerComponentName
      DisplayString,
   mscFrUniVFramerStorageType
      StorageType,
   mscFrUniVFramerIndex
      NonReplicated }

mscFrUniVFramerRowStatus OBJECT-TYPE
   SYNTAX     RowStatus 
   ACCESS     read-write
   STATUS     mandatory
   DESCRIPTION
     "This variable is used as the basis for SNMP naming of
      mscFrUniVFramer components.
      These components can be added and deleted."
::= { mscFrUniVFramerRowStatusEntry 1 }

mscFrUniVFramerComponentName OBJECT-TYPE
   SYNTAX     DisplayString 
   ACCESS     read-only
   STATUS     mandatory
   DESCRIPTION
     "This variable provides the component's string name for
      use with the ASCII Console Interface"
::= { mscFrUniVFramerRowStatusEntry 2 }

mscFrUniVFramerStorageType OBJECT-TYPE
   SYNTAX     StorageType 
   ACCESS     read-only
   STATUS     mandatory
   DESCRIPTION
     "This variable represents the storage type value for the
      mscFrUniVFramer tables."
::= { mscFrUniVFramerRowStatusEntry 4 }

mscFrUniVFramerIndex OBJECT-TYPE
   SYNTAX     NonReplicated 
   ACCESS     not-accessible
   STATUS     mandatory
   DESCRIPTION
     "This variable represents the index for the mscFrUniVFramer tables."
::= { mscFrUniVFramerRowStatusEntry 10 }

mscFrUniVFramerProvTable OBJECT-TYPE
   SYNTAX     SEQUENCE OF MscFrUniVFramerProvEntry
   ACCESS     not-accessible
   STATUS     mandatory
   DESCRIPTION
     "This group contains provisionable attributes for the VirtualFramer 
      component."
::= { mscFrUniVFramer 10 }

mscFrUniVFramerProvEntry OBJECT-TYPE
   SYNTAX     MscFrUniVFramerProvEntry
   ACCESS     not-accessible
   STATUS     mandatory
   DESCRIPTION
     "An entry in the mscFrUniVFramerProvTable."
   INDEX {
      mscFrUniIndex,
      mscFrUniVFramerIndex }
::= { mscFrUniVFramerProvTable 1 }

MscFrUniVFramerProvEntry ::= SEQUENCE {
   mscFrUniVFramerOtherVirtualFramer
      Link,
   mscFrUniVFramerLogicalProcessor
      Link }

mscFrUniVFramerOtherVirtualFramer OBJECT-TYPE
   SYNTAX     Link 
   ACCESS     read-write
   STATUS     mandatory
   DESCRIPTION
     "This attribute specifies the other VirtualFramer to which the service 
      is linked, for example, FrUni/n VirtualFramer, FrDte/n 
      VirtualFramer."
::= { mscFrUniVFramerProvEntry 1 }

mscFrUniVFramerLogicalProcessor OBJECT-TYPE
   SYNTAX     Link 
   ACCESS     read-write
   STATUS     mandatory
   DESCRIPTION
     "This attribute specifies the logical processor on which the service 
      component will reside."
::= { mscFrUniVFramerProvEntry 2 }

mscFrUniVFramerStateTable OBJECT-TYPE
   SYNTAX     SEQUENCE OF MscFrUniVFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscFrUniVFramer 11 }

mscFrUniVFramerStateEntry OBJECT-TYPE
   SYNTAX     MscFrUniVFramerStateEntry
   ACCESS     not-accessible
   STATUS     mandatory
   DESCRIPTION
     "An entry in the mscFrUniVFramerStateTable."
   INDEX {
      mscFrUniIndex,
      mscFrUniVFramerIndex }
::= { mscFrUniVFramerStateTable 1 }

MscFrUniVFramerStateEntry ::= SEQUENCE {
   mscFrUniVFramerAdminState
      INTEGER,
   mscFrUniVFramerOperationalState
      INTEGER,
   mscFrUniVFramerUsageState
      INTEGER }

mscFrUniVFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscFrUniVFramerStateEntry 1 }

mscFrUniVFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscFrUniVFramerStateEntry 2 }

mscFrUniVFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscFrUniVFramerStateEntry 3 }

mscFrUniVFramerStatsTable OBJECT-TYPE
   SYNTAX     SEQUENCE OF MscFrUniVFramerStatsEntry
   ACCESS     not-accessible
   STATUS     mandatory
   DESCRIPTION
     "This group contains the operational statistics data for a 
      VirtualFramer component."
::= { mscFrUniVFramer 12 }

mscFrUniVFramerStatsEntry OBJECT-TYPE
   SYNTAX     MscFrUniVFramerStatsEntry
   ACCESS     not-accessible
   STATUS     mandatory
   DESCRIPTION
     "An entry in the mscFrUniVFramerStatsTable."
   INDEX {
      mscFrUniIndex,
      mscFrUniVFramerIndex }
::= { mscFrUniVFramerStatsTable 1 }

MscFrUniVFramerStatsEntry ::= SEQUENCE {
   mscFrUniVFramerFrmToOtherVFramer
      PassportCounter64,
   mscFrUniVFramerFrmFromOtherVFramer
      PassportCounter64,
   mscFrUniVFramerOctetFromOtherVFramer
      PassportCounter64 }

mscFrUniVFramerFrmToOtherVFramer OBJECT-TYPE
   SYNTAX     PassportCounter64 
   ACCESS     read-only
   STATUS     mandatory
   DESCRIPTION
     "This attribute counts the frames transmitted to the 
      otherVirtualFramer."
::= { mscFrUniVFramerStatsEntry 2 }

mscFrUniVFramerFrmFromOtherVFramer OBJECT-TYPE
   SYNTAX     PassportCounter64 
   ACCESS     read-only
   STATUS     mandatory
   DESCRIPTION
     "This attribute counts the frames received from the 
      otherVirtualFramer."
::= { mscFrUniVFramerStatsEntry 3 }

mscFrUniVFramerOctetFromOtherVFramer OBJECT-TYPE
   SYNTAX     PassportCounter64 
   ACCESS     read-only
   STATUS     mandatory
   DESCRIPTION
     "This attribute counts the octets received from the 
      otherVirtualFramer."
::= { mscFrUniVFramerStatsEntry 5 }


-- FrUni/n LoadTestSystem
-- FrNni/n LoadTestSystem
-- This component defines an instance of the Frame Relay Load Test 
-- System (UNI) service. The component instance value n is a unique 
-- positive integer within a module.

mscFrUniLts OBJECT IDENTIFIER ::= { mscFrUni 9 }



mscFrUniLtsRowStatusTable OBJECT-TYPE
   SYNTAX     SEQUENCE OF MscFrUniLtsRowStatusEntry
   ACCESS     not-accessible
   STATUS     mandatory
   DESCRIPTION
     "This entry controls the addition and deletion of 
      mscFrUniLts components."
::= { mscFrUniLts 1 }

mscFrUniLtsRowStatusEntry OBJECT-TYPE
   SYNTAX     MscFrUniLtsRowStatusEntry
   ACCESS     not-accessible
   STATUS     mandatory
   DESCRIPTION
     "A single entry in the table represents a single 
      mscFrUniLts component."
   INDEX {
      mscFrUniIndex,
      mscFrUniLtsIndex }
::= { mscFrUniLtsRowStatusTable 1 }

MscFrUniLtsRowStatusEntry ::= SEQUENCE {
   mscFrUniLtsRowStatus
      RowStatus,
   mscFrUniLtsComponentName
      DisplayString,
   mscFrUniLtsStorageType
      StorageType,
   mscFrUniLtsIndex
      NonReplicated }

mscFrUniLtsRowStatus OBJECT-TYPE
   SYNTAX     RowStatus 
   ACCESS     read-write
   STATUS     mandatory
   DESCRIPTION
     "This variable is used as the basis for SNMP naming of
      mscFrUniLts components.
      These components can be added and deleted."
::= { mscFrUniLtsRowStatusEntry 1 }

mscFrUniLtsComponentName OBJECT-TYPE
   SYNTAX     DisplayString 
   ACCESS     read-only
   STATUS     mandatory
   DESCRIPTION
     "This variable provides the component's string name for
      use with the ASCII Console Interface"
::= { mscFrUniLtsRowStatusEntry 2 }

mscFrUniLtsStorageType OBJECT-TYPE
   SYNTAX     StorageType 
   ACCESS     read-only
   STATUS     mandatory
   DESCRIPTION
     "This variable represents the storage type value for the
      mscFrUniLts tables."
::= { mscFrUniLtsRowStatusEntry 4 }

mscFrUniLtsIndex OBJECT-TYPE
   SYNTAX     NonReplicated 
   ACCESS     not-accessible
   STATUS     mandatory
   DESCRIPTION
     "This variable represents the index for the mscFrUniLts tables."
::= { mscFrUniLtsRowStatusEntry 10 }

mscFrUniLtsSetupTable OBJECT-TYPE
   SYNTAX     SEQUENCE OF MscFrUniLtsSetupEntry
   ACCESS     not-accessible
   STATUS     mandatory
   DESCRIPTION
     "This attribute group contains the parameters used to configure the 
      behavior of the Frame Relay Load Test System."
::= { mscFrUniLts 10 }

mscFrUniLtsSetupEntry OBJECT-TYPE
   SYNTAX     MscFrUniLtsSetupEntry
   ACCESS     not-accessible
   STATUS     mandatory
   DESCRIPTION
     "An entry in the mscFrUniLtsSetupTable."
   INDEX {
      mscFrUniIndex,
      mscFrUniLtsIndex }
::= { mscFrUniLtsSetupTable 1 }

MscFrUniLtsSetupEntry ::= SEQUENCE {
   mscFrUniLtsDuration
      Unsigned32,
   mscFrUniLtsAlgorithm
      INTEGER,
   mscFrUniLtsBurstSize
      Unsigned32,
   mscFrUniLtsTimeInterval
      Unsigned32 }

mscFrUniLtsDuration OBJECT-TYPE
   SYNTAX     Unsigned32 (0..4294967295)
   ACCESS     read-write
   STATUS     mandatory
   DESCRIPTION
     "This attribute specifies the duration of the test in milliseconds. The 
      test will run until the duration expires or the STOP command is 
      issued. A value of 0 is used to indicate infinity."
   DEFVAL     { 0 }
::= { mscFrUniLtsSetupEntry 200 }

mscFrUniLtsAlgorithm OBJECT-TYPE
   SYNTAX     INTEGER  {
                 continousBurst(0),
                 intervalBurst(1),
                 delayBurst(2),
                 fixedBurst(3) }
   ACCESS     read-write
   STATUS     mandatory
   DESCRIPTION
     "This attribute specifies which algorithm is used to generate the 
      frames.
      
      ContinuousBurst
      This mode of traffic generation creates traffic at the maximum rate 
      possible until all of the frames have been sent. The generator then 
      waits until the end of the timeInterval to begin again.
      
      IntervalBurst
      This algorithm attempts to generate 10 ms bursts of burstSize 
      frames. It will generate as many of the burstSize frames as it can per 
      sub-interval.
      
      DelayedBurst
      This algorithm generates bursts of burstSize frames separated by 10 
      ms delays.
      
      FixedBurst
      This aglorithm is similar to IntervalBurst, except a fixed burst size 
      of 12 frames is used.
      
      delayMeasurement
      This algorithm is used to measure delay. The specified number of 
      frames in the indicated pattern are generated, one at a time, with a 
      maximum wait of maxDelay before sending the next frame.
      This algorithm is not implemented yet."
   DEFVAL     { continousBurst }
::= { mscFrUniLtsSetupEntry 201 }

mscFrUniLtsBurstSize OBJECT-TYPE
   SYNTAX     Unsigned32 (1..250)
   ACCESS     read-write
   STATUS     mandatory
   DESCRIPTION
     "This attribute specifies the number of frames per burst under the 
      delayedBurst and intervalBurst algorithms."
   DEFVAL     { 50 }
::= { mscFrUniLtsSetupEntry 204 }

mscFrUniLtsTimeInterval OBJECT-TYPE
   SYNTAX     Unsigned32 (1..60000)
   ACCESS     read-write
   STATUS     mandatory
   DESCRIPTION
     "This attribute specifies the time interval to the specified number of 
      seconds. Granuality is in centiseconds. Maximum is 1 minute."
   DEFVAL     { 100 }
::= { mscFrUniLtsSetupEntry 205 }

mscFrUniLtsStateTable OBJECT-TYPE
   SYNTAX     SEQUENCE OF MscFrUniLtsStateEntry
   ACCESS     not-accessible
   STATUS     mandatory
   DESCRIPTION
     "This group contains the operation statistics of the load generator."
::= { mscFrUniLts 11 }

mscFrUniLtsStateEntry OBJECT-TYPE
   SYNTAX     MscFrUniLtsStateEntry
   ACCESS     not-accessible
   STATUS     mandatory
   DESCRIPTION
     "An entry in the mscFrUniLtsStateTable."
   INDEX {
      mscFrUniIndex,
      mscFrUniLtsIndex }
::= { mscFrUniLtsStateTable 1 }

MscFrUniLtsStateEntry ::= SEQUENCE {
   mscFrUniLtsGeneratorState
      INTEGER,
   mscFrUniLtsCycleIncomplete
      INTEGER,
   mscFrUniLtsLastActiveInterval
      Unsigned32,
   mscFrUniLtsLoad
      FixedPoint3,
   mscFrUniLtsElapsedGenerationTime
      Unsigned32 }

mscFrUniLtsGeneratorState OBJECT-TYPE
   SYNTAX     INTEGER  {
                 stopped(0),
                 running(1) }
   ACCESS     read-only
   STATUS     mandatory
   DESCRIPTION
     "This attribute indicates whether the Lts is generating traffic."
   DEFVAL     { stopped }
::= { mscFrUniLtsStateEntry 200 }

mscFrUniLtsCycleIncomplete OBJECT-TYPE
   SYNTAX     INTEGER  {
                 false(0),
                 true(1) }
   ACCESS     read-only
   STATUS     mandatory
   DESCRIPTION
     "This attribute indicates whether the time required to generate all of 
      the enabled patterns is more than timeInterval by a true value. 
      Otherwise, this flag is set to false. Default is True."
   DEFVAL     { true }
::= { mscFrUniLtsStateEntry 201 }

mscFrUniLtsLastActiveInterval OBJECT-TYPE
   SYNTAX     Unsigned32 (0..4294967295)
   ACCESS     read-only
   STATUS     mandatory
   DESCRIPTION
     "This attribute indicates the actual time it took to generate all of the 
      enabled patterns in the last cycle. If cycleIncomplete is true, this 
      value should be zero."
::= { mscFrUniLtsStateEntry 202 }

mscFrUniLtsLoad OBJECT-TYPE
   SYNTAX     FixedPoint3 (0..4294967295)
   ACCESS     read-only
   STATUS     mandatory
   DESCRIPTION
     "This attribute indicates the load being generated. This value 
      represents that calculated using the set number of ticks. The actual 
      burstTimeInterval may differ. One entire cycle of the patterns is 
      completed in activeInterval and thus most of the load may be 
      concentrated early in the set interval."
::= { mscFrUniLtsStateEntry 204 }

mscFrUniLtsElapsedGenerationTime OBJECT-TYPE
   SYNTAX     Unsigned32 (0..4294967295)
   ACCESS     read-only
   STATUS     mandatory
   DESCRIPTION
     "This attribute indicates how many milliseconds have elapsed since 
      the start of this test."
::= { mscFrUniLtsStateEntry 205 }

mscFrUniLtsResultsTable OBJECT-TYPE
   SYNTAX     SEQUENCE OF MscFrUniLtsResultsEntry
   ACCESS     not-accessible
   STATUS     mandatory
   DESCRIPTION
     "This group contains the frame counting attributes for the LTS 
      component."
::= { mscFrUniLts 12 }

mscFrUniLtsResultsEntry OBJECT-TYPE
   SYNTAX     MscFrUniLtsResultsEntry
   ACCESS     not-accessible
   STATUS     mandatory
   DESCRIPTION
     "An entry in the mscFrUniLtsResultsTable."
   INDEX {
      mscFrUniIndex,
      mscFrUniLtsIndex }
::= { mscFrUniLtsResultsTable 1 }

MscFrUniLtsResultsEntry ::= SEQUENCE {
   mscFrUniLtsFramesTx
      Counter32,
   mscFrUniLtsBytesTx
      Unsigned32,
   mscFrUniLtsBitRateTx
      FixedPoint3,
   mscFrUniLtsFrameRateTx
      Unsigned32 }

mscFrUniLtsFramesTx OBJECT-TYPE
   SYNTAX     Counter32 
   ACCESS     read-only
   STATUS     mandatory
   DESCRIPTION
     "This attribute specifies the number of frames send to the network 
      since the last time these statistics were cleared. This is similar to the 
      framesToIf attribute of the FRAMER component."
::= { mscFrUniLtsResultsEntry 200 }

mscFrUniLtsBytesTx OBJECT-TYPE
   SYNTAX     Unsigned32 (0..4294967295)
   ACCESS     read-only
   STATUS     mandatory
   DESCRIPTION
     "This attribute indicates the number of bytes sent."
   DEFVAL     { 0 }
::= { mscFrUniLtsResultsEntry 204 }

mscFrUniLtsBitRateTx OBJECT-TYPE
   SYNTAX     FixedPoint3 (0..4294967295)
   ACCESS     read-only
   STATUS     mandatory
   DESCRIPTION
     "This attribute indicates the bit rate being sent to the link. It should 
      only differ from the load if the burstTimeInterval would be >= the 
      timeInterval or burstSize frames cannot be generated in 10ms 
      (intervalBurst algorithm)."
   DEFVAL     { 0 }
::= { mscFrUniLtsResultsEntry 208 }

mscFrUniLtsFrameRateTx OBJECT-TYPE
   SYNTAX     Unsigned32 (0..4294967295)
   ACCESS     read-only
   STATUS     mandatory
   DESCRIPTION
     "This attribute indicates the frame rate being sent to the link. It is 
      calculated using the number of frames sent to the link in one cycle 
      of the patterns."
   DEFVAL     { 0 }
::= { mscFrUniLtsResultsEntry 209 }


-- FrUni/n Lts Pattern
-- FrNni/n Lts Pattern
-- Each instance of this component specifies a pattern to be generated 
-- as part of each cycle.  One cycle represents one pass through each 
-- pattern.

mscFrUniLtsPat OBJECT IDENTIFIER ::= { mscFrUniLts 2 }



mscFrUniLtsPatRowStatusTable OBJECT-TYPE
   SYNTAX     SEQUENCE OF MscFrUniLtsPatRowStatusEntry
   ACCESS     not-accessible
   STATUS     mandatory
   DESCRIPTION
     "This entry controls the addition and deletion of 
      mscFrUniLtsPat components."
::= { mscFrUniLtsPat 1 }

mscFrUniLtsPatRowStatusEntry OBJECT-TYPE
   SYNTAX     MscFrUniLtsPatRowStatusEntry
   ACCESS     not-accessible
   STATUS     mandatory
   DESCRIPTION
     "A single entry in the table represents a single 
      mscFrUniLtsPat component."
   INDEX {
      mscFrUniIndex,
      mscFrUniLtsIndex,
      mscFrUniLtsPatIndex }
::= { mscFrUniLtsPatRowStatusTable 1 }

MscFrUniLtsPatRowStatusEntry ::= SEQUENCE {
   mscFrUniLtsPatRowStatus
      RowStatus,
   mscFrUniLtsPatComponentName
      DisplayString,
   mscFrUniLtsPatStorageType
      StorageType,
   mscFrUniLtsPatIndex
      Integer32 }

mscFrUniLtsPatRowStatus OBJECT-TYPE
   SYNTAX     RowStatus 
   ACCESS     read-write
   STATUS     mandatory
   DESCRIPTION
     "This variable is used as the basis for SNMP naming of
      mscFrUniLtsPat components.
      These components can be added and deleted."
::= { mscFrUniLtsPatRowStatusEntry 1 }

mscFrUniLtsPatComponentName OBJECT-TYPE
   SYNTAX     DisplayString 
   ACCESS     read-only
   STATUS     mandatory
   DESCRIPTION
     "This variable provides the component's string name for
      use with the ASCII Console Interface"
::= { mscFrUniLtsPatRowStatusEntry 2 }

mscFrUniLtsPatStorageType OBJECT-TYPE
   SYNTAX     StorageType 
   ACCESS     read-only
   STATUS     mandatory
   DESCRIPTION
     "This variable represents the storage type value for the
      mscFrUniLtsPat tables."
::= { mscFrUniLtsPatRowStatusEntry 4 }

mscFrUniLtsPatIndex OBJECT-TYPE
   SYNTAX     Integer32 (0..29)
   ACCESS     not-accessible
   STATUS     mandatory
   DESCRIPTION
     "This variable represents the index for the mscFrUniLtsPat tables."
::= { mscFrUniLtsPatRowStatusEntry 10 }

mscFrUniLtsPatDefaultsTable OBJECT-TYPE
   SYNTAX     SEQUENCE OF MscFrUniLtsPatDefaultsEntry
   ACCESS     not-accessible
   STATUS     mandatory
   DESCRIPTION
     "This attribute group contains the specifications of the pattern."
::= { mscFrUniLtsPat 10 }

mscFrUniLtsPatDefaultsEntry OBJECT-TYPE
   SYNTAX     MscFrUniLtsPatDefaultsEntry
   ACCESS     not-accessible
   STATUS     mandatory
   DESCRIPTION
     "An entry in the mscFrUniLtsPatDefaultsTable."
   INDEX {
      mscFrUniIndex,
      mscFrUniLtsIndex,
      mscFrUniLtsPatIndex }
::= { mscFrUniLtsPatDefaultsTable 1 }

MscFrUniLtsPatDefaultsEntry ::= SEQUENCE {
   mscFrUniLtsPatDefaultDlci
      Unsigned32,
   mscFrUniLtsPatDefaultNumFrames
      Unsigned32,
   mscFrUniLtsPatDefaultDataSize
      Unsigned32,
   mscFrUniLtsPatDefaultHeaderBits
      OCTET STRING,
   mscFrUniLtsPatDefaultHeaderLength
      Unsigned32,
   mscFrUniLtsPatDefaultEABits
      Hex,
   mscFrUniLtsPatDefaultPayloadPattern
      HexString,
   mscFrUniLtsPatDefaultRfc1490Header
      INTEGER,
   mscFrUniLtsPatDefaultUseBadLrc
      INTEGER }

mscFrUniLtsPatDefaultDlci OBJECT-TYPE
   SYNTAX     Unsigned32 (16..1007)
   ACCESS     read-write
   STATUS     mandatory
   DESCRIPTION
     "This attribute specifies for which dlci (on the local end) the frames 
      are destined."
   DEFVAL     { 16 }
::= { mscFrUniLtsPatDefaultsEntry 200 }

mscFrUniLtsPatDefaultNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { mscFrUniLtsPatDefaultsEntry 201 }

mscFrUniLtsPatDefaultDataSize OBJECT-TYPE
   SYNTAX     Unsigned32 (0..8200)
   ACCESS     read-write
   STATUS     mandatory
   DESCRIPTION
     "This attribute specifies the payload size of each frame in bytes.  
      This is in excess to the header."
   DEFVAL     { 512 }
::= { mscFrUniLtsPatDefaultsEntry 202 }

mscFrUniLtsPatDefaultHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { mscFrUniLtsPatDefaultsEntry 203 }

mscFrUniLtsPatDefaultHeaderLength OBJECT-TYPE
   SYNTAX     Unsigned32 (0 | 2..4)
   ACCESS     read-write
   STATUS     mandatory
   DESCRIPTION
     "This attribute specifies the size of the frame relay header in bytes.  
      Passport currently only supports a 2-byte header."
   DEFVAL     { 2 }
::= { mscFrUniLtsPatDefaultsEntry 204 }

mscFrUniLtsPatDefaultEABits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate 
      EABits is 2, or 0010.  This attribute can be used to create a header 
      of length greater than two bytes or to specify incorrect EABits in 
      the header."
   DEFVAL     { 4 }
::= { mscFrUniLtsPatDefaultsEntry 205 }

mscFrUniLtsPatDefaultPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { mscFrUniLtsPatDefaultsEntry 206 }

mscFrUniLtsPatDefaultRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { mscFrUniLtsPatDefaultsEntry 207 }

mscFrUniLtsPatDefaultUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { mscFrUniLtsPatDefaultsEntry 208 }

mscFrUniLtsPatSetupTable OBJECT-TYPE
   SYNTAX     SEQUENCE OF MscFrUniLtsPatSetupEntry
   ACCESS     not-accessible
   STATUS     mandatory
   DESCRIPTION
     "This attribute group contains the specifications of the pattern."
::= { mscFrUniLtsPat 11 }

mscFrUniLtsPatSetupEntry OBJECT-TYPE
   SYNTAX     MscFrUniLtsPatSetupEntry
   ACCESS     not-accessible
   STATUS     mandatory
   DESCRIPTION
     "An entry in the mscFrUniLtsPatSetupTable."
   INDEX {
      mscFrUniIndex,
      mscFrUniLtsIndex,
      mscFrUniLtsPatIndex }
::= { mscFrUniLtsPatSetupTable 1 }

MscFrUniLtsPatSetupEntry ::= SEQUENCE {
   mscFrUniLtsPatDlci
      Unsigned32,
   mscFrUniLtsPatNumFrames
      Unsigned32,
   mscFrUniLtsPatDataSize
      Unsigned32,
   mscFrUniLtsPatHeaderBits
      OCTET STRING,
   mscFrUniLtsPatHeaderLength
      Unsigned32,
   mscFrUniLtsPatEaBits
      Hex,
   mscFrUniLtsPatPayloadPattern
      HexString,
   mscFrUniLtsPatRfc1490Header
      INTEGER,
   mscFrUniLtsPatUseBadLrc
      INTEGER }

mscFrUniLtsPatDlci OBJECT-TYPE
   SYNTAX     Unsigned32 (16..1007)
   ACCESS     read-write
   STATUS     mandatory
   DESCRIPTION
     "This attribute specifies for which dlci (on the local end) the frames 
      are destined."
   DEFVAL     { 16 }
::= { mscFrUniLtsPatSetupEntry 200 }

mscFrUniLtsPatNumFrames OBJECT-TYPE
   SYNTAX     Unsigned32 (0..4294967295)
   ACCESS     read-write
   STATUS     mandatory
   DESCRIPTION
     "This attribute specifies the number of frames in this pattern.  This is 
      the number of frames of this type which will be generated in one 
      timeInterval."
   DEFVAL     { 100 }
::= { mscFrUniLtsPatSetupEntry 201 }

mscFrUniLtsPatDataSize OBJECT-TYPE
   SYNTAX     Unsigned32 (0..8200)
   ACCESS     read-write
   STATUS     mandatory
   DESCRIPTION
     "This attribute specifies the payload size of each frame in bytes.  
      This is in excess to the header."
   DEFVAL     { 512 }
::= { mscFrUniLtsPatSetupEntry 202 }

mscFrUniLtsPatHeaderBits OBJECT-TYPE
   SYNTAX     OCTET STRING (SIZE (1))
   ACCESS     read-write
   STATUS     mandatory
   DESCRIPTION
     "This attribute specifies whether the following bits are on/off in the 
      header of each frame. The following bits can be set:
      BeCn, C/R, De, FeCn

      Description of bits:
      becn(0)
      fecn(1)
      cr(2)
      de(3)"
::= { mscFrUniLtsPatSetupEntry 203 }

mscFrUniLtsPatHeaderLength OBJECT-TYPE
   SYNTAX     Unsigned32 (0 | 2..4)
   ACCESS     read-write
   STATUS     mandatory
   DESCRIPTION
     "This attribute specifies the size of the frame relay header in bytes.  
      Passport currently only supports a 2-byte header.  Valid values are 
      0, 2, 3, 4.  0 indicates to use no header.  That is, the frame will start 
      with either the payload or rfc1490 header."
   DEFVAL     { 2 }
::= { mscFrUniLtsPatSetupEntry 204 }

mscFrUniLtsPatEaBits OBJECT-TYPE
   SYNTAX     Hex (0..15)
   ACCESS     read-write
   STATUS     mandatory
   DESCRIPTION
     "This attribute specifies how the address field extension bits are set in 
      the frame header.  Consider the value to be a four bit binary number.  
      For example, 4 = 0100.  Only the first headerLength bits are used. 
      For instance, suppose headerLength is 3, then the appropriate eaBits 
      is 2, or 0010.  This attribute can be used to create a header of length 
      greater than two bytes or to specify incorrect eaBits in the header."
   DEFVAL     { 4 }
::= { mscFrUniLtsPatSetupEntry 205 }

mscFrUniLtsPatPayloadPattern OBJECT-TYPE
   SYNTAX     HexString (SIZE (1..12))
   ACCESS     read-write
   STATUS     mandatory
   DESCRIPTION
     "This attribute specifies the payload of each frame.  The value 
      specified is in hexadecimal, where every two digits represent a byte.  
      A maximum of 24 digits (12 bytes) may be set, after which the 
      pattern will repeat in the payload (depending on repeatPattern 
      attribute). 
      NOTE: If a RFC 1490 header is specified, via the 1490Header 
      attribute, the specified pattern will begin following the header (i.e. 
      at the 9th byte in the payload)."
   DEFVAL     { '55'H }  -- "55"
::= { mscFrUniLtsPatSetupEntry 206 }

mscFrUniLtsPatRfc1490Header OBJECT-TYPE
   SYNTAX     INTEGER  {
                 n0(0),
                 n1(1),
                 n2(2),
                 n3(3),
                 n4(4),
                 n5(5),
                 n6(6),
                 n7(7),
                 n8(8),
                 n9(9),
                 n10(10),
                 n11(11),
                 n12(12),
                 n13(13),
                 n14(14),
                 n15(15),
                 n16(16),
                 n17(17),
                 none(18) }
   ACCESS     read-write
   STATUS     mandatory
   DESCRIPTION
     "This attribute specifies the appropriate RFC 1490 encapsulated 
      header of the frame.  A value of 0 indicates no 1490 header.
      NOTE: This header resides in the first 8 bytes of the payload.  If the 
      specified value is non-zero, then the payload pattern provisioned 
      will begin at the 9th byte."
   DEFVAL     { none }
::= { mscFrUniLtsPatSetupEntry 207 }

mscFrUniLtsPatUseBadLrc OBJECT-TYPE
   SYNTAX     INTEGER  {
                 no(0),
                 yes(1) }
   ACCESS     read-write
   STATUS     mandatory
   DESCRIPTION
     "This attribute specifies whether the frames from this pattern are to 
      have a bad LRC prior to being sent to the framer.  The LRC is 
      checked while the frame is being put onto the link and the failure 
      should cause an abort frame to be sent."
   DEFVAL     { no }
::= { mscFrUniLtsPatSetupEntry 208 }

mscFrUniLtsPatOpDataTable OBJECT-TYPE
   SYNTAX     SEQUENCE OF MscFrUniLtsPatOpDataEntry
   ACCESS     not-accessible
   STATUS     mandatory
   DESCRIPTION
     "This group contains the operational attributes which allow changing 
      the pattern outside of provisioning mode."
::= { mscFrUniLtsPat 12 }

mscFrUniLtsPatOpDataEntry OBJECT-TYPE
   SYNTAX     MscFrUniLtsPatOpDataEntry
   ACCESS     not-accessible
   STATUS     mandatory
   DESCRIPTION
     "An entry in the mscFrUniLtsPatOpDataTable."
   INDEX {
      mscFrUniIndex,
      mscFrUniLtsIndex,
      mscFrUniLtsPatIndex }
::= { mscFrUniLtsPatOpDataTable 1 }

MscFrUniLtsPatOpDataEntry ::= SEQUENCE {
   mscFrUniLtsPatFramePattern
      HexString,
   mscFrUniLtsPatHdlcBitsInserted
      Unsigned32 }

mscFrUniLtsPatFramePattern OBJECT-TYPE
   SYNTAX     HexString (SIZE (20..24))
   ACCESS     read-only
   STATUS     mandatory
   DESCRIPTION
     "This attribute displays the first 20 to 24 bytes of the frame payload, 
      depending on the frame relay header size selected.  This attribute 
      represents the frame if it were at least 20 to 24 bytes in size.  That 
      is, the actual frame may be smaller."
::= { mscFrUniLtsPatOpDataEntry 200 }

mscFrUniLtsPatHdlcBitsInserted OBJECT-TYPE
   SYNTAX     Unsigned32 (0..65535)
   ACCESS     read-only
   STATUS     mandatory
   DESCRIPTION
     "This attribute displays how many times a zero bit will be inserted 
      after 5 consecutive 1 bits when a frame from this pattern is sent out."
::= { mscFrUniLtsPatOpDataEntry 201 }

mscFrUniLtsPatOpStateTable OBJECT-TYPE
   SYNTAX     SEQUENCE OF MscFrUniLtsPatOpStateEntry
   ACCESS     not-accessible
   STATUS     mandatory
   DESCRIPTION
     "This group contains the attributes containing the operational 
      statistics of the pattern."
::= { mscFrUniLtsPat 13 }

mscFrUniLtsPatOpStateEntry OBJECT-TYPE
   SYNTAX     MscFrUniLtsPatOpStateEntry
   ACCESS     not-accessible
   STATUS     mandatory
   DESCRIPTION
     "An entry in the mscFrUniLtsPatOpStateTable."
   INDEX {
      mscFrUniIndex,
      mscFrUniLtsIndex,
      mscFrUniLtsPatIndex }
::= { mscFrUniLtsPatOpStateTable 1 }

MscFrUniLtsPatOpStateEntry ::= SEQUENCE {
   mscFrUniLtsPatLoad
      FixedPoint3,
   mscFrUniLtsPatStatus
      INTEGER }

mscFrUniLtsPatLoad OBJECT-TYPE
   SYNTAX     FixedPoint3 (0..4294967295)
   ACCESS     read-only
   STATUS     mandatory
   DESCRIPTION
     "This attribute indicates the load due to this particular pattern.  The 
      loads associated with all of the provisioned patterns are summed to 
      arrive at the FrLts load."
::= { mscFrUniLtsPatOpStateEntry 200 }

mscFrUniLtsPatStatus OBJECT-TYPE
   SYNTAX     INTEGER  {
                 enabled(0),
                 disabled(1) }
   ACCESS     read-write
   STATUS     mandatory
   DESCRIPTION
     "This attributes specifies the administrative state of the pattern.  A 
      disabled pattern will not be generated, although it can still be 
      triggered."
   DEFVAL     { enabled }
::= { mscFrUniLtsPatOpStateEntry 201 }


-- FrNni/n ConnectionAdministrator
-- The Ca component allows the network operator to specify common 
-- subscription options for the parent  interface. It defines the call 
-- admission control parameters in the ingress and egress direction for 
-- the parent interface. 

mscFrUniCa OBJECT IDENTIFIER ::= { mscFrUni 101 }



mscFrUniCaRowStatusTable OBJECT-TYPE
   SYNTAX     SEQUENCE OF MscFrUniCaRowStatusEntry
   ACCESS     not-accessible
   STATUS     mandatory
   DESCRIPTION
     "This entry controls the addition and deletion of 
      mscFrUniCa components."
::= { mscFrUniCa 1 }

mscFrUniCaRowStatusEntry OBJECT-TYPE
   SYNTAX     MscFrUniCaRowStatusEntry
   ACCESS     not-accessible
   STATUS     mandatory
   DESCRIPTION
     "A single entry in the table represents a single 
      mscFrUniCa component."
   INDEX {
      mscFrUniIndex,
      mscFrUniCaIndex }
::= { mscFrUniCaRowStatusTable 1 }

MscFrUniCaRowStatusEntry ::= SEQUENCE {
   mscFrUniCaRowStatus
      RowStatus,
   mscFrUniCaComponentName
      DisplayString,
   mscFrUniCaStorageType
      StorageType,
   mscFrUniCaIndex
      NonReplicated }

mscFrUniCaRowStatus OBJECT-TYPE
   SYNTAX     RowStatus 
   ACCESS     read-only
   STATUS     mandatory
   DESCRIPTION
     "This variable is used as the basis for SNMP naming of
      mscFrUniCa components.
      These components cannot be added nor deleted."
::= { mscFrUniCaRowStatusEntry 1 }

mscFrUniCaComponentName OBJECT-TYPE
   SYNTAX     DisplayString 
   ACCESS     read-only
   STATUS     mandatory
   DESCRIPTION
     "This variable provides the component's string name for
      use with the ASCII Console Interface"
::= { mscFrUniCaRowStatusEntry 2 }

mscFrUniCaStorageType OBJECT-TYPE
   SYNTAX     StorageType 
   ACCESS     read-only
   STATUS     mandatory
   DESCRIPTION
     "This variable represents the storage type value for the
      mscFrUniCa tables."
::= { mscFrUniCaRowStatusEntry 4 }

mscFrUniCaIndex OBJECT-TYPE
   SYNTAX     NonReplicated 
   ACCESS     not-accessible
   STATUS     mandatory
   DESCRIPTION
     "This variable represents the index for the mscFrUniCa tables."
::= { mscFrUniCaRowStatusEntry 10 }

mscFrUniCaProvTable OBJECT-TYPE
   SYNTAX     SEQUENCE OF MscFrUniCaProvEntry
   ACCESS     not-accessible
   STATUS     mandatory
   DESCRIPTION
     "This attribute group contains the common provisionable attributes 
      of the Ca component."
::= { mscFrUniCa 10 }

mscFrUniCaProvEntry OBJECT-TYPE
   SYNTAX     MscFrUniCaProvEntry
   ACCESS     not-accessible
   STATUS     mandatory
   DESCRIPTION
     "An entry in the mscFrUniCaProvTable."
   INDEX {
      mscFrUniIndex,
      mscFrUniCaIndex }
::= { mscFrUniCaProvTable 1 }

MscFrUniCaProvEntry ::= SEQUENCE {
   mscFrUniCaOverrideLinkRate
      Unsigned32,
   mscFrUniCaMaximumBandwidthPerCall
      Unsigned32 }

mscFrUniCaOverrideLinkRate OBJECT-TYPE
   SYNTAX     Unsigned32 (0..429496729)
   ACCESS     read-write
   STATUS     mandatory
   DESCRIPTION
     "This attribute allows the link rate to be overridden for this interface.  
      This allows the user to specify a value other than the actual physical 
      link rate computed when a Framer component is provisioned.  
      When a VFramer component is provisioned, this attribute overrides 
      a link rate set to the maximum value supported by CAC .
      
      This attribute serves to provide the user control on the amount of 
      bandwidth available for performing CAC."
   DEFVAL     { 0 }
::= { mscFrUniCaProvEntry 2 }

mscFrUniCaMaximumBandwidthPerCall OBJECT-TYPE
   SYNTAX     Unsigned32 (0..520000000)
   ACCESS     read-write
   STATUS     mandatory
   DESCRIPTION
     "This attribute specifies the maximum bandwidth that can be 
      allocated per connection."
   DEFVAL     { 520000000 }
::= { mscFrUniCaProvEntry 3 }

mscFrUniCaIngressCacTable OBJECT-TYPE
   SYNTAX     SEQUENCE OF MscFrUniCaIngressCacEntry
   ACCESS     not-accessible
   STATUS     mandatory
   DESCRIPTION
     "This attribute group contains the common provisionable attributes 
      for ingress call admission control."
::= { mscFrUniCa 11 }

mscFrUniCaIngressCacEntry OBJECT-TYPE
   SYNTAX     MscFrUniCaIngressCacEntry
   ACCESS     not-accessible
   STATUS     mandatory
   DESCRIPTION
     "An entry in the mscFrUniCaIngressCacTable."
   INDEX {
      mscFrUniIndex,
      mscFrUniCaIndex }
::= { mscFrUniCaIngressCacTable 1 }

MscFrUniCaIngressCacEntry ::= SEQUENCE {
   mscFrUniCaIngressApplyToCos
      INTEGER,
   mscFrUniCaIngressMaximumEirOnlyCalls
      Unsigned32 }

mscFrUniCaIngressApplyToCos OBJECT-TYPE
   SYNTAX     INTEGER  {
                 none(0),
                 cirOnly(1),
                 cirAndEir(2) }
   ACCESS     read-write
   STATUS     mandatory
   DESCRIPTION
     "This attribute specifies which Classes of Service (CoS) have ingress 
      Call Admission Control (CAC) applied to them. Ingress CAC 
      applies only to swithced connections (SVCs and S-SPVCs).
      
      none - Ingress CAC is turned off for all classes of service.
      cirOnly - Ingress CAC is applied only to the CIR portion of a 
      connection's bandwidth requirements for CIR>0 classes of service.
      cirAndEir - Ingress CAC is applied to both CIR and EIR portions 
      of a connections bandwidth requirements for all classes of service."
   DEFVAL     { cirOnly }
::= { mscFrUniCaIngressCacEntry 2 }

mscFrUniCaIngressMaximumEirOnlyCalls OBJECT-TYPE
   SYNTAX     Unsigned32 (0..992)
   ACCESS     read-write
   STATUS     mandatory
   DESCRIPTION
     "This attribute specifies the maximum number of connections in the 
      ingress direction with EIR only traffic that can be up at a given 
      time."
   DEFVAL     { 992 }
::= { mscFrUniCaIngressCacEntry 4 }

mscFrUniCaEgressCacTable OBJECT-TYPE
   SYNTAX     SEQUENCE OF MscFrUniCaEgressCacEntry
   ACCESS     not-accessible
   STATUS     mandatory
   DESCRIPTION
     "This attribute group contains the common provisionable attributes 
      for egress call admission control."
::= { mscFrUniCa 12 }

mscFrUniCaEgressCacEntry OBJECT-TYPE
   SYNTAX     MscFrUniCaEgressCacEntry
   ACCESS     not-accessible
   STATUS     mandatory
   DESCRIPTION
     "An entry in the mscFrUniCaEgressCacTable."
   INDEX {
      mscFrUniIndex,
      mscFrUniCaIndex }
::= { mscFrUniCaEgressCacTable 1 }

MscFrUniCaEgressCacEntry ::= SEQUENCE {
   mscFrUniCaEgressApplyToCos
      INTEGER,
   mscFrUniCaEgressMaximumEirOnlyCalls
      Unsigned32 }

mscFrUniCaEgressApplyToCos OBJECT-TYPE
   SYNTAX     INTEGER  {
                 none(0),
                 cirOnly(1),
                 cirAndEir(2) }
   ACCESS     read-write
   STATUS     mandatory
   DESCRIPTION
     "This attribute specifies which Classes of Service (CoS) have egress 
      Call Admission Control (CAC) applied to them. Egress CAC 
      applies only to swithced connections (SVCs and S-SPVCs).
      
      none - Egress CAC is turned off for all classes of service.
      cirOnly - Egress CAC is applied only to the CIR portion of a 
      connection's bandwidth requirements for CIR>0 classes of service.
      cirAndEir - Egress CAC is applied to both CIR and EIR portions of 
      a connections bandwidth requirements for all classes of service."
   DEFVAL     { none }
::= { mscFrUniCaEgressCacEntry 2 }

mscFrUniCaEgressMaximumEirOnlyCalls OBJECT-TYPE
   SYNTAX     Unsigned32 (0..992)
   ACCESS     read-write
   STATUS     mandatory
   DESCRIPTION
     "This attribute specifies the maximum number of connections in the 
      egress direction with EIR only traffic that can be up at a given time."
   DEFVAL     { 992 }
::= { mscFrUniCaEgressCacEntry 4 }

mscFrUniCaOpTable OBJECT-TYPE
   SYNTAX     SEQUENCE OF MscFrUniCaOpEntry
   ACCESS     not-accessible
   STATUS     mandatory
   DESCRIPTION
     "This attribute group contains the operational status of the Ca 
      component."
::= { mscFrUniCa 13 }

mscFrUniCaOpEntry OBJECT-TYPE
   SYNTAX     MscFrUniCaOpEntry
   ACCESS     not-accessible
   STATUS     mandatory
   DESCRIPTION
     "An entry in the mscFrUniCaOpTable."
   INDEX {
      mscFrUniIndex,
      mscFrUniCaIndex }
::= { mscFrUniCaOpTable 1 }

MscFrUniCaOpEntry ::= SEQUENCE {
   mscFrUniCaLinkRate
      Unsigned32,
   mscFrUniCaNumberRejectedEgressCirPermConn
      Gauge32,
   mscFrUniCaNumberRejectedEgressEirPermConn
      Gauge32 }

mscFrUniCaLinkRate OBJECT-TYPE
   SYNTAX     Unsigned32 (0..520000000)
   ACCESS     read-only
   STATUS     mandatory
   DESCRIPTION
     "This attribute indicates the link rate used by both ingress and egress 
      CAC to calculate the effective bandwidth pool sizes.
      
      If the provisionable attribute overrideLinkRate under this 
      component is 0, then the link rate reported is the actual link rate of 
      the port or channel.  Otherwise, the link rate reported is the 
      overrideLinkRate under this component."
::= { mscFrUniCaOpEntry 2 }

mscFrUniCaNumberRejectedEgressCirPermConn OBJECT-TYPE
   SYNTAX     Gauge32 (0..992)
   ACCESS     read-only
   STATUS     mandatory
   DESCRIPTION
     "This attribute indicates the number of permanent connections (that 
      is, PVC and P-SPVC) that are rejected by egress CAC. A 
      connection is rejected by egress CAC if it requests more egress CIR 
      bandwidth than is available, and the egressApplyToCos attribute is 
      set to either cirOnly or cirAndEir."
::= { mscFrUniCaOpEntry 681 }

mscFrUniCaNumberRejectedEgressEirPermConn OBJECT-TYPE
   SYNTAX     Gauge32 (0..992)
   ACCESS     read-only
   STATUS     mandatory
   DESCRIPTION
     "This attribute indicates the number of permanent connections (that 
      is, PVC and P-SPVC) that are rejected by egress CAC.  A 
      connection is rejected by egress CAC if it requests more egress EIR 
      bandwidth than is available, and the egressApplyToCos attribute is 
      set to cirAndEir."
::= { mscFrUniCaOpEntry 682 }

mscFrUniCaIngCirBPTable OBJECT-TYPE
   SYNTAX     SEQUENCE OF MscFrUniCaIngCirBPEntry
   ACCESS     not-accessible
   STATUS     mandatory
   DESCRIPTION
     "Port capacity is partitioned into 16 pools (pool 0 through pool 15) 
      for the ingress CIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrUniCa 666 }

mscFrUniCaIngCirBPEntry OBJECT-TYPE
   SYNTAX     MscFrUniCaIngCirBPEntry
   ACCESS     not-accessible
   STATUS     mandatory
   DESCRIPTION
     "An entry in the mscFrUniCaIngCirBPTable."
   INDEX {
      mscFrUniIndex,
      mscFrUniCaIndex,
      mscFrUniCaIngCirBPIndex }
::= { mscFrUniCaIngCirBPTable 1 }

MscFrUniCaIngCirBPEntry ::= SEQUENCE {
   mscFrUniCaIngCirBPIndex
      Integer32,
   mscFrUniCaIngCirBPValue
      Unsigned32 }

mscFrUniCaIngCirBPIndex OBJECT-TYPE
   SYNTAX     Integer32 (0..15)
   ACCESS     not-accessible
   STATUS     mandatory
   DESCRIPTION
     "This variable represents the mscFrUniCaIngCirBPTable
      specific index for the mscFrUniCaIngCirBPTable."
::= { mscFrUniCaIngCirBPEntry 1 }

mscFrUniCaIngCirBPValue OBJECT-TYPE
   SYNTAX     Unsigned32 (0..1000)
   ACCESS     read-write
   STATUS     mandatory
   DESCRIPTION
     "This variable represents an individual value for the
      mscFrUniCaIngCirBPTable."
::= { mscFrUniCaIngCirBPEntry 2 }

mscFrUniCaEgCirBpTable OBJECT-TYPE
   SYNTAX     SEQUENCE OF MscFrUniCaEgCirBpEntry
   ACCESS     not-accessible
   STATUS     mandatory
   DESCRIPTION
     "Port capacity is partitioned into 16 pools (pool 0 through pool 15) 
      for the egress CIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrUniCa 667 }

mscFrUniCaEgCirBpEntry OBJECT-TYPE
   SYNTAX     MscFrUniCaEgCirBpEntry
   ACCESS     not-accessible
   STATUS     mandatory
   DESCRIPTION
     "An entry in the mscFrUniCaEgCirBpTable."
   INDEX {
      mscFrUniIndex,
      mscFrUniCaIndex,
      mscFrUniCaEgCirBpIndex }
::= { mscFrUniCaEgCirBpTable 1 }

MscFrUniCaEgCirBpEntry ::= SEQUENCE {
   mscFrUniCaEgCirBpIndex
      Integer32,
   mscFrUniCaEgCirBpValue
      Unsigned32 }

mscFrUniCaEgCirBpIndex OBJECT-TYPE
   SYNTAX     Integer32 (0..15)
   ACCESS     not-accessible
   STATUS     mandatory
   DESCRIPTION
     "This variable represents the mscFrUniCaEgCirBpTable
      specific index for the mscFrUniCaEgCirBpTable."
::= { mscFrUniCaEgCirBpEntry 1 }

mscFrUniCaEgCirBpValue OBJECT-TYPE
   SYNTAX     Unsigned32 (0..1000)
   ACCESS     read-write
   STATUS     mandatory
   DESCRIPTION
     "This variable represents an individual value for the
      mscFrUniCaEgCirBpTable."
::= { mscFrUniCaEgCirBpEntry 2 }

mscFrUniCaIngCirPoolAdmitBwTable OBJECT-TYPE
   SYNTAX     SEQUENCE OF MscFrUniCaIngCirPoolAdmitBwEntry
   ACCESS     not-accessible
   STATUS     mandatory
   DESCRIPTION
     "This attribute indicates the total admitted CIR bandwidth from each 
      CIR bandwidth pool in the ingress direction. Each value is the sum 
      of the equivalent bit rates of the admitted connections."
::= { mscFrUniCa 668 }

mscFrUniCaIngCirPoolAdmitBwEntry OBJECT-TYPE
   SYNTAX     MscFrUniCaIngCirPoolAdmitBwEntry
   ACCESS     not-accessible
   STATUS     mandatory
   DESCRIPTION
     "An entry in the mscFrUniCaIngCirPoolAdmitBwTable."
   INDEX {
      mscFrUniIndex,
      mscFrUniCaIndex,
      mscFrUniCaIngCirPoolAdmitBwIndex }
::= { mscFrUniCaIngCirPoolAdmitBwTable 1 }

MscFrUniCaIngCirPoolAdmitBwEntry ::= SEQUENCE {
   mscFrUniCaIngCirPoolAdmitBwIndex
      Integer32,
   mscFrUniCaIngCirPoolAdmitBwValue
      Gauge32 }

mscFrUniCaIngCirPoolAdmitBwIndex OBJECT-TYPE
   SYNTAX     Integer32 (0..15)
   ACCESS     not-accessible
   STATUS     mandatory
   DESCRIPTION
     "This variable represents the mscFrUniCaIngCirPoolAdmitBwTable
      specific index for the mscFrUniCaIngCirPoolAdmitBwTable."
::= { mscFrUniCaIngCirPoolAdmitBwEntry 1 }

mscFrUniCaIngCirPoolAdmitBwValue OBJECT-TYPE
   SYNTAX     Gauge32 (0..520000000)
   ACCESS     read-only
   STATUS     mandatory
   DESCRIPTION
     "This variable represents an individual value for the
      mscFrUniCaIngCirPoolAdmitBwTable."
::= { mscFrUniCaIngCirPoolAdmitBwEntry 2 }

mscFrUniCaIngCirPoolAvailBwTable OBJECT-TYPE
   SYNTAX     SEQUENCE OF MscFrUniCaIngCirPoolAvailBwEntry
   ACCESS     not-accessible
   STATUS     mandatory
   DESCRIPTION
     "This attribute indicates the remaining available CIR bandwidth in 
      each ingress CIR bandwidth pool."
::= { mscFrUniCa 669 }

mscFrUniCaIngCirPoolAvailBwEntry OBJECT-TYPE
   SYNTAX     MscFrUniCaIngCirPoolAvailBwEntry
   ACCESS     not-accessible
   STATUS     mandatory
   DESCRIPTION
     "An entry in the mscFrUniCaIngCirPoolAvailBwTable."
   INDEX {
      mscFrUniIndex,
      mscFrUniCaIndex,
      mscFrUniCaIngCirPoolAvailBwIndex }
::= { mscFrUniCaIngCirPoolAvailBwTable 1 }

MscFrUniCaIngCirPoolAvailBwEntry ::= SEQUENCE {
   mscFrUniCaIngCirPoolAvailBwIndex
      Integer32,
   mscFrUniCaIngCirPoolAvailBwValue
      Gauge32 }

mscFrUniCaIngCirPoolAvailBwIndex OBJECT-TYPE
   SYNTAX     Integer32 (0..15)
   ACCESS     not-accessible
   STATUS     mandatory
   DESCRIPTION
     "This variable represents the mscFrUniCaIngCirPoolAvailBwTable
      specific index for the mscFrUniCaIngCirPoolAvailBwTable."
::= { mscFrUniCaIngCirPoolAvailBwEntry 1 }

mscFrUniCaIngCirPoolAvailBwValue OBJECT-TYPE
   SYNTAX     Gauge32 (0..52000000)
   ACCESS     read-only
   STATUS     mandatory
   DESCRIPTION
     "This variable represents an individual value for the
      mscFrUniCaIngCirPoolAvailBwTable."
::= { mscFrUniCaIngCirPoolAvailBwEntry 2 }

mscFrUniCaEgCirPoolAdmitBwTable OBJECT-TYPE
   SYNTAX     SEQUENCE OF MscFrUniCaEgCirPoolAdmitBwEntry
   ACCESS     not-accessible
   STATUS     mandatory
   DESCRIPTION
     "This attribute indicates the total admitted CIR bandwidth from each 
      CIR bandwidth pool in the egress direction. Each value is the sum 
      of the equivalent bit rates of the admitted connections."
::= { mscFrUniCa 670 }

mscFrUniCaEgCirPoolAdmitBwEntry OBJECT-TYPE
   SYNTAX     MscFrUniCaEgCirPoolAdmitBwEntry
   ACCESS     not-accessible
   STATUS     mandatory
   DESCRIPTION
     "An entry in the mscFrUniCaEgCirPoolAdmitBwTable."
   INDEX {
      mscFrUniIndex,
      mscFrUniCaIndex,
      mscFrUniCaEgCirPoolAdmitBwIndex }
::= { mscFrUniCaEgCirPoolAdmitBwTable 1 }

MscFrUniCaEgCirPoolAdmitBwEntry ::= SEQUENCE {
   mscFrUniCaEgCirPoolAdmitBwIndex
      Integer32,
   mscFrUniCaEgCirPoolAdmitBwValue
      Gauge32 }

mscFrUniCaEgCirPoolAdmitBwIndex OBJECT-TYPE
   SYNTAX     Integer32 (0..15)
   ACCESS     not-accessible
   STATUS     mandatory
   DESCRIPTION
     "This variable represents the mscFrUniCaEgCirPoolAdmitBwTable
      specific index for the mscFrUniCaEgCirPoolAdmitBwTable."
::= { mscFrUniCaEgCirPoolAdmitBwEntry 1 }

mscFrUniCaEgCirPoolAdmitBwValue OBJECT-TYPE
   SYNTAX     Gauge32 (0..520000000)
   ACCESS     read-only
   STATUS     mandatory
   DESCRIPTION
     "This variable represents an individual value for the
      mscFrUniCaEgCirPoolAdmitBwTable."
::= { mscFrUniCaEgCirPoolAdmitBwEntry 2 }

mscFrUniCaEgCirPoolAvailBwTable OBJECT-TYPE
   SYNTAX     SEQUENCE OF MscFrUniCaEgCirPoolAvailBwEntry
   ACCESS     not-accessible
   STATUS     mandatory
   DESCRIPTION
     "This attribute indicates the remaining available CIR bandwidth in 
      each egress CIR bandwidth pool."
::= { mscFrUniCa 671 }

mscFrUniCaEgCirPoolAvailBwEntry OBJECT-TYPE
   SYNTAX     MscFrUniCaEgCirPoolAvailBwEntry
   ACCESS     not-accessible
   STATUS     mandatory
   DESCRIPTION
     "An entry in the mscFrUniCaEgCirPoolAvailBwTable."
   INDEX {
      mscFrUniIndex,
      mscFrUniCaIndex,
      mscFrUniCaEgCirPoolAvailBwIndex }
::= { mscFrUniCaEgCirPoolAvailBwTable 1 }

MscFrUniCaEgCirPoolAvailBwEntry ::= SEQUENCE {
   mscFrUniCaEgCirPoolAvailBwIndex
      Integer32,
   mscFrUniCaEgCirPoolAvailBwValue
      Gauge32 }

mscFrUniCaEgCirPoolAvailBwIndex OBJECT-TYPE
   SYNTAX     Integer32 (0..15)
   ACCESS     not-accessible
   STATUS     mandatory
   DESCRIPTION
     "This variable represents the mscFrUniCaEgCirPoolAvailBwTable
      specific index for the mscFrUniCaEgCirPoolAvailBwTable."
::= { mscFrUniCaEgCirPoolAvailBwEntry 1 }

mscFrUniCaEgCirPoolAvailBwValue OBJECT-TYPE
   SYNTAX     Gauge32 (0..52000000)
   ACCESS     read-only
   STATUS     mandatory
   DESCRIPTION
     "This variable represents an individual value for the
      mscFrUniCaEgCirPoolAvailBwTable."
::= { mscFrUniCaEgCirPoolAvailBwEntry 2 }

mscFrUniCaIngEirBpTable OBJECT-TYPE
   SYNTAX     SEQUENCE OF MscFrUniCaIngEirBpEntry
   ACCESS     not-accessible
   STATUS     mandatory
   DESCRIPTION
     "Port capacity is partitioned into 16 pools (pool 0 through pool 15) 
      for the ingress EIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrUniCa 673 }

mscFrUniCaIngEirBpEntry OBJECT-TYPE
   SYNTAX     MscFrUniCaIngEirBpEntry
   ACCESS     not-accessible
   STATUS     mandatory
   DESCRIPTION
     "An entry in the mscFrUniCaIngEirBpTable."
   INDEX {
      mscFrUniIndex,
      mscFrUniCaIndex,
      mscFrUniCaIngEirBpIndex }
::= { mscFrUniCaIngEirBpTable 1 }

MscFrUniCaIngEirBpEntry ::= SEQUENCE {
   mscFrUniCaIngEirBpIndex
      Integer32,
   mscFrUniCaIngEirBpValue
      Unsigned32 }

mscFrUniCaIngEirBpIndex OBJECT-TYPE
   SYNTAX     Integer32 (0..15)
   ACCESS     not-accessible
   STATUS     mandatory
   DESCRIPTION
     "This variable represents the mscFrUniCaIngEirBpTable
      specific index for the mscFrUniCaIngEirBpTable."
::= { mscFrUniCaIngEirBpEntry 1 }

mscFrUniCaIngEirBpValue OBJECT-TYPE
   SYNTAX     Unsigned32 (0..1000)
   ACCESS     read-write
   STATUS     mandatory
   DESCRIPTION
     "This variable represents an individual value for the
      mscFrUniCaIngEirBpTable."
::= { mscFrUniCaIngEirBpEntry 2 }

mscFrUniCaEgEirBpTable OBJECT-TYPE
   SYNTAX     SEQUENCE OF MscFrUniCaEgEirBpEntry
   ACCESS     not-accessible
   STATUS     mandatory
   DESCRIPTION
     "Port capacity is partitioned into 16 pools (pool 0 through pool 15) 
      for the egress EIR traffic. This attribute specifies the percentage of 
      port capacity that is allowed for each pool. The percentage for each 
      pool ranges from 0% to 1000% of the link rate. It allows for under 
      or over subscription of the port. Under subscription occurs when the 
      sum of the percentages assigned to the 16 pools is less than 100%. 
      Over subscription occurs when the sum of the percentages for the 
      16 pools exceeds 100%.
      
      The default is full sharing of port capacity with three pre-set 
      partitions."
::= { mscFrUniCa 674 }

mscFrUniCaEgEirBpEntry OBJECT-TYPE
   SYNTAX     MscFrUniCaEgEirBpEntry
   ACCESS     not-accessible
   STATUS     mandatory
   DESCRIPTION
     "An entry in the mscFrUniCaEgEirBpTable."
   INDEX {
      mscFrUniIndex,
      mscFrUniCaIndex,
      mscFrUniCaEgEirBpIndex }
::= { mscFrUniCaEgEirBpTable 1 }

MscFrUniCaEgEirBpEntry ::= SEQUENCE {
   mscFrUniCaEgEirBpIndex
      Integer32,
   mscFrUniCaEgEirBpValue
      Unsigned32 }

mscFrUniCaEgEirBpIndex OBJECT-TYPE
   SYNTAX     Integer32 (0..15)
   ACCESS     not-accessible
   STATUS     mandatory
   DESCRIPTION
     "This variable represents the mscFrUniCaEgEirBpTable
      specific index for the mscFrUniCaEgEirBpTable."
::= { mscFrUniCaEgEirBpEntry 1 }

mscFrUniCaEgEirBpValue OBJECT-TYPE
   SYNTAX     Unsigned32 (0..1000)
   ACCESS     read-write
   STATUS     mandatory
   DESCRIPTION
     "This variable represents an individual value for the
      mscFrUniCaEgEirBpTable."
::= { mscFrUniCaEgEirBpEntry 2 }

mscFrUniCaIngEirPoolAdmitBwTable OBJECT-TYPE
   SYNTAX     SEQUENCE OF MscFrUniCaIngEirPoolAdmitBwEntry
   ACCESS     not-accessible
   STATUS     mandatory
   DESCRIPTION
     "This attribute indicates the total admitted EIR bandwidth from each 
      EIR bandwidth pool in the ingress direction. Each value is the sum 
      of the equivalent bit rates of the admitted connections.
      
      If the ingressApplyToCos attribute is set to none, all ingress CIR 
      bandwidth pools are set to 0."
::= { mscFrUniCa 675 }

mscFrUniCaIngEirPoolAdmitBwEntry OBJECT-TYPE
   SYNTAX     MscFrUniCaIngEirPoolAdmitBwEntry
   ACCESS     not-accessible
   STATUS     mandatory
   DESCRIPTION
     "An entry in the mscFrUniCaIngEirPoolAdmitBwTable."
   INDEX {
      mscFrUniIndex,
      mscFrUniCaIndex,
      mscFrUniCaIngEirPoolAdmitBwIndex }
::= { mscFrUniCaIngEirPoolAdmitBwTable 1 }

MscFrUniCaIngEirPoolAdmitBwEntry ::= SEQUENCE {
   mscFrUniCaIngEirPoolAdmitBwIndex
      Integer32,
   mscFrUniCaIngEirPoolAdmitBwValue
      Gauge32 }

mscFrUniCaIngEirPoolAdmitBwIndex OBJECT-TYPE
   SYNTAX     Integer32 (0..15)
   ACCESS     not-accessible
   STATUS     mandatory
   DESCRIPTION
     "This variable represents the mscFrUniCaIngEirPoolAdmitBwTable
      specific index for the mscFrUniCaIngEirPoolAdmitBwTable."
::= { mscFrUniCaIngEirPoolAdmitBwEntry 1 }

mscFrUniCaIngEirPoolAdmitBwValue OBJECT-TYPE
   SYNTAX     Gauge32 (0..520000000)
   ACCESS     read-only
   STATUS     mandatory
   DESCRIPTION
     "This variable represents an individual value for the
      mscFrUniCaIngEirPoolAdmitBwTable."
::= { mscFrUniCaIngEirPoolAdmitBwEntry 2 }

mscFrUniCaIngEirPoolAvailBwTable OBJECT-TYPE
   SYNTAX     SEQUENCE OF MscFrUniCaIngEirPoolAvailBwEntry
   ACCESS     not-accessible
   STATUS     mandatory
   DESCRIPTION
     "This attribute indicates the remaining available EIR bandwidth in 
      each ingress EIR bandwidth pool.
      
      If the ingressApplyToCos attribute is set to either none or cirOnly, 
      all ingress EIR bandwidth pools are set to 0."
::= { mscFrUniCa 676 }

mscFrUniCaIngEirPoolAvailBwEntry OBJECT-TYPE
   SYNTAX     MscFrUniCaIngEirPoolAvailBwEntry
   ACCESS     not-accessible
   STATUS     mandatory
   DESCRIPTION
     "An entry in the mscFrUniCaIngEirPoolAvailBwTable."
   INDEX {
      mscFrUniIndex,
      mscFrUniCaIndex,
      mscFrUniCaIngEirPoolAvailBwIndex }
::= { mscFrUniCaIngEirPoolAvailBwTable 1 }

MscFrUniCaIngEirPoolAvailBwEntry ::= SEQUENCE {
   mscFrUniCaIngEirPoolAvailBwIndex
      Integer32,
   mscFrUniCaIngEirPoolAvailBwValue
      Gauge32 }

mscFrUniCaIngEirPoolAvailBwIndex OBJECT-TYPE
   SYNTAX     Integer32 (0..15)
   ACCESS     not-accessible
   STATUS     mandatory
   DESCRIPTION
     "This variable represents the mscFrUniCaIngEirPoolAvailBwTable
      specific index for the mscFrUniCaIngEirPoolAvailBwTable."
::= { mscFrUniCaIngEirPoolAvailBwEntry 1 }

mscFrUniCaIngEirPoolAvailBwValue OBJECT-TYPE
   SYNTAX     Gauge32 (0..52000000)
   ACCESS     read-only
   STATUS     mandatory
   DESCRIPTION
     "This variable represents an individual value for the
      mscFrUniCaIngEirPoolAvailBwTable."
::= { mscFrUniCaIngEirPoolAvailBwEntry 2 }

mscFrUniCaEgEirPoolAdmitBwTable OBJECT-TYPE
   SYNTAX     SEQUENCE OF MscFrUniCaEgEirPoolAdmitBwEntry
   ACCESS     not-accessible
   STATUS     mandatory
   DESCRIPTION
     "This attribute indicates the total admitted EIR bandwidth from each 
      EIR bandwidth pool in the egress direction. Each value is the sum 
      of the equivalent bit rates of the admitted connections.
      
      If the egressApplyToCos attribute is set to none, all egress CIR 
      bandwidth pools are set to 0."
::= { mscFrUniCa 677 }

mscFrUniCaEgEirPoolAdmitBwEntry OBJECT-TYPE
   SYNTAX     MscFrUniCaEgEirPoolAdmitBwEntry
   ACCESS     not-accessible
   STATUS     mandatory
   DESCRIPTION
     "An entry in the mscFrUniCaEgEirPoolAdmitBwTable."
   INDEX {
      mscFrUniIndex,
      mscFrUniCaIndex,
      mscFrUniCaEgEirPoolAdmitBwIndex }
::= { mscFrUniCaEgEirPoolAdmitBwTable 1 }

MscFrUniCaEgEirPoolAdmitBwEntry ::= SEQUENCE {
   mscFrUniCaEgEirPoolAdmitBwIndex
      Integer32,
   mscFrUniCaEgEirPoolAdmitBwValue
      Gauge32 }

mscFrUniCaEgEirPoolAdmitBwIndex OBJECT-TYPE
   SYNTAX     Integer32 (0..15)
   ACCESS     not-accessible
   STATUS     mandatory
   DESCRIPTION
     "This variable represents the mscFrUniCaEgEirPoolAdmitBwTable
      specific index for the mscFrUniCaEgEirPoolAdmitBwTable."
::= { mscFrUniCaEgEirPoolAdmitBwEntry 1 }

mscFrUniCaEgEirPoolAdmitBwValue OBJECT-TYPE
   SYNTAX     Gauge32 (0..520000000)
   ACCESS     read-only
   STATUS     mandatory
   DESCRIPTION
     "This variable represents an individual value for the
      mscFrUniCaEgEirPoolAdmitBwTable."
::= { mscFrUniCaEgEirPoolAdmitBwEntry 2 }

mscFrUniCaEgEirPoolAvailBwTable OBJECT-TYPE
   SYNTAX     SEQUENCE OF MscFrUniCaEgEirPoolAvailBwEntry
   ACCESS     not-accessible
   STATUS     mandatory
   DESCRIPTION
     "This attribute indicates the remaining available EIR bandwidth in 
      each egress EIR bandwidth pool.
      
      If the egressApplyToCos attribute is set to either none or cirOnly, 
      all egress EIR bandwidth pools are set to 0."
::= { mscFrUniCa 678 }

mscFrUniCaEgEirPoolAvailBwEntry OBJECT-TYPE
   SYNTAX     MscFrUniCaEgEirPoolAvailBwEntry
   ACCESS     not-accessible
   STATUS     mandatory
   DESCRIPTION
     "An entry in the mscFrUniCaEgEirPoolAvailBwTable."
   INDEX {
      mscFrUniIndex,
      mscFrUniCaIndex,
      mscFrUniCaEgEirPoolAvailBwIndex }
::= { mscFrUniCaEgEirPoolAvailBwTable 1 }

MscFrUniCaEgEirPoolAvailBwEntry ::= SEQUENCE {
   mscFrUniCaEgEirPoolAvailBwIndex
      Integer32,
   mscFrUniCaEgEirPoolAvailBwValue
      Gauge32 }

mscFrUniCaEgEirPoolAvailBwIndex OBJECT-TYPE
   SYNTAX     Integer32 (0..15)
   ACCESS     not-accessible
   STATUS     mandatory
   DESCRIPTION
     "This variable represents the mscFrUniCaEgEirPoolAvailBwTable
      specific index for the mscFrUniCaEgEirPoolAvailBwTable."
::= { mscFrUniCaEgEirPoolAvailBwEntry 1 }

mscFrUniCaEgEirPoolAvailBwValue OBJECT-TYPE
   SYNTAX     Gauge32 (0..52000000)
   ACCESS     read-only
   STATUS     mandatory
   DESCRIPTION
     "This variable represents an individual value for the
      mscFrUniCaEgEirPoolAvailBwTable."
::= { mscFrUniCaEgEirPoolAvailBwEntry 2 }


-- FrNni/n Ca TransferPriorityMapping/n
-- The Tpm component defines the corresponding traffic management 
-- subscription options on a FrNni interface corresponding to a 
-- particular transfer priority.  This component is needed only if there 
-- is a requirement to override the Mod Frs DprsNet Tpm component 
-- defaults.

mscFrUniCaTpm OBJECT IDENTIFIER ::= { mscFrUniCa 2 }



mscFrUniCaTpmRowStatusTable OBJECT-TYPE
   SYNTAX     SEQUENCE OF MscFrUniCaTpmRowStatusEntry
   ACCESS     not-accessible
   STATUS     mandatory
   DESCRIPTION
     "This entry controls the addition and deletion of 
      mscFrUniCaTpm components."
::= { mscFrUniCaTpm 1 }

mscFrUniCaTpmRowStatusEntry OBJECT-TYPE
   SYNTAX     MscFrUniCaTpmRowStatusEntry
   ACCESS     not-accessible
   STATUS     mandatory
   DESCRIPTION
     "A single entry in the table represents a single 
      mscFrUniCaTpm component."
   INDEX {
      mscFrUniIndex,
      mscFrUniCaIndex,
      mscFrUniCaTpmIndex }
::= { mscFrUniCaTpmRowStatusTable 1 }

MscFrUniCaTpmRowStatusEntry ::= SEQUENCE {
   mscFrUniCaTpmRowStatus
      RowStatus,
   mscFrUniCaTpmComponentName
      DisplayString,
   mscFrUniCaTpmStorageType
      StorageType,
   mscFrUniCaTpmIndex
      Integer32 }

mscFrUniCaTpmRowStatus OBJECT-TYPE
   SYNTAX     RowStatus 
   ACCESS     read-write
   STATUS     mandatory
   DESCRIPTION
     "This variable is used as the basis for SNMP naming of
      mscFrUniCaTpm components.
      These components can be added and deleted."
::= { mscFrUniCaTpmRowStatusEntry 1 }

mscFrUniCaTpmComponentName OBJECT-TYPE
   SYNTAX     DisplayString 
   ACCESS     read-only
   STATUS     mandatory
   DESCRIPTION
     "This variable provides the component's string name for
      use with the ASCII Console Interface"
::= { mscFrUniCaTpmRowStatusEntry 2 }

mscFrUniCaTpmStorageType OBJECT-TYPE
   SYNTAX     StorageType 
   ACCESS     read-only
   STATUS     mandatory
   DESCRIPTION
     "This variable represents the storage type value for the
      mscFrUniCaTpm tables."
::= { mscFrUniCaTpmRowStatusEntry 4 }

mscFrUniCaTpmIndex OBJECT-TYPE
   SYNTAX     Integer32 (0..15)
   ACCESS     not-accessible
   STATUS     mandatory
   DESCRIPTION
     "This variable represents the index for the mscFrUniCaTpm tables."
::= { mscFrUniCaTpmRowStatusEntry 10 }

mscFrUniCaTpmProvTable OBJECT-TYPE
   SYNTAX     SEQUENCE OF MscFrUniCaTpmProvEntry
   ACCESS     not-accessible
   STATUS     mandatory
   DESCRIPTION
     "This attribute group contains the provisionable attributes of the Tpm 
      component at this interface."
::= { mscFrUniCaTpm 10 }

mscFrUniCaTpmProvEntry OBJECT-TYPE
   SYNTAX     MscFrUniCaTpmProvEntry
   ACCESS     not-accessible
   STATUS     mandatory
   DESCRIPTION
     "An entry in the mscFrUniCaTpmProvTable."
   INDEX {
      mscFrUniIndex,
      mscFrUniCaIndex,
      mscFrUniCaTpmIndex }
::= { mscFrUniCaTpmProvTable 1 }

MscFrUniCaTpmProvEntry ::= SEQUENCE {
   mscFrUniCaTpmAssignedIngressBandwidthPool
      Unsigned32,
   mscFrUniCaTpmAssignedEgressBandwidthPool
      Unsigned32 }

mscFrUniCaTpmAssignedIngressBandwidthPool OBJECT-TYPE
   SYNTAX     Unsigned32 (0..15 | 16)
   ACCESS     read-write
   STATUS     mandatory
   DESCRIPTION
     "This attribute specifies the ingress bandwidth pool which is used to 
      support this transfer priority at this interface. When this attribute is 
      set to sameAsModule, the bandwidth pool that is used is obtained 
      from the  assignedIngressBandwidthPool attribute under the Mod 
      Frs DprsNet Tpm/n component.

      VALUES (

      16 = sameAsModule

      )"
   DEFVAL     { 16 }
::= { mscFrUniCaTpmProvEntry 2 }

mscFrUniCaTpmAssignedEgressBandwidthPool OBJECT-TYPE
   SYNTAX     Unsigned32 (0..15 | 16)
   ACCESS     read-write
   STATUS     mandatory
   DESCRIPTION
     "This attribute specifies the egress bandwidth pool which is used to 
      support this transfer priority at this interface. When this attribute is 
      set to sameAsModule, the bandwidth pool that is used is obtained 
      from the assignedEgressBandwidthPool attribute under the Mod 
      Frs DprsNet Tpm/n component.

      VALUES (

      16 = sameAsModule

      )"
   DEFVAL     { 16 }
::= { mscFrUniCaTpmProvEntry 3 }




-- 
-- Version and Compliance statements
-- 



-- Object-Group Statement:
-- A list of all current accessible leaf objects.

-- OBJECTS { mscFrUniSigDefaultExcessBurstSize,
--           mscFrUniDlciDiscardedSegFrm,
--           mscFrUniLtsPatDefaultHeaderLength,
--           mscFrUniSigInCallsRefused,
--           mscFrUniRowStatus,
--           mscFrUniDnaHgMRowStatus,
--           mscFrUniFramerNonOctetErrors,
--           mscFrUniDnaOutAccess,
--           mscFrUniDlciVcOoSeqPktCntExceeded,
--           mscFrUniSigStatusEnqTimer,
--           mscFrUniSigRestartReqTimer,
--           mscFrUniSigIFramesTransmitted,
--           mscFrUniDlciEgressSpExcessBurstSize,
--           mscFrUniDlciDiscExcessFromIf,
--           mscFrUniLtsPatFramePattern,
--           mscFrUniLmiFullStatusToIf,
--           mscFrUniOperationalState,
--           mscFrUniDlciEirPresent,
--           mscFrUniDnaAccountCollection,
--           mscFrUniCaTpmAssignedIngressBandwidthPool,
--           mscFrUniSigRateAdaptation,
--           mscFrUniCaIngEirPoolAvailBwValue,
--           mscFrUniLtsPatDefaultEABits,
--           mscFrUniDlciCallType,
--           mscFrUniAvailabilityStatus,
--           mscFrUniFramerOctetFromIf64,
--           mscFrUniDlciFciFromSubnet,
--           mscFrUniDlciDiscByteAbit,
--           mscFrUniSnmpOperStatus,
--           mscFrUniSigCurrentState,
--           mscFrUniFramerAdminState,
--           mscFrUniCaIngEirBpValue,
--           mscFrUniDlciCirPresent,
--           mscFrUniSigDefaultCommittedInformationRate,
--           mscFrUniLmiNetworkSideEventHistory,
--           mscFrUniDnaRowStatus,
--           mscFrUniFramerDataInversion,
--           mscFrUniVFramerOtherVirtualFramer,
--           mscFrUniLtsPatNumFrames,
--           mscFrUniDlciSpUpdateBCI,
--           mscFrUniDnaHgMHgAddrRowStatus,
--           mscFrUniDnaTransferPriorityOverRide,
--           mscFrUniDlciTransferPriToNwk,
--           mscFrUniDlciSpComponentName,
--           mscFrUniDnaNumberingPlanIndicator,
--           mscFrUniDnaServiceExchange,
--           mscFrUniLtsElapsedGenerationTime,
--           mscFrUniDnaAccountClass,
--           mscFrUniLmiFullStatusEnqFromIf,
--           mscFrUniDlciFecnFrmToIf,
--           mscFrUniDnaCugOutCalls,
--           mscFrUniDnaHgMHgAddrNumberingPlanIndicator,
--           mscFrUniDlciEgressSpCommittedBurstSize,
--           mscFrUniCaTpmAssignedEgressBandwidthPool,
--           mscFrUniDlciDiscardedBytes,
--           mscFrUniDlciVcElapsedTimeTillNow,
--           mscFrUniDlciComponentName,
--           mscFrUniDlciVcPeakOoSeqPktCount,
--           mscFrUniCaIngressMaximumEirOnlyCalls,
--           mscFrUniDlciABitReasonFromIf,
--           mscFrUniSigDefaultMaximumFrameSize,
--           mscFrUniFramerComponentName,
--           mscFrUniCaEgressApplyToCos,
--           mscFrUniControlStatus,
--           mscFrUniDlciLbLocalDeBytes,
--           mscFrUniSigOutCallsFailed,
--           mscFrUniDlciDiscCongestedFromIf,
--           mscFrUniDlciLbLocalDeFrm,
--           mscFrUniLtsPatDataSize,
--           mscFrUniDlciDeFrmFromIf,
--           mscFrUniLtsPatDefaultDataSize,
--           mscFrUniDlciVcEmissionPriorityFromNetwork,
--           mscFrUniSigCurrentQueueSize,
--           mscFrUniSigQualityOfServiceNotAvailable,
--           mscFrUniLmiUnexpectedIes,
--           mscFrUniDlciVcCallingDna,
--           mscFrUniDlciExcessBytesFromIf,
--           mscFrUniDlciVcPeakOoSeqFrmForwarded,
--           mscFrUniLtsBitRateTx,
--           mscFrUniDlciExcessFrmFromIf,
--           mscFrUniSigUpdateBCI,
--           mscFrUniVFramerOperationalState,
--           mscFrUniSigComponentName,
--           mscFrUniSigIFramesRcvdDiscarded,
--           mscFrUniLtsPatUseBadLrc,
--           mscFrUniCaEgEirPoolAdmitBwValue,
--           mscFrUniDlciBecnFrmToIf,
--           mscFrUniLmiKeepAliveEnqToIf,
--           mscFrUniVFramerUsageState,
--           mscFrUniCaComponentName,
--           mscFrUniLmiComponentName,
--           mscFrUniLmiErrorEventThreshold,
--           mscFrUniLastUnknownDlci,
--           mscFrUniLtsStorageType,
--           mscFrUniUnknownStatus,
--           mscFrUniLmiProcedures,
--           mscFrUniDlciVcDuplicatesFromSubnet,
--           mscFrUniDlciRateAdaptReductPeriod,
--           mscFrUniDlciControlStatus,
--           mscFrUniSigLastStateChangeReason,
--           mscFrUniDnaCugDnic,
--           mscFrUniLmiMessageCountTimer,
--           mscFrUniDlciDcRowStatus,
--           mscFrUniDlciEgressSpRowStatus,
--           mscFrUniDlciBciFromSubnet,
--           mscFrUniLtsPatRowStatus,
--           mscFrUniDlciDcMapIpCosToFrQos,
--           mscFrUniDlciUsageState,
--           mscFrUniIfAdminStatus,
--           mscFrUniCustomerIdentifier,
--           mscFrUniDlciDiscCongestedToIf,
--           mscFrUniVFramerLogicalProcessor,
--           mscFrUniLtsPatHeaderBits,
--           mscFrUniLmiOpProcedures,
--           mscFrUniCaStorageType,
--           mscFrUniDlciLoopbackState,
--           mscFrUniUnknownDlciFramesFromIf,
--           mscFrUniCaMaximumBandwidthPerCall,
--           mscFrUniCaIngEirPoolAdmitBwValue,
--           mscFrUniDlciVcFastSelectCall,
--           mscFrUniCaEgCirPoolAdmitBwValue,
--           mscFrUniDlciEirEgressSegFrm,
--           mscFrUniLtsCycleIncomplete,
--           mscFrUniDlciVcMaxSubnetPktSize,
--           mscFrUniFramerLrcErrors,
--           mscFrUniSigCallProceedingTimer,
--           mscFrUniDlciStartTime,
--           mscFrUniDlciLbLocalTotalBytes,
--           mscFrUniDlciABitStatusToIf,
--           mscFrUniDlciEmissionPriorityToIf,
--           mscFrUniDlciVcSendSequenceNumber,
--           mscFrUniSigX213IeHandling,
--           mscFrUniLmiUsageState,
--           mscFrUniDlciSpRaSensitivity,
--           mscFrUniDnaEgressAccounting,
--           mscFrUniDlciVcState,
--           mscFrUniLtsGeneratorState,
--           mscFrUniDnaCugPreferential,
--           mscFrUniSigUsageState,
--           mscFrUniSigLastClearRemoteDataNetworkAddress,
--           mscFrUniDlciVcEmissionPriorityToNetwork,
--           mscFrUniDlciLbRemoteDeBytes,
--           mscFrUniCaIngCirPoolAdmitBwValue,
--           mscFrUniDlciLbRemoteDeFrm,
--           mscFrUniSigIFramesReceived,
--           mscFrUniDlciDcRemoteDna,
--           mscFrUniCaTpmRowStatus,
--           mscFrUniDlciProceduralStatus,
--           mscFrUniDlciVcComponentName,
--           mscFrUniDlciSpMeasurementInterval,
--           mscFrUniLmiNoStatusReportCount,
--           mscFrUniDlciLbLocalTotalFrm,
--           mscFrUniDlciVcCalledNpi,
--           mscFrUniDlciTotalEgressBytes,
--           mscFrUniDlciFrmFromIf,
--           mscFrUniLtsPatHdlcBitsInserted,
--           mscFrUniDlciLocalRateAdaptOccurred,
--           mscFrUniDlciVcNotDataXferToSubnet,
--           mscFrUniSigDisconnectTimer,
--           mscFrUniSigAckTimer,
--           mscFrUniDlciVcCallReferenceNumberDecimal,
--           mscFrUniCaIngCirPoolAvailBwValue,
--           mscFrUniDlciMeasurementInterval,
--           mscFrUniSigAckTimeout,
--           mscFrUniSigStateChange,
--           mscFrUniComponentName,
--           mscFrUniDlciVcRcosToNetwork,
--           mscFrUniDnaHgMComponentName,
--           mscFrUniLmiStatusSequenceErrors,
--           mscFrUniSigRaSensitivity,
--           mscFrUniDlciTransferPriFromNwk,
--           mscFrUniLmiIgnoreActiveBit,
--           mscFrUniDlciVcSegmentsSent,
--           mscFrUniDlciEirEgressBytes,
--           mscFrUniInvalidHeaderFramesFromIf,
--           mscFrUniDlciLbLocalFecnFrm,
--           mscFrUniDlciFecnFrmFromIf,
--           mscFrUniDlciSpAccounting,
--           mscFrUniLtsPatRfc1490Header,
--           mscFrUniDlciDiscDeCongestedToIf,
--           mscFrUniLmiCheckPointTimer,
--           mscFrUniVFramerFrmToOtherVFramer,
--           mscFrUniDlciStandbyStatus,
--           mscFrUniLmiUserSideEventHistory,
--           mscFrUniLmiKeepAliveStatusToIf,
--           mscFrUniDlciStorageType,
--           mscFrUniDlciAccounting,
--           mscFrUniFramerNormPrioLinkUtilToIf,
--           mscFrUniSigNetworkType,
--           mscFrUniFramerStorageType,
--           mscFrUniDlciCallRefNumber,
--           mscFrUniDlciCommittedBurstSize,
--           mscFrUniFramerCrcErrors,
--           mscFrUniDlciSpRateEnforcement,
--           mscFrUniDlciAdminState,
--           mscFrUniDlciDcRemoteDlci,
--           mscFrUniDlciVcDiagnosticCode,
--           mscFrUniLtsAlgorithm,
--           mscFrUniCaTpmComponentName,
--           mscFrUniFramerUsageState,
--           mscFrUniDnaComponentName,
--           mscFrUniLmiAsyncStatusReport,
--           mscFrUniLtsPatDefaultPayloadPattern,
--           mscFrUniFramerLargeFrmErrors,
--           mscFrUniLtsRowStatus,
--           mscFrUniFrmToIfByQueueValue,
--           mscFrUniDlciLbComponentName,
--           mscFrUniDlciMaximumFrameSize,
--           mscFrUniDnaHgMHgAddrComponentName,
--           mscFrUniDlciLbLocalBecnFrm,
--           mscFrUniDlciVcType,
--           mscFrUniDlciBecnFrmFromIf,
--           mscFrUniLtsPatDefaultNumFrames,
--           mscFrUniDlciVcFrmLossTimeouts,
--           mscFrUniSigStorageType,
--           mscFrUniDlciDcDiscardPriority,
--           mscFrUniSigCurrentNumberOfSvcCalls,
--           mscFrUniDnaHgMMaximumAvailableAggregateCir,
--           mscFrUniDlciVcPeakRetryQueueSize,
--           mscFrUniSigCallSetupTimer,
--           mscFrUniUsageState,
--           mscFrUniDlciDcTransferPriority,
--           mscFrUniLmiStorageType,
--           mscFrUniLmiKeepAliveStatusEnqFromIf,
--           mscFrUniSigAdminState,
--           mscFrUniDlciExcessBurstSize,
--           mscFrUniDlciBytesToIf,
--           mscFrUniSigLastClearCause,
--           mscFrUniIfIndex,
--           mscFrUniLtsPatLoad,
--           mscFrUniCaEgEirPoolAvailBwValue,
--           mscFrUniDnaDataNetworkAddress,
--           mscFrUniVFramerComponentName,
--           mscFrUniLmiAdminState,
--           mscFrUniCaRowStatus,
--           mscFrUniSigRateEnforcement,
--           mscFrUniLtsPatDlci,
--           mscFrUniDnaHgMHgAddrDataNetworkAddress,
--           mscFrUniDlciAlarmStatus,
--           mscFrUniDnaOutDefaultPriority,
--           mscFrUniDlciVcPriority,
--           mscFrUniDlciVcPathReliability,
--           mscFrUniDlciVcCannotForwardToSubnet,
--           mscFrUniDnaHgMAvailableAggregateCir,
--           mscFrUniDnaIncAccess,
--           mscFrUniSigAckDelayTimer,
--           mscFrUniLtsFrameRateTx,
--           mscFrUniDlciElapsedDifference,
--           mscFrUniDlciDiscCongestedToIfBytes,
--           mscFrUniDlciRateAdaptReduct,
--           mscFrUniSigLastDlciReceivedStatus,
--           mscFrUniLtsPatHeaderLength,
--           mscFrUniFramerFlagsBetweenFrames,
--           mscFrUniDlciSpCommittedInformationRate,
--           mscFrUniLmiPvcConfigParmsInFsr,
--           mscFrUniDlciFrmToIf,
--           mscFrUniCaEgEirBpValue,
--           mscFrUniDnaCugInterlockCode,
--           mscFrUniLtsFramesTx,
--           mscFrUniFramerFrameCrcType,
--           mscFrUniDlciDiscDeCongestedFromIf,
--           mscFrUniDlciVcStorageType,
--           mscFrUniCaEgressMaximumEirOnlyCalls,
--           mscFrUniDlciCommittedInformationRate,
--           mscFrUniSigIFramesTxDiscarded,
--           mscFrUniFramerFrmToIf64,
--           mscFrUniDlciABitStatusFromIf,
--           mscFrUniCaIngressApplyToCos,
--           mscFrUniDlciVcAccountingEnd,
--           mscFrUniDlciEgressSpComponentName,
--           mscFrUniSigLastStateInStatusMsgReceived,
--           mscFrUniLtsBytesTx,
--           mscFrUniProceduralStatus,
--           mscFrUniOctetToIfByQueueValue,
--           mscFrUniCaEgCirBpValue,
--           mscFrUniLmiProtocolErrors,
--           mscFrUniLtsPatComponentName,
--           mscFrUniDnaDefaultTransferPriority,
--           mscFrUniDlciSpMaximumFrameSize,
--           mscFrUniDlciVcPreviousDiagnosticCode,
--           mscFrUniSigLastDiagnosticCode,
--           mscFrUniDlciVcDataPath,
--           mscFrUniLtsPatEaBits,
--           mscFrUniDlciTotalEgressSegFrm,
--           mscFrUniDnaCugStorageType,
--           mscFrUniDlciQstate,
--           mscFrUniLtsPatDefaultHeaderBits,
--           mscFrUniDlciSpExcessBurstSize,
--           mscFrUniSigBandwidthNotAvailableValue,
--           mscFrUniLtsTimeInterval,
--           mscFrUniDnaOutDefaultPathReliability,
--           mscFrUniDnaCugIncCalls,
--           mscFrUniDlciSpRowStatus,
--           mscFrUniLmiRowStatus,
--           mscFrUniDlciSpStorageType,
--           mscFrUniLtsDuration,
--           mscFrUniCaOverrideLinkRate,
--           mscFrUniLmiPollingVerifTimeouts,
--           mscFrUniDlciLbRemoteTotalBytes,
--           mscFrUniDlciBytesFromIf,
--           mscFrUniDlciVcFrmCongestedToSubnet,
--           mscFrUniDlciDcCugIndex,
--           mscFrUniDlciLbRemoteTotalFrm,
--           mscFrUniDlciDcCugType,
--           mscFrUniDlciLbRemoteBecnFrm,
--           mscFrUniCaNumberRejectedEgressEirPermConn,
--           mscFrUniSigSetupTimeout,
--           mscFrUniSigReleaseTimer,
--           mscFrUniDlciVcRcosFromNetwork,
--           mscFrUniDlciVcNotDataXferFromSubnet,
--           mscFrUniStandbyStatus,
--           mscFrUniDlciBciToSubnet,
--           mscFrUniStorageType,
--           mscFrUniDlciOperationalState,
--           mscFrUniDnaHgMStorageType,
--           mscFrUniDlciLbRowStatus,
--           mscFrUniDlciDcComponentName,
--           mscFrUniDlciTotalIngressSegFrm,
--           mscFrUniLtsLoad,
--           mscFrUniDlciRowStatus,
--           mscFrUniDnaHgMAvailabilityDelta,
--           mscFrUniSigMaximumFrameSize,
--           mscFrUniDlciVcOoSeqByteCntExceeded,
--           mscFrUniDnaCugType,
--           mscFrUniDlciVcPreviousState,
--           mscFrUniDlciErrorLongBytesFromIf,
--           mscFrUniAdminState,
--           mscFrUniDlciVcPktRetryTimeouts,
--           mscFrUniDlciVcOutOfRangeFrmFromSubnet,
--           mscFrUniDlciErrorLongFrmFromIf,
--           mscFrUniLtsLastActiveInterval,
--           mscFrUniDlciVcCalledDna,
--           mscFrUniDlciDiscDeCongestedFromIfBytes,
--           mscFrUniVFramerFrmFromOtherVFramer,
--           mscFrUniLmiFullStatusPollingCycles,
--           mscFrUniSigInCalls,
--           mscFrUniSigFrmrReceive,
--           mscFrUniDlciVcSubnetRecoveries,
--           mscFrUniFramerNormPrioLinkUtilFromIf,
--           mscFrUniDlciSpCommittedBurstSize,
--           mscFrUniSigWindowSize,
--           mscFrUniDlciEirIngressSegFrm,
--           mscFrUniFramerInterfaceName,
--           mscFrUniDlciDiscExcessFromIfBytes,
--           mscFrUniFramerRowStatus,
--           mscFrUniDlciVcSegmentSize,
--           mscFrUniDlciDeFrmToIf,
--           mscFrUniLmiSequenceErrors,
--           mscFrUniFramerOperationalState,
--           mscFrUniSigRowStatus,
--           mscFrUniFramerFrmModeErrors,
--           mscFrUniLmiProtocolStatus,
--           mscFrUniCaTpmStorageType,
--           mscFrUniDlciBecnFrmSetByService,
--           mscFrUniDlciVcCallingNpi,
--           mscFrUniDlciAvailabilityStatus,
--           mscFrUniCaIngCirBPValue,
--           mscFrUniDnaStorageType,
--           mscFrUniLmiFullStatusEnqToIf,
--           mscFrUniLtsBurstSize,
--           mscFrUniFramerAborts,
--           mscFrUniDlciDiscDeCongestedToIfBytes,
--           mscFrUniDlciLbStorageType,
--           mscFrUniDnaHgMHgAddrStorageType,
--           mscFrUniDlciLbRemoteFecnFrm,
--           mscFrUniSigReceiveRejectFrame,
--           mscFrUniSigOperationalState,
--           mscFrUniAlarmStatus,
--           mscFrUniDlciABitReasonToIf,
--           mscFrUniCaLinkRate,
--           mscFrUniDlciDcType,
--           mscFrUniDlciDiscFrameAbit,
--           mscFrUniLtsPatDefaultRfc1490Header,
--           mscFrUniDlciDeBytesToIf,
--           mscFrUniDlciVcCalledLcn,
--           mscFrUniDlciDeBytesFromIf,
--           mscFrUniSigRemoteBusy,
--           mscFrUniLtsPatStatus,
--           mscFrUniLmiOperationalState,
--           mscFrUniSigRetransmitLimit,
--           mscFrUniDnaDataPath,
--           mscFrUniSigDefaultLocCheck,
--           mscFrUniDlciTotalIngressBytes,
--           mscFrUniDlciVcPeakOoSeqByteCount,
--           mscFrUniVFramerStorageType,
--           mscFrUniFramerUnderruns,
--           mscFrUniSigRestartRcvTimer,
--           mscFrUniSigHighestFriPvcDlci,
--           mscFrUniVFramerRowStatus,
--           mscFrUniDnaHgMAvailableDlcis,
--           mscFrUniNumberOfEmissionQs,
--           mscFrUniDlciEgressSpMeasurementInterval,
--           mscFrUniVFramerAdminState,
--           mscFrUniLtsComponentName,
--           mscFrUniDlciVcRowStatus,
--           mscFrUniVFramerOctetFromOtherVFramer,
--           mscFrUniDlciDiscCongestedFromIfBytes,
--           mscFrUniDlciEirIngressBytes,
--           mscFrUniLtsPatPayloadPattern,
--           mscFrUniSigProtocolErrors,
--           mscFrUniCaEgCirPoolAvailBwValue,
--           mscFrUniSigDefaultAccounting,
--           mscFrUniDlciVcCombErrorsFromSubnet,
--           mscFrUniSigLastCauseInStatusMsgReceived,
--           mscFrUniDlciVcSegmentsRx,
--           mscFrUniFramerFrmFromIf64,
--           mscFrUniSigDefaultCommittedBurstSize,
--           mscFrUniLmiEventCount,
--           mscFrUniFramerOverruns,
--           mscFrUniCaNumberRejectedEgressCirPermConn,
--           mscFrUniDlciUnknownStatus,
--           mscFrUniDlciCallref,
--           mscFrUniDlciDcStorageType,
--           mscFrUniDlciEgressSpStorageType,
--           mscFrUniSigIdleProbeTimer,
--           mscFrUniDnaCugRowStatus,
--           mscFrUniDlciVcDmepValue,
--           mscFrUniLmiSide,
--           mscFrUniDlciEgressSpCommittedInformationRate,
--           mscFrUniDlciErrorShortBytesFromIf,
--           mscFrUniSigOutCalls,
--           mscFrUniLtsPatStorageType,
--           mscFrUniLmiLinkVerificationTimer,
--           mscFrUniLtsPatDefaultDlci,
--           mscFrUniDlciErrorShortFrmFromIf,
--           mscFrUniDlciDcDeDiscardPriority,
--           mscFrUniLtsPatDefaultUseBadLrc,
--           mscFrUniDlciVcStartTime,
--           mscFrUniLmiUnexpectedReports,
--           mscFrUniDlciSpRateAdaptation,
--           mscFrUniDnaHgMAvailabilityUpdateThreshold,
--           mscFrUniDnaCugComponentName,
--           mscFrUniDlciVcAccountingEnabled,
--           mscFrUniDlciVcCallingLcn,
--           mscFrUniDlciDcRemoteNpi,
--           mscFrUniDlciDcDataPath }
-- STATUS  mandatory
-- DESCRIPTION
--   "A list of all current accessible leaf objects."

frameRelayUniGroup OBJECT IDENTIFIER ::= { frameRelayUniMIB 1 }
frameRelayUniGroupCA OBJECT IDENTIFIER ::= { frameRelayUniGroup 1 }
frameRelayUniGroupCA02 OBJECT IDENTIFIER ::= { frameRelayUniGroupCA 3 }
frameRelayUniGroupCA02A OBJECT IDENTIFIER ::= { frameRelayUniGroupCA02 2 }



-- Agent-Capabilities Statement:

-- PRODUCT-RELEASE "MscPassport Release 1.2 FrameRelayUni."
-- STATUS          mandatory
-- DESCRIPTION     "Carrier Passport FrameRelayUni MIB: MIB Version CA02A,
--                  Software Version CA02S9C."
-- SUPPORTS        Nortel-MsCarrier-MscPassport-FrameRelayUniMIB
--    INCLUDES     { frameRelayUniGroupCA02A }

frameRelayUniCapabilities OBJECT IDENTIFIER ::= { frameRelayUniMIB 3 }
frameRelayUniCapabilitiesCA OBJECT IDENTIFIER ::= { frameRelayUniCapabilities 1 }
frameRelayUniCapabilitiesCA02 OBJECT IDENTIFIER ::= { frameRelayUniCapabilitiesCA 3 }
frameRelayUniCapabilitiesCA02A OBJECT IDENTIFIER ::= { frameRelayUniCapabilitiesCA02 2 }





END
