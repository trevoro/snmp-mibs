-- *****************************************************************************
-- MIB module identifier assignments for Unisphere Networks data communications
-- products.
--
-- Copyright (c) 1999, 2002 Unisphere Networks, Inc.  All Rights Reserved.
-- *****************************************************************************

Unisphere-Data-MIBs DEFINITIONS ::= BEGIN

IMPORTS
    MODULE-IDENTITY
        FROM SNMPv2-SMI
    usMibs
        FROM Unisphere-SMI;

usDataMibs MODULE-IDENTITY
    LAST-UPDATED "200206041437Z"  -- 04-Jun-02 10:37 AM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The assignment of the MIB module object identifiers for data
        commmunications products located under the Unisphere Networks
        top-level MIB module object identifier (usMibs)."
    -- Revision History
    REVISION    "200206041437Z"  -- 04-Jun-02 10:37 AM EDT  - RX 4.0
    DESCRIPTION
        "Added MIB module OIDs for:
         - Multiprotocol Label Switching (MPLS) MIB
         - System Clock MIB
         - Quality of Service (QoS) MIB
         - X.21/V.35 interface MIB."
    REVISION    "200205311433Z"  -- 31-May-02 10:33 AM EDT  - RX 3.6
    DESCRIPTION
        "Added MIB module OID for the L2TP Dialout MIB."
    REVISION    "200111301412Z"  -- 30-Nov-01 09:12 AM EST  - RX 3.2
    DESCRIPTION
        "Added IP Tunnel (GRE/DVMRP) MIB, Connection-Based Forwarding (CBF) MIB
        and Layer 2 Forwarding (L2F) Protocol MIB module OIDs."
    REVISION    "200012271550Z"  -- 27-Dec-00 10:50 AM EST  - RX 3.1
    DESCRIPTION
        "Added SMDS MIB module OID."
    REVISION    "200011220000Z"  -- 22-Nov-00               - RX 3.0
    DESCRIPTION
        "Revised .mi2 filenames in descriptions for PPP and PPPOE Profile MIBs.
         Added AUTOCONFIGURE and SUBSCRIBER MIBs."
    REVISION    "200009191540Z"  -- 19-Sep-00 11:40 AM EDT  - RX 2.0
    DESCRIPTION
        "Replaced OBJECT-IDENTITYs with OBJECT IDENTIFIERs.
         Added new MIB module IDs."
    REVISION      "9912151544Z"  -- 15-Dec-99 10:44 AM EST  - RX 1.3
    DESCRIPTION
        "Added OBJECT-IDENTITY definitions for all MIB module IDs."
    REVISION      "9911080000Z"  -- 08-Nov-99               - RX 1.2
    DESCRIPTION
        "Initial version of this management information module."
    ::= { usMibs 2 }


-- *****************************************************************************
-- The assignment of all Unisphere Networks data communications products' MIB
-- module identifiers are contained in this section of the SNMP object
-- identifier registration tree.  MIB object identifiers are allocated beneath
-- a MIB's MODULE-IDENTITY node.
-- *****************************************************************************
usdTextualConventions OBJECT IDENTIFIER
--  STATUS      current
--  DESCRIPTION
--      "Textual Conventions module for Unisphere Networks data communications
--      products."
--  REFERENCE
--      "The textual convention are defined in the Unisphere-Data-TC module (in
--      the usDataTc.mi2 file)."
    ::= { usDataMibs 1 }

usdSystemMIB OBJECT IDENTIFIER
--  STATUS      current
--  DESCRIPTION
--      "The generic system MIB module for Unisphere Networks data
--      communications products.  This value is reserved for future use."
    ::= { usDataMibs 2 }

usdIfMIB OBJECT IDENTIFIER
--  STATUS      current
--  DESCRIPTION
--      "Generic Interfaces MIB module for Unisphere Networks data
--      communications products."
--  REFERENCE
--      "The MIB objects are defined in the Unisphere-Data-IF-MIB module (in the
--      usDataIf.mi2 file)."
    ::= { usDataMibs 3 }

usdDs3MIB OBJECT IDENTIFIER
--  STATUS      current
--  DESCRIPTION
--      "DS3/E3 MIB module for Unisphere Networks data communications products."
--  REFERENCE
--      "The MIB objects are defined in the Unisphere-Data-DS3-MIB module (in
--      the usDataDs3.mi2 file)."
    ::= { usDataMibs 4 }

usdDs1MIB OBJECT IDENTIFIER
--  STATUS      current
--  DESCRIPTION
--      "DS1/E1 MIB module for Unisphere Networks data communications products."
--  REFERENCE
--      "The MIB objects are defined in the Unisphere-Data-DS1-MIB module (in
--      the usDataDs1.mi2 file)."
    ::= { usDataMibs 5 }

usdFt1MIB OBJECT IDENTIFIER
--  STATUS      current
--  DESCRIPTION
--      "Fractional T1 arrangements MIB module for Unisphere Networks data
--      communications products."
--  REFERENCE
--      "The MIB objects are defined in the Unisphere-Data-FRACTIONAL-T1-MIB
--      module (in the usDataFt1.mi2 file)."
    ::= { usDataMibs 6 }

usdSonetMIB OBJECT IDENTIFIER
--  STATUS      current
--  DESCRIPTION
--      "SONET MIB module for Unisphere Networks data communications products."
--  REFERENCE
--      "The MIB objects are defined in the Unisphere-Data-SONET-MIB module (in
--      the usDataSonet.mi2 file)."
    ::= { usDataMibs 7 }

usdAtmMIB OBJECT IDENTIFIER
--  STATUS      current
--  DESCRIPTION
--      "ATM MIB module for Unisphere Networks data communications products."
--  REFERENCE
--      "The MIB objects are defined in the Unisphere-Data-ATM-MIB module (in
--      the usDataAtm.mi2 file)."
    ::= { usDataMibs 8 }

usdHdlcMIB OBJECT IDENTIFIER
--  STATUS      current
--  DESCRIPTION
--      "HDLC MIB module for Unisphere Networks data communications products."
--  REFERENCE
--      "The MIB objects are defined in the Unisphere-Data-HDLC-MIB module (in
--      the usDataHdlc.mi2 file)."
    ::= { usDataMibs 9 }

usdFrameRelayMIB OBJECT IDENTIFIER
--  STATUS      current
--  DESCRIPTION
--      "Frame Relay MIB module for Unisphere Networks data communications
--      products."
--  REFERENCE
--      "The MIB objects are defined in the Unisphere-Data-FRAME-RELAY-MIB
--      module (in the usDataFr.mi2 file)."
    ::= { usDataMibs 10 }

usdPppMIB OBJECT IDENTIFIER
--  STATUS      current
--  DESCRIPTION
--      "PPP MIB module for Unisphere Networks data communications products."
--  REFERENCE
--      "The MIB objects are defined in the Unisphere-Data-PPP-MIB module (in
--      the usDataPpp.mi2 file)."
    ::= { usDataMibs 11 }

usdIpMIB OBJECT IDENTIFIER
--  STATUS      current
--  DESCRIPTION
--      "IP Protocol, Interfaces, Forwarding MIBs module for Unisphere Networks
--      data communications products."
--  REFERENCE
--      "The MIB objects are defined in the Unisphere-Data-IP-MIB module (in the
--      usDataIp.mi2 file)."
    ::= { usDataMibs 12 }

usdIpPolicyMIB OBJECT IDENTIFIER
--  STATUS      current
--  DESCRIPTION
--      "IP Access Lists, Route Maps MIB module for Unisphere Networks data
--      communications products."
--  REFERENCE
--      "The MIB objects are defined in the Unisphere-Data-IP-POLICY-MIB module
--      (in the usDataIpPolicy.mi2 file)."
    ::= { usDataMibs 13 }

usdOspfMIB OBJECT IDENTIFIER
--  STATUS      current
--  DESCRIPTION
--      "OSPF MIB module for Unisphere Networks data communications products."
--  REFERENCE
--      "The MIB objects are defined in the Unisphere-Data-OSPF-MIB module (in
--      the usDataOspf.mi2 file)."
    ::= { usDataMibs 14 }

usdSlepMIBS OBJECT IDENTIFIER
--  STATUS      current
--  DESCRIPTION
--      "SLEP MIB module for Unisphere Networks data communications products."
--  REFERENCE
--      "The MIB objects are defined in the Unisphere-Data-SLEP-MIB module (in
--      the usDataSlep.mi2 file)."
    ::= { usDataMibs 15 }

usdSnmpMIB OBJECT IDENTIFIER
--  STATUS      current
--  DESCRIPTION
--      "SNMP MIB module for Unisphere Networks data communications products."
--  REFERENCE
--      "The MIB objects are defined in the Unisphere-Data-SNMP-MIB module (in
--      the usDataSnmp.mi2 file)."
    ::= { usDataMibs 16 }

usdERXSysMIB OBJECT IDENTIFIER
--  STATUS      current
--  DESCRIPTION
--      "System MIB specific to the ERX1400/ERX700 products module for Unisphere
--      Networks data communications products."
--  REFERENCE
--      "The MIB objects are defined in the Unisphere-Data-ERX-System-MIB module
--      (in the usErxSystem.mi2 file)."
    ::= { usDataMibs 17 }

usdPPPoEMIB OBJECT IDENTIFIER
--  STATUS      current
--  DESCRIPTION
--      "PPP-over-Ethernet MIB module for Unisphere Networks data communications
--      products."
--  REFERENCE
--      "The MIB objects are defined in the Unisphere-Data-PPPOE-MIB module (in
--      the usDataPppoe.mi2 file)."
    ::= { usDataMibs 18 }

usdRadiusClientMIB OBJECT IDENTIFIER
--  STATUS      current
--  DESCRIPTION
--      "RADIUS Client MIB module for Unisphere Networks data communications
--      products."
--  REFERENCE
--      "The MIB objects are defined in the Unisphere-Data-RADIUS-CLIENT-MIB
--      module (in the usDataRadClient.mi2 file)."
    ::= { usDataMibs 19 }

usdAaaMIB OBJECT IDENTIFIER
--  STATUS      current
--  DESCRIPTION
--      "Authentication, Authorization, and Accounting Server MIB module for
--      Unisphere Networks data communications products."
--  REFERENCE
--      "The MIB objects are defined in the Unisphere-Data-AAA-MIB module (in
--      the usDataAaa.mi2 file)."
    ::= { usDataMibs 20 }

usdAddressPoolMIB OBJECT IDENTIFIER
--  STATUS      current
--  DESCRIPTION
--      "Address Pool MIB module for Unisphere Networks data communications
--      products."
--  REFERENCE
--      "The MIB objects are defined in the Unisphere-Data-ADDRESS-POOL-MIB
--      module (in the usDataAddrPool.mi2 file)."
    ::= { usDataMibs 21 }

usdDhcpMIB OBJECT IDENTIFIER
--  STATUS      current
--  DESCRIPTION
--      "DHCP MIB module for Unisphere Networks data communications products."
--  REFERENCE
--      "The MIB objects are defined in the Unisphere-Data-DHCP-MIB module (in
--      the usDataDhcp.mi2 file)."
    ::= { usDataMibs 22 }

usdFileXferMIB OBJECT IDENTIFIER
--  STATUS      current
--  DESCRIPTION
--      "File Transfer MIB module for Unisphere Networks data communications
--      products."
--  REFERENCE
--      "The MIB objects are defined in the Unisphere-Data-FILE-XFER-MIB module
--      (in the usDataFileXfer.mi2 file)."
    ::= { usDataMibs 23 }

usdAcctngMIB OBJECT IDENTIFIER
--  STATUS      current
--  DESCRIPTION
--      "Bulk Stats MIB module for Unisphere Networks data communications
--      products."
--  REFERENCE
--      "The MIB objects are defined in the Unisphere-Data-ACCOUNTING-MIB module
--      (in the usDataAcctng.mi2 file)."
    ::= { usDataMibs 24 }

usdProfileMIB OBJECT IDENTIFIER
--  STATUS      current
--  DESCRIPTION
--      "Name/identifier mapping of configuration profiles MIB module for
--      Unisphere Networks data communications products."
--  REFERENCE
--      "The MIB objects are defined in the Unisphere-Data-PROFILE-MIB module
--      (in the usDataTmpl.mi2 file)."
    ::= { usDataMibs 25 }

usdIpProfileMIB OBJECT IDENTIFIER
--  STATUS      current
--  DESCRIPTION
--      "IP interface profile configuration MIB module for Unisphere Networks
--      data communications products."
--  REFERENCE
--      "The MIB objects are defined in the Unisphere-Data-IP-PROFILE-MIB module
--      (in the usDataTmplIp.mi2 file)."
    ::= { usDataMibs 26 }

usdPolicyMIB OBJECT IDENTIFIER
--  STATUS      current
--  DESCRIPTION
--      "Policy Management MIB module for Unisphere Networks data communications
--      products."
--  REFERENCE
--      "The MIB objects are defined in the Unisphere-Data-POLICY-MIB module (in
--      the usDataPolicy.mi2 file)."
    ::= { usDataMibs 27 }

usdLogMIB OBJECT IDENTIFIER
--  STATUS      current
--  DESCRIPTION
--      "Logging Configuration and Monitoring MIB module for Unisphere Networks
--      data communications products."
--  REFERENCE
--      "The MIB objects are defined in the Unisphere-Data-LOG-MIB module (in
--      the usDataLog.mi2 file)."
    ::= { usDataMibs 28 }

usdBgpMIB OBJECT IDENTIFIER
--  STATUS      current
--  DESCRIPTION
--      "BGP MIB module for Unisphere Networks data communications products."
--  REFERENCE
--      "The MIB objects are defined in the Unisphere-Data-BGP-MIB module (in
--      the usDataBgp.mi2 file)."
    ::= { usDataMibs 29 }

usdCliMIB OBJECT IDENTIFIER
--  STATUS      current
--  DESCRIPTION
--      "CLI MIB module for Unisphere Networks data communications products."
--  REFERENCE
--      "The MIB objects are defined in the Unisphere-Data-CLI-MIB module (in
--      the usDataCli.mi2 file)."
    ::= { usDataMibs 30 }

usdBridgeEthernetMIB OBJECT IDENTIFIER
--  STATUS      current
--  DESCRIPTION
--      "Bridged Ethernet MIB module for Unisphere Networks data communications
--      products."
--  REFERENCE
--      "The MIB objects are defined in the Unisphere-Data-BRIDGE-ETHERNET-MIB
--      module (in the usDataBridgeEthernet.mi2 file)."
    ::= { usDataMibs 31 }

usdRouterMIB OBJECT IDENTIFIER
--  STATUS      current
--  DESCRIPTION
--      "Router MIB module for Unisphere Networks data communications products."
--  REFERENCE
--      "The MIB objects are defined in the Unisphere-Data-ROUTER-MIB module (in
--      the usDataRouter.mi2 file)."
    ::= { usDataMibs 32 }

usdHostMIB OBJECT IDENTIFIER
--  STATUS      current
--  DESCRIPTION
--      "Router MIB module for Unisphere Networks data communications products."
--  REFERENCE
--      "The MIB objects are defined in the Unisphere-Data-HOST-MIB module (in
--      the usDataHost.mi2 file)."
    ::= { usDataMibs 33 }

usdEthernetMIB OBJECT IDENTIFIER
--  STATUS      current
--  DESCRIPTION
--      "Ethernet MIB module for Unisphere Networks data communications
--      products."
--  REFERENCE
--      "The MIB objects are defined in the Unisphere-Data-ETHERNET-MIB module
--      (in the usDataEthernet.mi2 file)."
    ::= { usDataMibs 34 }

usdL2tpMIB OBJECT IDENTIFIER
--  STATUS      current
--  DESCRIPTION
--      "The Layer 2 Tunneling Protocol (L2TP) MIB module for Unisphere Networks
--      data communications products."
--  REFERENCE
--      "The MIB objects are defined in the Unisphere-Data-L2TP-MIB module (in
--      the usDataL2tp.mi2 file)."
    ::= { usDataMibs 35 }

usdSscClientMIB OBJECT IDENTIFIER
--  STATUS      current
--  DESCRIPTION
--      "SSC MIB module for Unisphere Networks data communications products."
--  REFERENCE
--      "The MIB objects are defined in the Unisphere-Data-SSC-CLIENT-MIB module
--      (in the usDataSscClient.mi2 file)."
    ::= { usDataMibs 36 }

usdCopsProtocolMIB OBJECT IDENTIFIER
--  STATUS      current
--  DESCRIPTION
--      "COPS MIB module for Unisphere Networks data communications products."
--  REFERENCE
--      "The MIB objects are defined in the Unisphere-Data-COPS-MIB module (in
--      the usDataCops.mi2 file)."
    ::= { usDataMibs 37 }

usdIsisMIB OBJECT IDENTIFIER
--  STATUS      current
--  DESCRIPTION
--      "ISIS MIB module for Unisphere Networks data communications products."
--  REFERENCE
--      "The MIB objects are defined in the Unisphere-Data-ISIS-MIB module (in
--      the usDataIsis.mi2 file)."
    ::= { usDataMibs 38 }

usdPingMIB OBJECT IDENTIFIER
--  STATUS      deprecated
--  DESCRIPTION
--      "IETF Distributed Management Ping MIB folded into Unisphere Networks
--      data communications products.  This MIB has been replaced by the
--      Internet Standards Track DISMAN-PING-MIB (RFC 2925)."
--  REFERENCE
--      "The MIB objects are defined in the Unisphere-Data-PING-MIB module (in
--      the usDataPing.mi2 file)."
    ::= { usDataMibs 39 }

usdIgmpMIB OBJECT IDENTIFIER
--  STATUS      current
--  DESCRIPTION
--      "IETF IGMP MIB folded into Unisphere Networks data communications
--      products."
--  REFERENCE
--      "The MIB objects are defined in the Unisphere-Data-IGMP-MIB module (in
--      the usDataIgmp.mi2 file)."
    ::= { usDataMibs 40 }

usdTraceRouteMIB OBJECT IDENTIFIER
--  STATUS      deprecated
--  DESCRIPTION
--      "IETF Distributed Management Trace-route MIB folded into Unisphere
--      Networks data communications products.  This MIB has been replaced by
--      the Internet Standards Track DISMAN-TRACEROUTE-MIB (RFC 2925)."
--  REFERENCE
--      "The MIB objects are defined in the Unisphere-Data-TRACEROUTE-MIB module
--      (in the usDataTraceRoute.mi2 file)."
    ::= { usDataMibs 41 }

usdLookupMIB OBJECT IDENTIFIER
--  STATUS      deprecated
--  DESCRIPTION
--      "IETF Distributed Management NS Lookup MIB folded into Unisphere
--      Networks data communications products.  This MIB has been replaced by
--      the Internet Standards Track DISMAN-NSLOOKUP-MIB (RFC 2925)."
--  REFERENCE
--      "The MIB objects are defined in the Unisphere-Data-NSLOOKUP-MIB module
--      (in the usDataNsLookup.mi2 file)."
    ::= { usDataMibs 42 }

usdPimMIB OBJECT IDENTIFIER
--  STATUS      current
--  DESCRIPTION
--      "PIM MIB module for Unisphere Networks data communications products."
--  REFERENCE
--      "The MIB objects are defined in the Unisphere-Data-PIM-MIB module (in
--      the usDataPim.mi2 file)."
    ::= { usDataMibs 43 }

usdDvmrpMIB OBJECT IDENTIFIER
--  STATUS      current
--  DESCRIPTION
--      "The Distance Vector Multicast Routing Protocol (DVMRP) MIB for
--      Unisphere Networks data communications products."
--  REFERENCE
--      "The MIB objects are defined in the Unisphere-Data-DVMRP-MIB module (in
--      the usDataDvmrp.mi2 file)."
    ::= { usDataMibs 44 }

usdPppProfileMIB OBJECT IDENTIFIER
--  STATUS      current
--  DESCRIPTION
--      "PPP interface profile configuration MIB module for Unisphere Networks
--      data communications products."
--  REFERENCE
--      "The MIB objects are defined in the Unisphere-Data-PPP-Profile-MIB
--      module (in the usDataTmplPpp.mi2 file)."
    ::= { usDataMibs 45 }

usdPppoeProfileMIB OBJECT IDENTIFIER
--  STATUS      current
--  DESCRIPTION
--      "PPP over Ethernet interface profile configuration MIB module for
--      Unisphere Networks data communications products."
--  REFERENCE
--      "The MIB objects are defined in the Unisphere-Data-PPPoE-Profile-MIB
--      module (in the usDataTmplPppoe.mi2 file)."
    ::= { usDataMibs 46 }

usdDnsMIB OBJECT IDENTIFIER
--  STATUS      current
--  DESCRIPTION
--      "Domain Name System (DNS) management MIB module for Unisphere Networks
--      data communications products."
--  REFERENCE
--      "The MIB objects are defined in the Unisphere-Data-DNS-MIB module (in
--      the usDataDns.mi2 file)."
    ::= { usDataMibs 47 }

usdAutoConfMIB OBJECT IDENTIFIER
--  STATUS      current
--  DESCRIPTION
--      "Auto-Configuration management MIB module for Unisphere Networks data
--      communications products."
--  REFERENCE
--      "The MIB objects are defined in the Unisphere-Data-AUTOCONFIGURE-MIB
--      module (in the usDataAutoconf.mi2 file)."
    ::= { usDataMibs 48 }

usdSubscriberMIB OBJECT IDENTIFIER
--  STATUS      current
--  DESCRIPTION
--      "Subscriber management MIB module for Unisphere Networks data
--      communications products."
--  REFERENCE
--      "The MIB objects are defined in the Unisphere-Data-SUBSCRIBER-MIB module
--      (in the usDataSubscriber.mi2 file)."
    ::= { usDataMibs 49 }

usdSmdsMIB OBJECT IDENTIFIER
--  STATUS      current
--  DESCRIPTION
--      "Switched Multimegabit Data Service (SMDS) MIB module for Unisphere
--      Networks data communications products."
--  REFERENCE
--      "The MIB objects are defined in the Unisphere-Data-SMDS-MIB module (in
--      the usDataSmds.mi2 file)."
    ::= { usDataMibs 50 }

usdIpTunnelMIB OBJECT IDENTIFIER
--  STATUS      current
--  DESCRIPTION
--      "IP Tunnel (GRE/DVMRP) MIB module for Unisphere Networks data
--      communications products."
--  REFERENCE
--      "The MIB objects are defined in the Unisphere-Data-IP-TUNNEL-MIB module
--      (in the usDataIpTunnel.mi2 file)."
    ::= { usDataMibs 51 }

usdCbfMIB OBJECT IDENTIFIER
--  STATUS      current
--  DESCRIPTION
--      "Connection-Based Forwarding (CBF) MIB module for Unisphere Networks
--      data communications products."
--  REFERENCE
--      "The MIB objects are defined in the Unisphere-Data-CBF-MIB module (in
--      the usDataCbf.mi2 file)."
    ::= { usDataMibs 52 }

usdL2fMIB OBJECT IDENTIFIER
--  STATUS      current
--  DESCRIPTION
--      "Layer 2 Forwarding (L2F) Protocol MIB module for Unisphere Networks
--      data communications products."
--  REFERENCE
--      "The MIB objects are defined in the Unisphere-Data-L2F-MIB module (in
--      the usDataL2f.mi2 file)."
    ::= { usDataMibs 53 }

usdMplsMIB OBJECT IDENTIFIER
--  STATUS      current
--  DESCRIPTION
--      "Multiprotocol Label Switching (MPLS) MIB module for Unisphere Networks
--      data communications products."
--  REFERENCE
--      "The MIB objects are defined in the Unisphere-Data-MPLS-MIB module (in
--      the usDataMpls.mi2 file)."
    ::= { usDataMibs 54 }

usdMrxSystemMIB OBJECT IDENTIFIER
--  STATUS      obsolete
--  DESCRIPTION
--      "This value is not used."
    ::= { usDataMibs 55 }

usdSysClockMIB OBJECT IDENTIFIER
--  STATUS      current
--  DESCRIPTION
--      "System Clock MIB module for Unisphere Networks data communications
--      products."
--  REFERENCE
--      "The MIB objects are defined in the Unisphere-Data-System-Clock-MIB
--      module (in the usDataSysClock.mi2 file)."
    ::= { usDataMibs 56 }

usdQosMIB OBJECT IDENTIFIER
--  STATUS      current
--  DESCRIPTION
--      "Quality of Service (QoS) MIB module for Unisphere Networks data
--      communications products."
--  REFERENCE
--      "The MIB objects are defined in the Unisphere-Data-QoS-MIB module (in
--      the usDataQos.mi2 file)."
    ::= { usDataMibs 57 }

usdV35MIB OBJECT IDENTIFIER
--  STATUS      current
--  DESCRIPTION
--      "The X.21/V.35 interface configuration MIB module for Unisphere Networks
--      data communications products."
--  REFERENCE
--      "The MIB objects are defined in the Unisphere-Data-V35-MIB module (in
--      the usDataV35.mi2 file)."
    ::= { usDataMibs 59 }

usdL2tpDialoutMIB OBJECT IDENTIFIER
--  STATUS      current
--  DESCRIPTION
--      "The Layer 2 Tunneling Protocol (L2TP) Dialout MIB module for Unisphere
--      Networks data communications products."
--  REFERENCE
--      "The MIB objects are defined in the Unisphere-Data-L2TP-Dialout-MIB
--      module (in the usDataL2tpDialout.mi2 file)."
    ::= { usDataMibs 62 }

END
