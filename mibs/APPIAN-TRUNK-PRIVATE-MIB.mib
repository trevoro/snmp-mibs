--
--  Title:  Appian-TRUNKS-PRIVATE-MIB
--
--  Date:   02/13/00
--
--  Description:
--
--  This file contains the ASN.1 MIB definition for network level 
--  provisioning of an OSAP2K series platform.  Network provisioning
--  supports the configuration of an OSAP physical layer RING at layer
--  one(1).  SONET ring topology, Uplink Physical Port mapping, STS level
--  mapping (timeslots), Trunking and Frame Relay configuration are 
--  implemented as configuration tables.
--
--
APPIAN-TRUNK-PRIVATE-MIB DEFINITIONS ::= BEGIN

    IMPORTS

        acTrunks, AcOpStatus, AcAdminStatus,
        AcNodeId                                        FROM APPIAN-SMI-MIB
       
        MODULE-IDENTITY, OBJECT-TYPE, NOTIFICATION-TYPE FROM SNMPv2-SMI

        acChassisCurrentTime, acChassisRingId     FROM APPIAN-CHASSIS-MIB
            
        DisplayString                                   FROM SNMPv2-TC;


acTrunksPrivate   MODULE-IDENTITY
    LAST-UPDATED    "0003200000Z"
    ORGANIZATION    "Appian Communications, Inc."
    CONTACT-INFO    "Douglas Theriault"
    DESCRIPTION
                    "Appian Communications Common trunking MIBs."
    REVISION
                    "0003200000Z"
    DESCRIPTION
                    "Draft engineering version.  Not for release."

    ::= { acTrunks 4 }

--
-- Trunk Table
--
acTrunkPrivateTable    OBJECT-TYPE
    SYNTAX  SEQUENCE OF AcTrunkPrivateEntry
    MAX-ACCESS  not-accessible
    STATUS      current
    DESCRIPTION
    "The trunking provisioning table. Records in this table are
     created by management action and not by the OSAP."

    ::= { acTrunksPrivate 1 }

acTrunkPrivateEntry    OBJECT-TYPE
    SYNTAX  AcTrunkPrivateEntry
    MAX-ACCESS  not-accessible
    STATUS      current
    DESCRIPTION
    "A row within the trunk provisioning table."

    INDEX { acTrunkPrivateNodeId, acTrunkPrivateIndex }
    
    ::= { acTrunkPrivateTable 1 }

    AcTrunkPrivateEntry ::=
        SEQUENCE {
            acTrunkPrivateNodeId        AcNodeId,
            acTrunkPrivateIndex         INTEGER,
            acTrunkPrivateAdminStatus   AcAdminStatus,
            acTrunkPrivateOpStatus      AcOpStatus,
            acTrunkPrivateDetailStatus  DisplayString
        }

--
-- TrunkEntry
--
acTrunkPrivateNodeId    OBJECT-TYPE
    SYNTAX      AcNodeId
    MAX-ACCESS  accessible-for-notify
    STATUS      current
    DESCRIPTION
    "A unique number assigned by the EMS which uniquely identifies a node
    within an Appian ring of OSAP's."

    ::= { acTrunkPrivateEntry 1 }

acTrunkPrivateIndex    OBJECT-TYPE
    SYNTAX      INTEGER
    MAX-ACCESS  accessible-for-notify
    STATUS      current
    DESCRIPTION
    "An index key that uniquely identifies a row in the trunk table.
     THis row is associated with the shared trunk row with the same 
     index"

    ::= { acTrunkPrivateEntry 2 }

acTrunkPrivateAdminStatus    OBJECT-TYPE
          SYNTAX      AcAdminStatus
          MAX-ACCESS  read-create
          STATUS      current
          DESCRIPTION
          "Appian Administrative Status attribute used to set the provisioning
          state as either activate(1), inactivate(2) or delete(3).  Refer to
          the Appian-SMI.mib file for additional information."

          DEFVAL { inactivate }
    ::= { acTrunkPrivateEntry 3 }

acTrunkPrivateOpStatus    OBJECT-TYPE
    SYNTAX      AcOpStatus
    MAX-ACCESS  read-only
    STATUS      current
    DESCRIPTION
    "Indicates the current state of the Trunk, in a general way. "

    ::= { acTrunkPrivateEntry 4 }

acTrunkPrivateDetailStatus    OBJECT-TYPE
    SYNTAX      DisplayString (SIZE (0..25))
    MAX-ACCESS  read-only
    STATUS      current
    DESCRIPTION
    "Provides details information about the trunk state"

    ::= { acTrunkPrivateEntry 5 }

acTrunkPrivateTraps  OBJECT IDENTIFIER ::= { acTrunksPrivate 0 }

acTrunkUpTrap NOTIFICATION-TYPE
    OBJECTS {  
      acChassisCurrentTime,
      acChassisRingId,
 
      acTrunkPrivateNodeId,
      acTrunkPrivateIndex,
      acTrunkPrivateOpStatus,
      acTrunkPrivateDetailStatus
    }
    STATUS  current
    DESCRIPTION
  "This trap indicates a trunk transition to the up state."

  ::= { acTrunkPrivateTraps 1}


acTrunkDownTrap NOTIFICATION-TYPE
    OBJECTS {  
      acChassisCurrentTime,
      acChassisRingId,
 
      acTrunkPrivateNodeId,
      acTrunkPrivateIndex,
      acTrunkPrivateOpStatus,
      acTrunkPrivateDetailStatus 
    }
    STATUS  current
    DESCRIPTION
  "This trap indicates a trunk transition to the down state."

  ::= { acTrunkPrivateTraps 2}
END
