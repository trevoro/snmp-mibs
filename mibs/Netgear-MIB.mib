-- ***************************************************************************
-- Netgear enterprise MIB for sysObjectID
-- Date: 5/12/2005
--
--
-- iso                  OBJECT IDENTIFIER ::= { 1 }
-- org                  OBJECT IDENTIFIER ::= { iso 3 }
-- dod                  OBJECT IDENTIFIER ::= { org 6 }
-- internet             OBJECT IDENTIFIER ::= { dod 1 }
-- private              OBJECT IDENTIFIER ::= { internet 4 }
-- enterprises          OBJECT IDENTIFIER ::= { private 1 }
-- netgear              OBJECT IDENTIFIER ::= { enterprises 4526 }
-- 
-- There are already MIB files defined
-- for quite a few managed switches, as well as access point. Those devices
-- did not follow the structure defined in this file. Instead, they put the
-- product ID right under major product category as followed:
--
--                             ==============
--                             |enterprises |
--                             ==============
--                                   |
--                              ============
--                              |  netgear |
--                              ============
--                                   |
--                  -------------------------------------
--                  |                |                  |
--            ===========       ===========         ============
--            | swicth 1|       | router 2|         |wireless 3|
--            ===========       ===========         ============
--                  |
--        =====================
--        |                   |
--    ===========         ===========
--    |fsm726s 1|         |fsm750s 2|
--    ===========         ===========
--        |                   |
--    ============        ============
--    |configport| :      |configport| :
--    ============        ============
--
-- This structure is wrong in that all the features/functions are defined under
-- each product repeatly. This makes the NMS difficult to collect MIB data
--
-- The new structure adds a product category right under netgear and put all product id there
--
--                             ==============
--                             |enterprises |
--                             ==============
--                                   |
--                              ============
--                              |  netgear |
--                              ============     OLD | NEW
--                                   |               |
--                  =================================|================================
--                  |            |             |     |      |           |           |
--            ===========   ===========   ========== |  ==========  =============
--            | swicth  |   | router  |   |wireless| |  |products|  |stackswitch|  ....
--            ===========   ===========   ========== |  ==========  =============
--                  |                                |      |           |
--        =====================                      |  ==========  ============
--        |                   |                         |FSM7328S|  |configport|
--    =========           =========                     ==========  ============
--    |fsm726s|           |fsm750s|
--    =========           =========
--        |                   |
--    ============        ============
--    |configport| :      |configport| :
--    ============        ============

Netgear-MIB DEFINITIONS ::= BEGIN
    IMPORTS
	TEXTUAL-CONVENTION FROM SNMPv2-TC
        enterprises FROM RFC1155-SMI;

netgear                 OBJECT IDENTIFIER ::= { enterprises 4526 }

--
-- below are products that defined prior to NMS100 release that they have product code
-- defined directly above the functions objects
--
managedSwitch           OBJECT IDENTIFIER ::= { netgear 1 } 
--router                  OBJECT IDENTIFIER ::= { netgear 2 }
carrier		        OBJECT IDENTIFIER ::= { netgear 3 }
wireless		OBJECT IDENTIFIER ::= { netgear 4 }
rps	OBJECT IDENTIFIER ::= { netgear 5 }
wlanswitch		OBJECT IDENTIFIER ::= { netgear 6 }

---
--- 700 series L2 managed switch
---
fsm726s                 OBJECT IDENTIFIER ::= { managedSwitch 1 }
fsm750s                 OBJECT IDENTIFIER ::= { managedSwitch 2 }
gsm712                  OBJECT IDENTIFIER ::= { managedSwitch 3 }
fsm726                  OBJECT IDENTIFIER ::= { managedSwitch 4 }  
gsm712f                 OBJECT IDENTIFIER ::= { managedSwitch 5 }
fsm726v2		OBJECT IDENTIFIER ::= { managedSwitch 10 }

---
--- AP
---
me103			OBJECT IDENTIFIER ::= { wireless 1 }
wg302			OBJECT IDENTIFIER ::= { wireless 2 }
wg102			OBJECT IDENTIFIER ::= { wireless 3 }
wag302			OBJECT IDENTIFIER ::= { wireless 4 }
wag102			OBJECT IDENTIFIER ::= { wireless 5 }

---
--- WLAN Switch
---
wls538			OBJECT IDENTIFIER ::= { wlanswitch 1 }

---
--- 7000 series L2/L3 managed switch
---
gsm7312                 OBJECT IDENTIFIER ::= { managedSwitch 6 }
gsm7324                 OBJECT IDENTIFIER ::= { managedSwitch 7 }
gsm7224                 OBJECT IDENTIFIER ::= { managedSwitch 8 }
fsm7326p                OBJECT IDENTIFIER ::= { managedSwitch 9 }

---********************************************************************
--- new post-NMS100 SNMP products 
---

--
-- new post-NMS100 SNMP-enabled products. These products will have their 
-- functions defined under each generic product category.
--
ng7000managedswitch   	OBJECT IDENTIFIER ::= { netgear 10 }
ng700smartswitch        OBJECT IDENTIFIER ::= { netgear 11 }
ngrouter		OBJECT IDENTIFIER ::= { netgear 12 }
ngfirewall		OBJECT IDENTIFIER ::= { netgear 13 }
ngap			OBJECT IDENTIFIER ::= { netgear 14 }
ngwlan			OBJECT IDENTIFIER ::= { netgear 15 }
ng9000chassisswitch     OBJECT IDENTIFIER ::= { netgear 16 }

--
-- and their sysObjectID will be under a branch on their own
--
productID               OBJECT IDENTIFIER ::= { netgear 100 }

stackswitch             OBJECT IDENTIFIER ::= { productID 1 }
l2switch                OBJECT IDENTIFIER ::= { productID 2 }
l3switch		OBJECT IDENTIFIER ::= { productID 3 }
smartswitch             OBJECT IDENTIFIER ::= { productID 4 }

router			OBJECT IDENTIFIER ::= { productID 5 }
firewall		OBJECT IDENTIFIER ::= { productID 6 }
accesspoint		OBJECT IDENTIFIER ::= { productID 7 }
wirelessLAN		OBJECT IDENTIFIER ::= { productID 8 }
chassisswitch		OBJECT IDENTIFIER ::= { productID 9 }

--
-- managed switches
--
fsm7328s                OBJECT IDENTIFIER ::= { stackswitch 1 }
fsm7352s                OBJECT IDENTIFIER ::= { stackswitch 2 }
gsm7328s		OBJECT IDENTIFIER ::= { stackswitch 3 }
gsm7352s                OBJECT IDENTIFIER ::= { stackswitch 4 }
fsm7352sp		OBJECT IDENTIFIER ::= { stackswitch 5 }
fsm7328sp		OBJECT IDENTIFIER ::= { stackswitch 6 }

gsm7312v2		OBJECT IDENTIFIER ::= { l3switch 1 }
gsm7324v2		OBJECT IDENTIFIER ::= { l3switch 2 }
xsm7312			OBJECT IDENTIFIER ::= { l3switch 3 }
gsm7324p		OBJECT IDENTIFIER ::= { l3switch 4 }

gsm7248                 OBJECT IDENTIFIER ::= { l2switch 1 }
gsm7212                 OBJECT IDENTIFIER ::= { l2switch 2 }

gcm9000			OBJECT IDENTIFIER ::= { chassisswitch 1 }

---
--- new SNMP-enabled Smartswitch
---
gs748t                  OBJECT IDENTIFIER ::= { smartswitch 1 }
fs726t			OBJECT IDENTIFIER ::= { smartswitch 2 }
gs716t			OBJECT IDENTIFIER ::= { smartswitch 3 }
fs750t			OBJECT IDENTIFIER ::= { smartswitch 4 }
gs724t			OBJECT IDENTIFIER ::= { smartswitch 5 }
fs726tp			OBJECT IDENTIFIER ::= { smartswitch 6 }

---
--- new SNMP-enabled business router/firewall
---
fvx538			OBJECT IDENTIFIER ::= { router 1 }
fvs338			OBJECT IDENTIFIER ::= { router 2 }
fvg318			OBJECT IDENTIFIER ::= { router 3 }

---
--- new SNMP-enabled firewall
---
fwag114			OBJECT IDENTIFIER ::= { firewall 3 }

---
--- new SNMP-enabled AP
---


---
--- new WLAN
---

--- 
--- Legacy stuff
---
--- New Textual Conventions
AgentPortMask ::= TEXTUAL-CONVENTION
   STATUS  current
   DESCRIPTION
       "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'
             
        When setting this value, the system will ignore 
        configuration for ports not between the first and last 
        valid ports.  Configuration of any port numbers between 
        this range that are not valid ports return a failure 
        message, but will still apply configuration for valid 
        ports."
   SYNTAX  OCTET STRING



END
