-- *****************************************************************
-- ciscoWanFrConnCapability MIB
--
-- AGENT-CAPABILITIES mib for Frame Relay Connection MIB
-- in MGX8850 products.
--
-- March 2002, Subra.Hegde
--
-- Copyright(c) 2002 by Cisco Systems,Inc.
--
-- *****************************************************************

CISCO-WAN-FR-CONN-CAPABILITY DEFINITIONS ::= BEGIN
IMPORTS
        MODULE-IDENTITY
                FROM SNMPv2-SMI
        AGENT-CAPABILITIES
                FROM SNMPv2-CONF
        ciscoWanAgentCapability
                FROM CISCOWAN-SMI;   

ciscoWanFrConnCapability MODULE-IDENTITY
        LAST-UPDATED    "200203270000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for Frame Relay
            connection mib objects.

            - The capability cwFrConnCapabilityFrsm12V3R00 is 
              for FRSM-12 module."
     
        REVISION "200203270000Z"
        DESCRIPTION
            "Initial version of this MIB Module."
        ::= { ciscoWanAgentCapability 358 }

cwFrConnCapabilityFrsm12V3R00 AGENT-CAPABILITIES
    PRODUCT-RELEASE      "MGX8850 Release 3.0.0."
    STATUS               current
    DESCRIPTION          "Frame Relay Connection 
                         Agent Capabilities for
                         Frame Relay Service Module(FRSM-12)."

-- The CISCO-WAN-AXIPOP-MIB is a SMIv1 MIB. This mib
-- contains the Frame Relay Connection Related MIB objects.
--
-- The AGENT CAPABILITIES related clauses are within comments.
--  However this mib can be used as a reference
--  for limitations in supporting objects in CISCO MGX8850 Products.

-- To Make it more readable, the OBJECT-GROUP for the objects 
-- applicable for Frame Relay Connections are defined here in comments.
--
--
-- ciscoWanFrConnGroup OBJECT-GROUP
--    OBJECTS {
--	   	chanNum,			
--		chanRowStatus ,         	 
--		chanPortNum    ,          
--		dLCI		,        
--		egressQSelect	 ,     	
--		ingressQDepth	  ,    	
--		ingressQDEThresh   ,	
--		ingressQECNThresh	,
--		egressQDepth	      	,
--		egressQDEThresh,	   	
--		egressQECNThresh	,
--       	deTaggingEnable     	,
--      	cir                 	,
--       	bc                  	,
--      	be                  	,
--        	ibs                 	,
--        	foreSightEnable     	,
--        	qir                 	,
--        	mir                 	,
--        	pir                 	,
--        	chanLocRmtLpbkState	,
--        	chanTestType            ,
--        	chanTestState           ,
--        	chanRTDResult           ,
--		chanType	,
--		chanFECNconfig	,
--		chanDEtoCLPmap	,
--		chanCLPtoDEmap	,
--		chanIngrPercentUtil,	
--		chanEgrPercentUtil  ,
--		chanEgrSrvRate      ,
--		chanOvrSubOvrRide   ,
--		chanFrConnType	,
--		frCDRNumber	,
--		frLocalVpi		,
--		frLocalVci		,
--		frLocalNSAP		,
--		frRemoteVpi		,
--		frRemoteVci		,
--		frRemoteNSAP	,
--		frMastership		,
--		frVpcFlag		,
--		frConnServiceType	,
--		frRoutingPriority	,
--		frMaxCost		,
--		frRestrictTrunkType 	,
--		frConnPCR		,
--		frConnRemotePCR		,
--		frConnMCR		,
--		frConnRemoteMCR		,
--		frConnPercentUtil	,
--		frConnRemotePercentUtil	,
--		frConnForeSightEnable	,
--		frConnFGCRAEnable	,
--		chanServType    ,
--		chanServiceRateOverride	,
--		chanServiceRate			,	
--		zeroCirConEir				,
--		chanReroute           ,
--		frConnSCR             ,
--		frConnRemoteSCR       ,
--		frConnTemplateId      ,
--		frConnAdminStatus     ,
--		frChanCnfChangeCount   , 
--		frChanCnfIgnoreIncomingDE,  
--		frChanOamCCEnable     ,
--		frChanStatsEnable ,    
--		frChanLocalLpbkEnable, 
--		frChanUpcEnable       ,
--		frChanSlaveType      ,
--		frConnRemoteMBS,
--              chanNumNextAvailable 
--   }
--  STATUS current
--    DESCRIPTION 
--       "For Frsm Channel group."

-- ciscoWanFrConnStateGroup OBJECT-GROUP
--     OBJECTS {
--        stateChanNum,
--         chanState,
--         xmtAbitState,
-- 	rcvAbitState,
-- 	xmtATMState,
-- 	rcvATMState,
-- 	chanStatusBitMap
--     }
--      STATUS current
--     DESCRIPTION 
--         "For Frsm Channel state group."
--     ::= { ciscoWanFrConnMIBGroups 2 }

-- ciscoWanFrConnEndptGroup OBJECT-GROUP
--     OBJECTS {
--         endPortNum,
-- 	endDLCI,
-- 	endChanNum,
-- 	endLineNum
--      }
--     STATUS current
--     DESCRIPTION 
--         "For Frsm Channel state group."
--
-- ciscoWanFrConnStdAbrGroup OBJECT-GROUP
--    OBJECTS {
--        frstdABRcnfChanNum,
--        frstdABRTBE,
--        frstdABRFRTT,
--        frstdABRRDF,
--        frstdABRRIF,
--        frstdABRNrm,
--        frstdABRTrm,
--        frstdABRCDF,
--        frstdABRADTF,
--        frstdABRICR,
--        frstdABRMCR,
--        frstdABRPCR         
--      }
--     STATUS current
--     DESCRIPTION 
--         "For Frsm Channel Standard ABR Group."
--
-- ciscoWanFrConnCntGroup OBJECT-GROUP
--    OBJECTS {
--        cntChanNum 	
--        rcvFrames		
--        rcvBytes	
--        rcvFramesDE		
--        rcvBytesDE		
--        rcvFramesDiscard	
--        rcvBytesDiscard	
--        rcvFramesDiscShelfAlarm	
--        rcvFramesDiscXceedQDepth
--        rcvBytesDiscXceedQDepth
--        rcvFramesDiscXceedDEThresh
--        rcvFramesFECN
--        rcvFramesBECN
--        rcvFramesTaggedFECN
--        rcvFramesTaggedBECN
--        rcvFramesTaggedDE
--        rcvBytesTaggedDE
--        rcvKbpsAIR
--        xmtFrames		
--        xmtBytes	
--        xmtFramesFECN
--        xmtFramesBECN
--        xmtFramesDE		
--        xmtBytesDE		
--        xmtFramesDiscard	
--        xmtBytesDiscard	
--        xmtFramesDiscXceedQDepth
--        xmtBytesDiscXceedQDepth
--        xmtFramesDiscXceedDEThresh
--        xmtFramesDiscPhyLayerFail
--        xmtFramesDiscCRCError
--        xmtFramesDiscReassmFail
--        xmtFramesDiscSrcAbort
--        xmtFramesDuringLMIAlarm
--        xmtBytesDuringLMIAlarm
--        xmtFramesTaggedFECN
--        xmtFramesTaggedBECN
--        xmtKbpsAIR
--        chanClrButton
--        chanSecUpTime
--        rcvFramesDiscUPC
--        xmtBytesTaggedDE
--        xmtFramesTaggedDE
--        xmtFramesInvalidCPIs
--        xmtFramesLengthViolations
--        xmtFramesOversizedSDUs
--        xmtFramesUnknownProtocols
--        rcvFramesUnknownProtocols
--      }
--     STATUS current
--     DESCRIPTION
--         "For Frsm Channel Statistics Group."
--
-- ciscoWanFrConnStdAbrCntGroup OBJECT-GROUP
--    OBJECTS {
--        frstdABRcntChanNum
--        frChanFrmXmtToNetworkCnt
--        frChanBrmXmtToNetworkCnt
--        frChanCrcErrRmRcvFromNetworkCnt
--        frChanFrmRcvFromNetworkCnt
--        frChanBrmRcvFromNetworkCnt
--        frChanFrmNotTurnedAroundCnt
--      }
--     STATUS current
--     DESCRIPTION
--         "For Frsm Channel Standard ABR Statistics Group."
--
-- NOTE: FRSM-12 Does not support following groups:
--   ciscoWanFrConnStdAbrCntGroup
--

    SUPPORTS   CISCO-WAN-AXIPOP-MIB 
    INCLUDES   { ciscoWanFrConnGroup, 
                 ciscoWanFrConnEndptGroup,
                 ciscoWanFrConnStateGroup,
                 ciscoWanFrConnStdAbrGroup,
                 ciscoWanFrConnCntGroup
               }

    VARIATION     ingressQDepth
    ACCESS        not-implemented
    DESCRIPTION
        "Not supported."

    VARIATION     ingressQECNThresh
    ACCESS        not-implemented
    DESCRIPTION
        "Not supported."

    VARIATION     ingressQDEThresh
    ACCESS        not-implemented
    DESCRIPTION
        "Not supported."

    VARIATION     egressQDepth
    ACCESS        not-implemented
    DESCRIPTION
        "Not supported."

    VARIATION     egressQDepth
    ACCESS        not-implemented
    DESCRIPTION
        "Not supported."

    VARIATION     egressQDEThresh
    ACCESS        not-implemented
    DESCRIPTION
        "Not supported."

    VARIATION     egressQECNThresh
    ACCESS        not-implemented
    DESCRIPTION
        "Not supported."

    VARIATION     cir
    SYNTAX INTEGER(0..44736000)
    DESCRIPTION
        "Restricted range is supported."

    VARIATION     ibs
    ACCESS        not-implemented
    DESCRIPTION
        "Not supported."

    VARIATION     foreSightEnable
    ACCESS        not-implemented
    DESCRIPTION
        "Not supported."

    VARIATION     qir
    ACCESS        not-implemented
    DESCRIPTION
        "Not supported."

    VARIATION     mir
    ACCESS        not-implemented
    DESCRIPTION
        "Not supported."

    VARIATION     pir
    ACCESS        not-implemented
    DESCRIPTION
        "Not supported."

    VARIATION     chanLocRmtLpbkState
    ACCESS        not-implemented
    DESCRIPTION
        "Not supported."

    VARIATION     chanType
    SYNTAX        INTEGER { frNIW(1), frSIW-transparent(2),
        frSIW-translate(3), frForward(5), frNIWReplace(6) }
    DESCRIPTION
        "Does not support  frFUNI(4)."

    VARIATION     chanEgrSrvRate
    SYNTAX        INTEGER(2400..44736000)
    DESCRIPTION
        "Supported with Restricted range."

    VARIATION     chanOvrSubOvrRide
    ACCESS        not-implemented
    DESCRIPTION
        "Not supported."
   
    VARIATION     chanFrConnType
    ACCESS        not-implemented
    DESCRIPTION
        "Not supported."
   
    VARIATION     frCDRNumber
    ACCESS        not-implemented
    DESCRIPTION
        "Not supported."
   
    VARIATION     frVpcFlag
    SYNTAX        INTEGER { vcc(2) }
    DESCRIPTION
        "Does not support vpc(1). Always set to vcc(2)."
   
    VARIATION     frConnServiceType
    ACCESS        read-only
    DESCRIPTION
        "Derived from chanServType"
   
    VARIATION     frMaxCost
    DEFVAL        { 2147483647 }
    DESCRIPTION
        ""
   
    VARIATION     frRestrictTrunkType
    ACCESS        not-implemented
    DESCRIPTION
        "Not supported."
   
    VARIATION     frConnPercentUtil
    ACCESS        not-implemented
    DESCRIPTION
        "Not supported."
   
    VARIATION     frConnRemotePercentUtil
    ACCESS        not-implemented
    DESCRIPTION
        "Not supported."
   
    VARIATION     frConnForeSightEnable
    ACCESS        not-implemented
    DESCRIPTION
        "Not supported."
   
    VARIATION     frConnFGCRAEnable
    ACCESS        not-implemented
    DESCRIPTION
        "Not supported."
   
    VARIATION     chanServType
    SYNTAX INTEGER{
		highpriority(1),
		rtVBR(2),
		nrtVBR(3),
		uBR(5),
		stdABR(9)
           }
    DESCRIPTION
        "Does not support aBR(4), queue6(6),queue(7),queue(8)."
   
    VARIATION     chanServiceRateOverride
    ACCESS        not-implemented
    DESCRIPTION
        "Not supported."
   
    VARIATION     chanServiceRate
    ACCESS        not-implemented
    DESCRIPTION
        "Not supported."
   
    VARIATION     frConnTemplateId
    ACCESS        not-implemented
    DESCRIPTION
        "Not supported."
   
    VARIATION     chanNumNextAvailable
    ACCESS        not-implemented
    DESCRIPTION
        "Not supported."

    VARIATION     xmtATMState
    SYNTAX        INTEGER { notSending(1), sendingAIS(2) }
    DESCRIPTION
        "Does not support sendingFERF(3)." 

    VARIATION     rcvATMState
    SYNTAX        INTEGER { notRcving(1), rcvingAIS(2) }
    DESCRIPTION
        "Does not support rcvingFERF(3)." 

    VARIATION     rcvFramesDiscShelfAlarm
    ACCESS        not-implemented
    DESCRIPTION
        "Not supported."
   
    VARIATION     xmtBytesDiscard
    ACCESS        not-implemented
    DESCRIPTION
        "Not supported."
   
    VARIATION     xmtFramesDiscXceedQDepth
    ACCESS        not-implemented
    DESCRIPTION
        "Not supported."
   
    VARIATION     xmtBytesDiscXceedQDepth
    ACCESS        not-implemented
    DESCRIPTION
        "Not supported."
   
    VARIATION     xmtFramesDiscXceedDEThresh
    ACCESS        not-implemented
    DESCRIPTION
        "Not supported."
   
    VARIATION     xmtFramesDiscReassmFail
    ACCESS        not-implemented
    DESCRIPTION
        "Not supported."
   
   ::= { ciscoWanFrConnCapability 1 }
END
