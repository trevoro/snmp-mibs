PDN-MPE-BRIDGE-MIB DEFINITIONS ::= BEGIN

-- Version :  0.1 DRAFT
-- Enterprise pdn bridge mib (mpe support)
-- Copyright (C) 2000 Paradyne Corporation.

-- Created by : Wayne Jadoo / Prakash Easwar

-- This MIB contains objects that is used to perform  
-- operations on the bridge.

IMPORTS

MacAddress
FROM SNMPv2-TC
Counter
FROM RFC1155-SMI
ifIndex
FROM RFC1213-MIB
OBJECT-TYPE
FROM RFC-1212
entPhysicalIndex
FROM ENTITY-MIB
mpe-bridge
FROM PDN-HEADER-MIB
VnidRange
FROM PDN-TC
;

mpePdnBridgeGenericMIBObjects OBJECT IDENTIFIER ::= { mpe-bridge 1 }
mpePdnBridgeMIBTraps OBJECT IDENTIFIER ::= { mpe-bridge 2 }
mpePdnDot1dGenericBridge OBJECT IDENTIFIER ::= { mpePdnBridgeGenericMIBObjects 1 }
mpePdnDot1dTpFdb      OBJECT IDENTIFIER ::= { mpePdnBridgeGenericMIBObjects  2 }

          mpePdnDot1dBridgeTable OBJECT-TYPE
              SYNTAX  SEQUENCE OF MpePdnDot1dBridgeEntry
              ACCESS  not-accessible
              STATUS  mandatory
              DESCRIPTION
                "A table that contains generic information about the bridge."
              ::= { mpePdnDot1dGenericBridge 1 }

          mpePdnDot1dBridgeEntry OBJECT-TYPE
              SYNTAX  MpePdnDot1dBridgeEntry
              ACCESS  not-accessible
              STATUS  mandatory
              DESCRIPTION
                      "A list of information for the bridge."
              INDEX  { entPhysicalIndex }
              ::= { mpePdnDot1dBridgeTable 1 }


          MpePdnDot1dBridgeEntry ::=
              SEQUENCE {
               mpePdnDot1dBaseBridgeAddress                MacAddress,
               mpePdnDot1dBaseNumPorts                     INTEGER,
               mpePdnDot1dBaseType                         INTEGER,
               mpePdnDot1dTpLearnedEntryDiscards           Counter,
               mpePdnDot1dTpAgeingTime                      INTEGER,
               mpePdnDot1dTpAgeingCleanupTime              INTEGER
              }

          mpePdnDot1dBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be
             unique."
              ::= { mpePdnDot1dBridgeEntry  1 }

          mpePdnDot1dBaseNumPorts OBJECT-TYPE
              SYNTAX  INTEGER
              ACCESS  read-only
              STATUS  mandatory
              DESCRIPTION
                      "The number of ports controlled by this bridging
              entity."
              ::= { mpePdnDot1dBridgeEntry 2 }

          mpePdnDot1dBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
            perform."
              ::= { mpePdnDot1dBridgeEntry 3 }

          mpePdnDot1dTpLearnedEntryDiscards OBJECT-TYPE
              SYNTAX  Counter
              ACCESS  read-only
              STATUS  mandatory
              DESCRIPTION
                      "The total number of Forwarding Database entries,
                      which have been or would have been learned, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              ::= { mpePdnDot1dBridgeEntry 4 }

          mpePdnDot1dTpAgeingTime OBJECT-TYPE
              SYNTAX   INTEGER (10..1000000)
              ACCESS   read-write
              STATUS   mandatory
              DESCRIPTION
                      "The timeout period in seconds for aging out
                      dynamically learned forwarding information.
                      802.1D-1990 recommends a default of 300 seconds."
              DEFVAL { 300 }
              ::= { mpePdnDot1dBridgeEntry 5 }
        
          mpePdnDot1dTpAgeingCleanupTime OBJECT-TYPE
              SYNTAX   INTEGER (5..500000)
              ACCESS   read-write
              STATUS   mandatory
              DESCRIPTION
                      " mpePdnDot1dTpEntryAgeingCleanupupTime is the length of 
                        time before an entry is removed from the bridge . 
                        This parameter is typically set to one-half of the 
                        bridge Ageing time."
              DEFVAL { 150 }
              ::= { mpePdnDot1dBridgeEntry 6 }
        


          --  The Forwarding Database for Transparent Bridges

          mpePdnDot1dTpFdbTable OBJECT-TYPE
              SYNTAX  SEQUENCE OF MpePdnDot1dTpFdbEntry
              ACCESS  not-accessible
              STATUS  mandatory
              DESCRIPTION
                      "A table that contains information about unicast
                      entries for which the bridge has forwarding and/or
                      filtering information.  This information is used
                      by the transparent bridging function in
                      determining how to propagate a received frame."
              ::= { mpePdnDot1dTpFdb 1 }

          mpePdnDot1dTpFdbEntry OBJECT-TYPE
              SYNTAX  MpePdnDot1dTpFdbEntry
              ACCESS  not-accessible
              STATUS  mandatory
              DESCRIPTION
                      "Information about a specific unicast MAC address
                      for which the bridge has some forwarding and/or
                      filtering information."
              INDEX   { entPhysicalIndex, 
                        mpePdnDot1dTpFdbAddress, 
                        mpePdnDot1dTpFdbVnidId }
              ::= { mpePdnDot1dTpFdbTable 1 }

          MpePdnDot1dTpFdbEntry ::=
              SEQUENCE {
                  mpePdnDot1dTpFdbAddress     MacAddress,
                  mpePdnDot1dTpFdbVnidId      VnidRange,
                  mpePdnDot1dTpFdbIfIndex     INTEGER,
                  mpePdnDot1dTpFdbStatus      INTEGER,
                  mpePdnDot1dTpFdbAgeTime     INTEGER,
                  mpePdnDot1dTpFdbFlags       INTEGER
               }

          mpePdnDot1dTpFdbAddress OBJECT-TYPE
              SYNTAX  MacAddress
              ACCESS  read-only
              STATUS  mandatory
              DESCRIPTION
                      "A unicast MAC address for which the bridge has
                       forwarding and/or filtering information."
              ::= { mpePdnDot1dTpFdbEntry 1 }

          mpePdnDot1dTpFdbVnidId OBJECT-TYPE
              SYNTAX  VnidRange
              ACCESS  read-only
              STATUS  mandatory
              DESCRIPTION
                 "The VNID Id number of the virtual network for which the
                  bridge has forwarding and/or filtering information."
              ::= { mpePdnDot1dTpFdbEntry 2 }
          
			 mpePdnDot1dTpFdbIfIndex OBJECT-TYPE
              SYNTAX  INTEGER
              ACCESS  read-only
              STATUS  mandatory
              DESCRIPTION
                 "The ifIndex of the interface associated with the 
						mac address and vlan-id."
              ::= { mpePdnDot1dTpFdbEntry 3 }

          mpePdnDot1dTpFdbStatus OBJECT-TYPE
              SYNTAX  INTEGER {
                          other(1),
                          invalid(2),
                          learned(3),
                          self(4),
                          mgmt(5)
                      }
              ACCESS  read-only
              STATUS  mandatory
              DESCRIPTION
                  "The status of this entry.  The meanings of the
                  values are:

                    other(1)   : none of the following.  This would
                                 include the case where some other
                                 MIB object (not the corresponding
                                 instance of mpePdnDot1dTpFdbPort, nor 
                                 an entry in the mpePdnDot1dStaticTable)
                                 in being used to determine if and how
                                 frames addressed to the value of
                                 the corresponding instance of
                                 mpePdnDot1dTpFdbAddress are being
                                 forwarded.

                    invalid(2) : this entry is not longer valid
                                 (e.g., it was learned but has since

                                 aged-out), but has not yet been
                                 flushed from the table.

                    learned(3) : the value of the corresponding
                                 instance of mpePdnDot1dTpFdbPort was
                                 learned, and is being used.

                    self(4)    : the value of the corresponding
                                 instance of mpePdnDot1dTpFdbAddress
                                 represents one of the bridge's
                                 addresses.  The corresponding
                                 instance of mpePdnDot1dTpFdbPort
                                 indicates which of the bridge's
                                 ports has this address.

                    mgmt(5)    : the value of the corresponding
                                 instance of mpePdnDot1dTpFdbAddress is

                                 also the value of an existing
                                 instance of mpePdnDot1dStaticAddress."
              ::= { mpePdnDot1dTpFdbEntry 4 }

          mpePdnDot1dTpFdbAgeTime OBJECT-TYPE
              SYNTAX  INTEGER
              ACCESS  read-only
              STATUS  mandatory
              DESCRIPTION
                      "The amount of time in seconds that 
                       this entry is in the Bridge table"
              ::= { mpePdnDot1dTpFdbEntry 5 }

          mpePdnDot1dTpFdbFlags OBJECT-TYPE
              SYNTAX  INTEGER {
                          other(1),
                          permanentDHCP(2),
                          permanentCONFIGURED(3),
                          dynamic(4)
                      }
              ACCESS  read-only
              STATUS  mandatory
              DESCRIPTION
                "This object indicates the type of
                 entry in the Bridge table.
                 permanentDHCP       -- Entry added due to DHCP client
                 permanentCONFIGURED -- Entry added by User 
                 dynamic             -- Dynamic Entry
                "
              ::= { mpePdnDot1dTpFdbEntry 6 }

          END
