Nortel-Magellan-Passport-FileSystemMIB
DEFINITIONS ::= BEGIN



IMPORTS

      OBJECT-TYPE
   FROM RFC-1212

      components,
      passportMIBs
   FROM Nortel-Magellan-Passport-UsefulDefinitionsMIB

      RowPointer,
      DisplayString,
      StorageType,
      RowStatus,
      Gauge32,
      Integer32,
      Unsigned32
   FROM Nortel-Magellan-Passport-StandardTextualConventionsMIB

      AsciiString,
      NonReplicated
   FROM Nortel-Magellan-Passport-TextualConventionsMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FileSystem Enterprise MIB."

fileSystemMIB OBJECT IDENTIFIER ::= { passportMIBs 16 }










-- FILESYSTEM
-- The Filesystem component provides and controls access to files and 
-- directories stored on one or two disks. It is automatically created 
-- and always present.
-- 
-- The Filesystem restricts files and directories names to 40 characters. 
-- It also restricts filenames including path to 128 characters. 
-- Directory names including the path cannot exceed 125 characters. 
-- There must be 112 or less directories and files at the root level. The 
-- maximum hierarchy depth is 10 directory levels. 
-- The only characters that can appear in a filename are the alpha-
-- numeric characters, the . (dot) and the _ (underscore). The names 
-- are case sensitive. A pathname is a sequence of zero to ten directory 
-- names along the path and separated by the / (slash) character. A 
-- pathname that begins with a slash is an absolute pathname, 
-- otherwise it is a relative pathname. Access to the standby disk is not 
-- allowed. 
-- 
-- When there are two disks, the standby control processor disk is 
-- normally synchronized with the disk of the active control processor. 
-- After a crash or a disk failure the standby control processor disk 
-- becomes unsynchronized with respect to the disk on the active CP. 
-- 

fs OBJECT IDENTIFIER ::= { components 15 }



fsRowStatusTable OBJECT-TYPE
   SYNTAX     SEQUENCE OF FsRowStatusEntry
   ACCESS     not-accessible
   STATUS     mandatory
   DESCRIPTION
     "This entry controls the addition and deletion of 
      fs components."
::= { fs 1 }

fsRowStatusEntry OBJECT-TYPE
   SYNTAX     FsRowStatusEntry
   ACCESS     not-accessible
   STATUS     mandatory
   DESCRIPTION
     "A single entry in the table represents a single 
      fs component."
   INDEX {
      fsIndex }
::= { fsRowStatusTable 1 }

FsRowStatusEntry ::= SEQUENCE {
   fsRowStatus
      RowStatus,
   fsComponentName
      DisplayString,
   fsStorageType
      StorageType,
   fsIndex
      NonReplicated }

fsRowStatus OBJECT-TYPE
   SYNTAX     RowStatus 
   ACCESS     read-only
   STATUS     mandatory
   DESCRIPTION
     "This variable is used as the basis for SNMP naming of
      fs components.
      These components cannot be added nor deleted."
::= { fsRowStatusEntry 1 }

fsComponentName OBJECT-TYPE
   SYNTAX     DisplayString 
   ACCESS     read-only
   STATUS     mandatory
   DESCRIPTION
     "This variable provides the component's string name for
      use with the ASCII Console Interface"
::= { fsRowStatusEntry 2 }

fsStorageType OBJECT-TYPE
   SYNTAX     StorageType 
   ACCESS     read-only
   STATUS     mandatory
   DESCRIPTION
     "This variable represents the storage type value for the
      fs tables."
::= { fsRowStatusEntry 4 }

fsIndex OBJECT-TYPE
   SYNTAX     NonReplicated 
   ACCESS     not-accessible
   STATUS     mandatory
   DESCRIPTION
     "This variable represents the index for the fs tables."
::= { fsRowStatusEntry 10 }

fsStateTable OBJECT-TYPE
   SYNTAX     SEQUENCE OF FsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { fs 10 }

fsStateEntry OBJECT-TYPE
   SYNTAX     FsStateEntry
   ACCESS     not-accessible
   STATUS     mandatory
   DESCRIPTION
     "An entry in the fsStateTable."
   INDEX {
      fsIndex }
::= { fsStateTable 1 }

FsStateEntry ::= SEQUENCE {
   fsAdminState
      INTEGER,
   fsOperationalState
      INTEGER,
   fsUsageState
      INTEGER }

fsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { fsStateEntry 1 }

fsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { fsStateEntry 2 }

fsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { fsStateEntry 3 }

fsOperTable OBJECT-TYPE
   SYNTAX     SEQUENCE OF FsOperEntry
   ACCESS     not-accessible
   STATUS     mandatory
   DESCRIPTION
     "This group contains the filesystem operational data."
::= { fs 11 }

fsOperEntry OBJECT-TYPE
   SYNTAX     FsOperEntry
   ACCESS     not-accessible
   STATUS     mandatory
   DESCRIPTION
     "An entry in the fsOperTable."
   INDEX {
      fsIndex }
::= { fsOperTable 1 }

FsOperEntry ::= SEQUENCE {
   fsVolumeName
      AsciiString,
   fsActiveDisk
      RowPointer,
   fsSyncStatus
      INTEGER,
   fsSyncProgress
      Gauge32,
   fsCapacity
      Unsigned32,
   fsFreeSpace
      Unsigned32,
   fsUsage
      Gauge32 }

fsVolumeName OBJECT-TYPE
   SYNTAX     AsciiString (SIZE (1..11))
   ACCESS     read-only
   STATUS     mandatory
   DESCRIPTION
     "This attribute describes the volume name of the filesystem. This is 
      the active disk volume name."
::= { fsOperEntry 1 }

fsActiveDisk OBJECT-TYPE
   SYNTAX     RowPointer 
   ACCESS     read-only
   STATUS     mandatory
   DESCRIPTION
     "The activeDisk attribute value is the Disk component instance value 
      of the active disk. This is also the card number of the active control 
      processor."
::= { fsOperEntry 2 }

fsSyncStatus OBJECT-TYPE
   SYNTAX     INTEGER  {
                 synchronized(0),
                 unSynchronized(1),
                 synchronizing(2) }
   ACCESS     read-only
   STATUS     mandatory
   DESCRIPTION
     "The synchronization status value indicates whether the file system is 
      synchronized or not."
::= { fsOperEntry 3 }

fsSyncProgress OBJECT-TYPE
   SYNTAX     Gauge32 (0..100)
   ACCESS     read-only
   STATUS     mandatory
   DESCRIPTION
     "The synchronization progress value indicates the percentage of the 
      standby disk already synchronized with the active disk. This value 
      is equal to 100 if the two disks are synchronized or 0 if they are out 
      of synchronization."
::= { fsOperEntry 4 }

fsCapacity OBJECT-TYPE
   SYNTAX     Unsigned32 (0..4294967295)
   ACCESS     read-only
   STATUS     mandatory
   DESCRIPTION
     "The Capacity attribute value is the total size of the filesystem (in 
      bytes). This value is equal to the smallest disk size in a 
      synchronized filesystem, otherwise it is the capacity of the active 
      disk."
::= { fsOperEntry 5 }

fsFreeSpace OBJECT-TYPE
   SYNTAX     Unsigned32 (0..4294967295)
   ACCESS     read-only
   STATUS     mandatory
   DESCRIPTION
     "This attribute describes the free disk space (in bytes) currently 
      available in the filesystem. It is equal to the smallest free disk space 
      size of the active and standby disks in a synchronized filesystem. 
      When the filesystem is unsynchronized it is the free disk space of 
      the active disk."
::= { fsOperEntry 6 }

fsUsage OBJECT-TYPE
   SYNTAX     Gauge32 (0..100)
   ACCESS     read-only
   STATUS     mandatory
   DESCRIPTION
     "This attribute describes the percentage of the free space available on 
      the filesystem."
::= { fsOperEntry 7 }

-- 
-- *** THIS SUBTREE CURRENTLY NOT IMPLEMENTED ***
-- 

-- 
-- A disk component is an operational subcomponent of the 
-- filesystem. When the system is in dual-mode configuration, there 
-- will be two instances of the disk component. The 0 instance 
-- represents the disk on the card 0 and the instance 15 represents the 
-- disk on the card 15. 

fsDisk OBJECT IDENTIFIER ::= { fs 2 }



fsDiskRowStatusTable OBJECT-TYPE
   SYNTAX     SEQUENCE OF FsDiskRowStatusEntry
   ACCESS     not-accessible
   STATUS     mandatory
   DESCRIPTION
     "*** THIS TABLE CURRENTLY NOT IMPLEMENTED ***

      This entry controls the addition and deletion of 
      fsDisk components."
::= { fsDisk 1 }

fsDiskRowStatusEntry OBJECT-TYPE
   SYNTAX     FsDiskRowStatusEntry
   ACCESS     not-accessible
   STATUS     mandatory
   DESCRIPTION
     "A single entry in the table represents a single 
      fsDisk component."
   INDEX {
      fsIndex,
      fsDiskIndex }
::= { fsDiskRowStatusTable 1 }

FsDiskRowStatusEntry ::= SEQUENCE {
   fsDiskRowStatus
      RowStatus,
   fsDiskComponentName
      DisplayString,
   fsDiskStorageType
      StorageType,
   fsDiskIndex
      Integer32 }

fsDiskRowStatus OBJECT-TYPE
   SYNTAX     RowStatus 
   ACCESS     read-only
   STATUS     mandatory
   DESCRIPTION
     "This variable is used as the basis for SNMP naming of
      fsDisk components.
      These components cannot be added nor deleted."
::= { fsDiskRowStatusEntry 1 }

fsDiskComponentName OBJECT-TYPE
   SYNTAX     DisplayString 
   ACCESS     read-only
   STATUS     mandatory
   DESCRIPTION
     "This variable provides the component's string name for
      use with the ASCII Console Interface"
::= { fsDiskRowStatusEntry 2 }

fsDiskStorageType OBJECT-TYPE
   SYNTAX     StorageType 
   ACCESS     read-only
   STATUS     mandatory
   DESCRIPTION
     "This variable represents the storage type value for the
      fsDisk tables."
::= { fsDiskRowStatusEntry 4 }

fsDiskIndex OBJECT-TYPE
   SYNTAX     Integer32 (0..15)
   ACCESS     not-accessible
   STATUS     mandatory
   DESCRIPTION
     "This variable represents the index for the fsDisk tables."
::= { fsDiskRowStatusEntry 10 }

fsDiskStateTable OBJECT-TYPE
   SYNTAX     SEQUENCE OF FsDiskStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { fsDisk 10 }

fsDiskStateEntry OBJECT-TYPE
   SYNTAX     FsDiskStateEntry
   ACCESS     not-accessible
   STATUS     mandatory
   DESCRIPTION
     "An entry in the fsDiskStateTable."
   INDEX {
      fsIndex,
      fsDiskIndex }
::= { fsDiskStateTable 1 }

FsDiskStateEntry ::= SEQUENCE {
   fsDiskAdminState
      INTEGER,
   fsDiskOperationalState
      INTEGER,
   fsDiskUsageState
      INTEGER }

fsDiskAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { fsDiskStateEntry 1 }

fsDiskOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { fsDiskStateEntry 2 }

fsDiskUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { fsDiskStateEntry 3 }

fsDiskOperTable OBJECT-TYPE
   SYNTAX     SEQUENCE OF FsDiskOperEntry
   ACCESS     not-accessible
   STATUS     mandatory
   DESCRIPTION
     "*** THIS TABLE CURRENTLY NOT IMPLEMENTED ***

      This group contains the disk component operational data."
::= { fsDisk 11 }

fsDiskOperEntry OBJECT-TYPE
   SYNTAX     FsDiskOperEntry
   ACCESS     not-accessible
   STATUS     mandatory
   DESCRIPTION
     "An entry in the fsDiskOperTable."
   INDEX {
      fsIndex,
      fsDiskIndex }
::= { fsDiskOperTable 1 }

FsDiskOperEntry ::= SEQUENCE {
   fsDiskVolumeName
      AsciiString,
   fsDiskCapacity
      Unsigned32,
   fsDiskFreeSpace
      Unsigned32,
   fsDiskBadBlocksPercentage
      Gauge32,
   fsDiskUnformattedCapacity
      Unsigned32 }

fsDiskVolumeName OBJECT-TYPE
   SYNTAX     AsciiString (SIZE (1..11))
   ACCESS     read-write
   STATUS     mandatory
   DESCRIPTION
     "This attribute describes the volume name of the disk. The volume 
      names of the two disks must be identical to be synchronized."
::= { fsDiskOperEntry 1 }

fsDiskCapacity OBJECT-TYPE
   SYNTAX     Unsigned32 (0..4294967295)
   ACCESS     read-only
   STATUS     mandatory
   DESCRIPTION
     "This attribute describes the total formatted disk size (in bytes) of the 
      disk."
::= { fsDiskOperEntry 2 }

fsDiskFreeSpace OBJECT-TYPE
   SYNTAX     Unsigned32 (0..4294967295)
   ACCESS     read-only
   STATUS     mandatory
   DESCRIPTION
     "freeSpace
      This attribute indicates the available free disk space(in bytes) on the 
      disk. Free space is reduced by bad blocks (if any). If there are 
      different numbers of bad blocks on the disks in a dual-disk system, 
      the reported free space will differ on the two disks.
      
      Moreover, due to the DOS file system internal representation of 
      directories and files, adding and deleting files may fragment the 
      disks differently resulting in some disk space wasted. A small 
      discrepancy (less than 1% of the disk size) in the disks free space is 
      considered as normal."
::= { fsDiskOperEntry 3 }

fsDiskBadBlocksPercentage OBJECT-TYPE
   SYNTAX     Gauge32 (0..100)
   ACCESS     read-only
   STATUS     mandatory
   DESCRIPTION
     "This attribute records the percentage of the disk space lost because 
      of defects. If this percentage is high, it is recommended to change 
      the disk."
::= { fsDiskOperEntry 4 }

fsDiskUnformattedCapacity OBJECT-TYPE
   SYNTAX     Unsigned32 (0..4294967295)
   ACCESS     read-only
   STATUS     mandatory
   DESCRIPTION
     "unformattedCapacity 
      This attribute indicates the physical disk size (in bytes). The 
      physical disk size may be different from the formatted disk size if 
      there are bad blocks or the disk has been formatted to a smaller disk 
      size for backward compatibility with older releases."
::= { fsDiskOperEntry 5 }

-- 
-- *** THIS SUBTREE CURRENTLY NOT IMPLEMENTED ***
-- 

-- Test
-- The Test component embodies logical and physical filesystem tests. 
-- It is an operational subcomponent of the Disk component. 

fsDiskTest OBJECT IDENTIFIER ::= { fsDisk 2 }



fsDiskTestRowStatusTable OBJECT-TYPE
   SYNTAX     SEQUENCE OF FsDiskTestRowStatusEntry
   ACCESS     not-accessible
   STATUS     mandatory
   DESCRIPTION
     "*** THIS TABLE CURRENTLY NOT IMPLEMENTED ***

      This entry controls the addition and deletion of 
      fsDiskTest components."
::= { fsDiskTest 1 }

fsDiskTestRowStatusEntry OBJECT-TYPE
   SYNTAX     FsDiskTestRowStatusEntry
   ACCESS     not-accessible
   STATUS     mandatory
   DESCRIPTION
     "A single entry in the table represents a single 
      fsDiskTest component."
   INDEX {
      fsIndex,
      fsDiskIndex,
      fsDiskTestIndex }
::= { fsDiskTestRowStatusTable 1 }

FsDiskTestRowStatusEntry ::= SEQUENCE {
   fsDiskTestRowStatus
      RowStatus,
   fsDiskTestComponentName
      DisplayString,
   fsDiskTestStorageType
      StorageType,
   fsDiskTestIndex
      NonReplicated }

fsDiskTestRowStatus OBJECT-TYPE
   SYNTAX     RowStatus 
   ACCESS     read-only
   STATUS     mandatory
   DESCRIPTION
     "This variable is used as the basis for SNMP naming of
      fsDiskTest components.
      These components cannot be added nor deleted."
::= { fsDiskTestRowStatusEntry 1 }

fsDiskTestComponentName OBJECT-TYPE
   SYNTAX     DisplayString 
   ACCESS     read-only
   STATUS     mandatory
   DESCRIPTION
     "This variable provides the component's string name for
      use with the ASCII Console Interface"
::= { fsDiskTestRowStatusEntry 2 }

fsDiskTestStorageType OBJECT-TYPE
   SYNTAX     StorageType 
   ACCESS     read-only
   STATUS     mandatory
   DESCRIPTION
     "This variable represents the storage type value for the
      fsDiskTest tables."
::= { fsDiskTestRowStatusEntry 4 }

fsDiskTestIndex OBJECT-TYPE
   SYNTAX     NonReplicated 
   ACCESS     not-accessible
   STATUS     mandatory
   DESCRIPTION
     "This variable represents the index for the fsDiskTest tables."
::= { fsDiskTestRowStatusEntry 10 }

fsDiskTestStateTable OBJECT-TYPE
   SYNTAX     SEQUENCE OF FsDiskTestStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { fsDiskTest 10 }

fsDiskTestStateEntry OBJECT-TYPE
   SYNTAX     FsDiskTestStateEntry
   ACCESS     not-accessible
   STATUS     mandatory
   DESCRIPTION
     "An entry in the fsDiskTestStateTable."
   INDEX {
      fsIndex,
      fsDiskIndex,
      fsDiskTestIndex }
::= { fsDiskTestStateTable 1 }

FsDiskTestStateEntry ::= SEQUENCE {
   fsDiskTestAdminState
      INTEGER,
   fsDiskTestOperationalState
      INTEGER,
   fsDiskTestUsageState
      INTEGER }

fsDiskTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { fsDiskTestStateEntry 1 }

fsDiskTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { fsDiskTestStateEntry 2 }

fsDiskTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { fsDiskTestStateEntry 3 }

fsDiskTestSetupTable OBJECT-TYPE
   SYNTAX     SEQUENCE OF FsDiskTestSetupEntry
   ACCESS     not-accessible
   STATUS     mandatory
   DESCRIPTION
     "*** THIS TABLE CURRENTLY NOT IMPLEMENTED ***

      This group contains the Test component operational data. The 
      testCount, duration and type can be set to control the duration and 
      the test type which will be run."
::= { fsDiskTest 11 }

fsDiskTestSetupEntry OBJECT-TYPE
   SYNTAX     FsDiskTestSetupEntry
   ACCESS     not-accessible
   STATUS     mandatory
   DESCRIPTION
     "An entry in the fsDiskTestSetupTable."
   INDEX {
      fsIndex,
      fsDiskIndex,
      fsDiskTestIndex }
::= { fsDiskTestSetupTable 1 }

FsDiskTestSetupEntry ::= SEQUENCE {
   fsDiskTestTestCount
      Unsigned32,
   fsDiskTestDuration
      Unsigned32,
   fsDiskTestType
      INTEGER }

fsDiskTestTestCount OBJECT-TYPE
   SYNTAX     Unsigned32 (0..4294967295)
   ACCESS     read-write
   STATUS     mandatory
   DESCRIPTION
     "This attribute indicates the number of times that the test will run. 
      Note that the test will not run that many times if 'duration' is not 
      long enough to allow the test to complete. The test will execute at 
      least one and then stop at the count where duration has just 
      exceeded."
   DEFVAL     { 1 }
::= { fsDiskTestSetupEntry 1 }

fsDiskTestDuration OBJECT-TYPE
   SYNTAX     Unsigned32 (0..35791394)
   ACCESS     read-write
   STATUS     mandatory
   DESCRIPTION
     "This attribute is the maximum duration (in minutes) that the test 
      will run. The test can finish in less time if the number of tests, as 
      recorded by testCount, is reached before this time. A test may take 
      longer than the specified duration since a test cycle (or pass) is not 
      interruptible."
   DEFVAL     { 60 }
::= { fsDiskTestSetupEntry 2 }

fsDiskTestType OBJECT-TYPE
   SYNTAX     INTEGER  {
                 filesystemCheck(0),
                 diskRead(1),
                 flakyBitDetection(2),
                 surfaceAnalysis(3) }
   ACCESS     read-write
   STATUS     mandatory
   DESCRIPTION
     "This attribute is the type of the test to be run. The diskRead test 
      reads every sector on the disk once and reports bad sectors. The 
      filesystemCheck does a sanity check and attempts to repair 
      corruption. The flakyBitDetection test reads every sector on the disk 
      twice and compares the two read results. The surfaceAnalysis test 
      writes a magnetically hard to record pattern to the disk and reads 
      back the pattern to determine the condition of the magnetic surface 
      of the disk. The surface analysis test destroys all the data and disk 
      should be formatted afterward."
   DEFVAL     { filesystemCheck }
::= { fsDiskTestSetupEntry 3 }

fsDiskTestResultsTable OBJECT-TYPE
   SYNTAX     SEQUENCE OF FsDiskTestResultsEntry
   ACCESS     not-accessible
   STATUS     mandatory
   DESCRIPTION
     "*** THIS TABLE CURRENTLY NOT IMPLEMENTED ***

      This group contains the results of the test."
::= { fsDiskTest 12 }

fsDiskTestResultsEntry OBJECT-TYPE
   SYNTAX     FsDiskTestResultsEntry
   ACCESS     not-accessible
   STATUS     mandatory
   DESCRIPTION
     "An entry in the fsDiskTestResultsTable."
   INDEX {
      fsIndex,
      fsDiskIndex,
      fsDiskTestIndex }
::= { fsDiskTestResultsTable 1 }

FsDiskTestResultsEntry ::= SEQUENCE {
   fsDiskTestCauseOfTermination
      INTEGER,
   fsDiskTestNatureOfError
      INTEGER,
   fsDiskTestSeverity
      INTEGER,
   fsDiskTestElapsedTime
      Unsigned32,
   fsDiskTestTestExecutionCount
      Unsigned32 }

fsDiskTestCauseOfTermination OBJECT-TYPE
   SYNTAX     INTEGER  {
                 testCountReached(0),
                 testTimeExpired(1),
                 stoppedByOperator(2),
                 neverStarted(3),
                 testRunning(4),
                 error(5),
                 internalError(6),
                 unknown(7) }
   ACCESS     read-only
   STATUS     mandatory
   DESCRIPTION
     "This attribute records the reason why the test was terminated. The 
      reasons are:
      testCountReached: the test ran the number of times specified in the 
      attribute testCount and ended normally.
      error: the test was terminated by an error that is recorded in the 
      natureOfError attribute.
      neverStarted: the test was never started.
      stoppedByOperator: the test was terminated by the Stop command.
      testTimeExpired: the duration of the test expired.
      testRunning: the test is still running.
      unknown: the test terminated for unknown reasons.
      internalError: An internal error terminated the test."
::= { fsDiskTestResultsEntry 1 }

fsDiskTestNatureOfError OBJECT-TYPE
   SYNTAX     INTEGER  {
                 logical(0),
                 media(1),
                 noErrorDetected(2),
                 failedToComplete(3) }
   ACCESS     read-only
   STATUS     mandatory
   DESCRIPTION
     "This attribute describes the error found by a test. A logical error can 
      be fixed by a filesystemCheck test followed eventually by a 
      synchronization. A media error indicates that a fault in the disk 
      hardware is suspected. A failedToComplete error indicates that the 
      test was terminated."
::= { fsDiskTestResultsEntry 2 }

fsDiskTestSeverity OBJECT-TYPE
   SYNTAX     INTEGER  {
                 noDataLost(0),
                 dataLost(1),
                 hardwareProblem(2),
                 noError(3) }
   ACCESS     read-only
   STATUS     mandatory
   DESCRIPTION
     "This attribute describes the severity of the error found by a test. 
      There are three types of severity: no data was lost, data was lost and 
      hardware problem. If the test found no error(s), this will be reported 
      as noError. If the test found error(s) but no data was lost, then 
      noDataLost is reported."
::= { fsDiskTestResultsEntry 3 }

fsDiskTestElapsedTime OBJECT-TYPE
   SYNTAX     Unsigned32 (0..4294967295)
   ACCESS     read-only
   STATUS     mandatory
   DESCRIPTION
     "This attribute records the elapsed time (in minutes) since the test 
      was started."
::= { fsDiskTestResultsEntry 4 }

fsDiskTestTestExecutionCount OBJECT-TYPE
   SYNTAX     Unsigned32 (0..4294967295)
   ACCESS     read-only
   STATUS     mandatory
   DESCRIPTION
     "The number of times the test had actually run."
::= { fsDiskTestResultsEntry 5 }




-- 
-- Version and Compliance statements
-- 



-- Object-Group Statement:
-- A list of all current accessible leaf objects.

-- OBJECTS { fsActiveDisk,
--           fsDiskTestComponentName,
--           fsDiskTestCauseOfTermination,
--           fsDiskOperationalState,
--           fsDiskTestTestCount,
--           fsFreeSpace,
--           fsSyncStatus,
--           fsDiskTestUsageState,
--           fsOperationalState,
--           fsRowStatus,
--           fsAdminState,
--           fsDiskTestType,
--           fsDiskTestOperationalState,
--           fsCapacity,
--           fsDiskAdminState,
--           fsDiskTestAdminState,
--           fsDiskBadBlocksPercentage,
--           fsDiskTestElapsedTime,
--           fsDiskRowStatus,
--           fsDiskCapacity,
--           fsDiskTestRowStatus,
--           fsDiskTestStorageType,
--           fsUsageState,
--           fsDiskTestNatureOfError,
--           fsComponentName,
--           fsVolumeName,
--           fsDiskTestTestExecutionCount,
--           fsDiskUnformattedCapacity,
--           fsSyncProgress,
--           fsStorageType,
--           fsDiskUsageState,
--           fsDiskFreeSpace,
--           fsDiskTestSeverity,
--           fsUsage,
--           fsDiskComponentName,
--           fsDiskVolumeName,
--           fsDiskTestDuration,
--           fsDiskStorageType }
-- STATUS  mandatory
-- DESCRIPTION
--   "A list of all current accessible leaf objects."

fileSystemGroup OBJECT IDENTIFIER ::= { fileSystemMIB 1 }
fileSystemGroupBD OBJECT IDENTIFIER ::= { fileSystemGroup 4 }
fileSystemGroupBD00 OBJECT IDENTIFIER ::= { fileSystemGroupBD 1 }
fileSystemGroupBD00A OBJECT IDENTIFIER ::= { fileSystemGroupBD00 2 }



-- Agent-Capabilities Statement:

-- PRODUCT-RELEASE "Passport Release 7.0 FileSystem."
-- STATUS          mandatory
-- DESCRIPTION     "FileSystem MIB: MIB Version BD00A,
--                  Software Version BG00S4C."
-- SUPPORTS        Nortel-Magellan-Passport-FileSystemMIB
--    INCLUDES     { fileSystemGroupBD00A }

fileSystemCapabilities OBJECT IDENTIFIER ::= { fileSystemMIB 3 }
fileSystemCapabilitiesBD OBJECT IDENTIFIER ::= { fileSystemCapabilities 4 }
fileSystemCapabilitiesBD00 OBJECT IDENTIFIER ::= { fileSystemCapabilitiesBD 1 }
fileSystemCapabilitiesBD00A OBJECT IDENTIFIER ::= { fileSystemCapabilitiesBD00 2 }





END
