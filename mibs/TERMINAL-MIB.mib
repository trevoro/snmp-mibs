TERMINAL-MIB 

   --FORCE-INCLUDE <mib.h>
   --FORCE-INCLUDE <snmpdefs.h>
   --FORCE-INCLUDE <snmpstat.h>
   --FORCE-INCLUDE "mibproto.h"

    DEFINITIONS ::= BEGIN

	IMPORTS
		MODULE-IDENTITY, OBJECT-TYPE
			FROM SNMPv2-SMI
		DisplayString
			FROM SNMPv2-TC
		TRAP-TYPE
			FROM RFC-1215
		terminalMgmt
			FROM APENT-MIB;


    terminalMgrMib MODULE-IDENTITY
	   LAST-UPDATED "9707202000Z" -- Wed July 20 20:00:00 EST 1997
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	    "This MIB module describes the ArrowPoint enterprise
	     MIB support for Terminal Options"
      ::= { terminalMgmt 1}

apTermSessIdleTimeout OBJECT-TYPE
	SYNTAX      INTEGER( 0..65535 )
	MAX-ACCESS  read-write
	STATUS      current
	DESCRIPTION
		"This object is the default session idle time applied to each
		active session to this unit."
	::= {terminalMgmt 2}

apTermSessLoginFailureInfo OBJECT-TYPE
	SYNTAX			DisplayString (SIZE (1 .. 255))
	MAX-ACCESS		read-only
	STATUS			current
	DESCRIPTION
		"This object contains information pertaining to the the last
         login failure.  It is a variable bind accompanying the apTerm-
         SessLoginFailureTrap"
	::= { terminalMgmt 3}

apTermSessTelnetDisallowed OBJECT-TYPE
	SYNTAX			INTEGER {
						disabled(0),
						enabled(1)
                    }		
	MAX-ACCESS		read-write
	STATUS			current
	DESCRIPTION
		"This object is the global setting on whether telnet access
         is allowed to this unit."
	::= { terminalMgmt 4}

apTermSessConsoleDisallowed OBJECT-TYPE
	SYNTAX			INTEGER {
						disabled(0),
						enabled(1)
                    }		
	MAX-ACCESS		read-write
	STATUS			current
	DESCRIPTION
		"This object is the global setting on whether Console access
         is allowed to this unit."
	::= { terminalMgmt 5}

apTermSessSNMPDisallowed OBJECT-TYPE
	SYNTAX			INTEGER {
						disabled(0),
						enabled(1)
                    }		
	MAX-ACCESS		read-write
	STATUS			current
	DESCRIPTION
		"This object is the global setting on whether SNMP access
         is allowed to this unit."
	::= { terminalMgmt 6}

apTermSessFTPDisallowed OBJECT-TYPE
	SYNTAX			INTEGER {
						disabled(0),
						enabled(1)
                    }		
	MAX-ACCESS		read-write
	STATUS			current
	DESCRIPTION
		"This object is the global setting on whether FTP access
         is allowed to this unit."
	::= { terminalMgmt 7}

apTermSessEuroDateDisplay OBJECT-TYPE
	SYNTAX			INTEGER {
						disabled(0),
						enabled(1)
                    }		
	MAX-ACCESS		read-write
	STATUS			current
	DESCRIPTION
		"This object is the global setting on whether dates are
         displayed in a European format: MM/DD/YY vs. DD/MM/YY."
	::= { terminalMgmt 8}


apTermSessXMLDisallowed OBJECT-TYPE
	SYNTAX			INTEGER {
						disabled(0),
						enabled(1)
                    }		
	MAX-ACCESS		read-write
	STATUS			current
	DESCRIPTION
		"This object is the global setting on whether XML access
         is allowed to this unit."
	::= { terminalMgmt 9}

apTermSessWebMgmtDisallowed OBJECT-TYPE
	SYNTAX			INTEGER {
						disabled(0),
						enabled(1)
                    }		
	MAX-ACCESS		read-write
	STATUS			current
	DESCRIPTION
		"This object is the global setting on whether Web-Mgmt access
         is allowed to this unit."
	::= { terminalMgmt 10}


apTermSessLoginFailureTrap TRAP-TYPE
	ENTERPRISE terminalMgmt
	VARIABLES { apTermSessLoginFailureInfo }
	DESCRIPTION
		"This trap is generated when a login failure occurs.  The login
         may have been attempted via Console/Ftp/Telnet, a description
         of the login failure accompanies this trap in the form of
         apTermSessLoginFailureInfo"
	::= 1



END
