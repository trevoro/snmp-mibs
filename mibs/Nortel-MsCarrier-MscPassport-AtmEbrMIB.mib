Nortel-MsCarrier-MscPassport-AtmEbrMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32
   FROM Nortel-MsCarrier-MscPassport-StandardTextualConventionsMIB

      NonReplicated
   FROM Nortel-MsCarrier-MscPassport-TextualConventionsMIB

      mscAtmIfVpcSrc,
      mscAtmIfVptVccSrcIndex,
      mscAtmIfVptVccSrc,
      mscAtmIfVccSrcIndex,
      mscAtmIfVccSrc,
      mscAtmIfVpcSrcIndex
   FROM Nortel-MsCarrier-MscPassport-AtmNetworkingMIB

      mscAtmIfVptVcc,
      mscAtmIfVccIndex,
      mscAtmIfVptIndex,
      mscAtmIfVcc,
      mscAtmIfVpcIndex,
      mscAtmIfVpc,
      mscAtmIfVptVccIndex,
      mscAtmIfIndex
   FROM Nortel-MsCarrier-MscPassport-AtmCoreMIB

      mscAtmIfUni,
      mscAtmIfVptUniIndex,
      mscAtmIfVptUni,
      mscAtmIfUniIndex
   FROM Nortel-MsCarrier-MscPassport-AtmUniMIB

      mscAtmIfVptIisp,
      mscAtmIfIispIndex,
      mscAtmIfIisp,
      mscAtmIfVptIispIndex
   FROM Nortel-MsCarrier-MscPassport-AtmIispMIB

      mscAtmIfVptPnni,
      mscAtmIfPnniIndex,
      mscAtmIfPnni,
      mscAtmIfVptPnniIndex
   FROM Nortel-MsCarrier-MscPassport-AtmPnniMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmEbr Enterprise MIB."

atmEbrMIB OBJECT IDENTIFIER ::= { mscPassportMIBs 159 }










-- AtmIf/n Vcc/vpi.vci SrcPvc EdgeBasedReroutingOverride
-- AtmIf/n Vpc/vpi SrcPvp EdgeBasedReroutingOverride
-- AtmIf/n Vpt/vpi Vcc/vci SrcPvc EdgeBasedReroutingOverride
-- 
-- This component represents the ability to override Edge Based 
-- Rerouting capabilities on a per connection basis for provisioned 
-- SPVC and SPVP connections. 
-- 
-- The addition of this component and changes to the attributes 
-- contained in this component are critical to the parent SPVC or 
-- SPVP. The deletion of this component is not a critical change for 
-- the connection. If this component is deleted, the connection remains 
-- active with the current subscription options until it restages.

mscAtmIfVpcSrcEbrOv OBJECT IDENTIFIER ::= { mscAtmIfVpcSrc 2 }



mscAtmIfVpcSrcEbrOvRowStatusTable OBJECT-TYPE
   SYNTAX     SEQUENCE OF MscAtmIfVpcSrcEbrOvRowStatusEntry
   ACCESS     not-accessible
   STATUS     mandatory
   DESCRIPTION
     "This entry controls the addition and deletion of 
      mscAtmIfVpcSrcEbrOv components."
::= { mscAtmIfVpcSrcEbrOv 1 }

mscAtmIfVpcSrcEbrOvRowStatusEntry OBJECT-TYPE
   SYNTAX     MscAtmIfVpcSrcEbrOvRowStatusEntry
   ACCESS     not-accessible
   STATUS     mandatory
   DESCRIPTION
     "A single entry in the table represents a single 
      mscAtmIfVpcSrcEbrOv component."
   INDEX {
      mscAtmIfIndex,
      mscAtmIfVpcIndex,
      mscAtmIfVpcSrcIndex,
      mscAtmIfVpcSrcEbrOvIndex }
::= { mscAtmIfVpcSrcEbrOvRowStatusTable 1 }

MscAtmIfVpcSrcEbrOvRowStatusEntry ::= SEQUENCE {
   mscAtmIfVpcSrcEbrOvRowStatus
      RowStatus,
   mscAtmIfVpcSrcEbrOvComponentName
      DisplayString,
   mscAtmIfVpcSrcEbrOvStorageType
      StorageType,
   mscAtmIfVpcSrcEbrOvIndex
      NonReplicated }

mscAtmIfVpcSrcEbrOvRowStatus OBJECT-TYPE
   SYNTAX     RowStatus 
   ACCESS     read-write
   STATUS     mandatory
   DESCRIPTION
     "This variable is used as the basis for SNMP naming of
      mscAtmIfVpcSrcEbrOv components.
      These components can be added and deleted."
::= { mscAtmIfVpcSrcEbrOvRowStatusEntry 1 }

mscAtmIfVpcSrcEbrOvComponentName OBJECT-TYPE
   SYNTAX     DisplayString 
   ACCESS     read-only
   STATUS     mandatory
   DESCRIPTION
     "This variable provides the component's string name for
      use with the ASCII Console Interface"
::= { mscAtmIfVpcSrcEbrOvRowStatusEntry 2 }

mscAtmIfVpcSrcEbrOvStorageType OBJECT-TYPE
   SYNTAX     StorageType 
   ACCESS     read-only
   STATUS     mandatory
   DESCRIPTION
     "This variable represents the storage type value for the
      mscAtmIfVpcSrcEbrOv tables."
::= { mscAtmIfVpcSrcEbrOvRowStatusEntry 4 }

mscAtmIfVpcSrcEbrOvIndex OBJECT-TYPE
   SYNTAX     NonReplicated 
   ACCESS     not-accessible
   STATUS     mandatory
   DESCRIPTION
     "This variable represents the index for the mscAtmIfVpcSrcEbrOv tables."
::= { mscAtmIfVpcSrcEbrOvRowStatusEntry 10 }

mscAtmIfVpcSrcEbrOvProvTable OBJECT-TYPE
   SYNTAX     SEQUENCE OF MscAtmIfVpcSrcEbrOvProvEntry
   ACCESS     not-accessible
   STATUS     mandatory
   DESCRIPTION
     "This group contains the provisionable attributes for the Edge Based 
      Rerouting subscription options for provisioned connections."
::= { mscAtmIfVpcSrcEbrOv 20 }

mscAtmIfVpcSrcEbrOvProvEntry OBJECT-TYPE
   SYNTAX     MscAtmIfVpcSrcEbrOvProvEntry
   ACCESS     not-accessible
   STATUS     mandatory
   DESCRIPTION
     "An entry in the mscAtmIfVpcSrcEbrOvProvTable."
   INDEX {
      mscAtmIfIndex,
      mscAtmIfVpcIndex,
      mscAtmIfVpcSrcIndex,
      mscAtmIfVpcSrcEbrOvIndex }
::= { mscAtmIfVpcSrcEbrOvProvTable 1 }

MscAtmIfVpcSrcEbrOvProvEntry ::= SEQUENCE {
   mscAtmIfVpcSrcEbrOvRecoverySubscribed
      INTEGER,
   mscAtmIfVpcSrcEbrOvOptimizationSubscribed
      INTEGER }

mscAtmIfVpcSrcEbrOvRecoverySubscribed OBJECT-TYPE
   SYNTAX     INTEGER  {
                 no(0),
                 yes(1) }
   ACCESS     read-write
   STATUS     mandatory
   DESCRIPTION
     "This attributes specifies whether connection recovery is subscribed 
      for this connection."
   DEFVAL     { yes }
::= { mscAtmIfVpcSrcEbrOvProvEntry 1 }

mscAtmIfVpcSrcEbrOvOptimizationSubscribed OBJECT-TYPE
   SYNTAX     INTEGER  {
                 no(0),
                 yes(1) }
   ACCESS     read-write
   STATUS     mandatory
   DESCRIPTION
     "This attributes specifies whether path optimization is subscribed for 
      this connection."
   DEFVAL     { yes }
::= { mscAtmIfVpcSrcEbrOvProvEntry 2 }


-- AtmIf/n Vcc/vpi.vci EdgeBasedReroutingInformation
-- AtmIf/n Vpc/vpi EdgeBasedReroutingInformation
-- AtmIf/n Vpt/vpi Vcc/vci EdgeBasedReroutingInformation
-- 
-- This component represents the Edge Based Rerouting capabilities 
-- of a connection.

mscAtmIfVpcEbrInfo OBJECT IDENTIFIER ::= { mscAtmIfVpc 11 }



mscAtmIfVpcEbrInfoRowStatusTable OBJECT-TYPE
   SYNTAX     SEQUENCE OF MscAtmIfVpcEbrInfoRowStatusEntry
   ACCESS     not-accessible
   STATUS     mandatory
   DESCRIPTION
     "This entry controls the addition and deletion of 
      mscAtmIfVpcEbrInfo components."
::= { mscAtmIfVpcEbrInfo 1 }

mscAtmIfVpcEbrInfoRowStatusEntry OBJECT-TYPE
   SYNTAX     MscAtmIfVpcEbrInfoRowStatusEntry
   ACCESS     not-accessible
   STATUS     mandatory
   DESCRIPTION
     "A single entry in the table represents a single 
      mscAtmIfVpcEbrInfo component."
   INDEX {
      mscAtmIfIndex,
      mscAtmIfVpcIndex,
      mscAtmIfVpcEbrInfoIndex }
::= { mscAtmIfVpcEbrInfoRowStatusTable 1 }

MscAtmIfVpcEbrInfoRowStatusEntry ::= SEQUENCE {
   mscAtmIfVpcEbrInfoRowStatus
      RowStatus,
   mscAtmIfVpcEbrInfoComponentName
      DisplayString,
   mscAtmIfVpcEbrInfoStorageType
      StorageType,
   mscAtmIfVpcEbrInfoIndex
      NonReplicated }

mscAtmIfVpcEbrInfoRowStatus OBJECT-TYPE
   SYNTAX     RowStatus 
   ACCESS     read-only
   STATUS     mandatory
   DESCRIPTION
     "This variable is used as the basis for SNMP naming of
      mscAtmIfVpcEbrInfo components.
      These components cannot be added nor deleted."
::= { mscAtmIfVpcEbrInfoRowStatusEntry 1 }

mscAtmIfVpcEbrInfoComponentName OBJECT-TYPE
   SYNTAX     DisplayString 
   ACCESS     read-only
   STATUS     mandatory
   DESCRIPTION
     "This variable provides the component's string name for
      use with the ASCII Console Interface"
::= { mscAtmIfVpcEbrInfoRowStatusEntry 2 }

mscAtmIfVpcEbrInfoStorageType OBJECT-TYPE
   SYNTAX     StorageType 
   ACCESS     read-only
   STATUS     mandatory
   DESCRIPTION
     "This variable represents the storage type value for the
      mscAtmIfVpcEbrInfo tables."
::= { mscAtmIfVpcEbrInfoRowStatusEntry 4 }

mscAtmIfVpcEbrInfoIndex OBJECT-TYPE
   SYNTAX     NonReplicated 
   ACCESS     not-accessible
   STATUS     mandatory
   DESCRIPTION
     "This variable represents the index for the mscAtmIfVpcEbrInfo tables."
::= { mscAtmIfVpcEbrInfoRowStatusEntry 10 }

mscAtmIfVpcEbrInfoOperTable OBJECT-TYPE
   SYNTAX     SEQUENCE OF MscAtmIfVpcEbrInfoOperEntry
   ACCESS     not-accessible
   STATUS     mandatory
   DESCRIPTION
     "This group contains the attributes that indicates the Edge Based 
      Rerouting characteristics of a connection."
::= { mscAtmIfVpcEbrInfo 30 }

mscAtmIfVpcEbrInfoOperEntry OBJECT-TYPE
   SYNTAX     MscAtmIfVpcEbrInfoOperEntry
   ACCESS     not-accessible
   STATUS     mandatory
   DESCRIPTION
     "An entry in the mscAtmIfVpcEbrInfoOperTable."
   INDEX {
      mscAtmIfIndex,
      mscAtmIfVpcIndex,
      mscAtmIfVpcEbrInfoIndex }
::= { mscAtmIfVpcEbrInfoOperTable 1 }

MscAtmIfVpcEbrInfoOperEntry ::= SEQUENCE {
   mscAtmIfVpcEbrInfoRecoverySubscribed
      INTEGER,
   mscAtmIfVpcEbrInfoOptimizationSubscribed
      INTEGER,
   mscAtmIfVpcEbrInfoConnectionRecovered
      INTEGER }

mscAtmIfVpcEbrInfoRecoverySubscribed OBJECT-TYPE
   SYNTAX     INTEGER  {
                 no(0),
                 yes(1) }
   ACCESS     read-only
   STATUS     mandatory
   DESCRIPTION
     "This attribute indicates whether the connection is subscribed to 
      connection recovery."
::= { mscAtmIfVpcEbrInfoOperEntry 1 }

mscAtmIfVpcEbrInfoOptimizationSubscribed OBJECT-TYPE
   SYNTAX     INTEGER  {
                 no(0),
                 yes(1) }
   ACCESS     read-only
   STATUS     mandatory
   DESCRIPTION
     "This attribute indicates whether the connection is subscribed to path 
      optimization."
::= { mscAtmIfVpcEbrInfoOperEntry 2 }

mscAtmIfVpcEbrInfoConnectionRecovered OBJECT-TYPE
   SYNTAX     INTEGER  {
                 no(0),
                 yes(1) }
   ACCESS     read-only
   STATUS     mandatory
   DESCRIPTION
     "This attribute indicates whether the connection has been recovered 
      since the last optimization occurred. The value is reset to no by the 
      Optimize command."
::= { mscAtmIfVpcEbrInfoOperEntry 3 }

mscAtmIfVpcEbrInfoStatsTable OBJECT-TYPE
   SYNTAX     SEQUENCE OF MscAtmIfVpcEbrInfoStatsEntry
   ACCESS     not-accessible
   STATUS     mandatory
   DESCRIPTION
     "This group contains the statistics related to Edge Based Rerouting."
::= { mscAtmIfVpcEbrInfo 40 }

mscAtmIfVpcEbrInfoStatsEntry OBJECT-TYPE
   SYNTAX     MscAtmIfVpcEbrInfoStatsEntry
   ACCESS     not-accessible
   STATUS     mandatory
   DESCRIPTION
     "An entry in the mscAtmIfVpcEbrInfoStatsTable."
   INDEX {
      mscAtmIfIndex,
      mscAtmIfVpcIndex,
      mscAtmIfVpcEbrInfoIndex }
::= { mscAtmIfVpcEbrInfoStatsTable 1 }

MscAtmIfVpcEbrInfoStatsEntry ::= SEQUENCE {
   mscAtmIfVpcEbrInfoTotalConnectionRecoveries
      Counter32,
   mscAtmIfVpcEbrInfoTotalPathOptimizations
      Counter32 }

mscAtmIfVpcEbrInfoTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfVpcEbrInfoStatsEntry 1 }

mscAtmIfVpcEbrInfoTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfVpcEbrInfoStatsEntry 2 }


-- AtmIf/n Vcc/vpi.vci SrcPvc EdgeBasedReroutingOverride
-- AtmIf/n Vpc/vpi SrcPvp EdgeBasedReroutingOverride
-- AtmIf/n Vpt/vpi Vcc/vci SrcPvc EdgeBasedReroutingOverride
-- 
-- This component represents the ability to override Edge Based 
-- Rerouting capabilities on a per connection basis for provisioned 
-- SPVC and SPVP connections. 
-- 
-- The addition of this component and changes to the attributes 
-- contained in this component are critical to the parent SPVC or 
-- SPVP. The deletion of this component is not a critical change for 
-- the connection. If this component is deleted, the connection remains 
-- active with the current subscription options until it restages.

mscAtmIfVccSrcEbrOv OBJECT IDENTIFIER ::= { mscAtmIfVccSrc 2 }



mscAtmIfVccSrcEbrOvRowStatusTable OBJECT-TYPE
   SYNTAX     SEQUENCE OF MscAtmIfVccSrcEbrOvRowStatusEntry
   ACCESS     not-accessible
   STATUS     mandatory
   DESCRIPTION
     "This entry controls the addition and deletion of 
      mscAtmIfVccSrcEbrOv components."
::= { mscAtmIfVccSrcEbrOv 1 }

mscAtmIfVccSrcEbrOvRowStatusEntry OBJECT-TYPE
   SYNTAX     MscAtmIfVccSrcEbrOvRowStatusEntry
   ACCESS     not-accessible
   STATUS     mandatory
   DESCRIPTION
     "A single entry in the table represents a single 
      mscAtmIfVccSrcEbrOv component."
   INDEX {
      mscAtmIfIndex,
      mscAtmIfVccIndex,
      mscAtmIfVccSrcIndex,
      mscAtmIfVccSrcEbrOvIndex }
::= { mscAtmIfVccSrcEbrOvRowStatusTable 1 }

MscAtmIfVccSrcEbrOvRowStatusEntry ::= SEQUENCE {
   mscAtmIfVccSrcEbrOvRowStatus
      RowStatus,
   mscAtmIfVccSrcEbrOvComponentName
      DisplayString,
   mscAtmIfVccSrcEbrOvStorageType
      StorageType,
   mscAtmIfVccSrcEbrOvIndex
      NonReplicated }

mscAtmIfVccSrcEbrOvRowStatus OBJECT-TYPE
   SYNTAX     RowStatus 
   ACCESS     read-write
   STATUS     mandatory
   DESCRIPTION
     "This variable is used as the basis for SNMP naming of
      mscAtmIfVccSrcEbrOv components.
      These components can be added and deleted."
::= { mscAtmIfVccSrcEbrOvRowStatusEntry 1 }

mscAtmIfVccSrcEbrOvComponentName OBJECT-TYPE
   SYNTAX     DisplayString 
   ACCESS     read-only
   STATUS     mandatory
   DESCRIPTION
     "This variable provides the component's string name for
      use with the ASCII Console Interface"
::= { mscAtmIfVccSrcEbrOvRowStatusEntry 2 }

mscAtmIfVccSrcEbrOvStorageType OBJECT-TYPE
   SYNTAX     StorageType 
   ACCESS     read-only
   STATUS     mandatory
   DESCRIPTION
     "This variable represents the storage type value for the
      mscAtmIfVccSrcEbrOv tables."
::= { mscAtmIfVccSrcEbrOvRowStatusEntry 4 }

mscAtmIfVccSrcEbrOvIndex OBJECT-TYPE
   SYNTAX     NonReplicated 
   ACCESS     not-accessible
   STATUS     mandatory
   DESCRIPTION
     "This variable represents the index for the mscAtmIfVccSrcEbrOv tables."
::= { mscAtmIfVccSrcEbrOvRowStatusEntry 10 }

mscAtmIfVccSrcEbrOvProvTable OBJECT-TYPE
   SYNTAX     SEQUENCE OF MscAtmIfVccSrcEbrOvProvEntry
   ACCESS     not-accessible
   STATUS     mandatory
   DESCRIPTION
     "This group contains the provisionable attributes for the Edge Based 
      Rerouting subscription options for provisioned connections."
::= { mscAtmIfVccSrcEbrOv 20 }

mscAtmIfVccSrcEbrOvProvEntry OBJECT-TYPE
   SYNTAX     MscAtmIfVccSrcEbrOvProvEntry
   ACCESS     not-accessible
   STATUS     mandatory
   DESCRIPTION
     "An entry in the mscAtmIfVccSrcEbrOvProvTable."
   INDEX {
      mscAtmIfIndex,
      mscAtmIfVccIndex,
      mscAtmIfVccSrcIndex,
      mscAtmIfVccSrcEbrOvIndex }
::= { mscAtmIfVccSrcEbrOvProvTable 1 }

MscAtmIfVccSrcEbrOvProvEntry ::= SEQUENCE {
   mscAtmIfVccSrcEbrOvRecoverySubscribed
      INTEGER,
   mscAtmIfVccSrcEbrOvOptimizationSubscribed
      INTEGER }

mscAtmIfVccSrcEbrOvRecoverySubscribed OBJECT-TYPE
   SYNTAX     INTEGER  {
                 no(0),
                 yes(1) }
   ACCESS     read-write
   STATUS     mandatory
   DESCRIPTION
     "This attributes specifies whether connection recovery is subscribed 
      for this connection."
   DEFVAL     { yes }
::= { mscAtmIfVccSrcEbrOvProvEntry 1 }

mscAtmIfVccSrcEbrOvOptimizationSubscribed OBJECT-TYPE
   SYNTAX     INTEGER  {
                 no(0),
                 yes(1) }
   ACCESS     read-write
   STATUS     mandatory
   DESCRIPTION
     "This attributes specifies whether path optimization is subscribed for 
      this connection."
   DEFVAL     { yes }
::= { mscAtmIfVccSrcEbrOvProvEntry 2 }


-- AtmIf/n Vcc/vpi.vci EdgeBasedReroutingInformation
-- AtmIf/n Vpc/vpi EdgeBasedReroutingInformation
-- AtmIf/n Vpt/vpi Vcc/vci EdgeBasedReroutingInformation
-- 
-- This component represents the Edge Based Rerouting capabilities 
-- of a connection.

mscAtmIfVccEbrInfo OBJECT IDENTIFIER ::= { mscAtmIfVcc 12 }



mscAtmIfVccEbrInfoRowStatusTable OBJECT-TYPE
   SYNTAX     SEQUENCE OF MscAtmIfVccEbrInfoRowStatusEntry
   ACCESS     not-accessible
   STATUS     mandatory
   DESCRIPTION
     "This entry controls the addition and deletion of 
      mscAtmIfVccEbrInfo components."
::= { mscAtmIfVccEbrInfo 1 }

mscAtmIfVccEbrInfoRowStatusEntry OBJECT-TYPE
   SYNTAX     MscAtmIfVccEbrInfoRowStatusEntry
   ACCESS     not-accessible
   STATUS     mandatory
   DESCRIPTION
     "A single entry in the table represents a single 
      mscAtmIfVccEbrInfo component."
   INDEX {
      mscAtmIfIndex,
      mscAtmIfVccIndex,
      mscAtmIfVccEbrInfoIndex }
::= { mscAtmIfVccEbrInfoRowStatusTable 1 }

MscAtmIfVccEbrInfoRowStatusEntry ::= SEQUENCE {
   mscAtmIfVccEbrInfoRowStatus
      RowStatus,
   mscAtmIfVccEbrInfoComponentName
      DisplayString,
   mscAtmIfVccEbrInfoStorageType
      StorageType,
   mscAtmIfVccEbrInfoIndex
      NonReplicated }

mscAtmIfVccEbrInfoRowStatus OBJECT-TYPE
   SYNTAX     RowStatus 
   ACCESS     read-only
   STATUS     mandatory
   DESCRIPTION
     "This variable is used as the basis for SNMP naming of
      mscAtmIfVccEbrInfo components.
      These components cannot be added nor deleted."
::= { mscAtmIfVccEbrInfoRowStatusEntry 1 }

mscAtmIfVccEbrInfoComponentName OBJECT-TYPE
   SYNTAX     DisplayString 
   ACCESS     read-only
   STATUS     mandatory
   DESCRIPTION
     "This variable provides the component's string name for
      use with the ASCII Console Interface"
::= { mscAtmIfVccEbrInfoRowStatusEntry 2 }

mscAtmIfVccEbrInfoStorageType OBJECT-TYPE
   SYNTAX     StorageType 
   ACCESS     read-only
   STATUS     mandatory
   DESCRIPTION
     "This variable represents the storage type value for the
      mscAtmIfVccEbrInfo tables."
::= { mscAtmIfVccEbrInfoRowStatusEntry 4 }

mscAtmIfVccEbrInfoIndex OBJECT-TYPE
   SYNTAX     NonReplicated 
   ACCESS     not-accessible
   STATUS     mandatory
   DESCRIPTION
     "This variable represents the index for the mscAtmIfVccEbrInfo tables."
::= { mscAtmIfVccEbrInfoRowStatusEntry 10 }

mscAtmIfVccEbrInfoOperTable OBJECT-TYPE
   SYNTAX     SEQUENCE OF MscAtmIfVccEbrInfoOperEntry
   ACCESS     not-accessible
   STATUS     mandatory
   DESCRIPTION
     "This group contains the attributes that indicates the Edge Based 
      Rerouting characteristics of a connection."
::= { mscAtmIfVccEbrInfo 30 }

mscAtmIfVccEbrInfoOperEntry OBJECT-TYPE
   SYNTAX     MscAtmIfVccEbrInfoOperEntry
   ACCESS     not-accessible
   STATUS     mandatory
   DESCRIPTION
     "An entry in the mscAtmIfVccEbrInfoOperTable."
   INDEX {
      mscAtmIfIndex,
      mscAtmIfVccIndex,
      mscAtmIfVccEbrInfoIndex }
::= { mscAtmIfVccEbrInfoOperTable 1 }

MscAtmIfVccEbrInfoOperEntry ::= SEQUENCE {
   mscAtmIfVccEbrInfoRecoverySubscribed
      INTEGER,
   mscAtmIfVccEbrInfoOptimizationSubscribed
      INTEGER,
   mscAtmIfVccEbrInfoConnectionRecovered
      INTEGER }

mscAtmIfVccEbrInfoRecoverySubscribed OBJECT-TYPE
   SYNTAX     INTEGER  {
                 no(0),
                 yes(1) }
   ACCESS     read-only
   STATUS     mandatory
   DESCRIPTION
     "This attribute indicates whether the connection is subscribed to 
      connection recovery."
::= { mscAtmIfVccEbrInfoOperEntry 1 }

mscAtmIfVccEbrInfoOptimizationSubscribed OBJECT-TYPE
   SYNTAX     INTEGER  {
                 no(0),
                 yes(1) }
   ACCESS     read-only
   STATUS     mandatory
   DESCRIPTION
     "This attribute indicates whether the connection is subscribed to path 
      optimization."
::= { mscAtmIfVccEbrInfoOperEntry 2 }

mscAtmIfVccEbrInfoConnectionRecovered OBJECT-TYPE
   SYNTAX     INTEGER  {
                 no(0),
                 yes(1) }
   ACCESS     read-only
   STATUS     mandatory
   DESCRIPTION
     "This attribute indicates whether the connection has been recovered 
      since the last optimization occurred. The value is reset to no by the 
      Optimize command."
::= { mscAtmIfVccEbrInfoOperEntry 3 }

mscAtmIfVccEbrInfoStatsTable OBJECT-TYPE
   SYNTAX     SEQUENCE OF MscAtmIfVccEbrInfoStatsEntry
   ACCESS     not-accessible
   STATUS     mandatory
   DESCRIPTION
     "This group contains the statistics related to Edge Based Rerouting."
::= { mscAtmIfVccEbrInfo 40 }

mscAtmIfVccEbrInfoStatsEntry OBJECT-TYPE
   SYNTAX     MscAtmIfVccEbrInfoStatsEntry
   ACCESS     not-accessible
   STATUS     mandatory
   DESCRIPTION
     "An entry in the mscAtmIfVccEbrInfoStatsTable."
   INDEX {
      mscAtmIfIndex,
      mscAtmIfVccIndex,
      mscAtmIfVccEbrInfoIndex }
::= { mscAtmIfVccEbrInfoStatsTable 1 }

MscAtmIfVccEbrInfoStatsEntry ::= SEQUENCE {
   mscAtmIfVccEbrInfoTotalConnectionRecoveries
      Counter32,
   mscAtmIfVccEbrInfoTotalPathOptimizations
      Counter32 }

mscAtmIfVccEbrInfoTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfVccEbrInfoStatsEntry 1 }

mscAtmIfVccEbrInfoTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfVccEbrInfoStatsEntry 2 }


-- AtmIf/n Iisp EdgeBasedRerouting
-- AtmIf/n Uni EdgeBasedRerouting
-- AtmIf/n Pnni EdgeBasedRerouting
-- AtmIf/n Vpt/vpi Iisp EdgeBasedRerouting
-- AtmIf/n Vpt/vpi Uni EdgeBasedRerouting
-- AtmIf/n Vpt/vpi Pnni EdgeBasedRerouting
-- 
-- This component represents the Edge Based Rerouting capabilities 
-- of the ATM Signaling interface. If this component is provisioned, 
-- the Artg Pnni component must already exist. The addition or 
-- deletion of this component, or changes to the provisioned 
-- subscription options, does not affect existing connections.

mscAtmIfUniEbr OBJECT IDENTIFIER ::= { mscAtmIfUni 7 }



mscAtmIfUniEbrRowStatusTable OBJECT-TYPE
   SYNTAX     SEQUENCE OF MscAtmIfUniEbrRowStatusEntry
   ACCESS     not-accessible
   STATUS     mandatory
   DESCRIPTION
     "This entry controls the addition and deletion of 
      mscAtmIfUniEbr components."
::= { mscAtmIfUniEbr 1 }

mscAtmIfUniEbrRowStatusEntry OBJECT-TYPE
   SYNTAX     MscAtmIfUniEbrRowStatusEntry
   ACCESS     not-accessible
   STATUS     mandatory
   DESCRIPTION
     "A single entry in the table represents a single 
      mscAtmIfUniEbr component."
   INDEX {
      mscAtmIfIndex,
      mscAtmIfUniIndex,
      mscAtmIfUniEbrIndex }
::= { mscAtmIfUniEbrRowStatusTable 1 }

MscAtmIfUniEbrRowStatusEntry ::= SEQUENCE {
   mscAtmIfUniEbrRowStatus
      RowStatus,
   mscAtmIfUniEbrComponentName
      DisplayString,
   mscAtmIfUniEbrStorageType
      StorageType,
   mscAtmIfUniEbrIndex
      NonReplicated }

mscAtmIfUniEbrRowStatus OBJECT-TYPE
   SYNTAX     RowStatus 
   ACCESS     read-write
   STATUS     mandatory
   DESCRIPTION
     "This variable is used as the basis for SNMP naming of
      mscAtmIfUniEbr components.
      These components can be added and deleted."
::= { mscAtmIfUniEbrRowStatusEntry 1 }

mscAtmIfUniEbrComponentName OBJECT-TYPE
   SYNTAX     DisplayString 
   ACCESS     read-only
   STATUS     mandatory
   DESCRIPTION
     "This variable provides the component's string name for
      use with the ASCII Console Interface"
::= { mscAtmIfUniEbrRowStatusEntry 2 }

mscAtmIfUniEbrStorageType OBJECT-TYPE
   SYNTAX     StorageType 
   ACCESS     read-only
   STATUS     mandatory
   DESCRIPTION
     "This variable represents the storage type value for the
      mscAtmIfUniEbr tables."
::= { mscAtmIfUniEbrRowStatusEntry 4 }

mscAtmIfUniEbrIndex OBJECT-TYPE
   SYNTAX     NonReplicated 
   ACCESS     not-accessible
   STATUS     mandatory
   DESCRIPTION
     "This variable represents the index for the mscAtmIfUniEbr tables."
::= { mscAtmIfUniEbrRowStatusEntry 10 }

mscAtmIfUniEbrProvTable OBJECT-TYPE
   SYNTAX     SEQUENCE OF MscAtmIfUniEbrProvEntry
   ACCESS     not-accessible
   STATUS     mandatory
   DESCRIPTION
     "This group contains the provisionable attributes for Edge Based 
      Rerouting at the ATM Signaling interface."
::= { mscAtmIfUniEbr 20 }

mscAtmIfUniEbrProvEntry OBJECT-TYPE
   SYNTAX     MscAtmIfUniEbrProvEntry
   ACCESS     not-accessible
   STATUS     mandatory
   DESCRIPTION
     "An entry in the mscAtmIfUniEbrProvTable."
   INDEX {
      mscAtmIfIndex,
      mscAtmIfUniIndex,
      mscAtmIfUniEbrIndex }
::= { mscAtmIfUniEbrProvTable 1 }

MscAtmIfUniEbrProvEntry ::= SEQUENCE {
   mscAtmIfUniEbrConnectionRecovery
      OCTET STRING,
   mscAtmIfUniEbrPathOptimization
      OCTET STRING }

mscAtmIfUniEbrConnectionRecovery OBJECT-TYPE
   SYNTAX     OCTET STRING (SIZE (1))
   ACCESS     read-write
   STATUS     mandatory
   DESCRIPTION
     "This attribute specifies the subscription of connections to hard 
      rerouting.
      dynamic: Connections that are transiting through this interface.
      provisioned: SPVC and SPVP connections that are provisioned at 
      this interface.

      Description of bits:
      dynamic(0)
      provisioned(1)"
   DEFVAL     { 'c0'H }
::= { mscAtmIfUniEbrProvEntry 1 }

mscAtmIfUniEbrPathOptimization OBJECT-TYPE
   SYNTAX     OCTET STRING (SIZE (1))
   ACCESS     read-write
   STATUS     mandatory
   DESCRIPTION
     "This attribute specifies the subscription of connections to soft 
      rerouting.
      dynamic: Connections that are transiting through this interface.
      provisioned: SPVC and SPVP connections that are provisioned at 
      this interface.

      Description of bits:
      dynamic(0)
      provisioned(1)"
   DEFVAL     { 'c0'H }
::= { mscAtmIfUniEbrProvEntry 2 }

mscAtmIfUniEbrOperTable OBJECT-TYPE
   SYNTAX     SEQUENCE OF MscAtmIfUniEbrOperEntry
   ACCESS     not-accessible
   STATUS     mandatory
   DESCRIPTION
     "This group contains the operational attributes that indicate the 
      rerouting activities for an ATM Signaling interface."
::= { mscAtmIfUniEbr 30 }

mscAtmIfUniEbrOperEntry OBJECT-TYPE
   SYNTAX     MscAtmIfUniEbrOperEntry
   ACCESS     not-accessible
   STATUS     mandatory
   DESCRIPTION
     "An entry in the mscAtmIfUniEbrOperTable."
   INDEX {
      mscAtmIfIndex,
      mscAtmIfUniIndex,
      mscAtmIfUniEbrIndex }
::= { mscAtmIfUniEbrOperTable 1 }

MscAtmIfUniEbrOperEntry ::= SEQUENCE {
   mscAtmIfUniEbrSubscribedConnections
      Gauge32,
   mscAtmIfUniEbrEligibleRecoveredConnections
      Gauge32,
   mscAtmIfUniEbrIneligibleRecoveredConnections
      Gauge32 }

mscAtmIfUniEbrSubscribedConnections OBJECT-TYPE
   SYNTAX     Gauge32 (0..4294967295)
   ACCESS     read-only
   STATUS     mandatory
   DESCRIPTION
     "This attribute indicates the number of connections subscribed to 
      rerouting capabilities."
::= { mscAtmIfUniEbrOperEntry 1 }

mscAtmIfUniEbrEligibleRecoveredConnections OBJECT-TYPE
   SYNTAX     Gauge32 (0..4294967295)
   ACCESS     read-only
   STATUS     mandatory
   DESCRIPTION
     "This attribute indicates the number of connections that have been 
      recovered and are eligible for path optimization. The count is reset 
      to zero when the Optimize command is executed on this component."
::= { mscAtmIfUniEbrOperEntry 2 }

mscAtmIfUniEbrIneligibleRecoveredConnections OBJECT-TYPE
   SYNTAX     Gauge32 (0..4294967295)
   ACCESS     read-only
   STATUS     mandatory
   DESCRIPTION
     "This attribute indicates the number of connections that have been 
      recovered but are not eligible for path optimization. The value 
      decreases as counted connections are released. The count is not 
      reset by the Optimize command."
::= { mscAtmIfUniEbrOperEntry 3 }

mscAtmIfUniEbrStatsTable OBJECT-TYPE
   SYNTAX     SEQUENCE OF MscAtmIfUniEbrStatsEntry
   ACCESS     not-accessible
   STATUS     mandatory
   DESCRIPTION
     "This group contains the statistics related to Edge Based Rerouting."
::= { mscAtmIfUniEbr 40 }

mscAtmIfUniEbrStatsEntry OBJECT-TYPE
   SYNTAX     MscAtmIfUniEbrStatsEntry
   ACCESS     not-accessible
   STATUS     mandatory
   DESCRIPTION
     "An entry in the mscAtmIfUniEbrStatsTable."
   INDEX {
      mscAtmIfIndex,
      mscAtmIfUniIndex,
      mscAtmIfUniEbrIndex }
::= { mscAtmIfUniEbrStatsTable 1 }

MscAtmIfUniEbrStatsEntry ::= SEQUENCE {
   mscAtmIfUniEbrTotalConnectionRecoveries
      Counter32,
   mscAtmIfUniEbrTotalPathOptimizations
      Counter32 }

mscAtmIfUniEbrTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfUniEbrStatsEntry 1 }

mscAtmIfUniEbrTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfUniEbrStatsEntry 2 }


-- AtmIf/n Iisp EdgeBasedRerouting
-- AtmIf/n Uni EdgeBasedRerouting
-- AtmIf/n Pnni EdgeBasedRerouting
-- AtmIf/n Vpt/vpi Iisp EdgeBasedRerouting
-- AtmIf/n Vpt/vpi Uni EdgeBasedRerouting
-- AtmIf/n Vpt/vpi Pnni EdgeBasedRerouting
-- 
-- This component represents the Edge Based Rerouting capabilities 
-- of the ATM Signaling interface. If this component is provisioned, 
-- the Artg Pnni component must already exist. The addition or 
-- deletion of this component, or changes to the provisioned 
-- subscription options, does not affect existing connections.

mscAtmIfIispEbr OBJECT IDENTIFIER ::= { mscAtmIfIisp 7 }



mscAtmIfIispEbrRowStatusTable OBJECT-TYPE
   SYNTAX     SEQUENCE OF MscAtmIfIispEbrRowStatusEntry
   ACCESS     not-accessible
   STATUS     mandatory
   DESCRIPTION
     "This entry controls the addition and deletion of 
      mscAtmIfIispEbr components."
::= { mscAtmIfIispEbr 1 }

mscAtmIfIispEbrRowStatusEntry OBJECT-TYPE
   SYNTAX     MscAtmIfIispEbrRowStatusEntry
   ACCESS     not-accessible
   STATUS     mandatory
   DESCRIPTION
     "A single entry in the table represents a single 
      mscAtmIfIispEbr component."
   INDEX {
      mscAtmIfIndex,
      mscAtmIfIispIndex,
      mscAtmIfIispEbrIndex }
::= { mscAtmIfIispEbrRowStatusTable 1 }

MscAtmIfIispEbrRowStatusEntry ::= SEQUENCE {
   mscAtmIfIispEbrRowStatus
      RowStatus,
   mscAtmIfIispEbrComponentName
      DisplayString,
   mscAtmIfIispEbrStorageType
      StorageType,
   mscAtmIfIispEbrIndex
      NonReplicated }

mscAtmIfIispEbrRowStatus OBJECT-TYPE
   SYNTAX     RowStatus 
   ACCESS     read-write
   STATUS     mandatory
   DESCRIPTION
     "This variable is used as the basis for SNMP naming of
      mscAtmIfIispEbr components.
      These components can be added and deleted."
::= { mscAtmIfIispEbrRowStatusEntry 1 }

mscAtmIfIispEbrComponentName OBJECT-TYPE
   SYNTAX     DisplayString 
   ACCESS     read-only
   STATUS     mandatory
   DESCRIPTION
     "This variable provides the component's string name for
      use with the ASCII Console Interface"
::= { mscAtmIfIispEbrRowStatusEntry 2 }

mscAtmIfIispEbrStorageType OBJECT-TYPE
   SYNTAX     StorageType 
   ACCESS     read-only
   STATUS     mandatory
   DESCRIPTION
     "This variable represents the storage type value for the
      mscAtmIfIispEbr tables."
::= { mscAtmIfIispEbrRowStatusEntry 4 }

mscAtmIfIispEbrIndex OBJECT-TYPE
   SYNTAX     NonReplicated 
   ACCESS     not-accessible
   STATUS     mandatory
   DESCRIPTION
     "This variable represents the index for the mscAtmIfIispEbr tables."
::= { mscAtmIfIispEbrRowStatusEntry 10 }

mscAtmIfIispEbrProvTable OBJECT-TYPE
   SYNTAX     SEQUENCE OF MscAtmIfIispEbrProvEntry
   ACCESS     not-accessible
   STATUS     mandatory
   DESCRIPTION
     "This group contains the provisionable attributes for Edge Based 
      Rerouting at the ATM Signaling interface."
::= { mscAtmIfIispEbr 20 }

mscAtmIfIispEbrProvEntry OBJECT-TYPE
   SYNTAX     MscAtmIfIispEbrProvEntry
   ACCESS     not-accessible
   STATUS     mandatory
   DESCRIPTION
     "An entry in the mscAtmIfIispEbrProvTable."
   INDEX {
      mscAtmIfIndex,
      mscAtmIfIispIndex,
      mscAtmIfIispEbrIndex }
::= { mscAtmIfIispEbrProvTable 1 }

MscAtmIfIispEbrProvEntry ::= SEQUENCE {
   mscAtmIfIispEbrConnectionRecovery
      OCTET STRING,
   mscAtmIfIispEbrPathOptimization
      OCTET STRING }

mscAtmIfIispEbrConnectionRecovery OBJECT-TYPE
   SYNTAX     OCTET STRING (SIZE (1))
   ACCESS     read-write
   STATUS     mandatory
   DESCRIPTION
     "This attribute specifies the subscription of connections to hard 
      rerouting.
      dynamic: Connections that are transiting through this interface.
      provisioned: SPVC and SPVP connections that are provisioned at 
      this interface.

      Description of bits:
      dynamic(0)
      provisioned(1)"
   DEFVAL     { 'c0'H }
::= { mscAtmIfIispEbrProvEntry 1 }

mscAtmIfIispEbrPathOptimization OBJECT-TYPE
   SYNTAX     OCTET STRING (SIZE (1))
   ACCESS     read-write
   STATUS     mandatory
   DESCRIPTION
     "This attribute specifies the subscription of connections to soft 
      rerouting.
      dynamic: Connections that are transiting through this interface.
      provisioned: SPVC and SPVP connections that are provisioned at 
      this interface.

      Description of bits:
      dynamic(0)
      provisioned(1)"
   DEFVAL     { 'c0'H }
::= { mscAtmIfIispEbrProvEntry 2 }

mscAtmIfIispEbrOperTable OBJECT-TYPE
   SYNTAX     SEQUENCE OF MscAtmIfIispEbrOperEntry
   ACCESS     not-accessible
   STATUS     mandatory
   DESCRIPTION
     "This group contains the operational attributes that indicate the 
      rerouting activities for an ATM Signaling interface."
::= { mscAtmIfIispEbr 30 }

mscAtmIfIispEbrOperEntry OBJECT-TYPE
   SYNTAX     MscAtmIfIispEbrOperEntry
   ACCESS     not-accessible
   STATUS     mandatory
   DESCRIPTION
     "An entry in the mscAtmIfIispEbrOperTable."
   INDEX {
      mscAtmIfIndex,
      mscAtmIfIispIndex,
      mscAtmIfIispEbrIndex }
::= { mscAtmIfIispEbrOperTable 1 }

MscAtmIfIispEbrOperEntry ::= SEQUENCE {
   mscAtmIfIispEbrSubscribedConnections
      Gauge32,
   mscAtmIfIispEbrEligibleRecoveredConnections
      Gauge32,
   mscAtmIfIispEbrIneligibleRecoveredConnections
      Gauge32 }

mscAtmIfIispEbrSubscribedConnections OBJECT-TYPE
   SYNTAX     Gauge32 (0..4294967295)
   ACCESS     read-only
   STATUS     mandatory
   DESCRIPTION
     "This attribute indicates the number of connections subscribed to 
      rerouting capabilities."
::= { mscAtmIfIispEbrOperEntry 1 }

mscAtmIfIispEbrEligibleRecoveredConnections OBJECT-TYPE
   SYNTAX     Gauge32 (0..4294967295)
   ACCESS     read-only
   STATUS     mandatory
   DESCRIPTION
     "This attribute indicates the number of connections that have been 
      recovered and are eligible for path optimization. The count is reset 
      to zero when the Optimize command is executed on this component."
::= { mscAtmIfIispEbrOperEntry 2 }

mscAtmIfIispEbrIneligibleRecoveredConnections OBJECT-TYPE
   SYNTAX     Gauge32 (0..4294967295)
   ACCESS     read-only
   STATUS     mandatory
   DESCRIPTION
     "This attribute indicates the number of connections that have been 
      recovered but are not eligible for path optimization. The value 
      decreases as counted connections are released. The count is not 
      reset by the Optimize command."
::= { mscAtmIfIispEbrOperEntry 3 }

mscAtmIfIispEbrStatsTable OBJECT-TYPE
   SYNTAX     SEQUENCE OF MscAtmIfIispEbrStatsEntry
   ACCESS     not-accessible
   STATUS     mandatory
   DESCRIPTION
     "This group contains the statistics related to Edge Based Rerouting."
::= { mscAtmIfIispEbr 40 }

mscAtmIfIispEbrStatsEntry OBJECT-TYPE
   SYNTAX     MscAtmIfIispEbrStatsEntry
   ACCESS     not-accessible
   STATUS     mandatory
   DESCRIPTION
     "An entry in the mscAtmIfIispEbrStatsTable."
   INDEX {
      mscAtmIfIndex,
      mscAtmIfIispIndex,
      mscAtmIfIispEbrIndex }
::= { mscAtmIfIispEbrStatsTable 1 }

MscAtmIfIispEbrStatsEntry ::= SEQUENCE {
   mscAtmIfIispEbrTotalConnectionRecoveries
      Counter32,
   mscAtmIfIispEbrTotalPathOptimizations
      Counter32 }

mscAtmIfIispEbrTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfIispEbrStatsEntry 1 }

mscAtmIfIispEbrTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfIispEbrStatsEntry 2 }


-- AtmIf/n Iisp EdgeBasedRerouting
-- AtmIf/n Uni EdgeBasedRerouting
-- AtmIf/n Pnni EdgeBasedRerouting
-- AtmIf/n Vpt/vpi Iisp EdgeBasedRerouting
-- AtmIf/n Vpt/vpi Uni EdgeBasedRerouting
-- AtmIf/n Vpt/vpi Pnni EdgeBasedRerouting
-- 
-- This component represents the Edge Based Rerouting capabilities 
-- of the ATM Signaling interface. If this component is provisioned, 
-- the Artg Pnni component must already exist. The addition or 
-- deletion of this component, or changes to the provisioned 
-- subscription options, does not affect existing connections.

mscAtmIfVptIispEbr OBJECT IDENTIFIER ::= { mscAtmIfVptIisp 7 }



mscAtmIfVptIispEbrRowStatusTable OBJECT-TYPE
   SYNTAX     SEQUENCE OF MscAtmIfVptIispEbrRowStatusEntry
   ACCESS     not-accessible
   STATUS     mandatory
   DESCRIPTION
     "This entry controls the addition and deletion of 
      mscAtmIfVptIispEbr components."
::= { mscAtmIfVptIispEbr 1 }

mscAtmIfVptIispEbrRowStatusEntry OBJECT-TYPE
   SYNTAX     MscAtmIfVptIispEbrRowStatusEntry
   ACCESS     not-accessible
   STATUS     mandatory
   DESCRIPTION
     "A single entry in the table represents a single 
      mscAtmIfVptIispEbr component."
   INDEX {
      mscAtmIfIndex,
      mscAtmIfVptIndex,
      mscAtmIfVptIispIndex,
      mscAtmIfVptIispEbrIndex }
::= { mscAtmIfVptIispEbrRowStatusTable 1 }

MscAtmIfVptIispEbrRowStatusEntry ::= SEQUENCE {
   mscAtmIfVptIispEbrRowStatus
      RowStatus,
   mscAtmIfVptIispEbrComponentName
      DisplayString,
   mscAtmIfVptIispEbrStorageType
      StorageType,
   mscAtmIfVptIispEbrIndex
      NonReplicated }

mscAtmIfVptIispEbrRowStatus OBJECT-TYPE
   SYNTAX     RowStatus 
   ACCESS     read-write
   STATUS     mandatory
   DESCRIPTION
     "This variable is used as the basis for SNMP naming of
      mscAtmIfVptIispEbr components.
      These components can be added and deleted."
::= { mscAtmIfVptIispEbrRowStatusEntry 1 }

mscAtmIfVptIispEbrComponentName OBJECT-TYPE
   SYNTAX     DisplayString 
   ACCESS     read-only
   STATUS     mandatory
   DESCRIPTION
     "This variable provides the component's string name for
      use with the ASCII Console Interface"
::= { mscAtmIfVptIispEbrRowStatusEntry 2 }

mscAtmIfVptIispEbrStorageType OBJECT-TYPE
   SYNTAX     StorageType 
   ACCESS     read-only
   STATUS     mandatory
   DESCRIPTION
     "This variable represents the storage type value for the
      mscAtmIfVptIispEbr tables."
::= { mscAtmIfVptIispEbrRowStatusEntry 4 }

mscAtmIfVptIispEbrIndex OBJECT-TYPE
   SYNTAX     NonReplicated 
   ACCESS     not-accessible
   STATUS     mandatory
   DESCRIPTION
     "This variable represents the index for the mscAtmIfVptIispEbr tables."
::= { mscAtmIfVptIispEbrRowStatusEntry 10 }

mscAtmIfVptIispEbrProvTable OBJECT-TYPE
   SYNTAX     SEQUENCE OF MscAtmIfVptIispEbrProvEntry
   ACCESS     not-accessible
   STATUS     mandatory
   DESCRIPTION
     "This group contains the provisionable attributes for Edge Based 
      Rerouting at the ATM Signaling interface."
::= { mscAtmIfVptIispEbr 20 }

mscAtmIfVptIispEbrProvEntry OBJECT-TYPE
   SYNTAX     MscAtmIfVptIispEbrProvEntry
   ACCESS     not-accessible
   STATUS     mandatory
   DESCRIPTION
     "An entry in the mscAtmIfVptIispEbrProvTable."
   INDEX {
      mscAtmIfIndex,
      mscAtmIfVptIndex,
      mscAtmIfVptIispIndex,
      mscAtmIfVptIispEbrIndex }
::= { mscAtmIfVptIispEbrProvTable 1 }

MscAtmIfVptIispEbrProvEntry ::= SEQUENCE {
   mscAtmIfVptIispEbrConnectionRecovery
      OCTET STRING,
   mscAtmIfVptIispEbrPathOptimization
      OCTET STRING }

mscAtmIfVptIispEbrConnectionRecovery OBJECT-TYPE
   SYNTAX     OCTET STRING (SIZE (1))
   ACCESS     read-write
   STATUS     mandatory
   DESCRIPTION
     "This attribute specifies the subscription of connections to hard 
      rerouting.
      dynamic: Connections that are transiting through this interface.
      provisioned: SPVC and SPVP connections that are provisioned at 
      this interface.

      Description of bits:
      dynamic(0)
      provisioned(1)"
   DEFVAL     { 'c0'H }
::= { mscAtmIfVptIispEbrProvEntry 1 }

mscAtmIfVptIispEbrPathOptimization OBJECT-TYPE
   SYNTAX     OCTET STRING (SIZE (1))
   ACCESS     read-write
   STATUS     mandatory
   DESCRIPTION
     "This attribute specifies the subscription of connections to soft 
      rerouting.
      dynamic: Connections that are transiting through this interface.
      provisioned: SPVC and SPVP connections that are provisioned at 
      this interface.

      Description of bits:
      dynamic(0)
      provisioned(1)"
   DEFVAL     { 'c0'H }
::= { mscAtmIfVptIispEbrProvEntry 2 }

mscAtmIfVptIispEbrOperTable OBJECT-TYPE
   SYNTAX     SEQUENCE OF MscAtmIfVptIispEbrOperEntry
   ACCESS     not-accessible
   STATUS     mandatory
   DESCRIPTION
     "This group contains the operational attributes that indicate the 
      rerouting activities for an ATM Signaling interface."
::= { mscAtmIfVptIispEbr 30 }

mscAtmIfVptIispEbrOperEntry OBJECT-TYPE
   SYNTAX     MscAtmIfVptIispEbrOperEntry
   ACCESS     not-accessible
   STATUS     mandatory
   DESCRIPTION
     "An entry in the mscAtmIfVptIispEbrOperTable."
   INDEX {
      mscAtmIfIndex,
      mscAtmIfVptIndex,
      mscAtmIfVptIispIndex,
      mscAtmIfVptIispEbrIndex }
::= { mscAtmIfVptIispEbrOperTable 1 }

MscAtmIfVptIispEbrOperEntry ::= SEQUENCE {
   mscAtmIfVptIispEbrSubscribedConnections
      Gauge32,
   mscAtmIfVptIispEbrEligibleRecoveredConnections
      Gauge32,
   mscAtmIfVptIispEbrIneligibleRecoveredConnections
      Gauge32 }

mscAtmIfVptIispEbrSubscribedConnections OBJECT-TYPE
   SYNTAX     Gauge32 (0..4294967295)
   ACCESS     read-only
   STATUS     mandatory
   DESCRIPTION
     "This attribute indicates the number of connections subscribed to 
      rerouting capabilities."
::= { mscAtmIfVptIispEbrOperEntry 1 }

mscAtmIfVptIispEbrEligibleRecoveredConnections OBJECT-TYPE
   SYNTAX     Gauge32 (0..4294967295)
   ACCESS     read-only
   STATUS     mandatory
   DESCRIPTION
     "This attribute indicates the number of connections that have been 
      recovered and are eligible for path optimization. The count is reset 
      to zero when the Optimize command is executed on this component."
::= { mscAtmIfVptIispEbrOperEntry 2 }

mscAtmIfVptIispEbrIneligibleRecoveredConnections OBJECT-TYPE
   SYNTAX     Gauge32 (0..4294967295)
   ACCESS     read-only
   STATUS     mandatory
   DESCRIPTION
     "This attribute indicates the number of connections that have been 
      recovered but are not eligible for path optimization. The value 
      decreases as counted connections are released. The count is not 
      reset by the Optimize command."
::= { mscAtmIfVptIispEbrOperEntry 3 }

mscAtmIfVptIispEbrStatsTable OBJECT-TYPE
   SYNTAX     SEQUENCE OF MscAtmIfVptIispEbrStatsEntry
   ACCESS     not-accessible
   STATUS     mandatory
   DESCRIPTION
     "This group contains the statistics related to Edge Based Rerouting."
::= { mscAtmIfVptIispEbr 40 }

mscAtmIfVptIispEbrStatsEntry OBJECT-TYPE
   SYNTAX     MscAtmIfVptIispEbrStatsEntry
   ACCESS     not-accessible
   STATUS     mandatory
   DESCRIPTION
     "An entry in the mscAtmIfVptIispEbrStatsTable."
   INDEX {
      mscAtmIfIndex,
      mscAtmIfVptIndex,
      mscAtmIfVptIispIndex,
      mscAtmIfVptIispEbrIndex }
::= { mscAtmIfVptIispEbrStatsTable 1 }

MscAtmIfVptIispEbrStatsEntry ::= SEQUENCE {
   mscAtmIfVptIispEbrTotalConnectionRecoveries
      Counter32,
   mscAtmIfVptIispEbrTotalPathOptimizations
      Counter32 }

mscAtmIfVptIispEbrTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfVptIispEbrStatsEntry 1 }

mscAtmIfVptIispEbrTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfVptIispEbrStatsEntry 2 }


-- AtmIf/n Iisp EdgeBasedRerouting
-- AtmIf/n Uni EdgeBasedRerouting
-- AtmIf/n Pnni EdgeBasedRerouting
-- AtmIf/n Vpt/vpi Iisp EdgeBasedRerouting
-- AtmIf/n Vpt/vpi Uni EdgeBasedRerouting
-- AtmIf/n Vpt/vpi Pnni EdgeBasedRerouting
-- 
-- This component represents the Edge Based Rerouting capabilities 
-- of the ATM Signaling interface. If this component is provisioned, 
-- the Artg Pnni component must already exist. The addition or 
-- deletion of this component, or changes to the provisioned 
-- subscription options, does not affect existing connections.

mscAtmIfVptPnniEbr OBJECT IDENTIFIER ::= { mscAtmIfVptPnni 7 }



mscAtmIfVptPnniEbrRowStatusTable OBJECT-TYPE
   SYNTAX     SEQUENCE OF MscAtmIfVptPnniEbrRowStatusEntry
   ACCESS     not-accessible
   STATUS     mandatory
   DESCRIPTION
     "This entry controls the addition and deletion of 
      mscAtmIfVptPnniEbr components."
::= { mscAtmIfVptPnniEbr 1 }

mscAtmIfVptPnniEbrRowStatusEntry OBJECT-TYPE
   SYNTAX     MscAtmIfVptPnniEbrRowStatusEntry
   ACCESS     not-accessible
   STATUS     mandatory
   DESCRIPTION
     "A single entry in the table represents a single 
      mscAtmIfVptPnniEbr component."
   INDEX {
      mscAtmIfIndex,
      mscAtmIfVptIndex,
      mscAtmIfVptPnniIndex,
      mscAtmIfVptPnniEbrIndex }
::= { mscAtmIfVptPnniEbrRowStatusTable 1 }

MscAtmIfVptPnniEbrRowStatusEntry ::= SEQUENCE {
   mscAtmIfVptPnniEbrRowStatus
      RowStatus,
   mscAtmIfVptPnniEbrComponentName
      DisplayString,
   mscAtmIfVptPnniEbrStorageType
      StorageType,
   mscAtmIfVptPnniEbrIndex
      NonReplicated }

mscAtmIfVptPnniEbrRowStatus OBJECT-TYPE
   SYNTAX     RowStatus 
   ACCESS     read-write
   STATUS     mandatory
   DESCRIPTION
     "This variable is used as the basis for SNMP naming of
      mscAtmIfVptPnniEbr components.
      These components can be added and deleted."
::= { mscAtmIfVptPnniEbrRowStatusEntry 1 }

mscAtmIfVptPnniEbrComponentName OBJECT-TYPE
   SYNTAX     DisplayString 
   ACCESS     read-only
   STATUS     mandatory
   DESCRIPTION
     "This variable provides the component's string name for
      use with the ASCII Console Interface"
::= { mscAtmIfVptPnniEbrRowStatusEntry 2 }

mscAtmIfVptPnniEbrStorageType OBJECT-TYPE
   SYNTAX     StorageType 
   ACCESS     read-only
   STATUS     mandatory
   DESCRIPTION
     "This variable represents the storage type value for the
      mscAtmIfVptPnniEbr tables."
::= { mscAtmIfVptPnniEbrRowStatusEntry 4 }

mscAtmIfVptPnniEbrIndex OBJECT-TYPE
   SYNTAX     NonReplicated 
   ACCESS     not-accessible
   STATUS     mandatory
   DESCRIPTION
     "This variable represents the index for the mscAtmIfVptPnniEbr tables."
::= { mscAtmIfVptPnniEbrRowStatusEntry 10 }

mscAtmIfVptPnniEbrProvTable OBJECT-TYPE
   SYNTAX     SEQUENCE OF MscAtmIfVptPnniEbrProvEntry
   ACCESS     not-accessible
   STATUS     mandatory
   DESCRIPTION
     "This group contains the provisionable attributes for Edge Based 
      Rerouting at the ATM Signaling interface."
::= { mscAtmIfVptPnniEbr 20 }

mscAtmIfVptPnniEbrProvEntry OBJECT-TYPE
   SYNTAX     MscAtmIfVptPnniEbrProvEntry
   ACCESS     not-accessible
   STATUS     mandatory
   DESCRIPTION
     "An entry in the mscAtmIfVptPnniEbrProvTable."
   INDEX {
      mscAtmIfIndex,
      mscAtmIfVptIndex,
      mscAtmIfVptPnniIndex,
      mscAtmIfVptPnniEbrIndex }
::= { mscAtmIfVptPnniEbrProvTable 1 }

MscAtmIfVptPnniEbrProvEntry ::= SEQUENCE {
   mscAtmIfVptPnniEbrConnectionRecovery
      OCTET STRING,
   mscAtmIfVptPnniEbrPathOptimization
      OCTET STRING }

mscAtmIfVptPnniEbrConnectionRecovery OBJECT-TYPE
   SYNTAX     OCTET STRING (SIZE (1))
   ACCESS     read-write
   STATUS     mandatory
   DESCRIPTION
     "This attribute specifies the subscription of connections to hard 
      rerouting.
      dynamic: Connections that are transiting through this interface.
      provisioned: SPVC and SPVP connections that are provisioned at 
      this interface.

      Description of bits:
      dynamic(0)
      provisioned(1)"
   DEFVAL     { 'c0'H }
::= { mscAtmIfVptPnniEbrProvEntry 1 }

mscAtmIfVptPnniEbrPathOptimization OBJECT-TYPE
   SYNTAX     OCTET STRING (SIZE (1))
   ACCESS     read-write
   STATUS     mandatory
   DESCRIPTION
     "This attribute specifies the subscription of connections to soft 
      rerouting.
      dynamic: Connections that are transiting through this interface.
      provisioned: SPVC and SPVP connections that are provisioned at 
      this interface.

      Description of bits:
      dynamic(0)
      provisioned(1)"
   DEFVAL     { 'c0'H }
::= { mscAtmIfVptPnniEbrProvEntry 2 }

mscAtmIfVptPnniEbrOperTable OBJECT-TYPE
   SYNTAX     SEQUENCE OF MscAtmIfVptPnniEbrOperEntry
   ACCESS     not-accessible
   STATUS     mandatory
   DESCRIPTION
     "This group contains the operational attributes that indicate the 
      rerouting activities for an ATM Signaling interface."
::= { mscAtmIfVptPnniEbr 30 }

mscAtmIfVptPnniEbrOperEntry OBJECT-TYPE
   SYNTAX     MscAtmIfVptPnniEbrOperEntry
   ACCESS     not-accessible
   STATUS     mandatory
   DESCRIPTION
     "An entry in the mscAtmIfVptPnniEbrOperTable."
   INDEX {
      mscAtmIfIndex,
      mscAtmIfVptIndex,
      mscAtmIfVptPnniIndex,
      mscAtmIfVptPnniEbrIndex }
::= { mscAtmIfVptPnniEbrOperTable 1 }

MscAtmIfVptPnniEbrOperEntry ::= SEQUENCE {
   mscAtmIfVptPnniEbrSubscribedConnections
      Gauge32,
   mscAtmIfVptPnniEbrEligibleRecoveredConnections
      Gauge32,
   mscAtmIfVptPnniEbrIneligibleRecoveredConnections
      Gauge32 }

mscAtmIfVptPnniEbrSubscribedConnections OBJECT-TYPE
   SYNTAX     Gauge32 (0..4294967295)
   ACCESS     read-only
   STATUS     mandatory
   DESCRIPTION
     "This attribute indicates the number of connections subscribed to 
      rerouting capabilities."
::= { mscAtmIfVptPnniEbrOperEntry 1 }

mscAtmIfVptPnniEbrEligibleRecoveredConnections OBJECT-TYPE
   SYNTAX     Gauge32 (0..4294967295)
   ACCESS     read-only
   STATUS     mandatory
   DESCRIPTION
     "This attribute indicates the number of connections that have been 
      recovered and are eligible for path optimization. The count is reset 
      to zero when the Optimize command is executed on this component."
::= { mscAtmIfVptPnniEbrOperEntry 2 }

mscAtmIfVptPnniEbrIneligibleRecoveredConnections OBJECT-TYPE
   SYNTAX     Gauge32 (0..4294967295)
   ACCESS     read-only
   STATUS     mandatory
   DESCRIPTION
     "This attribute indicates the number of connections that have been 
      recovered but are not eligible for path optimization. The value 
      decreases as counted connections are released. The count is not 
      reset by the Optimize command."
::= { mscAtmIfVptPnniEbrOperEntry 3 }

mscAtmIfVptPnniEbrStatsTable OBJECT-TYPE
   SYNTAX     SEQUENCE OF MscAtmIfVptPnniEbrStatsEntry
   ACCESS     not-accessible
   STATUS     mandatory
   DESCRIPTION
     "This group contains the statistics related to Edge Based Rerouting."
::= { mscAtmIfVptPnniEbr 40 }

mscAtmIfVptPnniEbrStatsEntry OBJECT-TYPE
   SYNTAX     MscAtmIfVptPnniEbrStatsEntry
   ACCESS     not-accessible
   STATUS     mandatory
   DESCRIPTION
     "An entry in the mscAtmIfVptPnniEbrStatsTable."
   INDEX {
      mscAtmIfIndex,
      mscAtmIfVptIndex,
      mscAtmIfVptPnniIndex,
      mscAtmIfVptPnniEbrIndex }
::= { mscAtmIfVptPnniEbrStatsTable 1 }

MscAtmIfVptPnniEbrStatsEntry ::= SEQUENCE {
   mscAtmIfVptPnniEbrTotalConnectionRecoveries
      Counter32,
   mscAtmIfVptPnniEbrTotalPathOptimizations
      Counter32 }

mscAtmIfVptPnniEbrTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfVptPnniEbrStatsEntry 1 }

mscAtmIfVptPnniEbrTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfVptPnniEbrStatsEntry 2 }


-- AtmIf/n Iisp EdgeBasedRerouting
-- AtmIf/n Uni EdgeBasedRerouting
-- AtmIf/n Pnni EdgeBasedRerouting
-- AtmIf/n Vpt/vpi Iisp EdgeBasedRerouting
-- AtmIf/n Vpt/vpi Uni EdgeBasedRerouting
-- AtmIf/n Vpt/vpi Pnni EdgeBasedRerouting
-- 
-- This component represents the Edge Based Rerouting capabilities 
-- of the ATM Signaling interface. If this component is provisioned, 
-- the Artg Pnni component must already exist. The addition or 
-- deletion of this component, or changes to the provisioned 
-- subscription options, does not affect existing connections.

mscAtmIfVptUniEbr OBJECT IDENTIFIER ::= { mscAtmIfVptUni 7 }



mscAtmIfVptUniEbrRowStatusTable OBJECT-TYPE
   SYNTAX     SEQUENCE OF MscAtmIfVptUniEbrRowStatusEntry
   ACCESS     not-accessible
   STATUS     mandatory
   DESCRIPTION
     "This entry controls the addition and deletion of 
      mscAtmIfVptUniEbr components."
::= { mscAtmIfVptUniEbr 1 }

mscAtmIfVptUniEbrRowStatusEntry OBJECT-TYPE
   SYNTAX     MscAtmIfVptUniEbrRowStatusEntry
   ACCESS     not-accessible
   STATUS     mandatory
   DESCRIPTION
     "A single entry in the table represents a single 
      mscAtmIfVptUniEbr component."
   INDEX {
      mscAtmIfIndex,
      mscAtmIfVptIndex,
      mscAtmIfVptUniIndex,
      mscAtmIfVptUniEbrIndex }
::= { mscAtmIfVptUniEbrRowStatusTable 1 }

MscAtmIfVptUniEbrRowStatusEntry ::= SEQUENCE {
   mscAtmIfVptUniEbrRowStatus
      RowStatus,
   mscAtmIfVptUniEbrComponentName
      DisplayString,
   mscAtmIfVptUniEbrStorageType
      StorageType,
   mscAtmIfVptUniEbrIndex
      NonReplicated }

mscAtmIfVptUniEbrRowStatus OBJECT-TYPE
   SYNTAX     RowStatus 
   ACCESS     read-write
   STATUS     mandatory
   DESCRIPTION
     "This variable is used as the basis for SNMP naming of
      mscAtmIfVptUniEbr components.
      These components can be added and deleted."
::= { mscAtmIfVptUniEbrRowStatusEntry 1 }

mscAtmIfVptUniEbrComponentName OBJECT-TYPE
   SYNTAX     DisplayString 
   ACCESS     read-only
   STATUS     mandatory
   DESCRIPTION
     "This variable provides the component's string name for
      use with the ASCII Console Interface"
::= { mscAtmIfVptUniEbrRowStatusEntry 2 }

mscAtmIfVptUniEbrStorageType OBJECT-TYPE
   SYNTAX     StorageType 
   ACCESS     read-only
   STATUS     mandatory
   DESCRIPTION
     "This variable represents the storage type value for the
      mscAtmIfVptUniEbr tables."
::= { mscAtmIfVptUniEbrRowStatusEntry 4 }

mscAtmIfVptUniEbrIndex OBJECT-TYPE
   SYNTAX     NonReplicated 
   ACCESS     not-accessible
   STATUS     mandatory
   DESCRIPTION
     "This variable represents the index for the mscAtmIfVptUniEbr tables."
::= { mscAtmIfVptUniEbrRowStatusEntry 10 }

mscAtmIfVptUniEbrProvTable OBJECT-TYPE
   SYNTAX     SEQUENCE OF MscAtmIfVptUniEbrProvEntry
   ACCESS     not-accessible
   STATUS     mandatory
   DESCRIPTION
     "This group contains the provisionable attributes for Edge Based 
      Rerouting at the ATM Signaling interface."
::= { mscAtmIfVptUniEbr 20 }

mscAtmIfVptUniEbrProvEntry OBJECT-TYPE
   SYNTAX     MscAtmIfVptUniEbrProvEntry
   ACCESS     not-accessible
   STATUS     mandatory
   DESCRIPTION
     "An entry in the mscAtmIfVptUniEbrProvTable."
   INDEX {
      mscAtmIfIndex,
      mscAtmIfVptIndex,
      mscAtmIfVptUniIndex,
      mscAtmIfVptUniEbrIndex }
::= { mscAtmIfVptUniEbrProvTable 1 }

MscAtmIfVptUniEbrProvEntry ::= SEQUENCE {
   mscAtmIfVptUniEbrConnectionRecovery
      OCTET STRING,
   mscAtmIfVptUniEbrPathOptimization
      OCTET STRING }

mscAtmIfVptUniEbrConnectionRecovery OBJECT-TYPE
   SYNTAX     OCTET STRING (SIZE (1))
   ACCESS     read-write
   STATUS     mandatory
   DESCRIPTION
     "This attribute specifies the subscription of connections to hard 
      rerouting.
      dynamic: Connections that are transiting through this interface.
      provisioned: SPVC and SPVP connections that are provisioned at 
      this interface.

      Description of bits:
      dynamic(0)
      provisioned(1)"
   DEFVAL     { 'c0'H }
::= { mscAtmIfVptUniEbrProvEntry 1 }

mscAtmIfVptUniEbrPathOptimization OBJECT-TYPE
   SYNTAX     OCTET STRING (SIZE (1))
   ACCESS     read-write
   STATUS     mandatory
   DESCRIPTION
     "This attribute specifies the subscription of connections to soft 
      rerouting.
      dynamic: Connections that are transiting through this interface.
      provisioned: SPVC and SPVP connections that are provisioned at 
      this interface.

      Description of bits:
      dynamic(0)
      provisioned(1)"
   DEFVAL     { 'c0'H }
::= { mscAtmIfVptUniEbrProvEntry 2 }

mscAtmIfVptUniEbrOperTable OBJECT-TYPE
   SYNTAX     SEQUENCE OF MscAtmIfVptUniEbrOperEntry
   ACCESS     not-accessible
   STATUS     mandatory
   DESCRIPTION
     "This group contains the operational attributes that indicate the 
      rerouting activities for an ATM Signaling interface."
::= { mscAtmIfVptUniEbr 30 }

mscAtmIfVptUniEbrOperEntry OBJECT-TYPE
   SYNTAX     MscAtmIfVptUniEbrOperEntry
   ACCESS     not-accessible
   STATUS     mandatory
   DESCRIPTION
     "An entry in the mscAtmIfVptUniEbrOperTable."
   INDEX {
      mscAtmIfIndex,
      mscAtmIfVptIndex,
      mscAtmIfVptUniIndex,
      mscAtmIfVptUniEbrIndex }
::= { mscAtmIfVptUniEbrOperTable 1 }

MscAtmIfVptUniEbrOperEntry ::= SEQUENCE {
   mscAtmIfVptUniEbrSubscribedConnections
      Gauge32,
   mscAtmIfVptUniEbrEligibleRecoveredConnections
      Gauge32,
   mscAtmIfVptUniEbrIneligibleRecoveredConnections
      Gauge32 }

mscAtmIfVptUniEbrSubscribedConnections OBJECT-TYPE
   SYNTAX     Gauge32 (0..4294967295)
   ACCESS     read-only
   STATUS     mandatory
   DESCRIPTION
     "This attribute indicates the number of connections subscribed to 
      rerouting capabilities."
::= { mscAtmIfVptUniEbrOperEntry 1 }

mscAtmIfVptUniEbrEligibleRecoveredConnections OBJECT-TYPE
   SYNTAX     Gauge32 (0..4294967295)
   ACCESS     read-only
   STATUS     mandatory
   DESCRIPTION
     "This attribute indicates the number of connections that have been 
      recovered and are eligible for path optimization. The count is reset 
      to zero when the Optimize command is executed on this component."
::= { mscAtmIfVptUniEbrOperEntry 2 }

mscAtmIfVptUniEbrIneligibleRecoveredConnections OBJECT-TYPE
   SYNTAX     Gauge32 (0..4294967295)
   ACCESS     read-only
   STATUS     mandatory
   DESCRIPTION
     "This attribute indicates the number of connections that have been 
      recovered but are not eligible for path optimization. The value 
      decreases as counted connections are released. The count is not 
      reset by the Optimize command."
::= { mscAtmIfVptUniEbrOperEntry 3 }

mscAtmIfVptUniEbrStatsTable OBJECT-TYPE
   SYNTAX     SEQUENCE OF MscAtmIfVptUniEbrStatsEntry
   ACCESS     not-accessible
   STATUS     mandatory
   DESCRIPTION
     "This group contains the statistics related to Edge Based Rerouting."
::= { mscAtmIfVptUniEbr 40 }

mscAtmIfVptUniEbrStatsEntry OBJECT-TYPE
   SYNTAX     MscAtmIfVptUniEbrStatsEntry
   ACCESS     not-accessible
   STATUS     mandatory
   DESCRIPTION
     "An entry in the mscAtmIfVptUniEbrStatsTable."
   INDEX {
      mscAtmIfIndex,
      mscAtmIfVptIndex,
      mscAtmIfVptUniIndex,
      mscAtmIfVptUniEbrIndex }
::= { mscAtmIfVptUniEbrStatsTable 1 }

MscAtmIfVptUniEbrStatsEntry ::= SEQUENCE {
   mscAtmIfVptUniEbrTotalConnectionRecoveries
      Counter32,
   mscAtmIfVptUniEbrTotalPathOptimizations
      Counter32 }

mscAtmIfVptUniEbrTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfVptUniEbrStatsEntry 1 }

mscAtmIfVptUniEbrTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfVptUniEbrStatsEntry 2 }


-- AtmIf/n Vcc/vpi.vci SrcPvc EdgeBasedReroutingOverride
-- AtmIf/n Vpc/vpi SrcPvp EdgeBasedReroutingOverride
-- AtmIf/n Vpt/vpi Vcc/vci SrcPvc EdgeBasedReroutingOverride
-- 
-- This component represents the ability to override Edge Based 
-- Rerouting capabilities on a per connection basis for provisioned 
-- SPVC and SPVP connections. 
-- 
-- The addition of this component and changes to the attributes 
-- contained in this component are critical to the parent SPVC or 
-- SPVP. The deletion of this component is not a critical change for 
-- the connection. If this component is deleted, the connection remains 
-- active with the current subscription options until it restages.

mscAtmIfVptVccSrcEbrOv OBJECT IDENTIFIER ::= { mscAtmIfVptVccSrc 2 }



mscAtmIfVptVccSrcEbrOvRowStatusTable OBJECT-TYPE
   SYNTAX     SEQUENCE OF MscAtmIfVptVccSrcEbrOvRowStatusEntry
   ACCESS     not-accessible
   STATUS     mandatory
   DESCRIPTION
     "This entry controls the addition and deletion of 
      mscAtmIfVptVccSrcEbrOv components."
::= { mscAtmIfVptVccSrcEbrOv 1 }

mscAtmIfVptVccSrcEbrOvRowStatusEntry OBJECT-TYPE
   SYNTAX     MscAtmIfVptVccSrcEbrOvRowStatusEntry
   ACCESS     not-accessible
   STATUS     mandatory
   DESCRIPTION
     "A single entry in the table represents a single 
      mscAtmIfVptVccSrcEbrOv component."
   INDEX {
      mscAtmIfIndex,
      mscAtmIfVptIndex,
      mscAtmIfVptVccIndex,
      mscAtmIfVptVccSrcIndex,
      mscAtmIfVptVccSrcEbrOvIndex }
::= { mscAtmIfVptVccSrcEbrOvRowStatusTable 1 }

MscAtmIfVptVccSrcEbrOvRowStatusEntry ::= SEQUENCE {
   mscAtmIfVptVccSrcEbrOvRowStatus
      RowStatus,
   mscAtmIfVptVccSrcEbrOvComponentName
      DisplayString,
   mscAtmIfVptVccSrcEbrOvStorageType
      StorageType,
   mscAtmIfVptVccSrcEbrOvIndex
      NonReplicated }

mscAtmIfVptVccSrcEbrOvRowStatus OBJECT-TYPE
   SYNTAX     RowStatus 
   ACCESS     read-write
   STATUS     mandatory
   DESCRIPTION
     "This variable is used as the basis for SNMP naming of
      mscAtmIfVptVccSrcEbrOv components.
      These components can be added and deleted."
::= { mscAtmIfVptVccSrcEbrOvRowStatusEntry 1 }

mscAtmIfVptVccSrcEbrOvComponentName OBJECT-TYPE
   SYNTAX     DisplayString 
   ACCESS     read-only
   STATUS     mandatory
   DESCRIPTION
     "This variable provides the component's string name for
      use with the ASCII Console Interface"
::= { mscAtmIfVptVccSrcEbrOvRowStatusEntry 2 }

mscAtmIfVptVccSrcEbrOvStorageType OBJECT-TYPE
   SYNTAX     StorageType 
   ACCESS     read-only
   STATUS     mandatory
   DESCRIPTION
     "This variable represents the storage type value for the
      mscAtmIfVptVccSrcEbrOv tables."
::= { mscAtmIfVptVccSrcEbrOvRowStatusEntry 4 }

mscAtmIfVptVccSrcEbrOvIndex OBJECT-TYPE
   SYNTAX     NonReplicated 
   ACCESS     not-accessible
   STATUS     mandatory
   DESCRIPTION
     "This variable represents the index for the mscAtmIfVptVccSrcEbrOv tables."
::= { mscAtmIfVptVccSrcEbrOvRowStatusEntry 10 }

mscAtmIfVptVccSrcEbrOvProvTable OBJECT-TYPE
   SYNTAX     SEQUENCE OF MscAtmIfVptVccSrcEbrOvProvEntry
   ACCESS     not-accessible
   STATUS     mandatory
   DESCRIPTION
     "This group contains the provisionable attributes for the Edge Based 
      Rerouting subscription options for provisioned connections."
::= { mscAtmIfVptVccSrcEbrOv 20 }

mscAtmIfVptVccSrcEbrOvProvEntry OBJECT-TYPE
   SYNTAX     MscAtmIfVptVccSrcEbrOvProvEntry
   ACCESS     not-accessible
   STATUS     mandatory
   DESCRIPTION
     "An entry in the mscAtmIfVptVccSrcEbrOvProvTable."
   INDEX {
      mscAtmIfIndex,
      mscAtmIfVptIndex,
      mscAtmIfVptVccIndex,
      mscAtmIfVptVccSrcIndex,
      mscAtmIfVptVccSrcEbrOvIndex }
::= { mscAtmIfVptVccSrcEbrOvProvTable 1 }

MscAtmIfVptVccSrcEbrOvProvEntry ::= SEQUENCE {
   mscAtmIfVptVccSrcEbrOvRecoverySubscribed
      INTEGER,
   mscAtmIfVptVccSrcEbrOvOptimizationSubscribed
      INTEGER }

mscAtmIfVptVccSrcEbrOvRecoverySubscribed OBJECT-TYPE
   SYNTAX     INTEGER  {
                 no(0),
                 yes(1) }
   ACCESS     read-write
   STATUS     mandatory
   DESCRIPTION
     "This attributes specifies whether connection recovery is subscribed 
      for this connection."
   DEFVAL     { yes }
::= { mscAtmIfVptVccSrcEbrOvProvEntry 1 }

mscAtmIfVptVccSrcEbrOvOptimizationSubscribed OBJECT-TYPE
   SYNTAX     INTEGER  {
                 no(0),
                 yes(1) }
   ACCESS     read-write
   STATUS     mandatory
   DESCRIPTION
     "This attributes specifies whether path optimization is subscribed for 
      this connection."
   DEFVAL     { yes }
::= { mscAtmIfVptVccSrcEbrOvProvEntry 2 }


-- AtmIf/n Vcc/vpi.vci EdgeBasedReroutingInformation
-- AtmIf/n Vpc/vpi EdgeBasedReroutingInformation
-- AtmIf/n Vpt/vpi Vcc/vci EdgeBasedReroutingInformation
-- 
-- This component represents the Edge Based Rerouting capabilities 
-- of a connection.

mscAtmIfVptVccEbrInfo OBJECT IDENTIFIER ::= { mscAtmIfVptVcc 12 }



mscAtmIfVptVccEbrInfoRowStatusTable OBJECT-TYPE
   SYNTAX     SEQUENCE OF MscAtmIfVptVccEbrInfoRowStatusEntry
   ACCESS     not-accessible
   STATUS     mandatory
   DESCRIPTION
     "This entry controls the addition and deletion of 
      mscAtmIfVptVccEbrInfo components."
::= { mscAtmIfVptVccEbrInfo 1 }

mscAtmIfVptVccEbrInfoRowStatusEntry OBJECT-TYPE
   SYNTAX     MscAtmIfVptVccEbrInfoRowStatusEntry
   ACCESS     not-accessible
   STATUS     mandatory
   DESCRIPTION
     "A single entry in the table represents a single 
      mscAtmIfVptVccEbrInfo component."
   INDEX {
      mscAtmIfIndex,
      mscAtmIfVptIndex,
      mscAtmIfVptVccIndex,
      mscAtmIfVptVccEbrInfoIndex }
::= { mscAtmIfVptVccEbrInfoRowStatusTable 1 }

MscAtmIfVptVccEbrInfoRowStatusEntry ::= SEQUENCE {
   mscAtmIfVptVccEbrInfoRowStatus
      RowStatus,
   mscAtmIfVptVccEbrInfoComponentName
      DisplayString,
   mscAtmIfVptVccEbrInfoStorageType
      StorageType,
   mscAtmIfVptVccEbrInfoIndex
      NonReplicated }

mscAtmIfVptVccEbrInfoRowStatus OBJECT-TYPE
   SYNTAX     RowStatus 
   ACCESS     read-only
   STATUS     mandatory
   DESCRIPTION
     "This variable is used as the basis for SNMP naming of
      mscAtmIfVptVccEbrInfo components.
      These components cannot be added nor deleted."
::= { mscAtmIfVptVccEbrInfoRowStatusEntry 1 }

mscAtmIfVptVccEbrInfoComponentName OBJECT-TYPE
   SYNTAX     DisplayString 
   ACCESS     read-only
   STATUS     mandatory
   DESCRIPTION
     "This variable provides the component's string name for
      use with the ASCII Console Interface"
::= { mscAtmIfVptVccEbrInfoRowStatusEntry 2 }

mscAtmIfVptVccEbrInfoStorageType OBJECT-TYPE
   SYNTAX     StorageType 
   ACCESS     read-only
   STATUS     mandatory
   DESCRIPTION
     "This variable represents the storage type value for the
      mscAtmIfVptVccEbrInfo tables."
::= { mscAtmIfVptVccEbrInfoRowStatusEntry 4 }

mscAtmIfVptVccEbrInfoIndex OBJECT-TYPE
   SYNTAX     NonReplicated 
   ACCESS     not-accessible
   STATUS     mandatory
   DESCRIPTION
     "This variable represents the index for the mscAtmIfVptVccEbrInfo tables."
::= { mscAtmIfVptVccEbrInfoRowStatusEntry 10 }

mscAtmIfVptVccEbrInfoOperTable OBJECT-TYPE
   SYNTAX     SEQUENCE OF MscAtmIfVptVccEbrInfoOperEntry
   ACCESS     not-accessible
   STATUS     mandatory
   DESCRIPTION
     "This group contains the attributes that indicates the Edge Based 
      Rerouting characteristics of a connection."
::= { mscAtmIfVptVccEbrInfo 30 }

mscAtmIfVptVccEbrInfoOperEntry OBJECT-TYPE
   SYNTAX     MscAtmIfVptVccEbrInfoOperEntry
   ACCESS     not-accessible
   STATUS     mandatory
   DESCRIPTION
     "An entry in the mscAtmIfVptVccEbrInfoOperTable."
   INDEX {
      mscAtmIfIndex,
      mscAtmIfVptIndex,
      mscAtmIfVptVccIndex,
      mscAtmIfVptVccEbrInfoIndex }
::= { mscAtmIfVptVccEbrInfoOperTable 1 }

MscAtmIfVptVccEbrInfoOperEntry ::= SEQUENCE {
   mscAtmIfVptVccEbrInfoRecoverySubscribed
      INTEGER,
   mscAtmIfVptVccEbrInfoOptimizationSubscribed
      INTEGER,
   mscAtmIfVptVccEbrInfoConnectionRecovered
      INTEGER }

mscAtmIfVptVccEbrInfoRecoverySubscribed OBJECT-TYPE
   SYNTAX     INTEGER  {
                 no(0),
                 yes(1) }
   ACCESS     read-only
   STATUS     mandatory
   DESCRIPTION
     "This attribute indicates whether the connection is subscribed to 
      connection recovery."
::= { mscAtmIfVptVccEbrInfoOperEntry 1 }

mscAtmIfVptVccEbrInfoOptimizationSubscribed OBJECT-TYPE
   SYNTAX     INTEGER  {
                 no(0),
                 yes(1) }
   ACCESS     read-only
   STATUS     mandatory
   DESCRIPTION
     "This attribute indicates whether the connection is subscribed to path 
      optimization."
::= { mscAtmIfVptVccEbrInfoOperEntry 2 }

mscAtmIfVptVccEbrInfoConnectionRecovered OBJECT-TYPE
   SYNTAX     INTEGER  {
                 no(0),
                 yes(1) }
   ACCESS     read-only
   STATUS     mandatory
   DESCRIPTION
     "This attribute indicates whether the connection has been recovered 
      since the last optimization occurred. The value is reset to no by the 
      Optimize command."
::= { mscAtmIfVptVccEbrInfoOperEntry 3 }

mscAtmIfVptVccEbrInfoStatsTable OBJECT-TYPE
   SYNTAX     SEQUENCE OF MscAtmIfVptVccEbrInfoStatsEntry
   ACCESS     not-accessible
   STATUS     mandatory
   DESCRIPTION
     "This group contains the statistics related to Edge Based Rerouting."
::= { mscAtmIfVptVccEbrInfo 40 }

mscAtmIfVptVccEbrInfoStatsEntry OBJECT-TYPE
   SYNTAX     MscAtmIfVptVccEbrInfoStatsEntry
   ACCESS     not-accessible
   STATUS     mandatory
   DESCRIPTION
     "An entry in the mscAtmIfVptVccEbrInfoStatsTable."
   INDEX {
      mscAtmIfIndex,
      mscAtmIfVptIndex,
      mscAtmIfVptVccIndex,
      mscAtmIfVptVccEbrInfoIndex }
::= { mscAtmIfVptVccEbrInfoStatsTable 1 }

MscAtmIfVptVccEbrInfoStatsEntry ::= SEQUENCE {
   mscAtmIfVptVccEbrInfoTotalConnectionRecoveries
      Counter32,
   mscAtmIfVptVccEbrInfoTotalPathOptimizations
      Counter32 }

mscAtmIfVptVccEbrInfoTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfVptVccEbrInfoStatsEntry 1 }

mscAtmIfVptVccEbrInfoTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfVptVccEbrInfoStatsEntry 2 }


-- AtmIf/n Iisp EdgeBasedRerouting
-- AtmIf/n Uni EdgeBasedRerouting
-- AtmIf/n Pnni EdgeBasedRerouting
-- AtmIf/n Vpt/vpi Iisp EdgeBasedRerouting
-- AtmIf/n Vpt/vpi Uni EdgeBasedRerouting
-- AtmIf/n Vpt/vpi Pnni EdgeBasedRerouting
-- 
-- This component represents the Edge Based Rerouting capabilities 
-- of the ATM Signaling interface. If this component is provisioned, 
-- the Artg Pnni component must already exist. The addition or 
-- deletion of this component, or changes to the provisioned 
-- subscription options, does not affect existing connections.

mscAtmIfPnniEbr OBJECT IDENTIFIER ::= { mscAtmIfPnni 7 }



mscAtmIfPnniEbrRowStatusTable OBJECT-TYPE
   SYNTAX     SEQUENCE OF MscAtmIfPnniEbrRowStatusEntry
   ACCESS     not-accessible
   STATUS     mandatory
   DESCRIPTION
     "This entry controls the addition and deletion of 
      mscAtmIfPnniEbr components."
::= { mscAtmIfPnniEbr 1 }

mscAtmIfPnniEbrRowStatusEntry OBJECT-TYPE
   SYNTAX     MscAtmIfPnniEbrRowStatusEntry
   ACCESS     not-accessible
   STATUS     mandatory
   DESCRIPTION
     "A single entry in the table represents a single 
      mscAtmIfPnniEbr component."
   INDEX {
      mscAtmIfIndex,
      mscAtmIfPnniIndex,
      mscAtmIfPnniEbrIndex }
::= { mscAtmIfPnniEbrRowStatusTable 1 }

MscAtmIfPnniEbrRowStatusEntry ::= SEQUENCE {
   mscAtmIfPnniEbrRowStatus
      RowStatus,
   mscAtmIfPnniEbrComponentName
      DisplayString,
   mscAtmIfPnniEbrStorageType
      StorageType,
   mscAtmIfPnniEbrIndex
      NonReplicated }

mscAtmIfPnniEbrRowStatus OBJECT-TYPE
   SYNTAX     RowStatus 
   ACCESS     read-write
   STATUS     mandatory
   DESCRIPTION
     "This variable is used as the basis for SNMP naming of
      mscAtmIfPnniEbr components.
      These components can be added and deleted."
::= { mscAtmIfPnniEbrRowStatusEntry 1 }

mscAtmIfPnniEbrComponentName OBJECT-TYPE
   SYNTAX     DisplayString 
   ACCESS     read-only
   STATUS     mandatory
   DESCRIPTION
     "This variable provides the component's string name for
      use with the ASCII Console Interface"
::= { mscAtmIfPnniEbrRowStatusEntry 2 }

mscAtmIfPnniEbrStorageType OBJECT-TYPE
   SYNTAX     StorageType 
   ACCESS     read-only
   STATUS     mandatory
   DESCRIPTION
     "This variable represents the storage type value for the
      mscAtmIfPnniEbr tables."
::= { mscAtmIfPnniEbrRowStatusEntry 4 }

mscAtmIfPnniEbrIndex OBJECT-TYPE
   SYNTAX     NonReplicated 
   ACCESS     not-accessible
   STATUS     mandatory
   DESCRIPTION
     "This variable represents the index for the mscAtmIfPnniEbr tables."
::= { mscAtmIfPnniEbrRowStatusEntry 10 }

mscAtmIfPnniEbrProvTable OBJECT-TYPE
   SYNTAX     SEQUENCE OF MscAtmIfPnniEbrProvEntry
   ACCESS     not-accessible
   STATUS     mandatory
   DESCRIPTION
     "This group contains the provisionable attributes for Edge Based 
      Rerouting at the ATM Signaling interface."
::= { mscAtmIfPnniEbr 20 }

mscAtmIfPnniEbrProvEntry OBJECT-TYPE
   SYNTAX     MscAtmIfPnniEbrProvEntry
   ACCESS     not-accessible
   STATUS     mandatory
   DESCRIPTION
     "An entry in the mscAtmIfPnniEbrProvTable."
   INDEX {
      mscAtmIfIndex,
      mscAtmIfPnniIndex,
      mscAtmIfPnniEbrIndex }
::= { mscAtmIfPnniEbrProvTable 1 }

MscAtmIfPnniEbrProvEntry ::= SEQUENCE {
   mscAtmIfPnniEbrConnectionRecovery
      OCTET STRING,
   mscAtmIfPnniEbrPathOptimization
      OCTET STRING }

mscAtmIfPnniEbrConnectionRecovery OBJECT-TYPE
   SYNTAX     OCTET STRING (SIZE (1))
   ACCESS     read-write
   STATUS     mandatory
   DESCRIPTION
     "This attribute specifies the subscription of connections to hard 
      rerouting.
      dynamic: Connections that are transiting through this interface.
      provisioned: SPVC and SPVP connections that are provisioned at 
      this interface.

      Description of bits:
      dynamic(0)
      provisioned(1)"
   DEFVAL     { 'c0'H }
::= { mscAtmIfPnniEbrProvEntry 1 }

mscAtmIfPnniEbrPathOptimization OBJECT-TYPE
   SYNTAX     OCTET STRING (SIZE (1))
   ACCESS     read-write
   STATUS     mandatory
   DESCRIPTION
     "This attribute specifies the subscription of connections to soft 
      rerouting.
      dynamic: Connections that are transiting through this interface.
      provisioned: SPVC and SPVP connections that are provisioned at 
      this interface.

      Description of bits:
      dynamic(0)
      provisioned(1)"
   DEFVAL     { 'c0'H }
::= { mscAtmIfPnniEbrProvEntry 2 }

mscAtmIfPnniEbrOperTable OBJECT-TYPE
   SYNTAX     SEQUENCE OF MscAtmIfPnniEbrOperEntry
   ACCESS     not-accessible
   STATUS     mandatory
   DESCRIPTION
     "This group contains the operational attributes that indicate the 
      rerouting activities for an ATM Signaling interface."
::= { mscAtmIfPnniEbr 30 }

mscAtmIfPnniEbrOperEntry OBJECT-TYPE
   SYNTAX     MscAtmIfPnniEbrOperEntry
   ACCESS     not-accessible
   STATUS     mandatory
   DESCRIPTION
     "An entry in the mscAtmIfPnniEbrOperTable."
   INDEX {
      mscAtmIfIndex,
      mscAtmIfPnniIndex,
      mscAtmIfPnniEbrIndex }
::= { mscAtmIfPnniEbrOperTable 1 }

MscAtmIfPnniEbrOperEntry ::= SEQUENCE {
   mscAtmIfPnniEbrSubscribedConnections
      Gauge32,
   mscAtmIfPnniEbrEligibleRecoveredConnections
      Gauge32,
   mscAtmIfPnniEbrIneligibleRecoveredConnections
      Gauge32 }

mscAtmIfPnniEbrSubscribedConnections OBJECT-TYPE
   SYNTAX     Gauge32 (0..4294967295)
   ACCESS     read-only
   STATUS     mandatory
   DESCRIPTION
     "This attribute indicates the number of connections subscribed to 
      rerouting capabilities."
::= { mscAtmIfPnniEbrOperEntry 1 }

mscAtmIfPnniEbrEligibleRecoveredConnections OBJECT-TYPE
   SYNTAX     Gauge32 (0..4294967295)
   ACCESS     read-only
   STATUS     mandatory
   DESCRIPTION
     "This attribute indicates the number of connections that have been 
      recovered and are eligible for path optimization. The count is reset 
      to zero when the Optimize command is executed on this component."
::= { mscAtmIfPnniEbrOperEntry 2 }

mscAtmIfPnniEbrIneligibleRecoveredConnections OBJECT-TYPE
   SYNTAX     Gauge32 (0..4294967295)
   ACCESS     read-only
   STATUS     mandatory
   DESCRIPTION
     "This attribute indicates the number of connections that have been 
      recovered but are not eligible for path optimization. The value 
      decreases as counted connections are released. The count is not 
      reset by the Optimize command."
::= { mscAtmIfPnniEbrOperEntry 3 }

mscAtmIfPnniEbrStatsTable OBJECT-TYPE
   SYNTAX     SEQUENCE OF MscAtmIfPnniEbrStatsEntry
   ACCESS     not-accessible
   STATUS     mandatory
   DESCRIPTION
     "This group contains the statistics related to Edge Based Rerouting."
::= { mscAtmIfPnniEbr 40 }

mscAtmIfPnniEbrStatsEntry OBJECT-TYPE
   SYNTAX     MscAtmIfPnniEbrStatsEntry
   ACCESS     not-accessible
   STATUS     mandatory
   DESCRIPTION
     "An entry in the mscAtmIfPnniEbrStatsTable."
   INDEX {
      mscAtmIfIndex,
      mscAtmIfPnniIndex,
      mscAtmIfPnniEbrIndex }
::= { mscAtmIfPnniEbrStatsTable 1 }

MscAtmIfPnniEbrStatsEntry ::= SEQUENCE {
   mscAtmIfPnniEbrTotalConnectionRecoveries
      Counter32,
   mscAtmIfPnniEbrTotalPathOptimizations
      Counter32 }

mscAtmIfPnniEbrTotalConnectionRecoveries OBJECT-TYPE
   SYNTAX     Counter32 
   ACCESS     read-only
   STATUS     mandatory
   DESCRIPTION
     "This attribute counts connection recovery, or hard reroute, events 
      that occur. The counter wraps to 0 when the maximum value is 
      exceeded."
::= { mscAtmIfPnniEbrStatsEntry 1 }

mscAtmIfPnniEbrTotalPathOptimizations OBJECT-TYPE
   SYNTAX     Counter32 
   ACCESS     read-only
   STATUS     mandatory
   DESCRIPTION
     "This attributes counts path optimization, or soft reroute, events that 
      occur. The counter wraps to 0 when the maximum value is 
      exceeded."
::= { mscAtmIfPnniEbrStatsEntry 2 }




-- 
-- Version and Compliance statements
-- 



-- Object-Group Statement:
-- A list of all current accessible leaf objects.

-- OBJECTS { mscAtmIfVptVccSrcEbrOvRecoverySubscribed,
--           mscAtmIfVptPnniEbrStorageType,
--           mscAtmIfVptPnniEbrTotalConnectionRecoveries,
--           mscAtmIfVptVccEbrInfoRowStatus,
--           mscAtmIfIispEbrTotalPathOptimizations,
--           mscAtmIfVccSrcEbrOvRowStatus,
--           mscAtmIfPnniEbrIneligibleRecoveredConnections,
--           mscAtmIfVptUniEbrSubscribedConnections,
--           mscAtmIfVccEbrInfoConnectionRecovered,
--           mscAtmIfVptVccEbrInfoStorageType,
--           mscAtmIfVccSrcEbrOvRecoverySubscribed,
--           mscAtmIfVptPnniEbrRowStatus,
--           mscAtmIfVptVccEbrInfoTotalConnectionRecoveries,
--           mscAtmIfVpcSrcEbrOvRowStatus,
--           mscAtmIfVptVccSrcEbrOvComponentName,
--           mscAtmIfVptUniEbrIneligibleRecoveredConnections,
--           mscAtmIfVptUniEbrConnectionRecovery,
--           mscAtmIfVpcSrcEbrOvRecoverySubscribed,
--           mscAtmIfVccEbrInfoOptimizationSubscribed,
--           mscAtmIfIispEbrComponentName,
--           mscAtmIfVccEbrInfoStorageType,
--           mscAtmIfVptUniEbrTotalPathOptimizations,
--           mscAtmIfVptUniEbrStorageType,
--           mscAtmIfVptIispEbrConnectionRecovery,
--           mscAtmIfVccEbrInfoTotalConnectionRecoveries,
--           mscAtmIfVptIispEbrSubscribedConnections,
--           mscAtmIfVccSrcEbrOvComponentName,
--           mscAtmIfUniEbrIneligibleRecoveredConnections,
--           mscAtmIfUniEbrSubscribedConnections,
--           mscAtmIfVpcEbrInfoStorageType,
--           mscAtmIfVptUniEbrTotalConnectionRecoveries,
--           mscAtmIfVpcEbrInfoTotalConnectionRecoveries,
--           mscAtmIfVptIispEbrIneligibleRecoveredConnections,
--           mscAtmIfVpcSrcEbrOvComponentName,
--           mscAtmIfPnniEbrTotalPathOptimizations,
--           mscAtmIfIispEbrConnectionRecovery,
--           mscAtmIfVpcEbrInfoTotalPathOptimizations,
--           mscAtmIfIispEbrSubscribedConnections,
--           mscAtmIfUniEbrStorageType,
--           mscAtmIfVptVccSrcEbrOvStorageType,
--           mscAtmIfUniEbrTotalConnectionRecoveries,
--           mscAtmIfVptPnniEbrConnectionRecovery,
--           mscAtmIfVptIispEbrStorageType,
--           mscAtmIfIispEbrIneligibleRecoveredConnections,
--           mscAtmIfVptIispEbrTotalConnectionRecoveries,
--           mscAtmIfVccSrcEbrOvStorageType,
--           mscAtmIfVccEbrInfoRowStatus,
--           mscAtmIfVpcSrcEbrOvOptimizationSubscribed,
--           mscAtmIfPnniEbrSubscribedConnections,
--           mscAtmIfVptPnniEbrIneligibleRecoveredConnections,
--           mscAtmIfVccEbrInfoRecoverySubscribed,
--           mscAtmIfVptUniEbrRowStatus,
--           mscAtmIfVptPnniEbrTotalPathOptimizations,
--           mscAtmIfIispEbrStorageType,
--           mscAtmIfVpcEbrInfoRowStatus,
--           mscAtmIfVptVccEbrInfoComponentName,
--           mscAtmIfPnniEbrEligibleRecoveredConnections,
--           mscAtmIfIispEbrTotalConnectionRecoveries,
--           mscAtmIfVptUniEbrEligibleRecoveredConnections,
--           mscAtmIfVpcEbrInfoRecoverySubscribed,
--           mscAtmIfVptPnniEbrComponentName,
--           mscAtmIfPnniEbrTotalConnectionRecoveries,
--           mscAtmIfUniEbrRowStatus,
--           mscAtmIfVptVccEbrInfoTotalPathOptimizations,
--           mscAtmIfVptVccEbrInfoRecoverySubscribed,
--           mscAtmIfVptUniEbrPathOptimization,
--           mscAtmIfVccEbrInfoComponentName,
--           mscAtmIfVptPnniEbrSubscribedConnections,
--           mscAtmIfVptIispEbrRowStatus,
--           mscAtmIfVptVccSrcEbrOvOptimizationSubscribed,
--           mscAtmIfVptUniEbrComponentName,
--           mscAtmIfVptVccEbrInfoConnectionRecovered,
--           mscAtmIfPnniEbrPathOptimization,
--           mscAtmIfVpcEbrInfoComponentName,
--           mscAtmIfVptIispEbrEligibleRecoveredConnections,
--           mscAtmIfVccEbrInfoTotalPathOptimizations,
--           mscAtmIfVptPnniEbrEligibleRecoveredConnections,
--           mscAtmIfUniEbrPathOptimization,
--           mscAtmIfVpcEbrInfoOptimizationSubscribed,
--           mscAtmIfIispEbrRowStatus,
--           mscAtmIfVccSrcEbrOvOptimizationSubscribed,
--           mscAtmIfUniEbrComponentName,
--           mscAtmIfPnniEbrStorageType,
--           mscAtmIfPnniEbrConnectionRecovery,
--           mscAtmIfIispEbrEligibleRecoveredConnections,
--           mscAtmIfVptVccEbrInfoOptimizationSubscribed,
--           mscAtmIfVptIispEbrComponentName,
--           mscAtmIfPnniEbrComponentName,
--           mscAtmIfVpcSrcEbrOvStorageType,
--           mscAtmIfVptIispEbrPathOptimization,
--           mscAtmIfUniEbrTotalPathOptimizations,
--           mscAtmIfVptPnniEbrPathOptimization,
--           mscAtmIfPnniEbrRowStatus,
--           mscAtmIfUniEbrEligibleRecoveredConnections,
--           mscAtmIfVptIispEbrTotalPathOptimizations,
--           mscAtmIfVptVccSrcEbrOvRowStatus,
--           mscAtmIfVpcEbrInfoConnectionRecovered,
--           mscAtmIfIispEbrPathOptimization,
--           mscAtmIfUniEbrConnectionRecovery }
-- STATUS  mandatory
-- DESCRIPTION
--   "A list of all current accessible leaf objects."

atmEbrGroup OBJECT IDENTIFIER ::= { atmEbrMIB 1 }
atmEbrGroupCA OBJECT IDENTIFIER ::= { atmEbrGroup 1 }
atmEbrGroupCA02 OBJECT IDENTIFIER ::= { atmEbrGroupCA 3 }
atmEbrGroupCA02A OBJECT IDENTIFIER ::= { atmEbrGroupCA02 2 }



-- Agent-Capabilities Statement:

-- PRODUCT-RELEASE "MscPassport Release 1.2 AtmEbr."
-- STATUS          mandatory
-- DESCRIPTION     "Carrier Passport AtmEbr MIB: MIB Version CA02A,
--                  Software Version CA02S9C."
-- SUPPORTS        Nortel-MsCarrier-MscPassport-AtmEbrMIB
--    INCLUDES     { atmEbrGroupCA02A }

atmEbrCapabilities OBJECT IDENTIFIER ::= { atmEbrMIB 3 }
atmEbrCapabilitiesCA OBJECT IDENTIFIER ::= { atmEbrCapabilities 1 }
atmEbrCapabilitiesCA02 OBJECT IDENTIFIER ::= { atmEbrCapabilitiesCA 3 }
atmEbrCapabilitiesCA02A OBJECT IDENTIFIER ::= { atmEbrCapabilitiesCA02 2 }





END
