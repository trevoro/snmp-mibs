Nortel-Magellan-Passport-VcTesterMIB
DEFINITIONS ::= BEGIN



IMPORTS

      OBJECT-TYPE
   FROM RFC-1212

      components,
      passportMIBs
   FROM Nortel-Magellan-Passport-UsefulDefinitionsMIB

      RowPointer,
      DisplayString,
      StorageType,
      RowStatus,
      Integer32,
      Unsigned32
   FROM Nortel-Magellan-Passport-StandardTextualConventionsMIB

      AsciiString,
      Hex,
      NonReplicated,
      HexString,
      EnterpriseDateAndTime,
      Link,
      DigitString
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VcTester Enterprise MIB."

vcTesterMIB OBJECT IDENTIFIER ::= { passportMIBs 34 }










-- 
-- This is the VcTester: a tool designed to test the Passport Virtual 
-- Circuit System (vcs)..

vct OBJECT IDENTIFIER ::= { components 5130 }



vctRowStatusTable OBJECT-TYPE
   SYNTAX     SEQUENCE OF VctRowStatusEntry
   ACCESS     not-accessible
   STATUS     mandatory
   DESCRIPTION
     "This entry controls the addition and deletion of 
      vct components."
::= { vct 1 }

vctRowStatusEntry OBJECT-TYPE
   SYNTAX     VctRowStatusEntry
   ACCESS     not-accessible
   STATUS     mandatory
   DESCRIPTION
     "A single entry in the table represents a single 
      vct component."
   INDEX {
      vctIndex }
::= { vctRowStatusTable 1 }

VctRowStatusEntry ::= SEQUENCE {
   vctRowStatus
      RowStatus,
   vctComponentName
      DisplayString,
   vctStorageType
      StorageType,
   vctIndex
      Integer32 }

vctRowStatus OBJECT-TYPE
   SYNTAX     RowStatus 
   ACCESS     read-write
   STATUS     mandatory
   DESCRIPTION
     "This variable is used as the basis for SNMP naming of
      vct components.
      These components can be added and deleted."
::= { vctRowStatusEntry 1 }

vctComponentName OBJECT-TYPE
   SYNTAX     DisplayString 
   ACCESS     read-only
   STATUS     mandatory
   DESCRIPTION
     "This variable provides the component's string name for
      use with the ASCII Console Interface"
::= { vctRowStatusEntry 2 }

vctStorageType OBJECT-TYPE
   SYNTAX     StorageType 
   ACCESS     read-only
   STATUS     mandatory
   DESCRIPTION
     "This variable represents the storage type value for the
      vct tables."
::= { vctRowStatusEntry 4 }

vctIndex OBJECT-TYPE
   SYNTAX     Integer32 (1..16)
   ACCESS     not-accessible
   STATUS     mandatory
   DESCRIPTION
     "This variable represents the index for the vct tables."
::= { vctRowStatusEntry 10 }

vctProvTable OBJECT-TYPE
   SYNTAX     SEQUENCE OF VctProvEntry
   ACCESS     not-accessible
   STATUS     mandatory
   DESCRIPTION
     "This group provides the set of parameters for theVcTester 
      component"
::= { vct 10 }

vctProvEntry OBJECT-TYPE
   SYNTAX     VctProvEntry
   ACCESS     not-accessible
   STATUS     mandatory
   DESCRIPTION
     "An entry in the vctProvTable."
   INDEX {
      vctIndex }
::= { vctProvTable 1 }

VctProvEntry ::= SEQUENCE {
   vctLogicalProcessor
      Link,
   vctVcName
      INTEGER }

vctLogicalProcessor OBJECT-TYPE
   SYNTAX     Link 
   ACCESS     read-write
   STATUS     mandatory
   DESCRIPTION
     "This attribute specifies the logical processor on which the VcTester 
      will run"
::= { vctProvEntry 1 }

vctVcName OBJECT-TYPE
   SYNTAX     INTEGER  {
                 gvc(1),
                 fvc(2) }
   ACCESS     read-write
   STATUS     mandatory
   DESCRIPTION
     "This attribute specifies the type of vc (fvc or gvc) which will be 
      used by VcTester."
   DEFVAL     { gvc }
::= { vctProvEntry 2 }


-- Fruni/n Dna
-- This is the description of the generic application Dna component. It 
-- includes the superset of all attributes which may apply to a Vc. 
-- Particular applications will typically offer only a subset of these 
-- attributes by providing a definition of their own Dna subcomponent. 

vctDna OBJECT IDENTIFIER ::= { vct 2 }



vctDnaRowStatusTable OBJECT-TYPE
   SYNTAX     SEQUENCE OF VctDnaRowStatusEntry
   ACCESS     not-accessible
   STATUS     mandatory
   DESCRIPTION
     "This entry controls the addition and deletion of 
      vctDna components."
::= { vctDna 1 }

vctDnaRowStatusEntry OBJECT-TYPE
   SYNTAX     VctDnaRowStatusEntry
   ACCESS     not-accessible
   STATUS     mandatory
   DESCRIPTION
     "A single entry in the table represents a single 
      vctDna component."
   INDEX {
      vctIndex,
      vctDnaIndex }
::= { vctDnaRowStatusTable 1 }

VctDnaRowStatusEntry ::= SEQUENCE {
   vctDnaRowStatus
      RowStatus,
   vctDnaComponentName
      DisplayString,
   vctDnaStorageType
      StorageType,
   vctDnaIndex
      NonReplicated }

vctDnaRowStatus OBJECT-TYPE
   SYNTAX     RowStatus 
   ACCESS     read-only
   STATUS     mandatory
   DESCRIPTION
     "This variable is used as the basis for SNMP naming of
      vctDna components.
      These components cannot be added nor deleted."
::= { vctDnaRowStatusEntry 1 }

vctDnaComponentName OBJECT-TYPE
   SYNTAX     DisplayString 
   ACCESS     read-only
   STATUS     mandatory
   DESCRIPTION
     "This variable provides the component's string name for
      use with the ASCII Console Interface"
::= { vctDnaRowStatusEntry 2 }

vctDnaStorageType OBJECT-TYPE
   SYNTAX     StorageType 
   ACCESS     read-only
   STATUS     mandatory
   DESCRIPTION
     "This variable represents the storage type value for the
      vctDna tables."
::= { vctDnaRowStatusEntry 4 }

vctDnaIndex OBJECT-TYPE
   SYNTAX     NonReplicated 
   ACCESS     not-accessible
   STATUS     mandatory
   DESCRIPTION
     "This variable represents the index for the vctDna tables."
::= { vctDnaRowStatusEntry 10 }

vctDnaAddressTable OBJECT-TYPE
   SYNTAX     SEQUENCE OF VctDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { vctDna 10 }

vctDnaAddressEntry OBJECT-TYPE
   SYNTAX     VctDnaAddressEntry
   ACCESS     not-accessible
   STATUS     mandatory
   DESCRIPTION
     "An entry in the vctDnaAddressTable."
   INDEX {
      vctIndex,
      vctDnaIndex }
::= { vctDnaAddressTable 1 }

VctDnaAddressEntry ::= SEQUENCE {
   vctDnaNumberingPlanIndicator
      INTEGER,
   vctDnaDataNetworkAddress
      DigitString }

vctDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { x121 }
::= { vctDnaAddressEntry 1 }

vctDnaDataNetworkAddress OBJECT-TYPE
   SYNTAX     DigitString (SIZE (1..15))
   ACCESS     read-write
   STATUS     mandatory
   DESCRIPTION
     "Dna attribute contains digits which form unique identifier of the 
      customer interface. It can be compared (approximation only) to 
      telephone number where phone number identifies unique telephone 
      set. Dna digits are selected and assigned by network operators."
::= { vctDnaAddressEntry 2 }

vctDnaOutgoingOptionsTable OBJECT-TYPE
   SYNTAX     SEQUENCE OF VctDnaOutgoingOptionsEntry
   ACCESS     not-accessible
   STATUS     mandatory
   DESCRIPTION
     "OutgoingOptions group defines call options of a Dna for calls 
      which are made out of the interface represented by Dna. All these 
      options are not used for calls arriving to the interface represented by 
      Dna."
::= { vctDna 11 }

vctDnaOutgoingOptionsEntry OBJECT-TYPE
   SYNTAX     VctDnaOutgoingOptionsEntry
   ACCESS     not-accessible
   STATUS     mandatory
   DESCRIPTION
     "An entry in the vctDnaOutgoingOptionsTable."
   INDEX {
      vctIndex,
      vctDnaIndex }
::= { vctDnaOutgoingOptionsTable 1 }

VctDnaOutgoingOptionsEntry ::= SEQUENCE {
   vctDnaOutCalls
      INTEGER,
   vctDnaOutNormalCharge
      INTEGER,
   vctDnaOutReverseCharge
      INTEGER,
   vctDnaOutForceReverseCharge
      INTEGER,
   vctDnaOutNormalPriority
      INTEGER,
   vctDnaOutHighPriority
      INTEGER,
   vctDnaOutDefaultPriority
      INTEGER,
   vctDnaOutIntl
      INTEGER,
   vctDnaOutFsRestrictedResponse
      INTEGER,
   vctDnaOutFsUnrestrictedResponse
      INTEGER,
   vctDnaOutDefaultPathSensitivity
      INTEGER,
   vctDnaOutPathSensitivityOverRide
      INTEGER,
   vctDnaOutPathSensitivitySignal
      INTEGER,
   vctDnaOutDefaultPathReliability
      INTEGER,
   vctDnaOutPathReliabilityOverRide
      INTEGER,
   vctDnaOutPathReliabilitySignal
      INTEGER,
   vctDnaOutAccess
      INTEGER,
   vctDnaDefaultTransferPriority
      INTEGER,
   vctDnaTransferPriorityOverRide
      INTEGER }

vctDnaOutCalls OBJECT-TYPE
   SYNTAX     INTEGER  {
                 disallowed(0),
                 allowed(1) }
   ACCESS     read-write
   STATUS     mandatory
   DESCRIPTION
     "This attribute, if set to a value of allowed indicates that outgoing 
      calls (from the DTE to the network) can be made using this 
      particular Dna. If set to a value of disallowed, then outgoing calls 
      cannot be made using this Dna - such calls will be cleared by the 
      local DCE. This attribute corresponds to the ITU-T 'Outgoing Calls 
      Barred' feature for Dnas in that outgoing calls are barred if this 
      attribute is set to a value of disallowed. Either outCalls, or incCalls 
      (or both) must be set to a value of allowed for this Dna to be 
      useable."
   DEFVAL     { allowed }
::= { vctDnaOutgoingOptionsEntry 1 }

vctDnaOutNormalCharge OBJECT-TYPE
   SYNTAX     INTEGER  {
                 disallowed(0),
                 allowed(1) }
   ACCESS     read-write
   STATUS     mandatory
   DESCRIPTION
     "This attribute, if set to a value of allowed indicates that outgoing 
      normal charged calls (from the DTE to the network) can be made 
      using this particular Dna. If set to a value of disallowed, then such 
      calls cannot be made using this Dna - such calls will be cleared by 
      the local DCE. This attribute is ignored if the corresponding 
      attribute, outCalls is set to a value of disallowed."
   DEFVAL     { allowed }
::= { vctDnaOutgoingOptionsEntry 2 }

vctDnaOutReverseCharge OBJECT-TYPE
   SYNTAX     INTEGER  {
                 disallowed(0),
                 allowed(1) }
   ACCESS     read-write
   STATUS     mandatory
   DESCRIPTION
     "This attribute, if set to a value of allowed indicates that outgoing 
      reverse charged calls (from the DTE to the network) can be made 
      using this particular Dna. If set to a value of disallowed, then such 
      calls cannot be made using this Dna - such calls will be cleared by 
      the local DCE. This attribute is ignored if the corresponding 
      attribute, outCalls is set to a value of disallowed."
   DEFVAL     { allowed }
::= { vctDnaOutgoingOptionsEntry 3 }

vctDnaOutForceReverseCharge OBJECT-TYPE
   SYNTAX     INTEGER  {
                 no(0),
                 yes(1) }
   ACCESS     read-write
   STATUS     mandatory
   DESCRIPTION
     "This attribute specifies whether to force outgoing reverse charged 
      calls. This attribute, if set to a value of yes forces reverse charging 
      on all outgoing calls (from the DTE to the network) using this 
      particular Dna unless the caller specifies a NUI in which case the 
      call is charged to the NUI. If set to a value of no then reverse 
      charging is not forced for outgoing calls.
      This attribute is ignored if the corresponding attribute, outCalls is 
      set to a value of disallowed.This attribute must be semantically 
      consistent with the corresponding attribute, outReverseChargeCalls."
   DEFVAL     { no }
::= { vctDnaOutgoingOptionsEntry 4 }

vctDnaOutNormalPriority OBJECT-TYPE
   SYNTAX     INTEGER  {
                 disallowed(0),
                 allowed(1) }
   ACCESS     read-write
   STATUS     mandatory
   DESCRIPTION
     "This attribute, if set to a value of allowed indicates that outgoing 
      normal priority calls (from the DTE to the network) can be made 
      using this particular Dna. If set to a value of disallowed, then such 
      calls cannot be made using this Dna - such calls will be cleared by 
      the local DCE. This attribute is ignored if the corresponding 
      attribute, outCalls is set to a value of disallowed.
      
      This option can be also included in X.25 signalling, in such case it 
      will be overruled."
   DEFVAL     { allowed }
::= { vctDnaOutgoingOptionsEntry 5 }

vctDnaOutHighPriority OBJECT-TYPE
   SYNTAX     INTEGER  {
                 disallowed(0),
                 allowed(1) }
   ACCESS     read-write
   STATUS     mandatory
   DESCRIPTION
     "This attribute, if set to a value of allowed indicates that outgoing 
      high priority calls (from the DTE to the network) can be made using 
      this particular Dna. If set to a value of disallowed, then such calls 
      cannot be made using this Dna - such calls will be cleared by the 
      local DCE. This attribute is ignored if the corresponding attribute, 
      outCalls is set to a value of disallowed.
      
      This option can be also included in X.25 signalling, in such case it 
      will be overruled."
   DEFVAL     { allowed }
::= { vctDnaOutgoingOptionsEntry 6 }

vctDnaOutDefaultPriority OBJECT-TYPE
   SYNTAX     INTEGER  {
                 normal(0),
                 high(1) }
   ACCESS     read-write
   STATUS     mandatory
   DESCRIPTION
     "This attribute, if set to normal indicates that the default priority for 
      outgoing calls (from the DTE to the network) using this particular 
      Dna is normal priority - if the priority is not specified by the DTE. 
      If this attribute is set to high then the default priority for outgoing 
      calls using this particular Dna is high priority.
      
      It can be overridden by the discardPriority under DLCI Direct Call 
      subcomponent.
      
      This option can be also included in X.25 signalling, in such case it 
      will be overruled."
   DEFVAL     { normal }
::= { vctDnaOutgoingOptionsEntry 7 }

vctDnaOutIntl OBJECT-TYPE
   SYNTAX     INTEGER  {
                 disallowed(0),
                 allowed(1) }
   ACCESS     read-write
   STATUS     mandatory
   DESCRIPTION
     "This attribute, if set to a value of allowed indicates that outgoing 
      international calls (from the DTE to the network) can be made using 
      this particular Dna. If set to a value of disallowed, then such calls 
      cannot be made using this Dna - such calls will be cleared by the 
      local DCE.
      
      This attribute also currently controls access to the E.164 numbering 
      plan, and if set to a value of allowed, then cross-numbering plan 
      calls are allowed.
      
      This attribute is ignored if the corresponding attribute, outCalls is 
      set to a value of disallowed."
   DEFVAL     { disallowed }
::= { vctDnaOutgoingOptionsEntry 8 }

vctDnaOutFsRestrictedResponse OBJECT-TYPE
   SYNTAX     INTEGER  {
                 disallowed(0),
                 allowed(1) }
   ACCESS     read-write
   STATUS     mandatory
   DESCRIPTION
     "This attribute, if set to a value of allowed indicates that outgoing 
      fast select calls (from the DTE to the network) with a restricted 
      response can be made using this particular Dna. If set to a value of 
      disallowed, then such calls cannot be made using this Dna - such 
      calls will be cleared by the local DCE. This attribute is ignored if 
      the corresponding attribute, outCalls is set to a value of disallowed."
   DEFVAL     { disallowed }
::= { vctDnaOutgoingOptionsEntry 9 }

vctDnaOutFsUnrestrictedResponse OBJECT-TYPE
   SYNTAX     INTEGER  {
                 disallowed(0),
                 allowed(1) }
   ACCESS     read-write
   STATUS     mandatory
   DESCRIPTION
     "This attribute, if set to a value of allowed indicates that outgoing 
      fast select calls (from the DTE to the network) with an unrestricted 
      response can be made using this particular Dna. If set to a value of 
      disallowed, then such calls cannot be made using this Dna - such 
      calls will be cleared by the local DCE.
      This attribute is ignored if the corresponding attribute, outCalls is 
      set to a value of disallowed."
   DEFVAL     { disallowed }
::= { vctDnaOutgoingOptionsEntry 10 }

vctDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls using this particular Dna. The chosen 
      default class of path sensitivity applies to all outgoing calls 
      established using this Dna. 
      
      This attribute, if set to a value of throughput, indicates that the 
      default class is throughput sensitive. If set to a value of delay, then 
      the default class is delay sensitive. The default of 
      outDefaultPathSensitivity is throughput.
      
      This attribute is obsoleted. Please refer to defaultTransferPriority 
      for the corresponding new attribute.
      
      The migration function here will provide"
   DEFVAL     { throughput }
::= { vctDnaOutgoingOptionsEntry 11 }

vctDnaOutPathSensitivityOverRide OBJECT-TYPE
   SYNTAX     INTEGER  {
                 no(0),
                 yes(1) }
   ACCESS     read-write
   STATUS     obsolete
   DESCRIPTION
     "If this attribute is set to in the call request, the called end will use 
      the calling end provisioning data on path sensitivity to override its 
      own provisioning data.
      
      The default of outPathSensitivityOverRide is no."
   DEFVAL     { no }
::= { vctDnaOutgoingOptionsEntry 12 }

vctDnaOutPathSensitivitySignal OBJECT-TYPE
   SYNTAX     INTEGER  {
                 disallowed(0),
                 allowed(1) }
   ACCESS     read-write
   STATUS     mandatory
   DESCRIPTION
     "This is the sensitivity signaling. If this attribute is set to allowed, the 
      signalled value on sensitivity will be used."
   DEFVAL     { disallowed }
::= { vctDnaOutgoingOptionsEntry 13 }

vctDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular Dna. The chosen default class of routing applies to 
      all outgoing calls established using this Dna, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the Vc 
      handles the duplication and disordering to ensure that packets are 
      delivered to the DTE properly.
      For the Frame Relay service, duplication of packets is not desired, 
      in which case, normal reliability may be chosen as the preferred 
      class of routing."
   DEFVAL     { high }
::= { vctDnaOutgoingOptionsEntry 14 }

vctDnaOutPathReliabilityOverRide OBJECT-TYPE
   SYNTAX     INTEGER  {
                 no(0),
                 yes(1) }
   ACCESS     read-write
   STATUS     mandatory
   DESCRIPTION
     "If outReliabilityOverRide set in the call request, the called end will 
      use the calling end provisioning data on reliability to overide his 
      provisioning data."
   DEFVAL     { no }
::= { vctDnaOutgoingOptionsEntry 15 }

vctDnaOutPathReliabilitySignal OBJECT-TYPE
   SYNTAX     INTEGER  {
                 disallowed(0),
                 allowed(1) }
   ACCESS     read-write
   STATUS     mandatory
   DESCRIPTION
     "outPathReliabilitySignal is reliability routing signaling. If this 
      attribute is set to allowed, the signalled value on reliability will be 
      used."
   DEFVAL     { disallowed }
::= { vctDnaOutgoingOptionsEntry 16 }

vctDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTE's 
      that have Incoming Access capabilities. If set to a value of 
      disallowed, then such calls cannot be made using this Dna - such 
      calls will be cleared by the local DCE.
      This attribute corresponds to the ITU-T 'Closed User Group with 
      Outgoing Access' feature for Dna's in that outgoing access is 
      granted if this attribute is set to a value of allowed."
   DEFVAL     { disallowed }
::= { vctDnaOutgoingOptionsEntry 17 }

vctDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of defaultTransferPriority is normal."
   DEFVAL     { normal }
::= { vctDnaOutgoingOptionsEntry 18 }

vctDnaTransferPriorityOverRide OBJECT-TYPE
   SYNTAX     INTEGER  {
                 no(0),
                 yes(1) }
   ACCESS     read-write
   STATUS     mandatory
   DESCRIPTION
     "When this attribute is set to yes, the called end will use the calling 
      end provisioning data on transfer priority to override its own 
      provisioning data. If it is set no, the called end will use its own 
      provisioning data on transfer priority.
      
      For more information about transfer priority, please refer to the 
      previous attribute defaultTransferPriority.
      
      The default of transferPriorityOverRide is no."
   DEFVAL     { no }
::= { vctDnaOutgoingOptionsEntry 19 }

vctDnaIncomingOptionsTable OBJECT-TYPE
   SYNTAX     SEQUENCE OF VctDnaIncomingOptionsEntry
   ACCESS     not-accessible
   STATUS     mandatory
   DESCRIPTION
     "IncomingOptions defines set of options for incoming calls. These 
      options are used for calls arriving to the interface represented by 
      Dna. For calls originated from the interfasce, IncomingOptions 
      attributes are not used."
::= { vctDna 12 }

vctDnaIncomingOptionsEntry OBJECT-TYPE
   SYNTAX     VctDnaIncomingOptionsEntry
   ACCESS     not-accessible
   STATUS     mandatory
   DESCRIPTION
     "An entry in the vctDnaIncomingOptionsTable."
   INDEX {
      vctIndex,
      vctDnaIndex }
::= { vctDnaIncomingOptionsTable 1 }

VctDnaIncomingOptionsEntry ::= SEQUENCE {
   vctDnaIncCalls
      INTEGER,
   vctDnaIncHighPriorityReverseCharge
      INTEGER,
   vctDnaIncNormalPriorityReverseCharge
      INTEGER,
   vctDnaIncIntlNormalCharge
      INTEGER,
   vctDnaIncIntlReverseCharge
      INTEGER,
   vctDnaIncFastSelect
      INTEGER,
   vctDnaIncSameService
      INTEGER,
   vctDnaIncChargeTransfer
      INTEGER,
   vctDnaIncAccess
      INTEGER }

vctDnaIncCalls OBJECT-TYPE
   SYNTAX     INTEGER  {
                 disallowed(0),
                 allowed(1) }
   ACCESS     read-write
   STATUS     mandatory
   DESCRIPTION
     "This attribute, if set to a value of allowed indicates that incoming 
      calls (from the network to the DTE) can be made to this Dna. If set 
      to a value of disallowed, then incoming calls cannot be made to this 
      Dna - such calls will be cleared by the local DCE. This attribute 
      corresponds to the ITU-T 'Incoming Calls Barred' feature for Dna's 
      in that incoming calls are barred if this attribute is set to a value of 
      disallowed.
      
      Either outCalls, or incCalls (or both) must be set to a value of 
      allowed for this Dna to be useable."
   DEFVAL     { allowed }
::= { vctDnaIncomingOptionsEntry 1 }

vctDnaIncHighPriorityReverseCharge OBJECT-TYPE
   SYNTAX     INTEGER  {
                 disallowed(0),
                 allowed(1) }
   ACCESS     read-write
   STATUS     mandatory
   DESCRIPTION
     "This attribute, if set to a value of allowed indicates that incoming 
      high priority, reverse charged calls (from the network to the DTE) 
      can be made to this Dna. If set to a value of disallowed,then such 
      calls cannot be made to this Dna - such calls will be cleared by the 
      local DCE.
      This attribute, together with the 
      incNormalPriorityReverseChargeCalls attribute corresponds
      to the ITU-T 'Reverse Charging Acceptance' feature for Dna's in 
      that reverse charged calls are accepted if both attributes are set to a 
      value of allowed.
      This attribute is ignored if the corresponding attribute, incCalls is 
      set to a value of disallowed."
   DEFVAL     { allowed }
::= { vctDnaIncomingOptionsEntry 2 }

vctDnaIncNormalPriorityReverseCharge OBJECT-TYPE
   SYNTAX     INTEGER  {
                 disallowed(0),
                 allowed(1) }
   ACCESS     read-write
   STATUS     mandatory
   DESCRIPTION
     "This attribute, if set to a value of allowed indicates that incoming 
      normal priority, reverse charged calls (from the network to the 
      DTE) can be made to this Dna. If set to a value of disallowed, then 
      such calls cannot be made to this Dna - such calls will be cleared by 
      the local DCE. 
      This attribute, together with the 
      incHighPriorityReverseChargeCalls attribute corresponds to the 
      ITU-T 'Reverse Charging Acceptance' feature for Dna's in that 
      reverse charged calls are accepted if both attributes are set to a value 
      of allowed.
      This attribute is ignored if the corresponding attribute, incCalls is 
      set to a value of disallowed."
   DEFVAL     { allowed }
::= { vctDnaIncomingOptionsEntry 3 }

vctDnaIncIntlNormalCharge OBJECT-TYPE
   SYNTAX     INTEGER  {
                 disallowed(0),
                 allowed(1) }
   ACCESS     read-write
   STATUS     mandatory
   DESCRIPTION
     "This attribute, if set to a value of allowed indicates that incoming 
      international normal charged calls (from the network to the DTE) 
      can be made to this Dna. If set to a value of disallowed, then such 
      calls cannot be made to this Dna - such calls will be cleared by the 
      local DCE.
      This attribute also currently controls access to/from the E.164 
      numbering plan, and if set to a value of allowed, then cross-
      numbering plan calls (also normal charged) are allowed. 
      This attribute is ignored if the corresponding attribute, incCalls is 
      set to a value of disallowed."
   DEFVAL     { allowed }
::= { vctDnaIncomingOptionsEntry 4 }

vctDnaIncIntlReverseCharge OBJECT-TYPE
   SYNTAX     INTEGER  {
                 disallowed(0),
                 allowed(1) }
   ACCESS     read-write
   STATUS     mandatory
   DESCRIPTION
     "This attribute, if set to a value of allowed indicates that incoming 
      international reverse charged calls (from the network to the DTE) 
      can be made to this Dna. If set to a value of disallowed, then such 
      calls cannot be made to this Dna - such calls will be cleared by the 
      local DCE.
      This attribute also currently controls access to/from the E.164 
      numbering plan, and if set to a value of allowed, then cross-
      numbering plan calls (also normal charged) are allowed.
      This attribute is ignored if the corresponding attribute, incCalls is 
      set to a value of disallowed."
   DEFVAL     { allowed }
::= { vctDnaIncomingOptionsEntry 5 }

vctDnaIncFastSelect OBJECT-TYPE
   SYNTAX     INTEGER  {
                 disallowed(0),
                 allowed(1) }
   ACCESS     read-write
   STATUS     mandatory
   DESCRIPTION
     "This attribute specifies whether fast select calls may be received.
      This attribute, if set to a value of allowed indicates that incoming 
      fast select calls (from the network to the DTE) can be made to this 
      Dna. If set to a value of disallowed, then such calls cannot be made 
      to this Dna - such calls will be cleared by the local DCE.
      This attribute corresponds to the ITU-T 'Fast Select Acceptance' 
      feature for Dnas in that incoming fast select calls are accepted if 
      this attribute is set to a value of allowed.
      This attribute is ignored if the corresponding attribute, incCalls is 
      set to a value of disallowed."
   DEFVAL     { disallowed }
::= { vctDnaIncomingOptionsEntry 6 }

vctDnaIncSameService OBJECT-TYPE
   SYNTAX     INTEGER  {
                 disallowed(0),
                 allowed(1) }
   ACCESS     read-write
   STATUS     mandatory
   DESCRIPTION
     "This attribute, if set to a value of allowed indicates that incoming 
      calls from the same service type (eg: X.25, ITI, SNA) (from the 
      network to the DTE) can be made to this Dna. If set to a value of 
      disallowed, then such calls cannot be made to this Dna - such calls 
      will be cleared by the local DCE.
      This attribute is ignored if the corresponding attribute, incCalls is 
      set to a value of disallowed."
   DEFVAL     { allowed }
::= { vctDnaIncomingOptionsEntry 7 }

vctDnaIncChargeTransfer OBJECT-TYPE
   SYNTAX     INTEGER  {
                 no(0),
                 yes(1) }
   ACCESS     read-write
   STATUS     mandatory
   DESCRIPTION
     "This attribute, if set to a value of yes indicates that the charges for 
      incoming normal charged calls from a DTE with the same DNIC 
      (calls from the network to the DTE) will be transferred to the called 
      DTE. If set to a value of no, then charges will not be transferred.
      This attribute is ignored if the corresponding attribute, incCalls is 
      set to a value of disallowed."
   DEFVAL     { no }
::= { vctDnaIncomingOptionsEntry 8 }

vctDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTE's that have Outgoing Access capabilities. If set to a value of 
      disallowed, then such calls cannot be made to this Dna - such calls 
      will be cleared by the local DCE.
      This attribute corresponds to the ITU-T 'Closed User Group with 
      Incoming Access' feature for Dnas in that incoming access is 
      granted if this attribute is set to a value of allowed."
   DEFVAL     { disallowed }
::= { vctDnaIncomingOptionsEntry 9 }

vctDnaCallOptionsTable OBJECT-TYPE
   SYNTAX     SEQUENCE OF VctDnaCallOptionsEntry
   ACCESS     not-accessible
   STATUS     mandatory
   DESCRIPTION
     "CallOptions group defines additional options for calls not related 
      directly to direction of a call."
::= { vctDna 13 }

vctDnaCallOptionsEntry OBJECT-TYPE
   SYNTAX     VctDnaCallOptionsEntry
   ACCESS     not-accessible
   STATUS     mandatory
   DESCRIPTION
     "An entry in the vctDnaCallOptionsTable."
   INDEX {
      vctIndex,
      vctDnaIndex }
::= { vctDnaCallOptionsTable 1 }

VctDnaCallOptionsEntry ::= SEQUENCE {
   vctDnaServiceCategory
      INTEGER,
   vctDnaPacketSizes
      OCTET STRING,
   vctDnaDefaultRecvFrmNetworkPacketSize
      INTEGER,
   vctDnaDefaultSendToNetworkPacketSize
      INTEGER,
   vctDnaDefaultRecvFrmNetworkThruputClass
      Unsigned32,
   vctDnaDefaultSendToNetworkThruputClass
      Unsigned32,
   vctDnaDefaultRecvFrmNetworkWindowSize
      Unsigned32,
   vctDnaDefaultSendToNetworkWindowSize
      Unsigned32,
   vctDnaPacketSizeNegotiation
      INTEGER,
   vctDnaCugFormat
      INTEGER,
   vctDnaCug0AsNonCugCall
      INTEGER,
   vctDnaSignalPreferentialCugToLink
      INTEGER,
   vctDnaSignalIntlAddressToLink
      INTEGER,
   vctDnaFastSelectCallsOnly
      INTEGER,
   vctDnaPreselectRpoa
      INTEGER,
   vctDnaAccountClass
      Unsigned32,
   vctDnaAccountCollection
      OCTET STRING,
   vctDnaServiceExchange
      Unsigned32,
   vctDnaEgressAccounting
      INTEGER,
   vctDnaRpoa
      DigitString,
   vctDnaDataPath
      INTEGER }

vctDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31),
                 gvcIf(32) }
   ACCESS     read-write
   STATUS     mandatory
   DESCRIPTION
     "This attribute is assigned for each different type of service within 
      which this Dna is configured. It is placed into the Service Category 
      attribute in the accounting record by both ends of the Vc."
   DEFVAL     { frameRelay }
::= { vctDnaCallOptionsEntry 1 }

vctDnaPacketSizes OBJECT-TYPE
   SYNTAX     OCTET STRING (SIZE (2))
   ACCESS     read-write
   STATUS     mandatory
   DESCRIPTION
     "This attribute indicates the allowable packet sizes supported for call 
      setup using this Dna. ITU-T recommends that packet size 128 
      always be supported. Attributes defaultRecvFrmNetworkPacketSize 
      and defaultSendToNetworkPacketSize are related to this attribute.

      Description of bits:
      n16(0)
      n32(1)
      n64(2)
      n128(3)
      n256(4)
      n512(5)
      n1024(6)
      n2048(7)
      n4096(8)"
   DEFVAL     { '1c00'H }
::= { vctDnaCallOptionsEntry 2 }

vctDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute indicates the default local receive packet size from 
      network to DTE for all calls using this particular Dna. Attribute 
      packetSizes has to be set with corresponding value."
   DEFVAL     { n128 }
::= { vctDnaCallOptionsEntry 3 }

vctDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute indicates the default local send packet size from DTE 
      to network for all calls using this particular Dna.
      Attribute packetSizes has to be set with corresponding value."
   DEFVAL     { n128 }
::= { vctDnaCallOptionsEntry 4 }

vctDnaDefaultRecvFrmNetworkThruputClass OBJECT-TYPE
   SYNTAX     Unsigned32 (3..15)
   ACCESS     read-write
   STATUS     mandatory
   DESCRIPTION
     "This attribute indicates the default receive throughput class for all 
      calls using this particular Dna."
   DEFVAL     { 10 }
::= { vctDnaCallOptionsEntry 5 }

vctDnaDefaultSendToNetworkThruputClass OBJECT-TYPE
   SYNTAX     Unsigned32 (0..15)
   ACCESS     read-write
   STATUS     mandatory
   DESCRIPTION
     "This attribute indicates the default send throughput class for all calls 
      using this particular Dna."
   DEFVAL     { 10 }
::= { vctDnaCallOptionsEntry 6 }

vctDnaDefaultRecvFrmNetworkWindowSize OBJECT-TYPE
   SYNTAX     Unsigned32 (1..7)
   ACCESS     read-write
   STATUS     mandatory
   DESCRIPTION
     "This attribute indicates the default number of data packets that can 
      be received by the DTE from the DCE before more packets can be 
      received. This view is oriented with respect to the DTE."
   DEFVAL     { 2 }
::= { vctDnaCallOptionsEntry 7 }

vctDnaDefaultSendToNetworkWindowSize OBJECT-TYPE
   SYNTAX     Unsigned32 (1..7)
   ACCESS     read-write
   STATUS     mandatory
   DESCRIPTION
     "This attribute indicates the number of data packets that can be 
      transmitted from the DTE to the DCE and must be acknowledged 
      before more packets can be transmitted."
   DEFVAL     { 2 }
::= { vctDnaCallOptionsEntry 8 }

vctDnaPacketSizeNegotiation OBJECT-TYPE
   SYNTAX     INTEGER  {
                 endToEnd(0),
                 local(1) }
   ACCESS     read-write
   STATUS     mandatory
   DESCRIPTION
     "This attribute, if set to local indicates that packet sizes can be 
      negotiated locally at the interface irrespective of the remote 
      interface. If set to endtoEnd, then local negotiation is not permitted 
      and packet sizes are negotiated between 2 ends of Vc."
   DEFVAL     { endToEnd }
::= { vctDnaCallOptionsEntry 9 }

vctDnaCugFormat OBJECT-TYPE
   SYNTAX     INTEGER  {
                 basic(0),
                 extended(1) }
   ACCESS     read-write
   STATUS     mandatory
   DESCRIPTION
     "This attribute specifies which cug format is used when DTE signals 
      CUG indices, basic or extended.
      This attribute, if set to extended indicates that the DTE signals and 
      receives CUG indices in extended CUG format. If set to a value of 
      basic, then the DTE signals and receives CUG indices in the basic 
      CUG format."
   DEFVAL     { basic }
::= { vctDnaCallOptionsEntry 10 }

vctDnaCug0AsNonCugCall OBJECT-TYPE
   SYNTAX     INTEGER  {
                 disallowed(0),
                 allowed(1) }
   ACCESS     read-write
   STATUS     mandatory
   DESCRIPTION
     "This attribute, if set to allowed indicates that when a CUG index of 
      0 is signalled in a call request packet, the call is treated as a non-
      CUG call. If this attribute is set to disallowed, then a CUG index of 
      0 is treated as an index, and an attempt is made to find the particular 
      CUG corresponding with the Dna."
   DEFVAL     { disallowed }
::= { vctDnaCallOptionsEntry 11 }

vctDnaSignalPreferentialCugToLink OBJECT-TYPE
   SYNTAX     INTEGER  {
                 no(0),
                 yes(1) }
   ACCESS     read-write
   STATUS     mandatory
   DESCRIPTION
     "This attribute, if set to no, indicates that, at the destination (called) 
      DTE, when a CUG call is received using the called DTE's 
      preferential CUG, the preferential CUG's index is not signalled to 
      the called DTE in the incoming call request packet. Otherwise, the 
      preferential CUG's index is signalled to the link in the incoming call 
      request packet."
   DEFVAL     { no }
::= { vctDnaCallOptionsEntry 12 }

vctDnaSignalIntlAddressToLink OBJECT-TYPE
   SYNTAX     INTEGER  {
                 no(0),
                 yes(1) }
   ACCESS     read-write
   STATUS     mandatory
   DESCRIPTION
     "This attribute, if set to yes, indicates that all addresses presented by 
      the network (DCE) to the link (DTE) within incoming call request., 
      call connected and clear packets are presented in international 
      format with no prefix digit. International format includes DNIC in 
      the address."
   DEFVAL     { no }
::= { vctDnaCallOptionsEntry 13 }

vctDnaFastSelectCallsOnly OBJECT-TYPE
   SYNTAX     INTEGER  {
                 no(0),
                 yes(1) }
   ACCESS     read-write
   STATUS     mandatory
   DESCRIPTION
     "This attribute, if set to yes, indicates that the service is permitted 
      restricted fast select calls in both the incoming and the outgoing 
      directions using this Dna. If set to no, then non fast select calls are 
      permitted as well."
   DEFVAL     { no }
::= { vctDnaCallOptionsEntry 14 }

vctDnaPreselectRpoa OBJECT-TYPE
   SYNTAX     INTEGER  {
                 no(0),
                 yes(1) }
   ACCESS     read-write
   STATUS     mandatory
   DESCRIPTION
     "This attribute, if set to yes, indicates that this Dna subscribes to a 
      pre-selected RPOA, in which case, the pre-selected RPOA is 
      contained in the rpoa attribute described below. If set to no, then a 
      pre-selected RPOA is not subscribed."
   DEFVAL     { no }
::= { vctDnaCallOptionsEntry 15 }

vctDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { vctDnaCallOptionsEntry 16 }

vctDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. If none 
      of these reasons are set, then accounting will be suppressed.

      Description of bits:
      bill(0)
      test(1)
      study(2)
      audit(3)
      force(4)"
   DEFVAL     { '80'H }
::= { vctDnaCallOptionsEntry 17 }

vctDnaServiceExchange OBJECT-TYPE
   SYNTAX     Unsigned32 (0..255)
   ACCESS     read-write
   STATUS     mandatory
   DESCRIPTION
     "This attribute is an arbitrary number, entered by the network 
      operator. The value of serviceExchange is included in the 
      accounting record generated by Vc."
   DEFVAL     { 0 }
::= { vctDnaCallOptionsEntry 18 }

vctDnaEgressAccounting OBJECT-TYPE
   SYNTAX     INTEGER  {
                 no(0),
                 yes(1) }
   ACCESS     read-write
   STATUS     mandatory
   DESCRIPTION
     "egressAccounting	 specifies if Egress accounting is enabled by 
      Frame Relay service. Disabling of Egress accounting means that 
      only segment counts are collected by VC and there are no frame 
      relay counts in accounting records for Frame Relay service. 
      Enabling of Egress accounting means that the accounting records 
      for Frame Relay contain frame relay specific counts."
   DEFVAL     { no }
::= { vctDnaCallOptionsEntry 19 }

vctDnaRpoa OBJECT-TYPE
   SYNTAX     DigitString (SIZE (4))
   ACCESS     read-write
   STATUS     mandatory
   DESCRIPTION
     "rpoa - Recognized Private Operating Agency is a ITU-T specified 
      facility which allows the user to specify--at call setup time--the next 
      transit network the call should use. The rpoa can override all 
      routing decisions.
      If Dna subscribes to preselectRpoa as indicated by the previously 
      described attribute, (preselectRpoa set to yes) then this attribute 
      contains preselected rpoa. If the preselectRpoa attribute is set to no, 
      then this attribute can be left at its default.
      This preselected rpoa will be used for all outgoing call request 
      packets using this Dna if an rpoa is not explicitly specified in the 
      call request. The rpoa represents the dnic of the directly connected 
      network through which the call will be routed in the presence of the 
      rpoa."
   DEFVAL     { '30303030'H }  -- "0000"
::= { vctDnaCallOptionsEntry 20 }

vctDnaDataPath OBJECT-TYPE
   SYNTAX     INTEGER  {
                 dprsOnly(0),
                 dprsMcsOnly(1),
                 dprsMcsFirst(2) }
   ACCESS     read-write
   STATUS     mandatory
   DESCRIPTION
     "This attribute specifies the data path to be used by Virtual Circuits 
      on this interface. If the connection has a DirectCall component then 
      the value can be overridden by the dataPath attribute of the 
      DirectCall component.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used."
   DEFVAL     { dprsOnly }
::= { vctDnaCallOptionsEntry 21 }


-- Fruni/n Dna Cug
-- ClosedUserGroup options defines options associated with national 
-- or international Cug Identifier. Other Dna's in the network can have 
-- Cug's defined which groups these Dna's by Cug interlockCode. If 
-- Dna's are defined with Cugs, calls from Dna's which do not have 
-- the same interlockCode defined are refused. Attributes incAccess 
-- and outAccess can override this rule.

vctDnaCug OBJECT IDENTIFIER ::= { vctDna 2 }



vctDnaCugRowStatusTable OBJECT-TYPE
   SYNTAX     SEQUENCE OF VctDnaCugRowStatusEntry
   ACCESS     not-accessible
   STATUS     mandatory
   DESCRIPTION
     "This entry controls the addition and deletion of 
      vctDnaCug components."
::= { vctDnaCug 1 }

vctDnaCugRowStatusEntry OBJECT-TYPE
   SYNTAX     VctDnaCugRowStatusEntry
   ACCESS     not-accessible
   STATUS     mandatory
   DESCRIPTION
     "A single entry in the table represents a single 
      vctDnaCug component."
   INDEX {
      vctIndex,
      vctDnaIndex,
      vctDnaCugIndex }
::= { vctDnaCugRowStatusTable 1 }

VctDnaCugRowStatusEntry ::= SEQUENCE {
   vctDnaCugRowStatus
      RowStatus,
   vctDnaCugComponentName
      DisplayString,
   vctDnaCugStorageType
      StorageType,
   vctDnaCugIndex
      Integer32 }

vctDnaCugRowStatus OBJECT-TYPE
   SYNTAX     RowStatus 
   ACCESS     read-write
   STATUS     mandatory
   DESCRIPTION
     "This variable is used as the basis for SNMP naming of
      vctDnaCug components.
      These components can be added and deleted."
::= { vctDnaCugRowStatusEntry 1 }

vctDnaCugComponentName OBJECT-TYPE
   SYNTAX     DisplayString 
   ACCESS     read-only
   STATUS     mandatory
   DESCRIPTION
     "This variable provides the component's string name for
      use with the ASCII Console Interface"
::= { vctDnaCugRowStatusEntry 2 }

vctDnaCugStorageType OBJECT-TYPE
   SYNTAX     StorageType 
   ACCESS     read-only
   STATUS     mandatory
   DESCRIPTION
     "This variable represents the storage type value for the
      vctDnaCug tables."
::= { vctDnaCugRowStatusEntry 4 }

vctDnaCugIndex OBJECT-TYPE
   SYNTAX     Integer32 (0..255)
   ACCESS     not-accessible
   STATUS     mandatory
   DESCRIPTION
     "This variable represents the index for the vctDnaCug tables."
::= { vctDnaCugRowStatusEntry 10 }

vctDnaCugCugOptionsTable OBJECT-TYPE
   SYNTAX     SEQUENCE OF VctDnaCugCugOptionsEntry
   ACCESS     not-accessible
   STATUS     mandatory
   DESCRIPTION
     "This group defines options for. Attributes in this group defines 
      ClosedUserGroup options associated with interlockCode. Dna's 
      with the same Cug (interlockCode) can make calls within this 
      group. Various combinations which permit or prevent calls in the 
      same Cug group are defined here."
::= { vctDnaCug 10 }

vctDnaCugCugOptionsEntry OBJECT-TYPE
   SYNTAX     VctDnaCugCugOptionsEntry
   ACCESS     not-accessible
   STATUS     mandatory
   DESCRIPTION
     "An entry in the vctDnaCugCugOptionsTable."
   INDEX {
      vctIndex,
      vctDnaIndex,
      vctDnaCugIndex }
::= { vctDnaCugCugOptionsTable 1 }

VctDnaCugCugOptionsEntry ::= SEQUENCE {
   vctDnaCugType
      INTEGER,
   vctDnaCugDnic
      DigitString,
   vctDnaCugInterlockCode
      Unsigned32,
   vctDnaCugPreferential
      INTEGER,
   vctDnaCugOutCalls
      INTEGER,
   vctDnaCugIncCalls
      INTEGER,
   vctDnaCugPrivileged
      INTEGER }

vctDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTE's for which there is an X.75 
      Gateway between; whereas national closed user groups are usually 
      established between DTE's for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { vctDnaCugCugOptionsEntry 1 }

vctDnaCugDnic OBJECT-TYPE
   SYNTAX     DigitString (SIZE (4))
   ACCESS     read-write
   STATUS     mandatory
   DESCRIPTION
     "This attribute specifies the dnic (Data Network ID Code) of the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      
      dnic value is not an arbitrary number. It is assigned by international 
      agreement and controlled by ITU-T."
   DEFVAL     { '30303030'H }  -- "0000"
::= { vctDnaCugCugOptionsEntry 2 }

vctDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dna's) defined with 
      this number can make calls to Dna's with the same interlockCode."
   DEFVAL     { 0 }
::= { vctDnaCugCugOptionsEntry 3 }

vctDnaCugPreferential OBJECT-TYPE
   SYNTAX     INTEGER  {
                 no(0),
                 yes(1) }
   ACCESS     read-write
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { vctDnaCugCugOptionsEntry 4 }

vctDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) can be made using this particular Cug. If 
      set to a value of disallowed, then outgoing calls cannot be made 
      using this Cug - such calls will be cleared by the local DCE.
      This attribute corresponds to the ITU-T 'Outgoing Calls Barred' 
      feature for cugs in that outgoing calls are barred if this attribute is 
      set to a value of disallowed."
   DEFVAL     { allowed }
::= { vctDnaCugCugOptionsEntry 5 }

vctDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular Cug. If 
      set to disallowed, then incoming calls cannot be made using this 
      Cug - such calls will be cleared by the local DCE.
      This attribute corresponds to the ITU-T 'Incoming Calls Barred' 
      feature for Cugs in that incoming calls are barred if this attribute is 
      set to a value of disallowed."
   DEFVAL     { allowed }
::= { vctDnaCugCugOptionsEntry 6 }

vctDnaCugPrivileged OBJECT-TYPE
   SYNTAX     INTEGER  {
                 no(0),
                 yes(1) }
   ACCESS     read-write
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTE's in which case the other DTE's cannot call one another, 
      but can call the host. In this example, the host would have the 
      privileged Cug, and the other DTE's would belong to the same Cug, 
      but it would not be privileged."
   DEFVAL     { yes }
::= { vctDnaCugCugOptionsEntry 7 }


-- GvcIf/n Dna/n HgMember
-- This component specifies the Hunt Groups to which this member 
-- belongs. A hunt group member subscribes to at least one hunt 
-- group.

vctDnaHgM OBJECT IDENTIFIER ::= { vctDna 3 }



vctDnaHgMRowStatusTable OBJECT-TYPE
   SYNTAX     SEQUENCE OF VctDnaHgMRowStatusEntry
   ACCESS     not-accessible
   STATUS     mandatory
   DESCRIPTION
     "This entry controls the addition and deletion of 
      vctDnaHgM components."
::= { vctDnaHgM 1 }

vctDnaHgMRowStatusEntry OBJECT-TYPE
   SYNTAX     VctDnaHgMRowStatusEntry
   ACCESS     not-accessible
   STATUS     mandatory
   DESCRIPTION
     "A single entry in the table represents a single 
      vctDnaHgM component."
   INDEX {
      vctIndex,
      vctDnaIndex,
      vctDnaHgMIndex }
::= { vctDnaHgMRowStatusTable 1 }

VctDnaHgMRowStatusEntry ::= SEQUENCE {
   vctDnaHgMRowStatus
      RowStatus,
   vctDnaHgMComponentName
      DisplayString,
   vctDnaHgMStorageType
      StorageType,
   vctDnaHgMIndex
      NonReplicated }

vctDnaHgMRowStatus OBJECT-TYPE
   SYNTAX     RowStatus 
   ACCESS     read-write
   STATUS     mandatory
   DESCRIPTION
     "This variable is used as the basis for SNMP naming of
      vctDnaHgM components.
      These components can be added and deleted."
::= { vctDnaHgMRowStatusEntry 1 }

vctDnaHgMComponentName OBJECT-TYPE
   SYNTAX     DisplayString 
   ACCESS     read-only
   STATUS     mandatory
   DESCRIPTION
     "This variable provides the component's string name for
      use with the ASCII Console Interface"
::= { vctDnaHgMRowStatusEntry 2 }

vctDnaHgMStorageType OBJECT-TYPE
   SYNTAX     StorageType 
   ACCESS     read-only
   STATUS     mandatory
   DESCRIPTION
     "This variable represents the storage type value for the
      vctDnaHgM tables."
::= { vctDnaHgMRowStatusEntry 4 }

vctDnaHgMIndex OBJECT-TYPE
   SYNTAX     NonReplicated 
   ACCESS     not-accessible
   STATUS     mandatory
   DESCRIPTION
     "This variable represents the index for the vctDnaHgM tables."
::= { vctDnaHgMRowStatusEntry 10 }

vctDnaHgMIfTable OBJECT-TYPE
   SYNTAX     SEQUENCE OF VctDnaHgMIfEntry
   ACCESS     not-accessible
   STATUS     mandatory
   DESCRIPTION
     "This group contains the interface parameters between the 
      HuntGroupMember and the Hunt Group server."
::= { vctDnaHgM 10 }

vctDnaHgMIfEntry OBJECT-TYPE
   SYNTAX     VctDnaHgMIfEntry
   ACCESS     not-accessible
   STATUS     mandatory
   DESCRIPTION
     "An entry in the vctDnaHgMIfTable."
   INDEX {
      vctIndex,
      vctDnaIndex,
      vctDnaHgMIndex }
::= { vctDnaHgMIfTable 1 }

VctDnaHgMIfEntry ::= SEQUENCE {
   vctDnaHgMAvailabilityUpdateThreshold
      Unsigned32 }

vctDnaHgMAvailabilityUpdateThreshold OBJECT-TYPE
   SYNTAX     Unsigned32 (0..4096)
   ACCESS     read-write
   STATUS     mandatory
   DESCRIPTION
     "This attribute indicates the number of channels that have to be freed 
      or occupied before the Availability Message Packet (AMP) is sent 
      to the Hunt Group Server informing it of the status of this interface."
   DEFVAL     { 1 }
::= { vctDnaHgMIfEntry 1 }

vctDnaHgMOpTable OBJECT-TYPE
   SYNTAX     SEQUENCE OF VctDnaHgMOpEntry
   ACCESS     not-accessible
   STATUS     mandatory
   DESCRIPTION
     "This group contains the operational attributes of the 
      HuntGroupMember component."
::= { vctDnaHgM 11 }

vctDnaHgMOpEntry OBJECT-TYPE
   SYNTAX     VctDnaHgMOpEntry
   ACCESS     not-accessible
   STATUS     mandatory
   DESCRIPTION
     "An entry in the vctDnaHgMOpTable."
   INDEX {
      vctIndex,
      vctDnaIndex,
      vctDnaHgMIndex }
::= { vctDnaHgMOpTable 1 }

VctDnaHgMOpEntry ::= SEQUENCE {
   vctDnaHgMMaxAvailableChannels
      Unsigned32,
   vctDnaHgMAvailableChannels
      Unsigned32,
   vctDnaHgMAvailabilityDelta
      INTEGER }

vctDnaHgMMaxAvailableChannels OBJECT-TYPE
   SYNTAX     Unsigned32 (0..4096)
   ACCESS     read-only
   STATUS     mandatory
   DESCRIPTION
     "This attribute indicates the maximum number of available channels 
      for this HuntGroupMember."
::= { vctDnaHgMOpEntry 1 }

vctDnaHgMAvailableChannels OBJECT-TYPE
   SYNTAX     Unsigned32 (0..4096)
   ACCESS     read-only
   STATUS     mandatory
   DESCRIPTION
     "This attribute indicates the number of available channels reported to 
      the hunt group in the Availability Message Packet (AMP). It is 
      modified by adding 1 by the application when a channel is freed and 
      subtracting 1 when a channel is occupied."
::= { vctDnaHgMOpEntry 2 }

vctDnaHgMAvailabilityDelta OBJECT-TYPE
   SYNTAX     INTEGER (-4096..4096)
   ACCESS     read-only
   STATUS     mandatory
   DESCRIPTION
     "This attribute indicates the net change in the available channels 
      since the last Availability Message Packet (AMP) was sent to the 
      Hunt Group. Once the absolute value of this attribute reaches the 
      availabilityUpdateThreshold an AMP is sent to the host and the 
      availabilityDelta is reset to 0.
      If this attribute is positive it means an increase of the number of 
      available channels. If it is negative it means a decrease in the 
      number of available channels."
::= { vctDnaHgMOpEntry 3 }


-- GvcIf/n Dna/n HgM HuntGroupAddress/n
-- This component specifies the Hunt Group address to which this 
-- member belongs. A hunt group member belongs to at least one hunt 
-- group.

vctDnaHgMHgAddr OBJECT IDENTIFIER ::= { vctDnaHgM 2 }



vctDnaHgMHgAddrRowStatusTable OBJECT-TYPE
   SYNTAX     SEQUENCE OF VctDnaHgMHgAddrRowStatusEntry
   ACCESS     not-accessible
   STATUS     mandatory
   DESCRIPTION
     "This entry controls the addition and deletion of 
      vctDnaHgMHgAddr components."
::= { vctDnaHgMHgAddr 1 }

vctDnaHgMHgAddrRowStatusEntry OBJECT-TYPE
   SYNTAX     VctDnaHgMHgAddrRowStatusEntry
   ACCESS     not-accessible
   STATUS     mandatory
   DESCRIPTION
     "A single entry in the table represents a single 
      vctDnaHgMHgAddr component."
   INDEX {
      vctIndex,
      vctDnaIndex,
      vctDnaHgMIndex,
      vctDnaHgMHgAddrIndex }
::= { vctDnaHgMHgAddrRowStatusTable 1 }

VctDnaHgMHgAddrRowStatusEntry ::= SEQUENCE {
   vctDnaHgMHgAddrRowStatus
      RowStatus,
   vctDnaHgMHgAddrComponentName
      DisplayString,
   vctDnaHgMHgAddrStorageType
      StorageType,
   vctDnaHgMHgAddrIndex
      Integer32 }

vctDnaHgMHgAddrRowStatus OBJECT-TYPE
   SYNTAX     RowStatus 
   ACCESS     read-write
   STATUS     mandatory
   DESCRIPTION
     "This variable is used as the basis for SNMP naming of
      vctDnaHgMHgAddr components.
      These components can be added and deleted."
::= { vctDnaHgMHgAddrRowStatusEntry 1 }

vctDnaHgMHgAddrComponentName OBJECT-TYPE
   SYNTAX     DisplayString 
   ACCESS     read-only
   STATUS     mandatory
   DESCRIPTION
     "This variable provides the component's string name for
      use with the ASCII Console Interface"
::= { vctDnaHgMHgAddrRowStatusEntry 2 }

vctDnaHgMHgAddrStorageType OBJECT-TYPE
   SYNTAX     StorageType 
   ACCESS     read-only
   STATUS     mandatory
   DESCRIPTION
     "This variable represents the storage type value for the
      vctDnaHgMHgAddr tables."
::= { vctDnaHgMHgAddrRowStatusEntry 4 }

vctDnaHgMHgAddrIndex OBJECT-TYPE
   SYNTAX     Integer32 (0..1)
   ACCESS     not-accessible
   STATUS     mandatory
   DESCRIPTION
     "This variable represents the index for the vctDnaHgMHgAddr tables."
::= { vctDnaHgMHgAddrRowStatusEntry 10 }

vctDnaHgMHgAddrAddrTable OBJECT-TYPE
   SYNTAX     SEQUENCE OF VctDnaHgMHgAddrAddrEntry
   ACCESS     not-accessible
   STATUS     mandatory
   DESCRIPTION
     "This group contains attributes common to all DNAs. Every DNA 
      used in the network is defined with this group of 2 attributes. String 
      of address digits complemented by the NPI."
::= { vctDnaHgMHgAddr 10 }

vctDnaHgMHgAddrAddrEntry OBJECT-TYPE
   SYNTAX     VctDnaHgMHgAddrAddrEntry
   ACCESS     not-accessible
   STATUS     mandatory
   DESCRIPTION
     "An entry in the vctDnaHgMHgAddrAddrTable."
   INDEX {
      vctIndex,
      vctDnaIndex,
      vctDnaHgMIndex,
      vctDnaHgMHgAddrIndex }
::= { vctDnaHgMHgAddrAddrTable 1 }

VctDnaHgMHgAddrAddrEntry ::= SEQUENCE {
   vctDnaHgMHgAddrNumberingPlanIndicator
      INTEGER,
   vctDnaHgMHgAddrDataNetworkAddress
      DigitString }

vctDnaHgMHgAddrNumberingPlanIndicator OBJECT-TYPE
   SYNTAX     INTEGER  {
                 x121(0),
                 e164(1) }
   ACCESS     read-write
   STATUS     mandatory
   DESCRIPTION
     "This attribute indicates the Numbering Plan Indicator (NPI) the Dna 
      that is entered. Address may belong to X.121 or E.164 plans."
   DEFVAL     { x121 }
::= { vctDnaHgMHgAddrAddrEntry 1 }

vctDnaHgMHgAddrDataNetworkAddress OBJECT-TYPE
   SYNTAX     DigitString (SIZE (1..15))
   ACCESS     read-write
   STATUS     mandatory
   DESCRIPTION
     "This attribute contains digits which form unique identifier of the 
      customer interface. It can be compared (approximation only) 
      telephone number where phone number identifies unique telephone 
      set. Dna digits are selected and assigned by network operators."
::= { vctDnaHgMHgAddrAddrEntry 2 }


-- Fruni/n Dlci/n dc
-- This component defines direct call options for calls issued without 
-- operator intervention. Connection is complete and can be initiated 
-- automatically. Frequency of connection tries is controlled by retry 
-- timer.

vctDc OBJECT IDENTIFIER ::= { vct 3 }



vctDcRowStatusTable OBJECT-TYPE
   SYNTAX     SEQUENCE OF VctDcRowStatusEntry
   ACCESS     not-accessible
   STATUS     mandatory
   DESCRIPTION
     "This entry controls the addition and deletion of 
      vctDc components."
::= { vctDc 1 }

vctDcRowStatusEntry OBJECT-TYPE
   SYNTAX     VctDcRowStatusEntry
   ACCESS     not-accessible
   STATUS     mandatory
   DESCRIPTION
     "A single entry in the table represents a single 
      vctDc component."
   INDEX {
      vctIndex,
      vctDcIndex }
::= { vctDcRowStatusTable 1 }

VctDcRowStatusEntry ::= SEQUENCE {
   vctDcRowStatus
      RowStatus,
   vctDcComponentName
      DisplayString,
   vctDcStorageType
      StorageType,
   vctDcIndex
      Integer32 }

vctDcRowStatus OBJECT-TYPE
   SYNTAX     RowStatus 
   ACCESS     read-write
   STATUS     mandatory
   DESCRIPTION
     "This variable is used as the basis for SNMP naming of
      vctDc components.
      These components can be added and deleted."
::= { vctDcRowStatusEntry 1 }

vctDcComponentName OBJECT-TYPE
   SYNTAX     DisplayString 
   ACCESS     read-only
   STATUS     mandatory
   DESCRIPTION
     "This variable provides the component's string name for
      use with the ASCII Console Interface"
::= { vctDcRowStatusEntry 2 }

vctDcStorageType OBJECT-TYPE
   SYNTAX     StorageType 
   ACCESS     read-only
   STATUS     mandatory
   DESCRIPTION
     "This variable represents the storage type value for the
      vctDc tables."
::= { vctDcRowStatusEntry 4 }

vctDcIndex OBJECT-TYPE
   SYNTAX     Integer32 (1..10)
   ACCESS     not-accessible
   STATUS     mandatory
   DESCRIPTION
     "This variable represents the index for the vctDc tables."
::= { vctDcRowStatusEntry 10 }

vctDcOptionsTable OBJECT-TYPE
   SYNTAX     SEQUENCE OF VctDcOptionsEntry
   ACCESS     not-accessible
   STATUS     mandatory
   DESCRIPTION
     "Options group defines attributes associated with direct call. It 
      defines complete connection in terms of path and call options. This 
      connection can be permanent (pvc) or switched (svc). It can have 
      facilities. The total number of bytes of facilities including the 
      facility codes, and all of the facility data from all of the four classes 
      of facilities:
      ITU-T_Facilities
      DTE_Facilities
      National_Facilities
      International_Facilities
      must not exceed maximum subnet packet size defined for the whole 
      network in ModuleData Vcs component."
::= { vctDc 10 }

vctDcOptionsEntry OBJECT-TYPE
   SYNTAX     VctDcOptionsEntry
   ACCESS     not-accessible
   STATUS     mandatory
   DESCRIPTION
     "An entry in the vctDcOptionsTable."
   INDEX {
      vctIndex,
      vctDcIndex }
::= { vctDcOptionsTable 1 }

VctDcOptionsEntry ::= SEQUENCE {
   vctDcLocalNpi
      INTEGER,
   vctDcLocalDna
      DigitString,
   vctDcRemoteNpi
      INTEGER,
   vctDcRemoteDna
      DigitString,
   vctDcRemoteLcn
      Unsigned32,
   vctDcType
      INTEGER,
   vctDcSvcAutoCallRetry
      INTEGER,
   vctDcUserData
      HexString,
   vctDcDiscardPriority
      INTEGER,
   vctDcDataPath
      INTEGER,
   vctDcCugIndex
      Unsigned32,
   vctDcCugType
      INTEGER }

vctDcLocalNpi OBJECT-TYPE
   SYNTAX     INTEGER  {
                 x121(0),
                 e164(1) }
   ACCESS     read-write
   STATUS     mandatory
   DESCRIPTION
     "This attribute specifies the Numbering Plan Indicator (NPI) of the 
      localDna."
   DEFVAL     { x121 }
::= { vctDcOptionsEntry 1 }

vctDcLocalDna OBJECT-TYPE
   SYNTAX     DigitString (SIZE (0..15))
   ACCESS     read-write
   STATUS     mandatory
   DESCRIPTION
     "This attribute specifies the Data Network Address (Dna) of the local 
      DTE. This address is used in formatting of call request to 
      remoteDna."
::= { vctDcOptionsEntry 2 }

vctDcRemoteNpi OBJECT-TYPE
   SYNTAX     INTEGER  {
                 x121(0),
                 e164(1) }
   ACCESS     read-write
   STATUS     mandatory
   DESCRIPTION
     "Remote numbering Plan Indicator (Npi) indicates the numbering 
      plan used in the remoteDna."
   DEFVAL     { x121 }
::= { vctDcOptionsEntry 3 }

vctDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { vctDcOptionsEntry 4 }

vctDcRemoteLcn OBJECT-TYPE
   SYNTAX     Unsigned32 (0..4095)
   ACCESS     read-write
   STATUS     mandatory
   DESCRIPTION
     "This attribute provides the remote LCN (Logical Channel Number) 
      - it is used only for PVCs, where attribute type is set to 
      permanentMaster or permanentSlave or permanentBackupSlave.
      In switched case, value of remoteLcn is not known when call 
      request is made."
   DEFVAL     { 0 }
::= { vctDcOptionsEntry 5 }

vctDcType OBJECT-TYPE
   SYNTAX     INTEGER  {
                 switched(0),
                 permanentMaster(1),
                 permanentSlave(2),
                 permanentBackupSlave(3),
                 permanentSlaveWithBackup(4) }
   ACCESS     read-write
   STATUS     mandatory
   DESCRIPTION
     "This attribute specifies the type of Vc call:
      switched,
      permanentMaster, 
      permanentSlave, 
      permanentSlaveWithBackup,
      permanentBackupSlave. 
      
      If the value of this attribute is set to switched then the remote end 
      must also be provisioned as switched. No information at the remote 
      end is defined about this switched interface.
      
      If the value is set to permanentMaster, then a permanent 
      connection will be established between 2 ends. The remote end 
      must be defined as a permanentSlave, permanentBackupSlave or 
      permanentSlaveWithBackup. The connection cannot be established 
      if the remote end is defined as anything else. The end defined as 
      permanentMaster always initiates the calls. It will attempt to call 
      once per minute.
      
      
      If the value is set to permanentSlave then a permanent connection 
      will be established between 2 ends. The remote end must be defined 
      as a permanentMaster. The connection cannot be established if the 
      remote end is defined as anything else. The permanentSlave end 
      will attempt to call once per minute.
      
      If the value is set to permanentSlaveWithBackup then a permanent 
      connection will be established between the two ends. The remote 
      end must be defined as a permanentMaster. The connection cannot 
      be established if the remote interface end is defined as anything 
      else. The permanentSlaveWithBackup end will attempt to call once 
      per minute. When type is set to permanentSlaveWithBackup 
      connection will be cleared if interface becomes unavailable. This 
      enables a retry of the connection which can be redirected to 
      permanentBackupSlave.
      
      If the value is set to permanentBackupSlave then a permanent 
      connection will be established between the 2 ends only if the 
      permanentMaster end is disconnected from the 
      permanentSlaveWithBackup end and a backup call is established 
      by the redirection system. If the permanentSlaveWithBackup 
      interface becomes available again, the permanentBackupSlave end 
      is disconnected and the permanentSlaveWithBackup end is 
      reconnected to the permanentMaster end. The 
      permanentBackupSlave end does not try to establish pvc call."
   DEFVAL     { switched }
::= { vctDcOptionsEntry 6 }

vctDcSvcAutoCallRetry OBJECT-TYPE
   SYNTAX     INTEGER  {
                 no(0),
                 yes(1) }
   ACCESS     read-write
   STATUS     mandatory
   DESCRIPTION
     "svcAutoCallRetry is used only for switched calls, in which case the 
      attribute type is set to switched. Otherwise, this attribute is ignored 
      by the Vcs.
      This attribute, if set to yes for Svc, indicates that the Vc will 
      continually try to establish the SVC rather than clearing the Vc after 
      the first unsuccessful call attempt. Further, if the call fails while in 
      data transfer phase, then the Vc will automatically attempt to 
      reconnect. The call attempts are made by the Vc once per time 
      provisioned in InterfaceOptions as callRetryTimer, repeatedly. If set 
      to no for SVCs, then the Vc behaves in the standard mode, making a 
      single call attempt."
   DEFVAL     { no }
::= { vctDcOptionsEntry 7 }

vctDcUserData OBJECT-TYPE
   SYNTAX     HexString (SIZE (0..128))
   ACCESS     read-write
   STATUS     mandatory
   DESCRIPTION
     "This attribute contains the user data, if present. userData is a 0 to 16 
      length string which is appended to the call request packet that is 
      presented to the called (destination) DTE.
      
      User data can be a 0 to 128 byte string for fast select calls; 
      otherwise it is 0 to 16 byte string. 
      
      Fast select calls are indicated as such using the X.25 ITU-T facility 
      for 'Reverse Charging'.
      
      The length of the user data attribute is not verified during service 
      provisioning. If more than 16 bytes of user data is specified on a 
      call without the fast select option, then the call is cleared with a 
      clear cause of 'local procedure error', and a diagnostic code of 39 
      (as defined in the ITU-T X.25 Recommendation)."
::= { vctDcOptionsEntry 8 }

vctDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { vctDcOptionsEntry 10 }

vctDcDataPath OBJECT-TYPE
   SYNTAX     INTEGER  {
                 dprsOnly(0),
                 dprsMcsOnly(1),
                 dprsMcsFirst(2),
                 useDnaValue(3) }
   ACCESS     read-write
   STATUS     mandatory
   DESCRIPTION
     "This attribute specifies the data path to be used by Virtual Circuits 
      on this interface. The value of the dataPath attribute in the Dna 
      component is overridden by this attribute if the value is not 
      useDnaValue.
      
      This value applies to the connection after data transfer state is 
      reached. All the data and control trafic will be sent using this data 
      path. If the provisioned dataPath is not available the connection is 
      not established.
      
      The value of the dataPath is signalled by both ends of the 
      connection. If this value is not the same at both ends dprsOnly is 
      used for the duration of the connection.
      
      A virtual circuit connection is always established using dprsOnly 
      even if this attribute is provisioned as some other value.
      
      dprsOnly - dynamic packet routing system is used
      
      dprsMcsOnly - dprs Multi-Service Cut-Through Switching path is 
      used.
      
      dprsMcsFirst - dprs Multi-Service Cut-Through Switching path is 
      used if it is available. If it is not avaliable dprsOnly is used.
      
      useDnaValue - use the value provisioned in Dna component."
   DEFVAL     { dprsOnly }
::= { vctDcOptionsEntry 11 }

vctDcCugIndex OBJECT-TYPE
   SYNTAX     Unsigned32 (0..255)
   ACCESS     read-write
   STATUS     mandatory
   DESCRIPTION
     "This attribute specifies the CUG index which is to be signalled in 
      PVC call requests to the remote end.
      
      The type of CUG signalling is defined in attribute cugType in this 
      component."
   DEFVAL     { 0 }
::= { vctDcOptionsEntry 13 }

vctDcCugType OBJECT-TYPE
   SYNTAX     INTEGER  {
                 doNotSignal(0),
                 cug(3),
                 cugOa(9) }
   ACCESS     read-write
   STATUS     mandatory
   DESCRIPTION
     "This attribute specifies the type of CUG signalling to be used in 
      PVC call request. Index of CUG to be used is defined in attribute 
      cugIndex in this component.
      
      Possible values are:
      cug - signal cug
      cugOa - signal cug with outgoing access
      doNotSignal - no CUG in call request"
   DEFVAL     { doNotSignal }
::= { vctDcOptionsEntry 14 }

vctDcCfaTable OBJECT-TYPE
   SYNTAX     SEQUENCE OF VctDcCfaEntry
   ACCESS     not-accessible
   STATUS     mandatory
   DESCRIPTION
     "This is the i'th ITU-T facility required for this direct call. Within 
      the provisioning system, the user specifies the facility code along 
      with the facility parameters. The facility is represented internally as 
      a hexadecimal string following the X.25 ITU-T representation for 
      facility data.
      The user specifies the facility code when adding, changing or 
      deleting a facility. The upper two bits of the facility code indicate 
      the class of facility. From the class of the facility, one can derive the 
      number of bytes of facility data, as follows:
      Class A - 1 byte of fax data
      Class B - 2 bytes of fax data
      Class C - 3 bytes of fax data
      Class D - variable length of fax data."
::= { vctDc 267 }

vctDcCfaEntry OBJECT-TYPE
   SYNTAX     VctDcCfaEntry
   ACCESS     not-accessible
   STATUS     mandatory
   DESCRIPTION
     "An entry in the vctDcCfaTable."
   INDEX {
      vctIndex,
      vctDcIndex,
      vctDcCfaIndex }
::= { vctDcCfaTable 1 }

VctDcCfaEntry ::= SEQUENCE {
   vctDcCfaIndex
      Integer32,
   vctDcCfaValue
      HexString,
   vctDcCfaRowStatus
      RowStatus }

vctDcCfaIndex OBJECT-TYPE
   SYNTAX     Integer32 (1 | 2 | 3 | 4 | 9 | 66 | 67 | 68 | 71 | 72 | 73 | 196 | 198)
   ACCESS     not-accessible
   STATUS     mandatory
   DESCRIPTION
     "This variable represents the index for the vctDcCfaTable."
::= { vctDcCfaEntry 1 }

vctDcCfaValue OBJECT-TYPE
   SYNTAX     HexString (SIZE (0..128))
   ACCESS     read-write
   STATUS     mandatory
   DESCRIPTION
     "This variable represents an individual value for the
      vctDcCfaTable."
::= { vctDcCfaEntry 2 }

vctDcCfaRowStatus OBJECT-TYPE
   SYNTAX     RowStatus 
   ACCESS     write-only
   STATUS     mandatory
   DESCRIPTION
     "This variable is used to control the addition and deletion 
      of individual values of the vctDcCfaTable."
::= { vctDcCfaEntry 3 }

vctDcDfaTable OBJECT-TYPE
   SYNTAX     SEQUENCE OF VctDcDfaEntry
   ACCESS     not-accessible
   STATUS     mandatory
   DESCRIPTION
     "This is the i'th DTE facility required for this direct call. Within the 
      provisioning system, the user specifies the facility code along with 
      the facility parameters. The facility is represented internally as a 
      hexadecimal string following the X.25 ITU-T representation for 
      facility data."
::= { vctDc 268 }

vctDcDfaEntry OBJECT-TYPE
   SYNTAX     VctDcDfaEntry
   ACCESS     not-accessible
   STATUS     mandatory
   DESCRIPTION
     "An entry in the vctDcDfaTable."
   INDEX {
      vctIndex,
      vctDcIndex,
      vctDcDfaIndex }
::= { vctDcDfaTable 1 }

VctDcDfaEntry ::= SEQUENCE {
   vctDcDfaIndex
      Integer32,
   vctDcDfaValue
      HexString,
   vctDcDfaRowStatus
      RowStatus }

vctDcDfaIndex OBJECT-TYPE
   SYNTAX     Integer32 (10 | 11 | 201 | 202 | 203 | 210 | 211)
   ACCESS     not-accessible
   STATUS     mandatory
   DESCRIPTION
     "This variable represents the index for the vctDcDfaTable."
::= { vctDcDfaEntry 1 }

vctDcDfaValue OBJECT-TYPE
   SYNTAX     HexString (SIZE (0..128))
   ACCESS     read-write
   STATUS     mandatory
   DESCRIPTION
     "This variable represents an individual value for the
      vctDcDfaTable."
::= { vctDcDfaEntry 2 }

vctDcDfaRowStatus OBJECT-TYPE
   SYNTAX     RowStatus 
   ACCESS     write-only
   STATUS     mandatory
   DESCRIPTION
     "This variable is used to control the addition and deletion 
      of individual values of the vctDcDfaTable."
::= { vctDcDfaEntry 3 }

vctDcNfaTable OBJECT-TYPE
   SYNTAX     SEQUENCE OF VctDcNfaEntry
   ACCESS     not-accessible
   STATUS     obsolete
   DESCRIPTION
     "This is the i'th National facility required for this direct call. Within 
      the provisioning system, the user specifies the facility code along 
      with the facility parameters. The facility is represented internally as 
      a hexadecimal string following the X.25 ITU-T representation for 
      facility data.
      
      Two explicit attributes discardPriority and transferPriority are 
      created to replace H.01 and H.30 in the group 
      VcsDirectCallOptionsProv of this file. The migrate escape here 
      propagates the old provisioning data under H.01 and H.30 into 
      discardPriority and transferPriority. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { vctDc 269 }

vctDcNfaEntry OBJECT-TYPE
   SYNTAX     VctDcNfaEntry
   ACCESS     not-accessible
   STATUS     obsolete
   DESCRIPTION
     "An entry in the vctDcNfaTable."
   INDEX {
      vctIndex,
      vctDcIndex,
      vctDcNfaIndex }
::= { vctDcNfaTable 1 }

VctDcNfaEntry ::= SEQUENCE {
   vctDcNfaIndex
      Integer32,
   vctDcNfaValue
      HexString,
   vctDcNfaRowStatus
      RowStatus }

vctDcNfaIndex OBJECT-TYPE
   SYNTAX     Integer32 (1 | 48 | 127 | 212)
   ACCESS     not-accessible
   STATUS     obsolete
   DESCRIPTION
     "This variable represents the index for the vctDcNfaTable."
::= { vctDcNfaEntry 1 }

vctDcNfaValue OBJECT-TYPE
   SYNTAX     HexString (SIZE (0..128))
   ACCESS     read-write
   STATUS     obsolete
   DESCRIPTION
     "This variable represents an individual value for the
      vctDcNfaTable."
::= { vctDcNfaEntry 2 }

vctDcNfaRowStatus OBJECT-TYPE
   SYNTAX     RowStatus 
   ACCESS     write-only
   STATUS     obsolete
   DESCRIPTION
     "This variable is used to control the addition and deletion 
      of individual values of the vctDcNfaTable."
::= { vctDcNfaEntry 3 }

vctDcIfaTable OBJECT-TYPE
   SYNTAX     SEQUENCE OF VctDcIfaEntry
   ACCESS     not-accessible
   STATUS     mandatory
   DESCRIPTION
     "This is the i'th International facility required for this direct call. 
      Within the provisioning system, the user specifies the facility code 
      along with the facility parameters. The facility is represented 
      internally as a hexadecimal string following the X.25 ITU-T 
      representation for facility data."
::= { vctDc 270 }

vctDcIfaEntry OBJECT-TYPE
   SYNTAX     VctDcIfaEntry
   ACCESS     not-accessible
   STATUS     mandatory
   DESCRIPTION
     "An entry in the vctDcIfaTable."
   INDEX {
      vctIndex,
      vctDcIndex,
      vctDcIfaIndex }
::= { vctDcIfaTable 1 }

VctDcIfaEntry ::= SEQUENCE {
   vctDcIfaIndex
      Integer32,
   vctDcIfaValue
      HexString,
   vctDcIfaRowStatus
      RowStatus }

vctDcIfaIndex OBJECT-TYPE
   SYNTAX     Integer32 (1..255)
   ACCESS     not-accessible
   STATUS     mandatory
   DESCRIPTION
     "This variable represents the index for the vctDcIfaTable."
::= { vctDcIfaEntry 1 }

vctDcIfaValue OBJECT-TYPE
   SYNTAX     HexString (SIZE (0..128))
   ACCESS     read-write
   STATUS     mandatory
   DESCRIPTION
     "This variable represents an individual value for the
      vctDcIfaTable."
::= { vctDcIfaEntry 2 }

vctDcIfaRowStatus OBJECT-TYPE
   SYNTAX     RowStatus 
   ACCESS     write-only
   STATUS     mandatory
   DESCRIPTION
     "This variable is used to control the addition and deletion 
      of individual values of the vctDcIfaTable."
::= { vctDcIfaEntry 3 }


-- ... Vc()
-- This component defines display of general Vc dynamic attributes

vctVc OBJECT IDENTIFIER ::= { vct 4 }



vctVcRowStatusTable OBJECT-TYPE
   SYNTAX     SEQUENCE OF VctVcRowStatusEntry
   ACCESS     not-accessible
   STATUS     mandatory
   DESCRIPTION
     "This entry controls the addition and deletion of 
      vctVc components."
::= { vctVc 1 }

vctVcRowStatusEntry OBJECT-TYPE
   SYNTAX     VctVcRowStatusEntry
   ACCESS     not-accessible
   STATUS     mandatory
   DESCRIPTION
     "A single entry in the table represents a single 
      vctVc component."
   INDEX {
      vctIndex,
      vctVcIndex }
::= { vctVcRowStatusTable 1 }

VctVcRowStatusEntry ::= SEQUENCE {
   vctVcRowStatus
      RowStatus,
   vctVcComponentName
      DisplayString,
   vctVcStorageType
      StorageType,
   vctVcIndex
      NonReplicated }

vctVcRowStatus OBJECT-TYPE
   SYNTAX     RowStatus 
   ACCESS     read-only
   STATUS     mandatory
   DESCRIPTION
     "This variable is used as the basis for SNMP naming of
      vctVc components.
      These components cannot be added nor deleted."
::= { vctVcRowStatusEntry 1 }

vctVcComponentName OBJECT-TYPE
   SYNTAX     DisplayString 
   ACCESS     read-only
   STATUS     mandatory
   DESCRIPTION
     "This variable provides the component's string name for
      use with the ASCII Console Interface"
::= { vctVcRowStatusEntry 2 }

vctVcStorageType OBJECT-TYPE
   SYNTAX     StorageType 
   ACCESS     read-only
   STATUS     mandatory
   DESCRIPTION
     "This variable represents the storage type value for the
      vctVc tables."
::= { vctVcRowStatusEntry 4 }

vctVcIndex OBJECT-TYPE
   SYNTAX     NonReplicated 
   ACCESS     not-accessible
   STATUS     mandatory
   DESCRIPTION
     "This variable represents the index for the vctVc tables."
::= { vctVcRowStatusEntry 10 }

vctVcCadTable OBJECT-TYPE
   SYNTAX     SEQUENCE OF VctVcCadEntry
   ACCESS     not-accessible
   STATUS     mandatory
   DESCRIPTION
     "This group represents operational call data related to General Vc. It 
      can be displayed only for General Vc which is created by 
      application."
::= { vctVc 10 }

vctVcCadEntry OBJECT-TYPE
   SYNTAX     VctVcCadEntry
   ACCESS     not-accessible
   STATUS     mandatory
   DESCRIPTION
     "An entry in the vctVcCadTable."
   INDEX {
      vctIndex,
      vctVcIndex }
::= { vctVcCadTable 1 }

VctVcCadEntry ::= SEQUENCE {
   vctVcType
      INTEGER,
   vctVcState
      INTEGER,
   vctVcPreviousState
      INTEGER,
   vctVcDiagnosticCode
      Unsigned32,
   vctVcPreviousDiagnosticCode
      Unsigned32,
   vctVcCalledNpi
      INTEGER,
   vctVcCalledDna
      DigitString,
   vctVcCalledLcn
      Unsigned32,
   vctVcCallingNpi
      INTEGER,
   vctVcCallingDna
      DigitString,
   vctVcCallingLcn
      Unsigned32,
   vctVcAccountingEnabled
      INTEGER,
   vctVcFastSelectCall
      INTEGER,
   vctVcLocalRxPktSize
      INTEGER,
   vctVcLocalTxPktSize
      INTEGER,
   vctVcLocalTxWindowSize
      Unsigned32,
   vctVcLocalRxWindowSize
      Unsigned32,
   vctVcPathReliability
      INTEGER,
   vctVcAccountingEnd
      INTEGER,
   vctVcPriority
      INTEGER,
   vctVcSegmentSize
      Unsigned32,
   vctVcSubnetTxPktSize
      INTEGER,
   vctVcSubnetTxWindowSize
      Unsigned32,
   vctVcSubnetRxPktSize
      INTEGER,
   vctVcSubnetRxWindowSize
      Unsigned32,
   vctVcMaxSubnetPktSize
      Unsigned32,
   vctVcTransferPriorityToNetwork
      INTEGER,
   vctVcTransferPriorityFromNetwork
      INTEGER }

vctVcType OBJECT-TYPE
   SYNTAX     INTEGER  {
                 svc(0),
                 pvc(1) }
   ACCESS     read-only
   STATUS     mandatory
   DESCRIPTION
     "This attribute displays the type of call, pvc or svc. type is provided 
      at provisioning time."
::= { vctVcCadEntry 1 }

vctVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { vctVcCadEntry 2 }

vctVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { vctVcCadEntry 3 }

vctVcDiagnosticCode OBJECT-TYPE
   SYNTAX     Unsigned32 (0..255)
   ACCESS     read-only
   STATUS     mandatory
   DESCRIPTION
     "This attribute displays the internal substate of call control. It is used 
      to further refine state of call processing."
::= { vctVcCadEntry 4 }

vctVcPreviousDiagnosticCode OBJECT-TYPE
   SYNTAX     Unsigned32 (0..255)
   ACCESS     read-only
   STATUS     mandatory
   DESCRIPTION
     "This attribute displays the internal substate of call control. It is used 
      to further refine state of call processing."
::= { vctVcCadEntry 5 }

vctVcCalledNpi OBJECT-TYPE
   SYNTAX     INTEGER  {
                 x121(0),
                 e164(1) }
   ACCESS     read-only
   STATUS     mandatory
   DESCRIPTION
     "This attribute displays the Numbering Plan Indicator (NPI) of the 
      called end."
::= { vctVcCadEntry 6 }

vctVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { vctVcCadEntry 7 }

vctVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { vctVcCadEntry 8 }

vctVcCallingNpi OBJECT-TYPE
   SYNTAX     INTEGER  {
                 x121(0),
                 e164(1) }
   ACCESS     read-only
   STATUS     mandatory
   DESCRIPTION
     "This attribute displays the Numbering Plan Indicator (NPI) of the 
      calling end."
::= { vctVcCadEntry 9 }

vctVcCallingDna OBJECT-TYPE
   SYNTAX     DigitString (SIZE (1..15))
   ACCESS     read-only
   STATUS     mandatory
   DESCRIPTION
     "This attribute displays the Data Network Address (Dna) of the 
      calling end."
::= { vctVcCadEntry 10 }

vctVcCallingLcn OBJECT-TYPE
   SYNTAX     Unsigned32 (1..65535)
   ACCESS     read-only
   STATUS     mandatory
   DESCRIPTION
     "This attribute displays the Logical Channel Number of the calling 
      end."
::= { vctVcCadEntry 11 }

vctVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { vctVcCadEntry 12 }

vctVcFastSelectCall OBJECT-TYPE
   SYNTAX     INTEGER  {
                 no(0),
                 yes(1) }
   ACCESS     read-only
   STATUS     mandatory
   DESCRIPTION
     "This attribute displays that this is a fast select call."
::= { vctVcCadEntry 13 }

vctVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { vctVcCadEntry 14 }

vctVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { vctVcCadEntry 15 }

vctVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { vctVcCadEntry 16 }

vctVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { vctVcCadEntry 17 }

vctVcPathReliability OBJECT-TYPE
   SYNTAX     INTEGER  {
                 high(0),
                 normal(1) }
   ACCESS     read-only
   STATUS     mandatory
   DESCRIPTION
     "This attribute displays the path reliability."
::= { vctVcCadEntry 19 }

vctVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { vctVcCadEntry 20 }

vctVcPriority OBJECT-TYPE
   SYNTAX     INTEGER  {
                 normal(0),
                 high(1) }
   ACCESS     read-only
   STATUS     mandatory
   DESCRIPTION
     "This attribute displays whether the call is a normal or a high 
      priority call."
::= { vctVcCadEntry 21 }

vctVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { vctVcCadEntry 22 }

vctVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { vctVcCadEntry 23 }

vctVcSubnetTxWindowSize OBJECT-TYPE
   SYNTAX     Unsigned32 (0..4096)
   ACCESS     read-only
   STATUS     mandatory
   DESCRIPTION
     "This attribute displays the current send window size of Vc."
::= { vctVcCadEntry 24 }

vctVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { vctVcCadEntry 25 }

vctVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { vctVcCadEntry 26 }

vctVcMaxSubnetPktSize OBJECT-TYPE
   SYNTAX     Unsigned32 (0..4096)
   ACCESS     read-only
   STATUS     mandatory
   DESCRIPTION
     "This attribute displays the maximum packet size allowed on Vc."
::= { vctVcCadEntry 27 }

vctVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { vctVcCadEntry 28 }

vctVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { vctVcCadEntry 29 }

vctVcIntdTable OBJECT-TYPE
   SYNTAX     SEQUENCE OF VctVcIntdEntry
   ACCESS     not-accessible
   STATUS     mandatory
   DESCRIPTION
     "This group defines display of interval data collected by Vc. Data in 
      this group is variable and may depend on time when this display 
      command is issued."
::= { vctVc 11 }

vctVcIntdEntry OBJECT-TYPE
   SYNTAX     VctVcIntdEntry
   ACCESS     not-accessible
   STATUS     mandatory
   DESCRIPTION
     "An entry in the vctVcIntdTable."
   INDEX {
      vctIndex,
      vctVcIndex }
::= { vctVcIntdTable 1 }

VctVcIntdEntry ::= SEQUENCE {
   vctVcCallReferenceNumber
      Hex,
   vctVcElapsedTimeTillNow
      Unsigned32,
   vctVcSegmentsRx
      Unsigned32,
   vctVcSegmentsSent
      Unsigned32,
   vctVcStartTime
      EnterpriseDateAndTime }

vctVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { vctVcIntdEntry 1 }

vctVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { vctVcIntdEntry 2 }

vctVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { vctVcIntdEntry 3 }

vctVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { vctVcIntdEntry 4 }

vctVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { vctVcIntdEntry 5 }

vctVcStatsTable OBJECT-TYPE
   SYNTAX     SEQUENCE OF VctVcStatsEntry
   ACCESS     not-accessible
   STATUS     mandatory
   DESCRIPTION
     "... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { vctVc 12 }

vctVcStatsEntry OBJECT-TYPE
   SYNTAX     VctVcStatsEntry
   ACCESS     not-accessible
   STATUS     mandatory
   DESCRIPTION
     "An entry in the vctVcStatsTable."
   INDEX {
      vctIndex,
      vctVcIndex }
::= { vctVcStatsTable 1 }

VctVcStatsEntry ::= SEQUENCE {
   vctVcAckStackingTimeouts
      Unsigned32,
   vctVcOutOfRangeFrmFromSubnet
      Unsigned32,
   vctVcDuplicatesFromSubnet
      Unsigned32,
   vctVcFrmRetryTimeouts
      Unsigned32,
   vctVcPeakRetryQueueSize
      Unsigned32,
   vctVcPeakOoSeqQueueSize
      Unsigned32,
   vctVcPeakOoSeqFrmForwarded
      Unsigned32,
   vctVcPeakStackedAcksRx
      Unsigned32,
   vctVcSubnetRecoveries
      Unsigned32,
   vctVcWindowClosuresToSubnet
      Unsigned32,
   vctVcWindowClosuresFromSubnet
      Unsigned32,
   vctVcWrTriggers
      Unsigned32 }

vctVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { vctVcStatsEntry 1 }

vctVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { vctVcStatsEntry 2 }

vctVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { vctVcStatsEntry 3 }

vctVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { vctVcStatsEntry 4 }

vctVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { vctVcStatsEntry 5 }

vctVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { vctVcStatsEntry 6 }

vctVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { vctVcStatsEntry 7 }

vctVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { vctVcStatsEntry 8 }

vctVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { vctVcStatsEntry 9 }

vctVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { vctVcStatsEntry 10 }

vctVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { vctVcStatsEntry 11 }

vctVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { vctVcStatsEntry 12 }


-- 
-- This component defines the statistics collected by Frame Relay Vc. 
-- It is needed for ligthweight vc.

vctVcfr OBJECT IDENTIFIER ::= { vct 5 }



vctVcfrRowStatusTable OBJECT-TYPE
   SYNTAX     SEQUENCE OF VctVcfrRowStatusEntry
   ACCESS     not-accessible
   STATUS     mandatory
   DESCRIPTION
     "This entry controls the addition and deletion of 
      vctVcfr components."
::= { vctVcfr 1 }

vctVcfrRowStatusEntry OBJECT-TYPE
   SYNTAX     VctVcfrRowStatusEntry
   ACCESS     not-accessible
   STATUS     mandatory
   DESCRIPTION
     "A single entry in the table represents a single 
      vctVcfr component."
   INDEX {
      vctIndex,
      vctVcfrIndex }
::= { vctVcfrRowStatusTable 1 }

VctVcfrRowStatusEntry ::= SEQUENCE {
   vctVcfrRowStatus
      RowStatus,
   vctVcfrComponentName
      DisplayString,
   vctVcfrStorageType
      StorageType,
   vctVcfrIndex
      NonReplicated }

vctVcfrRowStatus OBJECT-TYPE
   SYNTAX     RowStatus 
   ACCESS     read-only
   STATUS     mandatory
   DESCRIPTION
     "This variable is used as the basis for SNMP naming of
      vctVcfr components.
      These components cannot be added nor deleted."
::= { vctVcfrRowStatusEntry 1 }

vctVcfrComponentName OBJECT-TYPE
   SYNTAX     DisplayString 
   ACCESS     read-only
   STATUS     mandatory
   DESCRIPTION
     "This variable provides the component's string name for
      use with the ASCII Console Interface"
::= { vctVcfrRowStatusEntry 2 }

vctVcfrStorageType OBJECT-TYPE
   SYNTAX     StorageType 
   ACCESS     read-only
   STATUS     mandatory
   DESCRIPTION
     "This variable represents the storage type value for the
      vctVcfr tables."
::= { vctVcfrRowStatusEntry 4 }

vctVcfrIndex OBJECT-TYPE
   SYNTAX     NonReplicated 
   ACCESS     not-accessible
   STATUS     mandatory
   DESCRIPTION
     "This variable represents the index for the vctVcfr tables."
::= { vctVcfrRowStatusEntry 10 }

vctVcfrCadTable OBJECT-TYPE
   SYNTAX     SEQUENCE OF VctVcfrCadEntry
   ACCESS     not-accessible
   STATUS     mandatory
   DESCRIPTION
     "This group represents operational call data related to Frame Relay 
      Vc. It can be displayed only for Frame Relay Vc which is created by 
      application."
::= { vctVcfr 10 }

vctVcfrCadEntry OBJECT-TYPE
   SYNTAX     VctVcfrCadEntry
   ACCESS     not-accessible
   STATUS     mandatory
   DESCRIPTION
     "An entry in the vctVcfrCadTable."
   INDEX {
      vctIndex,
      vctVcfrIndex }
::= { vctVcfrCadTable 1 }

VctVcfrCadEntry ::= SEQUENCE {
   vctVcfrType
      INTEGER,
   vctVcfrState
      INTEGER,
   vctVcfrPreviousState
      INTEGER,
   vctVcfrDiagnosticCode
      Unsigned32,
   vctVcfrPreviousDiagnosticCode
      Unsigned32,
   vctVcfrCalledNpi
      INTEGER,
   vctVcfrCalledDna
      DigitString,
   vctVcfrCalledLcn
      Unsigned32,
   vctVcfrCallingNpi
      INTEGER,
   vctVcfrCallingDna
      DigitString,
   vctVcfrCallingLcn
      Unsigned32,
   vctVcfrAccountingEnabled
      INTEGER,
   vctVcfrFastSelectCall
      INTEGER,
   vctVcfrPathReliability
      INTEGER,
   vctVcfrAccountingEnd
      INTEGER,
   vctVcfrPriority
      INTEGER,
   vctVcfrSegmentSize
      Unsigned32,
   vctVcfrMaxSubnetPktSize
      Unsigned32,
   vctVcfrRcosToNetwork
      INTEGER,
   vctVcfrRcosFromNetwork
      INTEGER,
   vctVcfrEmissionPriorityToNetwork
      INTEGER,
   vctVcfrEmissionPriorityFromNetwork
      INTEGER,
   vctVcfrDataPath
      AsciiString }

vctVcfrType OBJECT-TYPE
   SYNTAX     INTEGER  {
                 svc(0),
                 pvc(1),
                 spvc(2) }
   ACCESS     read-only
   STATUS     mandatory
   DESCRIPTION
     "This attribute displays the type of call, pvc,svc or spvc."
::= { vctVcfrCadEntry 1 }

vctVcfrState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { vctVcfrCadEntry 2 }

vctVcfrPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { vctVcfrCadEntry 3 }

vctVcfrDiagnosticCode OBJECT-TYPE
   SYNTAX     Unsigned32 (0..255)
   ACCESS     read-only
   STATUS     mandatory
   DESCRIPTION
     "This attribute displays the internal substate of call control. It is used 
      to further refine state of call processing."
::= { vctVcfrCadEntry 4 }

vctVcfrPreviousDiagnosticCode OBJECT-TYPE
   SYNTAX     Unsigned32 (0..255)
   ACCESS     read-only
   STATUS     mandatory
   DESCRIPTION
     "This attribute displays the internal substate of call control. It is used 
      to further refine state of call processing."
::= { vctVcfrCadEntry 5 }

vctVcfrCalledNpi OBJECT-TYPE
   SYNTAX     INTEGER  {
                 x121(0),
                 e164(1) }
   ACCESS     read-only
   STATUS     mandatory
   DESCRIPTION
     "This attribute displays the Numbering Plan Indicator (NPI) of the 
      called end."
::= { vctVcfrCadEntry 6 }

vctVcfrCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { vctVcfrCadEntry 7 }

vctVcfrCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { vctVcfrCadEntry 8 }

vctVcfrCallingNpi OBJECT-TYPE
   SYNTAX     INTEGER  {
                 x121(0),
                 e164(1) }
   ACCESS     read-only
   STATUS     mandatory
   DESCRIPTION
     "This attribute displays the Numbering Plan Indicator (NPI) of the 
      calling end."
::= { vctVcfrCadEntry 9 }

vctVcfrCallingDna OBJECT-TYPE
   SYNTAX     DigitString (SIZE (1..15))
   ACCESS     read-only
   STATUS     mandatory
   DESCRIPTION
     "This attribute displays the Data Network Address (Dna) of the 
      calling end."
::= { vctVcfrCadEntry 10 }

vctVcfrCallingLcn OBJECT-TYPE
   SYNTAX     Unsigned32 (1..65535)
   ACCESS     read-only
   STATUS     mandatory
   DESCRIPTION
     "This attribute displays the Logical Channel Number of the calling 
      end."
::= { vctVcfrCadEntry 11 }

vctVcfrAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { vctVcfrCadEntry 12 }

vctVcfrFastSelectCall OBJECT-TYPE
   SYNTAX     INTEGER  {
                 no(0),
                 yes(1) }
   ACCESS     read-only
   STATUS     mandatory
   DESCRIPTION
     "This attribute displays that this is a fast select call."
::= { vctVcfrCadEntry 13 }

vctVcfrPathReliability OBJECT-TYPE
   SYNTAX     INTEGER  {
                 high(0),
                 normal(1) }
   ACCESS     read-only
   STATUS     mandatory
   DESCRIPTION
     "This attribute displays the path reliability."
::= { vctVcfrCadEntry 19 }

vctVcfrAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { vctVcfrCadEntry 20 }

vctVcfrPriority OBJECT-TYPE
   SYNTAX     INTEGER  {
                 normal(0),
                 high(1) }
   ACCESS     read-only
   STATUS     mandatory
   DESCRIPTION
     "This attribute displays whether the call is a normal or a high 
      priority call."
::= { vctVcfrCadEntry 21 }

vctVcfrSegmentSize OBJECT-TYPE
   SYNTAX     Unsigned32 (0..4096)
   ACCESS     read-only
   STATUS     mandatory
   DESCRIPTION
     "This attribute displays the segment size (in bytes) used on the call. 
      It is used to calculate the number of segments transmitted and 
      received."
::= { vctVcfrCadEntry 22 }

vctVcfrMaxSubnetPktSize OBJECT-TYPE
   SYNTAX     Unsigned32 (0..4096)
   ACCESS     read-only
   STATUS     mandatory
   DESCRIPTION
     "This attribute indicates the maximum packet size allowed on the Vc."
::= { vctVcfrCadEntry 27 }

vctVcfrRcosToNetwork OBJECT-TYPE
   SYNTAX     INTEGER  {
                 throughput(0),
                 delay(1),
                 multimedia(2) }
   ACCESS     read-only
   STATUS     mandatory
   DESCRIPTION
     "This attribute indicates the routing metric routing class of service to
      the network."
::= { vctVcfrCadEntry 28 }

vctVcfrRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { vctVcfrCadEntry 29 }

vctVcfrEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { vctVcfrCadEntry 30 }

vctVcfrEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { vctVcfrCadEntry 31 }

vctVcfrDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { vctVcfrCadEntry 32 }

vctVcfrIntdTable OBJECT-TYPE
   SYNTAX     SEQUENCE OF VctVcfrIntdEntry
   ACCESS     not-accessible
   STATUS     mandatory
   DESCRIPTION
     "This group defines display of interval data collected by Vc. Data in 
      this group is variable and may depend on time when this display 
      command is issued."
::= { vctVcfr 11 }

vctVcfrIntdEntry OBJECT-TYPE
   SYNTAX     VctVcfrIntdEntry
   ACCESS     not-accessible
   STATUS     mandatory
   DESCRIPTION
     "An entry in the vctVcfrIntdTable."
   INDEX {
      vctIndex,
      vctVcfrIndex }
::= { vctVcfrIntdTable 1 }

VctVcfrIntdEntry ::= SEQUENCE {
   vctVcfrCallReferenceNumber
      Hex,
   vctVcfrElapsedTimeTillNow
      Unsigned32,
   vctVcfrSegmentsRx
      Unsigned32,
   vctVcfrSegmentsSent
      Unsigned32,
   vctVcfrStartTime
      EnterpriseDateAndTime }

vctVcfrCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { vctVcfrIntdEntry 1 }

vctVcfrElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { vctVcfrIntdEntry 2 }

vctVcfrSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { vctVcfrIntdEntry 3 }

vctVcfrSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { vctVcfrIntdEntry 4 }

vctVcfrStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { vctVcfrIntdEntry 5 }

vctVcfrFrdTable OBJECT-TYPE
   SYNTAX     SEQUENCE OF VctVcfrFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { vctVcfr 12 }

vctVcfrFrdEntry OBJECT-TYPE
   SYNTAX     VctVcfrFrdEntry
   ACCESS     not-accessible
   STATUS     mandatory
   DESCRIPTION
     "An entry in the vctVcfrFrdTable."
   INDEX {
      vctIndex,
      vctVcfrIndex }
::= { vctVcfrFrdTable 1 }

VctVcfrFrdEntry ::= SEQUENCE {
   vctVcfrFrmCongestedToSubnet
      Unsigned32,
   vctVcfrCannotForwardToSubnet
      Unsigned32,
   vctVcfrNotDataXferToSubnet
      Unsigned32,
   vctVcfrOutOfRangeFrmFromSubnet
      Unsigned32,
   vctVcfrCombErrorsFromSubnet
      Unsigned32,
   vctVcfrDuplicatesFromSubnet
      Unsigned32,
   vctVcfrNotDataXferFromSubnet
      Unsigned32,
   vctVcfrFrmLossTimeouts
      Unsigned32,
   vctVcfrOoSeqByteCntExceeded
      Unsigned32,
   vctVcfrPeakOoSeqPktCount
      Unsigned32,
   vctVcfrPeakOoSeqFrmForwarded
      Unsigned32,
   vctVcfrSendSequenceNumber
      Unsigned32,
   vctVcfrPktRetryTimeouts
      Unsigned32,
   vctVcfrPeakRetryQueueSize
      Unsigned32,
   vctVcfrSubnetRecoveries
      Unsigned32,
   vctVcfrOoSeqPktCntExceeded
      Unsigned32,
   vctVcfrPeakOoSeqByteCount
      Unsigned32 }

vctVcfrFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { vctVcfrFrdEntry 2 }

vctVcfrCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { vctVcfrFrdEntry 3 }

vctVcfrNotDataXferToSubnet OBJECT-TYPE
   SYNTAX     Unsigned32 (0..5000)
   ACCESS     read-only
   STATUS     mandatory
   DESCRIPTION
     "This attribute records the number of frames from link discarded 
      when the Vc tries to recover from internal path failure."
::= { vctVcfrFrdEntry 4 }

vctVcfrOutOfRangeFrmFromSubnet OBJECT-TYPE
   SYNTAX     Unsigned32 (0..5000)
   ACCESS     read-only
   STATUS     mandatory
   DESCRIPTION
     "This attribute displays the number of frames from subnet discarded 
      due to out of sequence range for arriving too late."
::= { vctVcfrFrdEntry 5 }

vctVcfrCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { vctVcfrFrdEntry 6 }

vctVcfrDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { vctVcfrFrdEntry 7 }

vctVcfrNotDataXferFromSubnet OBJECT-TYPE
   SYNTAX     Unsigned32 (0..5000)
   ACCESS     read-only
   STATUS     mandatory
   DESCRIPTION
     "This attribute displays the number of subnet packets discarded when 
      data transfer is suspended in Vc recovery."
::= { vctVcfrFrdEntry 8 }

vctVcfrFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { vctVcfrFrdEntry 9 }

vctVcfrOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { vctVcfrFrdEntry 10 }

vctVcfrPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { vctVcfrFrdEntry 11 }

vctVcfrPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { vctVcfrFrdEntry 12 }

vctVcfrSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { vctVcfrFrdEntry 13 }

vctVcfrPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { vctVcfrFrdEntry 15 }

vctVcfrPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { vctVcfrFrdEntry 16 }

vctVcfrSubnetRecoveries OBJECT-TYPE
   SYNTAX     Unsigned32 (0..5000)
   ACCESS     read-only
   STATUS     mandatory
   DESCRIPTION
     "This attribute displays the number of successful Vc recovery 
      attempts."
::= { vctVcfrFrdEntry 17 }

vctVcfrOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { vctVcfrFrdEntry 19 }

vctVcfrPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { vctVcfrFrdEntry 20 }

vctVcfrDmepTable OBJECT-TYPE
   SYNTAX     SEQUENCE OF VctVcfrDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { vctVcfr 417 }

vctVcfrDmepEntry OBJECT-TYPE
   SYNTAX     VctVcfrDmepEntry
   ACCESS     not-accessible
   STATUS     mandatory
   DESCRIPTION
     "An entry in the vctVcfrDmepTable."
   INDEX {
      vctIndex,
      vctVcfrIndex,
      vctVcfrDmepValue }
::= { vctVcfrDmepTable 1 }

VctVcfrDmepEntry ::= SEQUENCE {
   vctVcfrDmepValue
      RowPointer }

vctVcfrDmepValue OBJECT-TYPE
   SYNTAX     RowPointer 
   ACCESS     read-only
   STATUS     mandatory
   DESCRIPTION
     "This variable represents both the value and the index for the
      vctVcfrDmepTable."
::= { vctVcfrDmepEntry 1 }




-- 
-- Version and Compliance statements
-- 



-- Object-Group Statement:
-- A list of all current accessible leaf objects.

-- OBJECTS { vctDcIfaRowStatus,
--           vctVcfrPeakRetryQueueSize,
--           vctDnaDefaultSendToNetworkPacketSize,
--           vctDnaComponentName,
--           vctVcDuplicatesFromSubnet,
--           vctDnaAccountClass,
--           vctVcfrFastSelectCall,
--           vctVcfrPeakOoSeqFrmForwarded,
--           vctDnaRpoa,
--           vctVcSubnetRxWindowSize,
--           vctDcDfaValue,
--           vctVcAccountingEnd,
--           vctVcDiagnosticCode,
--           vctDcRowStatus,
--           vctDnaHgMHgAddrComponentName,
--           vctVcfrCallingNpi,
--           vctRowStatus,
--           vctVcLocalRxWindowSize,
--           vctDnaHgMRowStatus,
--           vctVcCallingLcn,
--           vctVcWindowClosuresToSubnet,
--           vctDnaOutCalls,
--           vctVcfrPathReliability,
--           vctVcfrMaxSubnetPktSize,
--           vctVcAccountingEnabled,
--           vctDcDataPath,
--           vctVcfrCalledLcn,
--           vctVcfrType,
--           vctDnaOutAccess,
--           vctDnaHgMMaxAvailableChannels,
--           vctVcfrPeakOoSeqPktCount,
--           vctVcCalledDna,
--           vctVcfrDataPath,
--           vctVcType,
--           vctVcTransferPriorityFromNetwork,
--           vctDnaCugPrivileged,
--           vctDnaOutFsUnrestrictedResponse,
--           vctVcfrSegmentsSent,
--           vctVcSegmentsSent,
--           vctDcDiscardPriority,
--           vctVcfrState,
--           vctVcState,
--           vctDnaHgMAvailableChannels,
--           vctVcSubnetRecoveries,
--           vctVcPeakRetryQueueSize,
--           vctDnaSignalPreferentialCugToLink,
--           vctVcLocalTxPktSize,
--           vctDnaDefaultTransferPriority,
--           vctVcfrCannotForwardToSubnet,
--           vctDnaDataNetworkAddress,
--           vctDnaOutIntl,
--           vctVcSegmentSize,
--           vctDnaAccountCollection,
--           vctVcMaxSubnetPktSize,
--           vctVcfrPeakOoSeqByteCount,
--           vctDnaCugFormat,
--           vctVcfrCallingDna,
--           vctDnaStorageType,
--           vctDnaCugType,
--           vctDcLocalNpi,
--           vctDnaIncNormalPriorityReverseCharge,
--           vctDnaHgMHgAddrDataNetworkAddress,
--           vctVcfrStorageType,
--           vctVcComponentName,
--           vctDnaOutDefaultPriority,
--           vctDnaOutDefaultPathReliability,
--           vctDnaIncCalls,
--           vctVcPeakOoSeqQueueSize,
--           vctVcWindowClosuresFromSubnet,
--           vctDnaHgMHgAddrStorageType,
--           vctVcPathReliability,
--           vctVcCallingNpi,
--           vctDnaIncAccess,
--           vctDnaDefaultRecvFrmNetworkThruputClass,
--           vctVcSubnetTxWindowSize,
--           vctVcfrAccountingEnd,
--           vctVcLocalRxPktSize,
--           vctVcfrCalledNpi,
--           vctVcfrDmepValue,
--           vctDnaEgressAccounting,
--           vctVcfrCallReferenceNumber,
--           vctVcAckStackingTimeouts,
--           vctVcCalledLcn,
--           vctDnaOutForceReverseCharge,
--           vctDnaOutFsRestrictedResponse,
--           vctVcfrFrmLossTimeouts,
--           vctDnaRowStatus,
--           vctDnaHgMAvailabilityDelta,
--           vctVcfrCallingLcn,
--           vctDcSvcAutoCallRetry,
--           vctVcfrSubnetRecoveries,
--           vctVcCallReferenceNumber,
--           vctDcCfaRowStatus,
--           vctDcIfaValue,
--           vctDnaIncChargeTransfer,
--           vctDnaCugComponentName,
--           vctDnaServiceCategory,
--           vctDnaHgMHgAddrRowStatus,
--           vctDnaDataPath,
--           vctDnaIncSameService,
--           vctDcType,
--           vctDnaIncIntlNormalCharge,
--           vctDnaCugInterlockCode,
--           vctDnaNumberingPlanIndicator,
--           vctDnaServiceExchange,
--           vctVcfrOutOfRangeFrmFromSubnet,
--           vctLogicalProcessor,
--           vctVcfrOoSeqByteCntExceeded,
--           vctVcPeakStackedAcksRx,
--           vctVcWrTriggers,
--           vctVcfrCombErrorsFromSubnet,
--           vctDnaCugOutCalls,
--           vctVcfrRowStatus,
--           vctDnaHgMHgAddrNumberingPlanIndicator,
--           vctDnaOutPathReliabilityOverRide,
--           vctVcfrNotDataXferToSubnet,
--           vctVcfrEmissionPriorityFromNetwork,
--           vctVcfrSegmentsRx,
--           vctDcRemoteDna,
--           vctVcfrElapsedTimeTillNow,
--           vctVcStorageType,
--           vctVcName,
--           vctDnaSignalIntlAddressToLink,
--           vctVcPreviousState,
--           vctDnaDefaultRecvFrmNetworkWindowSize,
--           vctDnaCugPreferential,
--           vctVcfrPreviousDiagnosticCode,
--           vctDnaDefaultSendToNetworkWindowSize,
--           vctDnaPreselectRpoa,
--           vctDnaOutReverseCharge,
--           vctVcfrNotDataXferFromSubnet,
--           vctDcComponentName,
--           vctVcSubnetTxPktSize,
--           vctVcCalledNpi,
--           vctDnaDefaultRecvFrmNetworkPacketSize,
--           vctVcElapsedTimeTillNow,
--           vctComponentName,
--           vctVcfrOoSeqPktCntExceeded,
--           vctVcfrSendSequenceNumber,
--           vctDnaHgMComponentName,
--           vctVcTransferPriorityToNetwork,
--           vctVcPriority,
--           vctVcfrRcosFromNetwork,
--           vctDcCugIndex,
--           vctVcFastSelectCall,
--           vctVcRowStatus,
--           vctVcfrDuplicatesFromSubnet,
--           vctDnaCugStorageType,
--           vctVcfrStartTime,
--           vctVcfrPreviousState,
--           vctVcOutOfRangeFrmFromSubnet,
--           vctDnaOutPathReliabilitySignal,
--           vctVcfrRcosToNetwork,
--           vctVcSubnetRxPktSize,
--           vctVcfrDiagnosticCode,
--           vctDnaOutNormalPriority,
--           vctDnaCugIncCalls,
--           vctDcUserData,
--           vctDcLocalDna,
--           vctDnaOutHighPriority,
--           vctVcfrPriority,
--           vctDnaOutNormalCharge,
--           vctDnaTransferPriorityOverRide,
--           vctVcFrmRetryTimeouts,
--           vctDnaDefaultSendToNetworkThruputClass,
--           vctVcCallingDna,
--           vctVcStartTime,
--           vctDcRemoteLcn,
--           vctDnaIncHighPriorityReverseCharge,
--           vctDnaIncIntlReverseCharge,
--           vctVcPeakOoSeqFrmForwarded,
--           vctVcSegmentsRx,
--           vctDnaCugRowStatus,
--           vctVcPreviousDiagnosticCode,
--           vctVcfrFrmCongestedToSubnet,
--           vctVcfrCalledDna,
--           vctDnaPacketSizeNegotiation,
--           vctDcCfaValue,
--           vctVcfrPktRetryTimeouts,
--           vctDnaIncFastSelect,
--           vctDcRemoteNpi,
--           vctVcfrEmissionPriorityToNetwork,
--           vctVcfrComponentName,
--           vctDnaPacketSizes,
--           vctVcfrAccountingEnabled,
--           vctDcStorageType,
--           vctVcLocalTxWindowSize,
--           vctDcCugType,
--           vctDnaFastSelectCallsOnly,
--           vctStorageType,
--           vctDnaCug0AsNonCugCall,
--           vctDnaOutPathSensitivitySignal,
--           vctDnaHgMStorageType,
--           vctDnaCugDnic,
--           vctDnaHgMAvailabilityUpdateThreshold,
--           vctVcfrSegmentSize,
--           vctDcDfaRowStatus }
-- STATUS  mandatory
-- DESCRIPTION
--   "A list of all current accessible leaf objects."

vcTesterGroup OBJECT IDENTIFIER ::= { vcTesterMIB 1 }
vcTesterGroupBE OBJECT IDENTIFIER ::= { vcTesterGroup 5 }
vcTesterGroupBE01 OBJECT IDENTIFIER ::= { vcTesterGroupBE 2 }
vcTesterGroupBE01A OBJECT IDENTIFIER ::= { vcTesterGroupBE01 2 }



-- Agent-Capabilities Statement:

-- PRODUCT-RELEASE "Passport Release 7.0 VcTester."
-- STATUS          mandatory
-- DESCRIPTION     "VcTester MIB: MIB Version BE01A,
--                  Software Version BG00S4C."
-- SUPPORTS        Nortel-Magellan-Passport-VcTesterMIB
--    INCLUDES     { vcTesterGroupBE01A }

vcTesterCapabilities OBJECT IDENTIFIER ::= { vcTesterMIB 3 }
vcTesterCapabilitiesBE OBJECT IDENTIFIER ::= { vcTesterCapabilities 5 }
vcTesterCapabilitiesBE01 OBJECT IDENTIFIER ::= { vcTesterCapabilitiesBE 2 }
vcTesterCapabilitiesBE01A OBJECT IDENTIFIER ::= { vcTesterCapabilitiesBE01 2 }





END
