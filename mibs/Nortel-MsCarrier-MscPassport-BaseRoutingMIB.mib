Nortel-MsCarrier-MscPassport-BaseRoutingMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      Gauge32,
      Integer32,
      Unsigned32
   FROM Nortel-MsCarrier-MscPassport-StandardTextualConventionsMIB

      NonReplicated,
      FixedPoint1,
      AsciiStringIndex,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     BaseRouting Enterprise MIB."

baseRoutingMIB OBJECT IDENTIFIER ::= { mscPassportMIBs 18 }










-- Routing
-- This is the description for the Routing system component. This is 
-- the top level component of the routing hierarchy.

mscRtg OBJECT IDENTIFIER ::= { mscComponents 40 }



mscRtgRowStatusTable OBJECT-TYPE
   SYNTAX     SEQUENCE OF MscRtgRowStatusEntry
   ACCESS     not-accessible
   STATUS     mandatory
   DESCRIPTION
     "This entry controls the addition and deletion of 
      mscRtg components."
::= { mscRtg 1 }

mscRtgRowStatusEntry OBJECT-TYPE
   SYNTAX     MscRtgRowStatusEntry
   ACCESS     not-accessible
   STATUS     mandatory
   DESCRIPTION
     "A single entry in the table represents a single 
      mscRtg component."
   INDEX {
      mscRtgIndex }
::= { mscRtgRowStatusTable 1 }

MscRtgRowStatusEntry ::= SEQUENCE {
   mscRtgRowStatus
      RowStatus,
   mscRtgComponentName
      DisplayString,
   mscRtgStorageType
      StorageType,
   mscRtgIndex
      NonReplicated }

mscRtgRowStatus OBJECT-TYPE
   SYNTAX     RowStatus 
   ACCESS     read-write
   STATUS     mandatory
   DESCRIPTION
     "This variable is used as the basis for SNMP naming of
      mscRtg components.
      These components can be added."
::= { mscRtgRowStatusEntry 1 }

mscRtgComponentName OBJECT-TYPE
   SYNTAX     DisplayString 
   ACCESS     read-only
   STATUS     mandatory
   DESCRIPTION
     "This variable provides the component's string name for
      use with the ASCII Console Interface"
::= { mscRtgRowStatusEntry 2 }

mscRtgStorageType OBJECT-TYPE
   SYNTAX     StorageType 
   ACCESS     read-only
   STATUS     mandatory
   DESCRIPTION
     "This variable represents the storage type value for the
      mscRtg tables."
::= { mscRtgRowStatusEntry 4 }

mscRtgIndex OBJECT-TYPE
   SYNTAX     NonReplicated 
   ACCESS     not-accessible
   STATUS     mandatory
   DESCRIPTION
     "This variable represents the index for the mscRtg tables."
::= { mscRtgRowStatusEntry 10 }

mscRtgProvTable OBJECT-TYPE
   SYNTAX     SEQUENCE OF MscRtgProvEntry
   ACCESS     not-accessible
   STATUS     mandatory
   DESCRIPTION
     "This group contains the provisioning data for the routing system."
::= { mscRtg 12 }

mscRtgProvEntry OBJECT-TYPE
   SYNTAX     MscRtgProvEntry
   ACCESS     not-accessible
   STATUS     mandatory
   DESCRIPTION
     "An entry in the mscRtgProvTable."
   INDEX {
      mscRtgIndex }
::= { mscRtgProvTable 1 }

MscRtgProvEntry ::= SEQUENCE {
   mscRtgTandemTraffic
      INTEGER }

mscRtgTandemTraffic OBJECT-TYPE
   SYNTAX     INTEGER  {
                 allowed(0),
                 denied(1) }
   ACCESS     read-write
   STATUS     mandatory
   DESCRIPTION
     "This attribute specifies whether tandem traffic is permitted through 
      the node. 
      
      Tandem traffic is traffic which arrives at the node on a trunk and 
      leaves the node on a trunk. Traffic to or from a gateway (internal or 
      external) is not affected by the setting of this attribute.
      
      The default value of this attribute is allowed, which permits tandem 
      traffic to be routed through the node. When this attribute is set to 
      denied, DPN, VNS, and PORS traffic are not permitted to tandem 
      through the node. 
      
      Changing this attribute has no effect on PORS calls which were set 
      up before the change. These calls can be manually forced to reroute 
      using the new setting by clearing the calls or locking the trunks on 
      which they are routed."
   DEFVAL     { allowed }
::= { mscRtgProvEntry 1 }

mscRtgSplittingRegionIdsTable OBJECT-TYPE
   SYNTAX     SEQUENCE OF MscRtgSplittingRegionIdsEntry
   ACCESS     not-accessible
   STATUS     mandatory
   DESCRIPTION
     "This attribute is used only when splitting or merging existing 
      topology regions. It specifies which topology regions are in a 
      migration status. A node will only exchange topological 
      information with a connected node under the following conditions: 
      (i) the nodes belong to the same topology region, (ii) one of the 
      nodes is provisioned with the default regionId of 0, (iii) the 
      connected node's splittingRegionIds attribute is provisioned to 
      contain the local node's regionId value and the local node's 
      splittingRegionIds is also provisioned to contain the connected 
      node's regionId value when both two nodes' regionIds are different 
      and non-zero. 
      
      When this attribute is used during migration of regions, values for 
      the attribute are normally the old and new regionIds for the node. 
      Use of this attribute makes it possible to migrate existing topology 
      regions in the following cases: (i) splitting a topology region into 
      two without isolating a node, (ii) merging two different topology 
      regions into one without introducing an extra topological barrier.
      
      The attribute should be cleaned when all migration activities are 
      complete. At this point, the region boundary will take effect."
::= { mscRtg 407 }

mscRtgSplittingRegionIdsEntry OBJECT-TYPE
   SYNTAX     MscRtgSplittingRegionIdsEntry
   ACCESS     not-accessible
   STATUS     mandatory
   DESCRIPTION
     "An entry in the mscRtgSplittingRegionIdsTable."
   INDEX {
      mscRtgIndex,
      mscRtgSplittingRegionIdsValue }
::= { mscRtgSplittingRegionIdsTable 1 }

MscRtgSplittingRegionIdsEntry ::= SEQUENCE {
   mscRtgSplittingRegionIdsValue
      Integer32,
   mscRtgSplittingRegionIdsRowStatus
      RowStatus }

mscRtgSplittingRegionIdsValue OBJECT-TYPE
   SYNTAX     Integer32 (1..126)
   ACCESS     read-write
   STATUS     mandatory
   DESCRIPTION
     "This variable represents both the value and the index for the
      mscRtgSplittingRegionIdsTable."
::= { mscRtgSplittingRegionIdsEntry 1 }

mscRtgSplittingRegionIdsRowStatus OBJECT-TYPE
   SYNTAX     RowStatus 
   ACCESS     write-only
   STATUS     mandatory
   DESCRIPTION
     "This variable is used to control the addition and deletion 
      of individual values of the mscRtgSplittingRegionIdsTable."
::= { mscRtgSplittingRegionIdsEntry 2 }


-- Rtg Topology 
-- This component is a subcomponent of Routing. It resides on all 
-- Passport modules and is responsible for maintaining a topological 
-- database describing the Passport network topology in terms of 
-- nodes and connectivity between them. It computes the reachability 
-- costs to each Passport node for multiple address plans taking into 
-- account the underlying transport attributes of interest to them.

mscRtgTop OBJECT IDENTIFIER ::= { mscRtg 5 }



mscRtgTopRowStatusTable OBJECT-TYPE
   SYNTAX     SEQUENCE OF MscRtgTopRowStatusEntry
   ACCESS     not-accessible
   STATUS     mandatory
   DESCRIPTION
     "This entry controls the addition and deletion of 
      mscRtgTop components."
::= { mscRtgTop 1 }

mscRtgTopRowStatusEntry OBJECT-TYPE
   SYNTAX     MscRtgTopRowStatusEntry
   ACCESS     not-accessible
   STATUS     mandatory
   DESCRIPTION
     "A single entry in the table represents a single 
      mscRtgTop component."
   INDEX {
      mscRtgIndex,
      mscRtgTopIndex }
::= { mscRtgTopRowStatusTable 1 }

MscRtgTopRowStatusEntry ::= SEQUENCE {
   mscRtgTopRowStatus
      RowStatus,
   mscRtgTopComponentName
      DisplayString,
   mscRtgTopStorageType
      StorageType,
   mscRtgTopIndex
      NonReplicated }

mscRtgTopRowStatus OBJECT-TYPE
   SYNTAX     RowStatus 
   ACCESS     read-only
   STATUS     mandatory
   DESCRIPTION
     "This variable is used as the basis for SNMP naming of
      mscRtgTop components.
      These components cannot be added nor deleted."
::= { mscRtgTopRowStatusEntry 1 }

mscRtgTopComponentName OBJECT-TYPE
   SYNTAX     DisplayString 
   ACCESS     read-only
   STATUS     mandatory
   DESCRIPTION
     "This variable provides the component's string name for
      use with the ASCII Console Interface"
::= { mscRtgTopRowStatusEntry 2 }

mscRtgTopStorageType OBJECT-TYPE
   SYNTAX     StorageType 
   ACCESS     read-only
   STATUS     mandatory
   DESCRIPTION
     "This variable represents the storage type value for the
      mscRtgTop tables."
::= { mscRtgTopRowStatusEntry 4 }

mscRtgTopIndex OBJECT-TYPE
   SYNTAX     NonReplicated 
   ACCESS     not-accessible
   STATUS     mandatory
   DESCRIPTION
     "This variable represents the index for the mscRtgTop tables."
::= { mscRtgTopRowStatusEntry 10 }

mscRtgTopStatsTable OBJECT-TYPE
   SYNTAX     SEQUENCE OF MscRtgTopStatsEntry
   ACCESS     not-accessible
   STATUS     mandatory
   DESCRIPTION
     "Rtg Top Statistics
      This group contains operational data stored and maintained by this 
      component for recording statistics of Passport routing control 
      packets which have been sent or received by Topology."
::= { mscRtgTop 11 }

mscRtgTopStatsEntry OBJECT-TYPE
   SYNTAX     MscRtgTopStatsEntry
   ACCESS     not-accessible
   STATUS     mandatory
   DESCRIPTION
     "An entry in the mscRtgTopStatsTable."
   INDEX {
      mscRtgIndex,
      mscRtgTopIndex }
::= { mscRtgTopStatsTable 1 }

MscRtgTopStatsEntry ::= SEQUENCE {
   mscRtgTopControlPktRx
      Counter32,
   mscRtgTopControlBytesRx
      Counter32,
   mscRtgTopControlPktTx
      Counter32,
   mscRtgTopControlBytesTx
      Counter32 }

mscRtgTopControlPktRx OBJECT-TYPE
   SYNTAX     Counter32 
   ACCESS     read-only
   STATUS     mandatory
   DESCRIPTION
     "This attribute shows the total number of topology routing control 
      packets which have been received by this node from other Passport 
      nodes in the network."
::= { mscRtgTopStatsEntry 1 }

mscRtgTopControlBytesRx OBJECT-TYPE
   SYNTAX     Counter32 
   ACCESS     read-only
   STATUS     mandatory
   DESCRIPTION
     "This attribute shows the total number of topology routing control 
      packet bytes received by this node from other Passport nodes in the 
      network."
::= { mscRtgTopStatsEntry 2 }

mscRtgTopControlPktTx OBJECT-TYPE
   SYNTAX     Counter32 
   ACCESS     read-only
   STATUS     mandatory
   DESCRIPTION
     "This attribute shows the total number of topology routing control 
      packets which have been sent by this node to other Passport nodes 
      in the network."
::= { mscRtgTopStatsEntry 3 }

mscRtgTopControlBytesTx OBJECT-TYPE
   SYNTAX     Counter32 
   ACCESS     read-only
   STATUS     mandatory
   DESCRIPTION
     "This attribute shows the total number of topology routing control 
      packet bytes sent by this node to other Passport nodes in the 
      network."
::= { mscRtgTopStatsEntry 4 }

-- 
-- *** THIS SUBTREE CURRENTLY NOT IMPLEMENTED ***
-- 

-- Rtg Top Node/<neighborNodeName>
-- This component is a dynamic subcomponent of Topology. There is 
-- one instance of this component for each reachable node in the 
-- topological database. It describes this node's view of 
-- interconnections to its neighbour Passport modules.

mscRtgTopNode OBJECT IDENTIFIER ::= { mscRtgTop 2 }



mscRtgTopNodeRowStatusTable OBJECT-TYPE
   SYNTAX     SEQUENCE OF MscRtgTopNodeRowStatusEntry
   ACCESS     not-accessible
   STATUS     mandatory
   DESCRIPTION
     "*** THIS TABLE CURRENTLY NOT IMPLEMENTED ***

      This entry controls the addition and deletion of 
      mscRtgTopNode components."
::= { mscRtgTopNode 1 }

mscRtgTopNodeRowStatusEntry OBJECT-TYPE
   SYNTAX     MscRtgTopNodeRowStatusEntry
   ACCESS     not-accessible
   STATUS     mandatory
   DESCRIPTION
     "A single entry in the table represents a single 
      mscRtgTopNode component."
   INDEX {
      mscRtgIndex,
      mscRtgTopIndex,
      mscRtgTopNodeIndex }
::= { mscRtgTopNodeRowStatusTable 1 }

MscRtgTopNodeRowStatusEntry ::= SEQUENCE {
   mscRtgTopNodeRowStatus
      RowStatus,
   mscRtgTopNodeComponentName
      DisplayString,
   mscRtgTopNodeStorageType
      StorageType,
   mscRtgTopNodeIndex
      AsciiStringIndex }

mscRtgTopNodeRowStatus OBJECT-TYPE
   SYNTAX     RowStatus 
   ACCESS     read-only
   STATUS     mandatory
   DESCRIPTION
     "This variable is used as the basis for SNMP naming of
      mscRtgTopNode components.
      These components cannot be added nor deleted."
::= { mscRtgTopNodeRowStatusEntry 1 }

mscRtgTopNodeComponentName OBJECT-TYPE
   SYNTAX     DisplayString 
   ACCESS     read-only
   STATUS     mandatory
   DESCRIPTION
     "This variable provides the component's string name for
      use with the ASCII Console Interface"
::= { mscRtgTopNodeRowStatusEntry 2 }

mscRtgTopNodeStorageType OBJECT-TYPE
   SYNTAX     StorageType 
   ACCESS     read-only
   STATUS     mandatory
   DESCRIPTION
     "This variable represents the storage type value for the
      mscRtgTopNode tables."
::= { mscRtgTopNodeRowStatusEntry 4 }

mscRtgTopNodeIndex OBJECT-TYPE
   SYNTAX     AsciiStringIndex (SIZE (1..12))
   ACCESS     not-accessible
   STATUS     mandatory
   DESCRIPTION
     "This variable represents the index for the mscRtgTopNode tables."
::= { mscRtgTopNodeRowStatusEntry 10 }

mscRtgTopNodeOperTable OBJECT-TYPE
   SYNTAX     SEQUENCE OF MscRtgTopNodeOperEntry
   ACCESS     not-accessible
   STATUS     mandatory
   DESCRIPTION
     "*** THIS TABLE CURRENTLY NOT IMPLEMENTED ***

      Rtg Top Node/<neighborNodeName> Operational
      This group contains operational data about each node in the 
      Passport network and its connectivity to its neighbours."
::= { mscRtgTopNode 10 }

mscRtgTopNodeOperEntry OBJECT-TYPE
   SYNTAX     MscRtgTopNodeOperEntry
   ACCESS     not-accessible
   STATUS     mandatory
   DESCRIPTION
     "An entry in the mscRtgTopNodeOperTable."
   INDEX {
      mscRtgIndex,
      mscRtgTopIndex,
      mscRtgTopNodeIndex }
::= { mscRtgTopNodeOperTable 1 }

MscRtgTopNodeOperEntry ::= SEQUENCE {
   mscRtgTopNodeNodeId
      Unsigned32 }

mscRtgTopNodeNodeId OBJECT-TYPE
   SYNTAX     Unsigned32 (1..4095)
   ACCESS     read-only
   STATUS     mandatory
   DESCRIPTION
     "The nodeId is a number that uniquely identifies the Node 
      component instance in the Passport network. It is the identifier used 
      in the routing control packets sent by this node to other Passport 
      nodes in the network.
      
      The nodeId, for each node in the network, is learned from the 
      Passport routing protocol packets."
::= { mscRtgTopNodeOperEntry 1 }

-- 
-- *** THIS SUBTREE CURRENTLY NOT IMPLEMENTED ***
-- 

-- Rtg Top Node/<neighborNodeName> LinkGroup/ 
-- <neighborNodeName>
-- This component is a dynamic subcomponent of the Node 
-- component. For each node, there is one instance of this component 
-- for each trunk group that this node has (i.e. the number of active 
-- neighbours the node has). It shows the operational attributes of the 
-- trunk group.

mscRtgTopNodeLg OBJECT IDENTIFIER ::= { mscRtgTopNode 2 }



mscRtgTopNodeLgRowStatusTable OBJECT-TYPE
   SYNTAX     SEQUENCE OF MscRtgTopNodeLgRowStatusEntry
   ACCESS     not-accessible
   STATUS     mandatory
   DESCRIPTION
     "*** THIS TABLE CURRENTLY NOT IMPLEMENTED ***

      This entry controls the addition and deletion of 
      mscRtgTopNodeLg components."
::= { mscRtgTopNodeLg 1 }

mscRtgTopNodeLgRowStatusEntry OBJECT-TYPE
   SYNTAX     MscRtgTopNodeLgRowStatusEntry
   ACCESS     not-accessible
   STATUS     mandatory
   DESCRIPTION
     "A single entry in the table represents a single 
      mscRtgTopNodeLg component."
   INDEX {
      mscRtgIndex,
      mscRtgTopIndex,
      mscRtgTopNodeIndex,
      mscRtgTopNodeLgIndex }
::= { mscRtgTopNodeLgRowStatusTable 1 }

MscRtgTopNodeLgRowStatusEntry ::= SEQUENCE {
   mscRtgTopNodeLgRowStatus
      RowStatus,
   mscRtgTopNodeLgComponentName
      DisplayString,
   mscRtgTopNodeLgStorageType
      StorageType,
   mscRtgTopNodeLgIndex
      AsciiStringIndex }

mscRtgTopNodeLgRowStatus OBJECT-TYPE
   SYNTAX     RowStatus 
   ACCESS     read-only
   STATUS     mandatory
   DESCRIPTION
     "This variable is used as the basis for SNMP naming of
      mscRtgTopNodeLg components.
      These components cannot be added nor deleted."
::= { mscRtgTopNodeLgRowStatusEntry 1 }

mscRtgTopNodeLgComponentName OBJECT-TYPE
   SYNTAX     DisplayString 
   ACCESS     read-only
   STATUS     mandatory
   DESCRIPTION
     "This variable provides the component's string name for
      use with the ASCII Console Interface"
::= { mscRtgTopNodeLgRowStatusEntry 2 }

mscRtgTopNodeLgStorageType OBJECT-TYPE
   SYNTAX     StorageType 
   ACCESS     read-only
   STATUS     mandatory
   DESCRIPTION
     "This variable represents the storage type value for the
      mscRtgTopNodeLg tables."
::= { mscRtgTopNodeLgRowStatusEntry 4 }

mscRtgTopNodeLgIndex OBJECT-TYPE
   SYNTAX     AsciiStringIndex (SIZE (1..12))
   ACCESS     not-accessible
   STATUS     mandatory
   DESCRIPTION
     "This variable represents the index for the mscRtgTopNodeLg tables."
::= { mscRtgTopNodeLgRowStatusEntry 10 }

mscRtgTopNodeLgOperTable OBJECT-TYPE
   SYNTAX     SEQUENCE OF MscRtgTopNodeLgOperEntry
   ACCESS     not-accessible
   STATUS     mandatory
   DESCRIPTION
     "*** THIS TABLE CURRENTLY NOT IMPLEMENTED ***

      Rtg Top Node/<neighborNodeName> LinkGroup/
      <neighborNodeName> Operational
      This group contains the operational data stored and maintained by 
      TrunkGroup component for each trunk group attached to a node in 
      the Passport network."
::= { mscRtgTopNodeLg 10 }

mscRtgTopNodeLgOperEntry OBJECT-TYPE
   SYNTAX     MscRtgTopNodeLgOperEntry
   ACCESS     not-accessible
   STATUS     mandatory
   DESCRIPTION
     "An entry in the mscRtgTopNodeLgOperTable."
   INDEX {
      mscRtgIndex,
      mscRtgTopIndex,
      mscRtgTopNodeIndex,
      mscRtgTopNodeLgIndex }
::= { mscRtgTopNodeLgOperTable 1 }

MscRtgTopNodeLgOperEntry ::= SEQUENCE {
   mscRtgTopNodeLgDelayMetric
      Unsigned32,
   mscRtgTopNodeLgTputMetric
      Unsigned32 }

mscRtgTopNodeLgDelayMetric OBJECT-TYPE
   SYNTAX     Unsigned32 (1..2147483647)
   ACCESS     read-only
   STATUS     mandatory
   DESCRIPTION
     "This attribute specifies the outbound cost to forward packets across 
      the trunk group for a delay class of service. It represents the trunk in 
      the trunk group with the lowest round trip delay. A low outbound 
      cost is preferable to a higher value as it is associated with higher 
      speed facilities.
      
      A metric value of 2147483647 means that the trunk group is 
      unusable for the delay class of service."
::= { mscRtgTopNodeLgOperEntry 1 }

mscRtgTopNodeLgTputMetric OBJECT-TYPE
   SYNTAX     Unsigned32 (1..2147483647)
   ACCESS     read-only
   STATUS     mandatory
   DESCRIPTION
     "This attribute specifies the outbound cost to forward packets across 
      the trunk group for a throughput class of service. It is computed 
      from the combined speed of each link in the trunk group. A low 
      outbound cost is preferable to a higher value as it is associated with 
      higher speed facilities.
      
      A metric value of 2147483647 means that the trunk group is 
      unusable for the throughput class of service."
::= { mscRtgTopNodeLgOperEntry 2 }

mscRtgTopNodeLgLnnTable OBJECT-TYPE
   SYNTAX     SEQUENCE OF MscRtgTopNodeLgLnnEntry
   ACCESS     not-accessible
   STATUS     mandatory
   DESCRIPTION
     "*** THIS TABLE CURRENTLY NOT IMPLEMENTED ***

      This attribute is a list of integers which specify the logical network 
      numbers supported by the trunk group. 
      
      Each of these numbers corresponds with a particular instance of 
      network protocol supported on this switch. LNN 0 is present on all 
      trunks by default to allow Passport control traffic on the trunk."
::= { mscRtgTopNodeLg 235 }

mscRtgTopNodeLgLnnEntry OBJECT-TYPE
   SYNTAX     MscRtgTopNodeLgLnnEntry
   ACCESS     not-accessible
   STATUS     mandatory
   DESCRIPTION
     "An entry in the mscRtgTopNodeLgLnnTable."
   INDEX {
      mscRtgIndex,
      mscRtgTopIndex,
      mscRtgTopNodeIndex,
      mscRtgTopNodeLgIndex,
      mscRtgTopNodeLgLnnValue }
::= { mscRtgTopNodeLgLnnTable 1 }

MscRtgTopNodeLgLnnEntry ::= SEQUENCE {
   mscRtgTopNodeLgLnnValue
      Integer32 }

mscRtgTopNodeLgLnnValue OBJECT-TYPE
   SYNTAX     Integer32 (0..2047)
   ACCESS     read-only
   STATUS     mandatory
   DESCRIPTION
     "This variable represents both the value and the index for the
      mscRtgTopNodeLgLnnTable."
::= { mscRtgTopNodeLgLnnEntry 1 }

-- 
-- *** THIS SUBTREE CURRENTLY NOT IMPLEMENTED ***
-- 

-- Rtg Top Node/<neighborNodeName> LinkGroup/
-- <neighborNodeName> Trunk/<Trm Lk Id>
-- This component corresponds to a trunk object stored in topological 
-- database. There is one instance of this component for every 
-- TplPorTrunk that the TplTrunkGroup component consists of. The 
-- TplPorTrunk instance is the same as link instance allocated by Trm 
-- to a Trunk which can carry PORS traffic. Display command applied 
-- to this component shows PORS data of the trunk object in 
-- topological database. 

mscRtgTopNodeLgTrkObj OBJECT IDENTIFIER ::= { mscRtgTopNodeLg 2 }



mscRtgTopNodeLgTrkObjRowStatusTable OBJECT-TYPE
   SYNTAX     SEQUENCE OF MscRtgTopNodeLgTrkObjRowStatusEntry
   ACCESS     not-accessible
   STATUS     mandatory
   DESCRIPTION
     "*** THIS TABLE CURRENTLY NOT IMPLEMENTED ***

      This entry controls the addition and deletion of 
      mscRtgTopNodeLgTrkObj components."
::= { mscRtgTopNodeLgTrkObj 1 }

mscRtgTopNodeLgTrkObjRowStatusEntry OBJECT-TYPE
   SYNTAX     MscRtgTopNodeLgTrkObjRowStatusEntry
   ACCESS     not-accessible
   STATUS     mandatory
   DESCRIPTION
     "A single entry in the table represents a single 
      mscRtgTopNodeLgTrkObj component."
   INDEX {
      mscRtgIndex,
      mscRtgTopIndex,
      mscRtgTopNodeIndex,
      mscRtgTopNodeLgIndex,
      mscRtgTopNodeLgTrkObjIndex }
::= { mscRtgTopNodeLgTrkObjRowStatusTable 1 }

MscRtgTopNodeLgTrkObjRowStatusEntry ::= SEQUENCE {
   mscRtgTopNodeLgTrkObjRowStatus
      RowStatus,
   mscRtgTopNodeLgTrkObjComponentName
      DisplayString,
   mscRtgTopNodeLgTrkObjStorageType
      StorageType,
   mscRtgTopNodeLgTrkObjIndex
      Integer32 }

mscRtgTopNodeLgTrkObjRowStatus OBJECT-TYPE
   SYNTAX     RowStatus 
   ACCESS     read-only
   STATUS     mandatory
   DESCRIPTION
     "This variable is used as the basis for SNMP naming of
      mscRtgTopNodeLgTrkObj components.
      These components cannot be added nor deleted."
::= { mscRtgTopNodeLgTrkObjRowStatusEntry 1 }

mscRtgTopNodeLgTrkObjComponentName OBJECT-TYPE
   SYNTAX     DisplayString 
   ACCESS     read-only
   STATUS     mandatory
   DESCRIPTION
     "This variable provides the component's string name for
      use with the ASCII Console Interface"
::= { mscRtgTopNodeLgTrkObjRowStatusEntry 2 }

mscRtgTopNodeLgTrkObjStorageType OBJECT-TYPE
   SYNTAX     StorageType 
   ACCESS     read-only
   STATUS     mandatory
   DESCRIPTION
     "This variable represents the storage type value for the
      mscRtgTopNodeLgTrkObj tables."
::= { mscRtgTopNodeLgTrkObjRowStatusEntry 4 }

mscRtgTopNodeLgTrkObjIndex OBJECT-TYPE
   SYNTAX     Integer32 (1..1023)
   ACCESS     not-accessible
   STATUS     mandatory
   DESCRIPTION
     "This variable represents the index for the mscRtgTopNodeLgTrkObj tables."
::= { mscRtgTopNodeLgTrkObjRowStatusEntry 10 }

mscRtgTopNodeLgTrkObjOperTable OBJECT-TYPE
   SYNTAX     SEQUENCE OF MscRtgTopNodeLgTrkObjOperEntry
   ACCESS     not-accessible
   STATUS     mandatory
   DESCRIPTION
     "*** THIS TABLE CURRENTLY NOT IMPLEMENTED ***

      Rtg Top Node/<neighborNodeName> LinkGroup/
      <neighborNodeName> Trunk/<Trm Lk Id> Operational
      This group contains the operational data stored and maintained by 
      TplPorTrunk component."
::= { mscRtgTopNodeLgTrkObj 10 }

mscRtgTopNodeLgTrkObjOperEntry OBJECT-TYPE
   SYNTAX     MscRtgTopNodeLgTrkObjOperEntry
   ACCESS     not-accessible
   STATUS     mandatory
   DESCRIPTION
     "An entry in the mscRtgTopNodeLgTrkObjOperTable."
   INDEX {
      mscRtgIndex,
      mscRtgTopIndex,
      mscRtgTopNodeIndex,
      mscRtgTopNodeLgIndex,
      mscRtgTopNodeLgTrkObjIndex }
::= { mscRtgTopNodeLgTrkObjOperTable 1 }

MscRtgTopNodeLgTrkObjOperEntry ::= SEQUENCE {
   mscRtgTopNodeLgTrkObjMaxReservableBwOut
      Gauge32,
   mscRtgTopNodeLgTrkObjTrunkCost
      Unsigned32,
   mscRtgTopNodeLgTrkObjTrunkDelay
      Unsigned32,
   mscRtgTopNodeLgTrkObjTrunkSecurity
      Unsigned32,
   mscRtgTopNodeLgTrkObjSupportedTrafficTypes
      OCTET STRING,
   mscRtgTopNodeLgTrkObjTrunkType
      INTEGER,
   mscRtgTopNodeLgTrkObjCustomerParameter
      Unsigned32,
   mscRtgTopNodeLgTrkObjFarEndTrmLkInstance
      Unsigned32 }

mscRtgTopNodeLgTrkObjMaxReservableBwOut OBJECT-TYPE
   SYNTAX     Gauge32 (0..4294967295)
   ACCESS     read-only
   STATUS     mandatory
   DESCRIPTION
     "This attribute displays trunk bandwidth which can be used for 
      reservations on behalf of connections requiring path oriented 
      routing. This bandwidth is displayed in bit/s and has been calculated 
      by concerned trunk path administrator from the trunk bandwidth 
      and from the percentage of trunk bandwidth provisioned for 
      reservations by PORS."
::= { mscRtgTopNodeLgTrkObjOperEntry 1 }

mscRtgTopNodeLgTrkObjTrunkCost OBJECT-TYPE
   SYNTAX     Unsigned32 (1..255)
   ACCESS     read-only
   STATUS     mandatory
   DESCRIPTION
     "This attribute displays trunk cost metric provisioned as trunkCost 
      attribute of a concerned trunk path administrator."
::= { mscRtgTopNodeLgTrkObjOperEntry 2 }

mscRtgTopNodeLgTrkObjTrunkDelay OBJECT-TYPE
   SYNTAX     Unsigned32 (0..65535)
   ACCESS     read-only
   STATUS     mandatory
   DESCRIPTION
     "This attribute displays one-directional trunk delay measured by 
      trunk during staging. This is half (rounded down to an integer) of 
      delay displayable by attribute of ID aTrmLinkDelay_c."
::= { mscRtgTopNodeLgTrkObjOperEntry 3 }

mscRtgTopNodeLgTrkObjTrunkSecurity OBJECT-TYPE
   SYNTAX     Unsigned32 (0..7)
   ACCESS     read-only
   STATUS     mandatory
   DESCRIPTION
     "This attribute displays trunk security metric provisioned as 
      trunkSecurity attribute of a concerned trunk path administrator."
::= { mscRtgTopNodeLgTrkObjOperEntry 4 }

mscRtgTopNodeLgTrkObjSupportedTrafficTypes OBJECT-TYPE
   SYNTAX     OCTET STRING (SIZE (1))
   ACCESS     read-only
   STATUS     mandatory
   DESCRIPTION
     "This attribute indicates the type of traffic that can be transmitted on 
      the trunk. There are eight(8) possible traffic types, and the trunk can 
      transmit all of them if desired. The voice, data and video traffic 
      types are defined, and five(5) other traffic types can be defined in 
      concerned trunk path administrator. This attribute is used in the 
      route selection process to limit the route to trunks that support the 
      traffic to be carried by the path.

      Description of bits:
      voice(0)
      data(1)
      video(2)
      trafficType1(3)
      trafficType2(4)
      trafficType3(5)
      trafficType4(6)
      trafficType5(7)"
::= { mscRtgTopNodeLgTrkObjOperEntry 5 }

mscRtgTopNodeLgTrkObjTrunkType OBJECT-TYPE
   SYNTAX     INTEGER  {
                 terrestrial(0),
                 satellite(1),
                 trunkType1(2),
                 trunkType2(3),
                 trunkType3(4),
                 trunkType4(5),
                 trunkType5(6),
                 trunkType6(7) }
   ACCESS     read-only
   STATUS     mandatory
   DESCRIPTION
     "This attribute lists the type of the trunk. There can be up to eight(8) 
      types of trunks. The terrestrial and satellite trunk types have been 
      defined, leaving six(6) remaining types that can be defined by the 
      network administration. The set of allowed trunk types for a path is 
      indicated in the permittedTrunkType attribute of the PLC. When 
      selecting a route, PORS only chooses trunks whose PA trunkType 
      are in the permittedTrunkTypes set of the path."
::= { mscRtgTopNodeLgTrkObjOperEntry 6 }

mscRtgTopNodeLgTrkObjCustomerParameter OBJECT-TYPE
   SYNTAX     Unsigned32 (0..7)
   ACCESS     read-only
   STATUS     mandatory
   DESCRIPTION
     "This attribute indicates the customer defined parameter for the 
      trunk. Its value, a number from zero(0) to seven(7), is chosen by a 
      network administration to have a meaning specific to their network, 
      thus allowing them to customize the use of their trunks. A 
      complementary PLC attribute, requiredCustomerParameter, also has 
      a value from zero(0) to seven(7). The Route Selector does not 
      consider trunks whose PA customerParameter is greater than the 
      requiredCustomParameter of the path."
::= { mscRtgTopNodeLgTrkObjOperEntry 7 }

mscRtgTopNodeLgTrkObjFarEndTrmLkInstance OBJECT-TYPE
   SYNTAX     Unsigned32 (1..1023)
   ACCESS     read-only
   STATUS     mandatory
   DESCRIPTION
     "This attribute indicates identification of the corresponding trunk 
      providing the reverse direction of transmission."
::= { mscRtgTopNodeLgTrkObjOperEntry 8 }

mscRtgTopNodeLgTrkObjUnresTable OBJECT-TYPE
   SYNTAX     SEQUENCE OF MscRtgTopNodeLgTrkObjUnresEntry
   ACCESS     not-accessible
   STATUS     mandatory
   DESCRIPTION
     "*** THIS TABLE CURRENTLY NOT IMPLEMENTED ***

      This attribute displays a table. In the first row there are setup 
      priorities. In the second row there are numerators of parts of 
      unreserved bandwidth corresponding to setup priority 0 (first 
      column) through 4 (fifth column). The denominator is 255."
::= { mscRtgTopNodeLgTrkObj 234 }

mscRtgTopNodeLgTrkObjUnresEntry OBJECT-TYPE
   SYNTAX     MscRtgTopNodeLgTrkObjUnresEntry
   ACCESS     not-accessible
   STATUS     mandatory
   DESCRIPTION
     "An entry in the mscRtgTopNodeLgTrkObjUnresTable."
   INDEX {
      mscRtgIndex,
      mscRtgTopIndex,
      mscRtgTopNodeIndex,
      mscRtgTopNodeLgIndex,
      mscRtgTopNodeLgTrkObjIndex,
      mscRtgTopNodeLgTrkObjUnresSetupPriorityIndex,
      mscRtgTopNodeLgTrkObjUnresUnreservedBwPartsIndex }
::= { mscRtgTopNodeLgTrkObjUnresTable 1 }

MscRtgTopNodeLgTrkObjUnresEntry ::= SEQUENCE {
   mscRtgTopNodeLgTrkObjUnresSetupPriorityIndex
      INTEGER,
   mscRtgTopNodeLgTrkObjUnresUnreservedBwPartsIndex
      Integer32,
   mscRtgTopNodeLgTrkObjUnresValue
      Unsigned32 }

mscRtgTopNodeLgTrkObjUnresSetupPriorityIndex OBJECT-TYPE
   SYNTAX     INTEGER  {
                 bwPartOver255(0) }
   ACCESS     not-accessible
   STATUS     mandatory
   DESCRIPTION
     "This variable represents the next to last index for the 
      mscRtgTopNodeLgTrkObjUnresTable."
::= { mscRtgTopNodeLgTrkObjUnresEntry 1 }

mscRtgTopNodeLgTrkObjUnresUnreservedBwPartsIndex OBJECT-TYPE
   SYNTAX     Integer32 (0..4)
   ACCESS     not-accessible
   STATUS     mandatory
   DESCRIPTION
     "This variable represents the final index for the 
      mscRtgTopNodeLgTrkObjUnresTable."
::= { mscRtgTopNodeLgTrkObjUnresEntry 2 }

mscRtgTopNodeLgTrkObjUnresValue OBJECT-TYPE
   SYNTAX     Unsigned32 (0..255)
   ACCESS     read-only
   STATUS     mandatory
   DESCRIPTION
     "This variable represents an individual value for the
      mscRtgTopNodeLgTrkObjUnresTable."
::= { mscRtgTopNodeLgTrkObjUnresEntry 3 }


-- TransportResource
-- This component resides on all Passport modules and is responsible 
-- for managing link resources. It acts as an intermediary between a 
-- link and all the routing systems that use the link.

mscTrm OBJECT IDENTIFIER ::= { mscComponents 41 }



mscTrmRowStatusTable OBJECT-TYPE
   SYNTAX     SEQUENCE OF MscTrmRowStatusEntry
   ACCESS     not-accessible
   STATUS     mandatory
   DESCRIPTION
     "This entry controls the addition and deletion of 
      mscTrm components."
::= { mscTrm 1 }

mscTrmRowStatusEntry OBJECT-TYPE
   SYNTAX     MscTrmRowStatusEntry
   ACCESS     not-accessible
   STATUS     mandatory
   DESCRIPTION
     "A single entry in the table represents a single 
      mscTrm component."
   INDEX {
      mscTrmIndex }
::= { mscTrmRowStatusTable 1 }

MscTrmRowStatusEntry ::= SEQUENCE {
   mscTrmRowStatus
      RowStatus,
   mscTrmComponentName
      DisplayString,
   mscTrmStorageType
      StorageType,
   mscTrmIndex
      NonReplicated }

mscTrmRowStatus OBJECT-TYPE
   SYNTAX     RowStatus 
   ACCESS     read-only
   STATUS     mandatory
   DESCRIPTION
     "This variable is used as the basis for SNMP naming of
      mscTrm components.
      These components cannot be added nor deleted."
::= { mscTrmRowStatusEntry 1 }

mscTrmComponentName OBJECT-TYPE
   SYNTAX     DisplayString 
   ACCESS     read-only
   STATUS     mandatory
   DESCRIPTION
     "This variable provides the component's string name for
      use with the ASCII Console Interface"
::= { mscTrmRowStatusEntry 2 }

mscTrmStorageType OBJECT-TYPE
   SYNTAX     StorageType 
   ACCESS     read-only
   STATUS     mandatory
   DESCRIPTION
     "This variable represents the storage type value for the
      mscTrm tables."
::= { mscTrmRowStatusEntry 4 }

mscTrmIndex OBJECT-TYPE
   SYNTAX     NonReplicated 
   ACCESS     not-accessible
   STATUS     mandatory
   DESCRIPTION
     "This variable represents the index for the mscTrm tables."
::= { mscTrmRowStatusEntry 10 }

-- 
-- *** THIS SUBTREE CURRENTLY NOT IMPLEMENTED ***
-- 

-- Trm Link/<n> 
-- This component is a dynamic subcomponent of TransportResource. 
-- It has operational attributes only which are stored and maintained 
-- by this component for listing links.

mscTrmLk OBJECT IDENTIFIER ::= { mscTrm 2 }



mscTrmLkRowStatusTable OBJECT-TYPE
   SYNTAX     SEQUENCE OF MscTrmLkRowStatusEntry
   ACCESS     not-accessible
   STATUS     mandatory
   DESCRIPTION
     "*** THIS TABLE CURRENTLY NOT IMPLEMENTED ***

      This entry controls the addition and deletion of 
      mscTrmLk components."
::= { mscTrmLk 1 }

mscTrmLkRowStatusEntry OBJECT-TYPE
   SYNTAX     MscTrmLkRowStatusEntry
   ACCESS     not-accessible
   STATUS     mandatory
   DESCRIPTION
     "A single entry in the table represents a single 
      mscTrmLk component."
   INDEX {
      mscTrmIndex,
      mscTrmLkIndex }
::= { mscTrmLkRowStatusTable 1 }

MscTrmLkRowStatusEntry ::= SEQUENCE {
   mscTrmLkRowStatus
      RowStatus,
   mscTrmLkComponentName
      DisplayString,
   mscTrmLkStorageType
      StorageType,
   mscTrmLkIndex
      Integer32 }

mscTrmLkRowStatus OBJECT-TYPE
   SYNTAX     RowStatus 
   ACCESS     read-only
   STATUS     mandatory
   DESCRIPTION
     "This variable is used as the basis for SNMP naming of
      mscTrmLk components.
      These components cannot be added nor deleted."
::= { mscTrmLkRowStatusEntry 1 }

mscTrmLkComponentName OBJECT-TYPE
   SYNTAX     DisplayString 
   ACCESS     read-only
   STATUS     mandatory
   DESCRIPTION
     "This variable provides the component's string name for
      use with the ASCII Console Interface"
::= { mscTrmLkRowStatusEntry 2 }

mscTrmLkStorageType OBJECT-TYPE
   SYNTAX     StorageType 
   ACCESS     read-only
   STATUS     mandatory
   DESCRIPTION
     "This variable represents the storage type value for the
      mscTrmLk tables."
::= { mscTrmLkRowStatusEntry 4 }

mscTrmLkIndex OBJECT-TYPE
   SYNTAX     Integer32 (1..1023)
   ACCESS     not-accessible
   STATUS     mandatory
   DESCRIPTION
     "This variable represents the index for the mscTrmLk tables."
::= { mscTrmLkRowStatusEntry 10 }

mscTrmLkOperTable OBJECT-TYPE
   SYNTAX     SEQUENCE OF MscTrmLkOperEntry
   ACCESS     not-accessible
   STATUS     mandatory
   DESCRIPTION
     "*** THIS TABLE CURRENTLY NOT IMPLEMENTED ***

      Trm Lk/<n> Operational
      This group of attributes is used to list links. These links are all 
      registered with Transport Resource Manager. They have a status 
      which reflects the current view of the link."
::= { mscTrmLk 10 }

mscTrmLkOperEntry OBJECT-TYPE
   SYNTAX     MscTrmLkOperEntry
   ACCESS     not-accessible
   STATUS     mandatory
   DESCRIPTION
     "An entry in the mscTrmLkOperTable."
   INDEX {
      mscTrmIndex,
      mscTrmLkIndex }
::= { mscTrmLkOperTable 1 }

MscTrmLkOperEntry ::= SEQUENCE {
   mscTrmLkStatus
      INTEGER,
   mscTrmLkThroughput
      Gauge32,
   mscTrmLkDelay
      Gauge32,
   mscTrmLkMaxTxUnit
      Unsigned32,
   mscTrmLkLinkComponentName
      RowPointer,
   mscTrmLkDelayUsec
      FixedPoint1 }

mscTrmLkStatus OBJECT-TYPE
   SYNTAX     INTEGER  {
                 inactive(1),
                 joining(2),
                 online(3) }
   ACCESS     read-only
   STATUS     mandatory
   DESCRIPTION
     "This attribute indicates if the inactive link is disabled, joining, 
      waiting to join, or in standby mode.
      
      inactive - The link is known to TRM but is not active. This can 
      mean that it is disabled, or has not yet started to join.
      joining - The link has requested to join the routing systems.
      online- The link is active and has joined one or more routing 
      systems."
::= { mscTrmLkOperEntry 1 }

mscTrmLkThroughput OBJECT-TYPE
   SYNTAX     Gauge32 (1..640000000)
   ACCESS     read-only
   STATUS     mandatory
   DESCRIPTION
     "This attribute indicates the throughput of the link in kbit/s. This 
      value represents a nominal bandwidth available for connectionless 
      traffic, after the maximum reserved for path-oriented traffic has 
      been subtracted from trunk bandwidth. If a trunk speed override is 
      specified, it is used instead. The 'throughput' value can be 
      exceeded by connectionless traffic whenever path-oriented traffic is 
      not using it's reserved bandwidth."
::= { mscTrmLkOperEntry 2 }

mscTrmLkDelay OBJECT-TYPE
   SYNTAX     Gauge32 (1..1500)
   ACCESS     read-only
   STATUS     obsolete
   DESCRIPTION
     "This is the round trip delay of the link in milliseconds. This value 
      represents a nominal delay for connectionless traffic. 
      Connectionless traffic is biased away from trunks carrying path-
      oriented traffic by increasing this value. The value of this attribute is 
      a function of the percentage of reserved path-oriented bandwidth 
      and takes a maximum value of 1500 msec for 100% path-oriented 
      trunks. If an override delay is specified, it will be used instead."
::= { mscTrmLkOperEntry 3 }

mscTrmLkMaxTxUnit OBJECT-TYPE
   SYNTAX     Unsigned32 (1..65535)
   ACCESS     read-only
   STATUS     mandatory
   DESCRIPTION
     "This attribute indicates the maximum data unit in bytes of this link. 
      It represents the maximum frame length (including user data and 
      routing headers) that can be sent on the link."
::= { mscTrmLkOperEntry 4 }

mscTrmLkLinkComponentName OBJECT-TYPE
   SYNTAX     RowPointer 
   ACCESS     read-only
   STATUS     mandatory
   DESCRIPTION
     "This attribute indicates the link's component name. A link is either 
      a trunk or a gateway to another module. The component name may 
      be used to obtain additional information from the link system."
::= { mscTrmLkOperEntry 5 }

mscTrmLkDelayUsec OBJECT-TYPE
   SYNTAX     FixedPoint1 (10..15000)
   ACCESS     read-only
   STATUS     mandatory
   DESCRIPTION
     "This attribute indicates the round trip delay of the link in 
      milliseconds. This value represents a nominal delay for 
      connectionless traffic. Connectionless traffic is biased away from 
      trunks carrying path-oriented traffic by increasing this value. The 
      value of this attribute is a function of the percentage of reserved 
      path-oriented bandwidth and takes a maximum value of 1500 msec 
      for 100% path-oriented trunks. If a delay override is specified, it 
      will be used instead."
::= { mscTrmLkOperEntry 6 }

mscTrmLkFwdStatsTable OBJECT-TYPE
   SYNTAX     SEQUENCE OF MscTrmLkFwdStatsEntry
   ACCESS     not-accessible
   STATUS     mandatory
   DESCRIPTION
     "*** THIS TABLE CURRENTLY NOT IMPLEMENTED ***

      This group of attributes is used to display egress statistics collected 
      by packet forwarding on this link. The statistics can be used to 
      monitor congestion conditions and packet discards on a link."
::= { mscTrmLk 11 }

mscTrmLkFwdStatsEntry OBJECT-TYPE
   SYNTAX     MscTrmLkFwdStatsEntry
   ACCESS     not-accessible
   STATUS     mandatory
   DESCRIPTION
     "An entry in the mscTrmLkFwdStatsTable."
   INDEX {
      mscTrmIndex,
      mscTrmLkIndex }
::= { mscTrmLkFwdStatsTable 1 }

MscTrmLkFwdStatsEntry ::= SEQUENCE {
   mscTrmLkFciSet
      Counter32,
   mscTrmLkOverflowAttempts
      Counter32,
   mscTrmLkPathOverflowAttempts
      Counter32 }

mscTrmLkFciSet OBJECT-TYPE
   SYNTAX     Counter32 
   ACCESS     read-only
   STATUS     mandatory
   DESCRIPTION
     "This attribute counts the packets whose FCI bits are set by packet 
      forwarding due to congestion on this link, and when the 
      forwardingPolicy attribute of Routing DpnAddressPlan is set to 
      loadshare or loadspread. This counter wraps around to zero when 
      the maximum value is reached."
::= { mscTrmLkFwdStatsEntry 1 }

mscTrmLkOverflowAttempts OBJECT-TYPE
   SYNTAX     Counter32 
   ACCESS     read-only
   STATUS     mandatory
   DESCRIPTION
     "This attribute counts the number of times DPRS packet forwarding 
      attempts to overflow packets to another link in a link group due to 
      congestion on this link. It is used only when the attribute 
      forwardingPolicy in component rtg dpn is set to the value 
      loadspreading. This counter wraps around to zero when the 
      maximum value is reached."
::= { mscTrmLkFwdStatsEntry 2 }

mscTrmLkPathOverflowAttempts OBJECT-TYPE
   SYNTAX     Counter32 
   ACCESS     read-only
   STATUS     mandatory
   DESCRIPTION
     "This attribute counts the number of times DPRS packet forwarding 
      attempts to overflow packets to another link group due to 
      congestion on the link group of this link. This counter wraps around 
      to zero when the maximum value is reached."
::= { mscTrmLkFwdStatsEntry 3 }

mscTrmLkDiscardCongestedTable OBJECT-TYPE
   SYNTAX     SEQUENCE OF MscTrmLkDiscardCongestedEntry
   ACCESS     not-accessible
   STATUS     mandatory
   DESCRIPTION
     "*** THIS TABLE CURRENTLY NOT IMPLEMENTED ***

      This attribute counts the packets that have been discarded by packet 
      forwarding due to congestion on this link and when the 
      forwardingPolicy attribute of Routing DpnAddressPlan is set to 
      loadshare or loadspread. 
      
      This attribute is a vector with three entries. Each entry corresponds 
      to a discard priority of the packet. The first entry represents the 
      discard count of packets with discard priority 1, the second entry 
      discard priority 2, and the third entry discard priority 3. Each entry 
      (counter) wraps around to zero when the maximum value is 
      reached."
::= { mscTrmLk 280 }

mscTrmLkDiscardCongestedEntry OBJECT-TYPE
   SYNTAX     MscTrmLkDiscardCongestedEntry
   ACCESS     not-accessible
   STATUS     mandatory
   DESCRIPTION
     "An entry in the mscTrmLkDiscardCongestedTable."
   INDEX {
      mscTrmIndex,
      mscTrmLkIndex,
      mscTrmLkDiscardCongestedIndex }
::= { mscTrmLkDiscardCongestedTable 1 }

MscTrmLkDiscardCongestedEntry ::= SEQUENCE {
   mscTrmLkDiscardCongestedIndex
      INTEGER,
   mscTrmLkDiscardCongestedValue
      Counter32 }

mscTrmLkDiscardCongestedIndex OBJECT-TYPE
   SYNTAX     INTEGER  {
                 discardPriority1(0),
                 discardPriority2(1),
                 discardPriority3(2) }
   ACCESS     not-accessible
   STATUS     mandatory
   DESCRIPTION
     "This variable represents the mscTrmLkDiscardCongestedTable
      specific index for the mscTrmLkDiscardCongestedTable."
::= { mscTrmLkDiscardCongestedEntry 1 }

mscTrmLkDiscardCongestedValue OBJECT-TYPE
   SYNTAX     Counter32 
   ACCESS     read-only
   STATUS     mandatory
   DESCRIPTION
     "This variable represents an individual value for the
      mscTrmLkDiscardCongestedTable."
::= { mscTrmLkDiscardCongestedEntry 2 }

-- 
-- *** THIS SUBTREE CURRENTLY NOT IMPLEMENTED ***
-- 

-- Trm LinkGroup /<neighborNodeName>
-- This component is a dynamic subcomponent of TransportResource. 
-- It has operational attributes only which are stored and maintained 
-- by this component for the purpose of displaying link groups.
-- 
-- A link group contains 1 to 4 links, all of which are active.
-- 
-- The neighbour node name is the node name provisioned in the 
-- Module component on the remote Passport module if the link group 
-- connects to a Passport switch. Otherwise it is the remote module 
-- node name provisioned in the components of gateways in this link 
-- group.
-- 
-- Links in a link group can have differing throughputs and round trip 
-- delays. If the difference within the set of throughputs, or within the 
-- set of delays is significant, some links may not be used. The rule 
-- that is applied is that links within 50% of the throughput of the 
-- highest throughput link are used for the throughput RCOS. 
-- Similiarily links within 50% of the delay of the lowest delay link 
-- are used for the throughput RCOS. As links are added or removed 
-- from the link group, the set of links which are used is re-evaluated.

mscTrmLg OBJECT IDENTIFIER ::= { mscTrm 3 }



mscTrmLgRowStatusTable OBJECT-TYPE
   SYNTAX     SEQUENCE OF MscTrmLgRowStatusEntry
   ACCESS     not-accessible
   STATUS     mandatory
   DESCRIPTION
     "*** THIS TABLE CURRENTLY NOT IMPLEMENTED ***

      This entry controls the addition and deletion of 
      mscTrmLg components."
::= { mscTrmLg 1 }

mscTrmLgRowStatusEntry OBJECT-TYPE
   SYNTAX     MscTrmLgRowStatusEntry
   ACCESS     not-accessible
   STATUS     mandatory
   DESCRIPTION
     "A single entry in the table represents a single 
      mscTrmLg component."
   INDEX {
      mscTrmIndex,
      mscTrmLgIndex }
::= { mscTrmLgRowStatusTable 1 }

MscTrmLgRowStatusEntry ::= SEQUENCE {
   mscTrmLgRowStatus
      RowStatus,
   mscTrmLgComponentName
      DisplayString,
   mscTrmLgStorageType
      StorageType,
   mscTrmLgIndex
      AsciiStringIndex }

mscTrmLgRowStatus OBJECT-TYPE
   SYNTAX     RowStatus 
   ACCESS     read-only
   STATUS     mandatory
   DESCRIPTION
     "This variable is used as the basis for SNMP naming of
      mscTrmLg components.
      These components cannot be added nor deleted."
::= { mscTrmLgRowStatusEntry 1 }

mscTrmLgComponentName OBJECT-TYPE
   SYNTAX     DisplayString 
   ACCESS     read-only
   STATUS     mandatory
   DESCRIPTION
     "This variable provides the component's string name for
      use with the ASCII Console Interface"
::= { mscTrmLgRowStatusEntry 2 }

mscTrmLgStorageType OBJECT-TYPE
   SYNTAX     StorageType 
   ACCESS     read-only
   STATUS     mandatory
   DESCRIPTION
     "This variable represents the storage type value for the
      mscTrmLg tables."
::= { mscTrmLgRowStatusEntry 4 }

mscTrmLgIndex OBJECT-TYPE
   SYNTAX     AsciiStringIndex (SIZE (1..12))
   ACCESS     not-accessible
   STATUS     mandatory
   DESCRIPTION
     "This variable represents the index for the mscTrmLg tables."
::= { mscTrmLgRowStatusEntry 10 }

-- 
-- *** THIS SUBTREE CURRENTLY NOT IMPLEMENTED ***
-- 

-- Trm Lg/<neighborNodeName> Link /<linkInstance> 
-- This component is a dynamic subcomponent of LinkGroup. It has 
-- operational attributes only which are stored and maintained by this 
-- component for displaying links in a link group. There are 1 to 4 
-- active links in a link group. A link group object is not created until 
-- there is at least one active link in the group. Inactive links are not 
-- shown in a link group.

mscTrmLgLk OBJECT IDENTIFIER ::= { mscTrmLg 2 }



mscTrmLgLkRowStatusTable OBJECT-TYPE
   SYNTAX     SEQUENCE OF MscTrmLgLkRowStatusEntry
   ACCESS     not-accessible
   STATUS     mandatory
   DESCRIPTION
     "*** THIS TABLE CURRENTLY NOT IMPLEMENTED ***

      This entry controls the addition and deletion of 
      mscTrmLgLk components."
::= { mscTrmLgLk 1 }

mscTrmLgLkRowStatusEntry OBJECT-TYPE
   SYNTAX     MscTrmLgLkRowStatusEntry
   ACCESS     not-accessible
   STATUS     mandatory
   DESCRIPTION
     "A single entry in the table represents a single 
      mscTrmLgLk component."
   INDEX {
      mscTrmIndex,
      mscTrmLgIndex,
      mscTrmLgLkIndex }
::= { mscTrmLgLkRowStatusTable 1 }

MscTrmLgLkRowStatusEntry ::= SEQUENCE {
   mscTrmLgLkRowStatus
      RowStatus,
   mscTrmLgLkComponentName
      DisplayString,
   mscTrmLgLkStorageType
      StorageType,
   mscTrmLgLkIndex
      Integer32 }

mscTrmLgLkRowStatus OBJECT-TYPE
   SYNTAX     RowStatus 
   ACCESS     read-only
   STATUS     mandatory
   DESCRIPTION
     "This variable is used as the basis for SNMP naming of
      mscTrmLgLk components.
      These components cannot be added nor deleted."
::= { mscTrmLgLkRowStatusEntry 1 }

mscTrmLgLkComponentName OBJECT-TYPE
   SYNTAX     DisplayString 
   ACCESS     read-only
   STATUS     mandatory
   DESCRIPTION
     "This variable provides the component's string name for
      use with the ASCII Console Interface"
::= { mscTrmLgLkRowStatusEntry 2 }

mscTrmLgLkStorageType OBJECT-TYPE
   SYNTAX     StorageType 
   ACCESS     read-only
   STATUS     mandatory
   DESCRIPTION
     "This variable represents the storage type value for the
      mscTrmLgLk tables."
::= { mscTrmLgLkRowStatusEntry 4 }

mscTrmLgLkIndex OBJECT-TYPE
   SYNTAX     Integer32 (1..1023)
   ACCESS     not-accessible
   STATUS     mandatory
   DESCRIPTION
     "This variable represents the index for the mscTrmLgLk tables."
::= { mscTrmLgLkRowStatusEntry 10 }

mscTrmLgLkOperTable OBJECT-TYPE
   SYNTAX     SEQUENCE OF MscTrmLgLkOperEntry
   ACCESS     not-accessible
   STATUS     mandatory
   DESCRIPTION
     "*** THIS TABLE CURRENTLY NOT IMPLEMENTED ***

      Trm Lk/<n> Operational
      This group of attributes is used to list links. These links are all 
      registered with Transport Resource Manager. They have a status 
      which reflects the current view of the link."
::= { mscTrmLgLk 10 }

mscTrmLgLkOperEntry OBJECT-TYPE
   SYNTAX     MscTrmLgLkOperEntry
   ACCESS     not-accessible
   STATUS     mandatory
   DESCRIPTION
     "An entry in the mscTrmLgLkOperTable."
   INDEX {
      mscTrmIndex,
      mscTrmLgIndex,
      mscTrmLgLkIndex }
::= { mscTrmLgLkOperTable 1 }

MscTrmLgLkOperEntry ::= SEQUENCE {
   mscTrmLgLkStatus
      INTEGER,
   mscTrmLgLkThroughput
      Gauge32,
   mscTrmLgLkDelay
      Gauge32,
   mscTrmLgLkMaxTxUnit
      Unsigned32,
   mscTrmLgLkLinkComponentName
      RowPointer,
   mscTrmLgLkDelayUsec
      FixedPoint1 }

mscTrmLgLkStatus OBJECT-TYPE
   SYNTAX     INTEGER  {
                 inactive(1),
                 joining(2),
                 online(3) }
   ACCESS     read-only
   STATUS     mandatory
   DESCRIPTION
     "This attribute indicates if the inactive link is disabled, joining, 
      waiting to join, or in standby mode.
      
      inactive - The link is known to TRM but is not active. This can 
      mean that it is disabled, or has not yet started to join.
      joining - The link has requested to join the routing systems.
      online- The link is active and has joined one or more routing 
      systems."
::= { mscTrmLgLkOperEntry 1 }

mscTrmLgLkThroughput OBJECT-TYPE
   SYNTAX     Gauge32 (1..640000000)
   ACCESS     read-only
   STATUS     mandatory
   DESCRIPTION
     "This attribute indicates the throughput of the link in kbit/s. This 
      value represents a nominal bandwidth available for connectionless 
      traffic, after the maximum reserved for path-oriented traffic has 
      been subtracted from trunk bandwidth. If a trunk speed override is 
      specified, it is used instead. The 'throughput' value can be 
      exceeded by connectionless traffic whenever path-oriented traffic is 
      not using it's reserved bandwidth."
::= { mscTrmLgLkOperEntry 2 }

mscTrmLgLkDelay OBJECT-TYPE
   SYNTAX     Gauge32 (1..1500)
   ACCESS     read-only
   STATUS     obsolete
   DESCRIPTION
     "This is the round trip delay of the link in milliseconds. This value 
      represents a nominal delay for connectionless traffic. 
      Connectionless traffic is biased away from trunks carrying path-
      oriented traffic by increasing this value. The value of this attribute is 
      a function of the percentage of reserved path-oriented bandwidth 
      and takes a maximum value of 1500 msec for 100% path-oriented 
      trunks. If an override delay is specified, it will be used instead."
::= { mscTrmLgLkOperEntry 3 }

mscTrmLgLkMaxTxUnit OBJECT-TYPE
   SYNTAX     Unsigned32 (1..65535)
   ACCESS     read-only
   STATUS     mandatory
   DESCRIPTION
     "This attribute indicates the maximum data unit in bytes of this link. 
      It represents the maximum frame length (including user data and 
      routing headers) that can be sent on the link."
::= { mscTrmLgLkOperEntry 4 }

mscTrmLgLkLinkComponentName OBJECT-TYPE
   SYNTAX     RowPointer 
   ACCESS     read-only
   STATUS     mandatory
   DESCRIPTION
     "This attribute indicates the link's component name. A link is either 
      a trunk or a gateway to another module. The component name may 
      be used to obtain additional information from the link system."
::= { mscTrmLgLkOperEntry 5 }

mscTrmLgLkDelayUsec OBJECT-TYPE
   SYNTAX     FixedPoint1 (10..15000)
   ACCESS     read-only
   STATUS     mandatory
   DESCRIPTION
     "This attribute indicates the round trip delay of the link in 
      milliseconds. This value represents a nominal delay for 
      connectionless traffic. Connectionless traffic is biased away from 
      trunks carrying path-oriented traffic by increasing this value. The 
      value of this attribute is a function of the percentage of reserved 
      path-oriented bandwidth and takes a maximum value of 1500 msec 
      for 100% path-oriented trunks. If a delay override is specified, it 
      will be used instead."
::= { mscTrmLgLkOperEntry 6 }

mscTrmLgLkFwdStatsTable OBJECT-TYPE
   SYNTAX     SEQUENCE OF MscTrmLgLkFwdStatsEntry
   ACCESS     not-accessible
   STATUS     mandatory
   DESCRIPTION
     "*** THIS TABLE CURRENTLY NOT IMPLEMENTED ***

      This group of attributes is used to display egress statistics collected 
      by packet forwarding on this link. The statistics can be used to 
      monitor congestion conditions and packet discards on a link."
::= { mscTrmLgLk 11 }

mscTrmLgLkFwdStatsEntry OBJECT-TYPE
   SYNTAX     MscTrmLgLkFwdStatsEntry
   ACCESS     not-accessible
   STATUS     mandatory
   DESCRIPTION
     "An entry in the mscTrmLgLkFwdStatsTable."
   INDEX {
      mscTrmIndex,
      mscTrmLgIndex,
      mscTrmLgLkIndex }
::= { mscTrmLgLkFwdStatsTable 1 }

MscTrmLgLkFwdStatsEntry ::= SEQUENCE {
   mscTrmLgLkFciSet
      Counter32,
   mscTrmLgLkOverflowAttempts
      Counter32,
   mscTrmLgLkPathOverflowAttempts
      Counter32 }

mscTrmLgLkFciSet OBJECT-TYPE
   SYNTAX     Counter32 
   ACCESS     read-only
   STATUS     mandatory
   DESCRIPTION
     "This attribute counts the packets whose FCI bits are set by packet 
      forwarding due to congestion on this link, and when the 
      forwardingPolicy attribute of Routing DpnAddressPlan is set to 
      loadshare or loadspread. This counter wraps around to zero when 
      the maximum value is reached."
::= { mscTrmLgLkFwdStatsEntry 1 }

mscTrmLgLkOverflowAttempts OBJECT-TYPE
   SYNTAX     Counter32 
   ACCESS     read-only
   STATUS     mandatory
   DESCRIPTION
     "This attribute counts the number of times DPRS packet forwarding 
      attempts to overflow packets to another link in a link group due to 
      congestion on this link. It is used only when the attribute 
      forwardingPolicy in component rtg dpn is set to the value 
      loadspreading. This counter wraps around to zero when the 
      maximum value is reached."
::= { mscTrmLgLkFwdStatsEntry 2 }

mscTrmLgLkPathOverflowAttempts OBJECT-TYPE
   SYNTAX     Counter32 
   ACCESS     read-only
   STATUS     mandatory
   DESCRIPTION
     "This attribute counts the number of times DPRS packet forwarding 
      attempts to overflow packets to another link group due to 
      congestion on the link group of this link. This counter wraps around 
      to zero when the maximum value is reached."
::= { mscTrmLgLkFwdStatsEntry 3 }

mscTrmLgLkDiscardCongestedTable OBJECT-TYPE
   SYNTAX     SEQUENCE OF MscTrmLgLkDiscardCongestedEntry
   ACCESS     not-accessible
   STATUS     mandatory
   DESCRIPTION
     "*** THIS TABLE CURRENTLY NOT IMPLEMENTED ***

      This attribute counts the packets that have been discarded by packet 
      forwarding due to congestion on this link and when the 
      forwardingPolicy attribute of Routing DpnAddressPlan is set to 
      loadshare or loadspread. 
      
      This attribute is a vector with three entries. Each entry corresponds 
      to a discard priority of the packet. The first entry represents the 
      discard count of packets with discard priority 1, the second entry 
      discard priority 2, and the third entry discard priority 3. Each entry 
      (counter) wraps around to zero when the maximum value is 
      reached."
::= { mscTrmLgLk 280 }

mscTrmLgLkDiscardCongestedEntry OBJECT-TYPE
   SYNTAX     MscTrmLgLkDiscardCongestedEntry
   ACCESS     not-accessible
   STATUS     mandatory
   DESCRIPTION
     "An entry in the mscTrmLgLkDiscardCongestedTable."
   INDEX {
      mscTrmIndex,
      mscTrmLgIndex,
      mscTrmLgLkIndex,
      mscTrmLgLkDiscardCongestedIndex }
::= { mscTrmLgLkDiscardCongestedTable 1 }

MscTrmLgLkDiscardCongestedEntry ::= SEQUENCE {
   mscTrmLgLkDiscardCongestedIndex
      INTEGER,
   mscTrmLgLkDiscardCongestedValue
      Counter32 }

mscTrmLgLkDiscardCongestedIndex OBJECT-TYPE
   SYNTAX     INTEGER  {
                 discardPriority1(0),
                 discardPriority2(1),
                 discardPriority3(2) }
   ACCESS     not-accessible
   STATUS     mandatory
   DESCRIPTION
     "This variable represents the mscTrmLgLkDiscardCongestedTable
      specific index for the mscTrmLgLkDiscardCongestedTable."
::= { mscTrmLgLkDiscardCongestedEntry 1 }

mscTrmLgLkDiscardCongestedValue OBJECT-TYPE
   SYNTAX     Counter32 
   ACCESS     read-only
   STATUS     mandatory
   DESCRIPTION
     "This variable represents an individual value for the
      mscTrmLgLkDiscardCongestedTable."
::= { mscTrmLgLkDiscardCongestedEntry 2 }

-- 
-- *** THIS SUBTREE CURRENTLY NOT IMPLEMENTED ***
-- 

-- Trm Lg/<neighborNodeName> LNN /<logical network number> 
-- This component is a dynamic subcomponent of LinkGroup. It has 
-- operational attributes only which are stored and maintained by this 
-- component for displaying address plans supported over this link 
-- group. A logical network number (which is used as an instance to 
-- this component) uniquely identifies an address plan and its traffic in 
-- a Passport network.

mscTrmLgLNN OBJECT IDENTIFIER ::= { mscTrmLg 3 }



mscTrmLgLNNRowStatusTable OBJECT-TYPE
   SYNTAX     SEQUENCE OF MscTrmLgLNNRowStatusEntry
   ACCESS     not-accessible
   STATUS     mandatory
   DESCRIPTION
     "*** THIS TABLE CURRENTLY NOT IMPLEMENTED ***

      This entry controls the addition and deletion of 
      mscTrmLgLNN components."
::= { mscTrmLgLNN 1 }

mscTrmLgLNNRowStatusEntry OBJECT-TYPE
   SYNTAX     MscTrmLgLNNRowStatusEntry
   ACCESS     not-accessible
   STATUS     mandatory
   DESCRIPTION
     "A single entry in the table represents a single 
      mscTrmLgLNN component."
   INDEX {
      mscTrmIndex,
      mscTrmLgIndex,
      mscTrmLgLNNIndex }
::= { mscTrmLgLNNRowStatusTable 1 }

MscTrmLgLNNRowStatusEntry ::= SEQUENCE {
   mscTrmLgLNNRowStatus
      RowStatus,
   mscTrmLgLNNComponentName
      DisplayString,
   mscTrmLgLNNStorageType
      StorageType,
   mscTrmLgLNNIndex
      Integer32 }

mscTrmLgLNNRowStatus OBJECT-TYPE
   SYNTAX     RowStatus 
   ACCESS     read-only
   STATUS     mandatory
   DESCRIPTION
     "This variable is used as the basis for SNMP naming of
      mscTrmLgLNN components.
      These components cannot be added nor deleted."
::= { mscTrmLgLNNRowStatusEntry 1 }

mscTrmLgLNNComponentName OBJECT-TYPE
   SYNTAX     DisplayString 
   ACCESS     read-only
   STATUS     mandatory
   DESCRIPTION
     "This variable provides the component's string name for
      use with the ASCII Console Interface"
::= { mscTrmLgLNNRowStatusEntry 2 }

mscTrmLgLNNStorageType OBJECT-TYPE
   SYNTAX     StorageType 
   ACCESS     read-only
   STATUS     mandatory
   DESCRIPTION
     "This variable represents the storage type value for the
      mscTrmLgLNN tables."
::= { mscTrmLgLNNRowStatusEntry 4 }

mscTrmLgLNNIndex OBJECT-TYPE
   SYNTAX     Integer32 (0..2047)
   ACCESS     not-accessible
   STATUS     mandatory
   DESCRIPTION
     "This variable represents the index for the mscTrmLgLNN tables."
::= { mscTrmLgLNNRowStatusEntry 10 }

mscTrmLgLNNOperTable OBJECT-TYPE
   SYNTAX     SEQUENCE OF MscTrmLgLNNOperEntry
   ACCESS     not-accessible
   STATUS     mandatory
   DESCRIPTION
     "*** THIS TABLE CURRENTLY NOT IMPLEMENTED ***

      Trm Lg/<neighborNodeName> LNN/<logical network number> 
      Operational
      This group of attributes is the information associated with an 
      address plan."
::= { mscTrmLgLNN 10 }

mscTrmLgLNNOperEntry OBJECT-TYPE
   SYNTAX     MscTrmLgLNNOperEntry
   ACCESS     not-accessible
   STATUS     mandatory
   DESCRIPTION
     "An entry in the mscTrmLgLNNOperTable."
   INDEX {
      mscTrmIndex,
      mscTrmLgIndex,
      mscTrmLgLNNIndex }
::= { mscTrmLgLNNOperTable 1 }

MscTrmLgLNNOperEntry ::= SEQUENCE {
   mscTrmLgLNNLinkType
      INTEGER,
   mscTrmLgLNNAddressPlanComponentName
      RowPointer }

mscTrmLgLNNLinkType OBJECT-TYPE
   SYNTAX     INTEGER  {
                 trunk(0),
                 internalGateway(1),
                 externalGateway(2) }
   ACCESS     read-only
   STATUS     mandatory
   DESCRIPTION
     "This attribute indicates how the LNN is transported over the link 
      group. It can be one of three types:
      trunk - the LNN is supported by Topology over a Passport to 
      Passport link
      internal gateway - the LNN is supported by an address plan (but not 
      Topology) over a Passport to Passport link
      external gateway - the LNN is supported by an address plan (but not 
      Topology) over a Passport to non-Passport link"
::= { mscTrmLgLNNOperEntry 1 }

mscTrmLgLNNAddressPlanComponentName OBJECT-TYPE
   SYNTAX     RowPointer 
   ACCESS     read-only
   STATUS     mandatory
   DESCRIPTION
     "This attribute indicates the component name of the address plan 
      which owns the logical network number of this component."
::= { mscTrmLgLNNOperEntry 2 }


-- NumberingPlanIndicator / <x121,e164>
-- This component collects all DNAs for a particular numbering plan 
-- indicator e.g., X.121. 

mscNpi OBJECT IDENTIFIER ::= { mscComponents 43 }



mscNpiRowStatusTable OBJECT-TYPE
   SYNTAX     SEQUENCE OF MscNpiRowStatusEntry
   ACCESS     not-accessible
   STATUS     mandatory
   DESCRIPTION
     "This entry controls the addition and deletion of 
      mscNpi components."
::= { mscNpi 1 }

mscNpiRowStatusEntry OBJECT-TYPE
   SYNTAX     MscNpiRowStatusEntry
   ACCESS     not-accessible
   STATUS     mandatory
   DESCRIPTION
     "A single entry in the table represents a single 
      mscNpi component."
   INDEX {
      mscNpiIndex }
::= { mscNpiRowStatusTable 1 }

MscNpiRowStatusEntry ::= SEQUENCE {
   mscNpiRowStatus
      RowStatus,
   mscNpiComponentName
      DisplayString,
   mscNpiStorageType
      StorageType,
   mscNpiIndex
      INTEGER }

mscNpiRowStatus OBJECT-TYPE
   SYNTAX     RowStatus 
   ACCESS     read-only
   STATUS     mandatory
   DESCRIPTION
     "This variable is used as the basis for SNMP naming of
      mscNpi components.
      These components cannot be added nor deleted."
::= { mscNpiRowStatusEntry 1 }

mscNpiComponentName OBJECT-TYPE
   SYNTAX     DisplayString 
   ACCESS     read-only
   STATUS     mandatory
   DESCRIPTION
     "This variable provides the component's string name for
      use with the ASCII Console Interface"
::= { mscNpiRowStatusEntry 2 }

mscNpiStorageType OBJECT-TYPE
   SYNTAX     StorageType 
   ACCESS     read-only
   STATUS     mandatory
   DESCRIPTION
     "This variable represents the storage type value for the
      mscNpi tables."
::= { mscNpiRowStatusEntry 4 }

mscNpiIndex OBJECT-TYPE
   SYNTAX     INTEGER  {
                 x121(0),
                 e164(1) }
   ACCESS     not-accessible
   STATUS     mandatory
   DESCRIPTION
     "This variable represents the index for the mscNpi tables."
::= { mscNpiRowStatusEntry 10 }

mscNpiStatsTable OBJECT-TYPE
   SYNTAX     SEQUENCE OF MscNpiStatsEntry
   ACCESS     not-accessible
   STATUS     mandatory
   DESCRIPTION
     "Npi/<x121,e164> Statistics
      This group of attributes contains the statistics kept for a particular 
      numbering plan indicator. The only statistic present is the total 
      number of DNAs provisioned for the numbering plan."
::= { mscNpi 10 }

mscNpiStatsEntry OBJECT-TYPE
   SYNTAX     MscNpiStatsEntry
   ACCESS     not-accessible
   STATUS     mandatory
   DESCRIPTION
     "An entry in the mscNpiStatsTable."
   INDEX {
      mscNpiIndex }
::= { mscNpiStatsTable 1 }

MscNpiStatsEntry ::= SEQUENCE {
   mscNpiTotalDnas
      Unsigned32 }

mscNpiTotalDnas OBJECT-TYPE
   SYNTAX     Unsigned32 (0..4294967295)
   ACCESS     read-only
   STATUS     mandatory
   DESCRIPTION
     "This attribute holds the total number of Dnas that are in the 
      numbering plan. If this attribute is displayed in provisioning mode, 
      the number includes the Dnas that have been added/deleted in that 
      provisioning session, otherwise the number only includes the Dnas 
      that have been activated."
   DEFVAL     { 0 }
::= { mscNpiStatsEntry 1 }

-- 
-- *** THIS SUBTREE CURRENTLY NOT IMPLEMENTED ***
-- 

-- Npi/<x121,e164> Dna/<BCD(1..15)>
-- This component is a dynamic subcomponent of 
-- NumberingPlanIndicator. This subcomponent represents a DNA in 
-- the numbering plan. 

mscNpiDna OBJECT IDENTIFIER ::= { mscNpi 2 }



mscNpiDnaRowStatusTable OBJECT-TYPE
   SYNTAX     SEQUENCE OF MscNpiDnaRowStatusEntry
   ACCESS     not-accessible
   STATUS     mandatory
   DESCRIPTION
     "*** THIS TABLE CURRENTLY NOT IMPLEMENTED ***

      This entry controls the addition and deletion of 
      mscNpiDna components."
::= { mscNpiDna 1 }

mscNpiDnaRowStatusEntry OBJECT-TYPE
   SYNTAX     MscNpiDnaRowStatusEntry
   ACCESS     not-accessible
   STATUS     mandatory
   DESCRIPTION
     "A single entry in the table represents a single 
      mscNpiDna component."
   INDEX {
      mscNpiIndex,
      mscNpiDnaIndex }
::= { mscNpiDnaRowStatusTable 1 }

MscNpiDnaRowStatusEntry ::= SEQUENCE {
   mscNpiDnaRowStatus
      RowStatus,
   mscNpiDnaComponentName
      DisplayString,
   mscNpiDnaStorageType
      StorageType,
   mscNpiDnaIndex
      DigitString }

mscNpiDnaRowStatus OBJECT-TYPE
   SYNTAX     RowStatus 
   ACCESS     read-only
   STATUS     mandatory
   DESCRIPTION
     "This variable is used as the basis for SNMP naming of
      mscNpiDna components.
      These components cannot be added nor deleted."
::= { mscNpiDnaRowStatusEntry 1 }

mscNpiDnaComponentName OBJECT-TYPE
   SYNTAX     DisplayString 
   ACCESS     read-only
   STATUS     mandatory
   DESCRIPTION
     "This variable provides the component's string name for
      use with the ASCII Console Interface"
::= { mscNpiDnaRowStatusEntry 2 }

mscNpiDnaStorageType OBJECT-TYPE
   SYNTAX     StorageType 
   ACCESS     read-only
   STATUS     mandatory
   DESCRIPTION
     "This variable represents the storage type value for the
      mscNpiDna tables."
::= { mscNpiDnaRowStatusEntry 4 }

mscNpiDnaIndex OBJECT-TYPE
   SYNTAX     DigitString (SIZE (1..15))
   ACCESS     not-accessible
   STATUS     mandatory
   DESCRIPTION
     "This variable represents the index for the mscNpiDna tables."
::= { mscNpiDnaRowStatusEntry 10 }

mscNpiDnaInfoTable OBJECT-TYPE
   SYNTAX     SEQUENCE OF MscNpiDnaInfoEntry
   ACCESS     not-accessible
   STATUS     mandatory
   DESCRIPTION
     "*** THIS TABLE CURRENTLY NOT IMPLEMENTED ***

      Npi/<x121,e164> Dna/<BCD(1..15)> Information
      This group of attributes contains the attributes for a DNA in the 
      numbering plan."
::= { mscNpiDna 10 }

mscNpiDnaInfoEntry OBJECT-TYPE
   SYNTAX     MscNpiDnaInfoEntry
   ACCESS     not-accessible
   STATUS     mandatory
   DESCRIPTION
     "An entry in the mscNpiDnaInfoTable."
   INDEX {
      mscNpiIndex,
      mscNpiDnaIndex }
::= { mscNpiDnaInfoTable 1 }

MscNpiDnaInfoEntry ::= SEQUENCE {
   mscNpiDnaDestinationName
      RowPointer }

mscNpiDnaDestinationName OBJECT-TYPE
   SYNTAX     RowPointer 
   ACCESS     read-only
   STATUS     mandatory
   DESCRIPTION
     "This attribute holds the Component Name of the application to 
      which the DNA belongs."
::= { mscNpiDnaInfoEntry 1 }




-- 
-- Version and Compliance statements
-- 



-- Object-Group Statement:
-- A list of all current accessible leaf objects.

-- OBJECTS { mscTrmLkPathOverflowAttempts,
--           mscRtgSplittingRegionIdsValue,
--           mscTrmLgLNNStorageType,
--           mscTrmLkDiscardCongestedValue,
--           mscNpiDnaComponentName,
--           mscTrmLgLkDelayUsec,
--           mscRtgTopNodeLgTputMetric,
--           mscRtgTopNodeLgTrkObjFarEndTrmLkInstance,
--           mscNpiStorageType,
--           mscRtgTopNodeLgComponentName,
--           mscRtgTopStorageType,
--           mscRtgTopControlPktTx,
--           mscTrmLgLkStatus,
--           mscTrmLkRowStatus,
--           mscTrmLgLkPathOverflowAttempts,
--           mscRtgStorageType,
--           mscTrmLkDelayUsec,
--           mscRtgTopNodeLgTrkObjMaxReservableBwOut,
--           mscTrmLgLNNAddressPlanComponentName,
--           mscRtgTopNodeLgTrkObjStorageType,
--           mscNpiDnaRowStatus,
--           mscTrmLgLkMaxTxUnit,
--           mscRtgTopNodeLgDelayMetric,
--           mscTrmStorageType,
--           mscNpiDnaStorageType,
--           mscRtgComponentName,
--           mscTrmLgLkRowStatus,
--           mscTrmLkComponentName,
--           mscNpiRowStatus,
--           mscRtgTopRowStatus,
--           mscNpiDnaDestinationName,
--           mscRtgTopControlPktRx,
--           mscRtgRowStatus,
--           mscTrmLgLNNLinkType,
--           mscRtgTopNodeLgTrkObjCustomerParameter,
--           mscRtgTopNodeStorageType,
--           mscTrmLgLNNComponentName,
--           mscTrmLkLinkComponentName,
--           mscRtgTopNodeLgTrkObjTrunkSecurity,
--           mscNpiComponentName,
--           mscRtgTopNodeLgTrkObjTrunkType,
--           mscRtgTopNodeComponentName,
--           mscTrmLgLkOverflowAttempts,
--           mscTrmRowStatus,
--           mscRtgTopComponentName,
--           mscRtgTopNodeLgLnnValue,
--           mscTrmLkFciSet,
--           mscTrmLgLkComponentName,
--           mscTrmLgStorageType,
--           mscTrmLkMaxTxUnit,
--           mscRtgTopNodeLgTrkObjRowStatus,
--           mscRtgTopNodeLgStorageType,
--           mscRtgTopControlBytesTx,
--           mscTrmLgLkLinkComponentName,
--           mscTrmLgLkThroughput,
--           mscTrmLgRowStatus,
--           mscTrmComponentName,
--           mscRtgTopNodeRowStatus,
--           mscNpiTotalDnas,
--           mscTrmLgLkFciSet,
--           mscRtgTandemTraffic,
--           mscRtgTopNodeLgTrkObjUnresValue,
--           mscRtgTopNodeNodeId,
--           mscRtgTopNodeLgTrkObjComponentName,
--           mscTrmLkOverflowAttempts,
--           mscRtgTopNodeLgTrkObjTrunkDelay,
--           mscTrmLgLkDiscardCongestedValue,
--           mscRtgTopNodeLgTrkObjTrunkCost,
--           mscTrmLkStorageType,
--           mscRtgSplittingRegionIdsRowStatus,
--           mscRtgTopNodeLgRowStatus,
--           mscTrmLgComponentName,
--           mscRtgTopNodeLgTrkObjSupportedTrafficTypes,
--           mscTrmLkThroughput,
--           mscTrmLgLkStorageType,
--           mscTrmLkStatus,
--           mscRtgTopControlBytesRx,
--           mscTrmLgLNNRowStatus }
-- STATUS  mandatory
-- DESCRIPTION
--   "A list of all current accessible leaf objects."

baseRoutingGroup OBJECT IDENTIFIER ::= { baseRoutingMIB 1 }
baseRoutingGroupCA OBJECT IDENTIFIER ::= { baseRoutingGroup 1 }
baseRoutingGroupCA02 OBJECT IDENTIFIER ::= { baseRoutingGroupCA 3 }
baseRoutingGroupCA02A OBJECT IDENTIFIER ::= { baseRoutingGroupCA02 2 }



-- Agent-Capabilities Statement:

-- PRODUCT-RELEASE "MscPassport Release 1.2 BaseRouting."
-- STATUS          mandatory
-- DESCRIPTION     "Carrier Passport BaseRouting MIB: MIB Version CA02A,
--                  Software Version CA02S9C."
-- SUPPORTS        Nortel-MsCarrier-MscPassport-BaseRoutingMIB
--    INCLUDES     { baseRoutingGroupCA02A }

baseRoutingCapabilities OBJECT IDENTIFIER ::= { baseRoutingMIB 3 }
baseRoutingCapabilitiesCA OBJECT IDENTIFIER ::= { baseRoutingCapabilities 1 }
baseRoutingCapabilitiesCA02 OBJECT IDENTIFIER ::= { baseRoutingCapabilitiesCA 3 }
baseRoutingCapabilitiesCA02A OBJECT IDENTIFIER ::= { baseRoutingCapabilitiesCA02 2 }





END
