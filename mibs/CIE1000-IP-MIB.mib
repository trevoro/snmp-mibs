-- *****************************************************************
-- IP-MIB:  Cisco private MIB
-- ****************************************************************

CIE1000-IP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000InterfaceIndex FROM CIE1000-TC
    CIE1000RowEditorState FROM CIE1000-TC
    CIE1000Unsigned8 FROM CIE1000-TC
    InetAddressIPv6 FROM INET-ADDRESS-MIB
    Counter64 FROM SNMPv2-SMI
    Integer32 FROM SNMPv2-SMI
    IpAddress FROM SNMPv2-SMI
    Unsigned32 FROM SNMPv2-SMI
    MacAddress FROM SNMPv2-TC
    TruthValue FROM SNMPv2-TC
    ;

cie1000IpMib MODULE-IDENTITY
    LAST-UPDATED "201508240000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "Private IP MIB."
    REVISION    "201508240000Z"
    DESCRIPTION
        "Add capability for IPv4/IPv6 statistics availability."
    REVISION    "201410290000Z"
    DESCRIPTION
        "Removed the fields arpRetransmitTime and reasmMaxSize."
    REVISION    "201410210000Z"
    DESCRIPTION
        "Added arpCheck in the DhcpClientState enum"
    REVISION    "201409110000Z"
    DESCRIPTION
        "Revise definition of IPv4/IPv6 interface status table index."
    REVISION    "201407010000Z"
    DESCRIPTION
        "Initial version."
    ::= { cie1000SwitchMgmt 102 }


CIE1000IpDhcpClientState ::= TEXTUAL-CONVENTION
    STATUS      current
    DESCRIPTION
        "-"
    SYNTAX      INTEGER { stopped(0), init(1), selecting(2),
                          requesting(3), rebinding(4), bound(5),
                          renewing(6), fallback(7), arpCheck(8) }

cie1000IpMibObjects OBJECT IDENTIFIER
    ::= { cie1000IpMib 1 }

cie1000IpCapabilities OBJECT IDENTIFIER
    ::= { cie1000IpMibObjects 1 }

cie1000IpCapabilitiesHasIpv4HostCapabilities OBJECT-TYPE
    SYNTAX      TruthValue
    MAX-ACCESS  read-only
    STATUS      current
    DESCRIPTION
        "The device has IPv4 host capabilities for management."
    ::= { cie1000IpCapabilities 1 }

cie1000IpCapabilitiesHasIpv6HostCapabilities OBJECT-TYPE
    SYNTAX      TruthValue
    MAX-ACCESS  read-only
    STATUS      current
    DESCRIPTION
        "The device has IPv6 host capabilities for management."
    ::= { cie1000IpCapabilities 2 }

cie1000IpCapabilitiesHasIpv4UnicastRoutingCapabilities OBJECT-TYPE
    SYNTAX      TruthValue
    MAX-ACCESS  read-only
    STATUS      current
    DESCRIPTION
        "The device has IPv4 unicast routing capabilities."
    ::= { cie1000IpCapabilities 3 }

cie1000IpCapabilitiesHasIpv4UnicastHwRoutingCapabilities OBJECT-TYPE
    SYNTAX      TruthValue
    MAX-ACCESS  read-only
    STATUS      current
    DESCRIPTION
        "The device has IPv4 unicast hardware accelerated routing capabilities."
    ::= { cie1000IpCapabilities 4 }

cie1000IpCapabilitiesHasIpv6UnicastRoutingCapabilities OBJECT-TYPE
    SYNTAX      TruthValue
    MAX-ACCESS  read-only
    STATUS      current
    DESCRIPTION
        "The device has IPv6 unicast routing capabilities."
    ::= { cie1000IpCapabilities 5 }

cie1000IpCapabilitiesHasIpv6UnicastHwRoutingCapabilities OBJECT-TYPE
    SYNTAX      TruthValue
    MAX-ACCESS  read-only
    STATUS      current
    DESCRIPTION
        "The device has IPv6 unicast hardware accelerated routing capabilities."
    ::= { cie1000IpCapabilities 6 }

cie1000IpCapabilitiesMaxNumberOfIpInterfaces OBJECT-TYPE
    SYNTAX      Unsigned32
    MAX-ACCESS  read-only
    STATUS      current
    DESCRIPTION
        "Maximum number of IP interfaces supported by the device."
    ::= { cie1000IpCapabilities 7 }

cie1000IpCapabilitiesMaxNumberOfStaticRoutes OBJECT-TYPE
    SYNTAX      Unsigned32
    MAX-ACCESS  read-only
    STATUS      current
    DESCRIPTION
        "Maximum number of static configured IP routes (shared by IPv4 and
         IPv6)."
    ::= { cie1000IpCapabilities 8 }

cie1000IpCapabilitiesNumberOfLpmHardwareEntries OBJECT-TYPE
    SYNTAX      Unsigned32
    MAX-ACCESS  read-only
    STATUS      current
    DESCRIPTION
        "Number of hardware LPM (longest prefix match) entries."
    ::= { cie1000IpCapabilities 9 }

cie1000IpCapabilitiesHasPerInterfaceIpv4Statistics OBJECT-TYPE
    SYNTAX      TruthValue
    MAX-ACCESS  read-only
    STATUS      current
    DESCRIPTION
        "If true, the platform supports detailed IPv4 statistics per interface."
    ::= { cie1000IpCapabilities 10 }

cie1000IpCapabilitiesHasPerInterfaceIpv6Statistics OBJECT-TYPE
    SYNTAX      TruthValue
    MAX-ACCESS  read-only
    STATUS      current
    DESCRIPTION
        "If true, the platform supports detailed IPv6 statistics per interface."
    ::= { cie1000IpCapabilities 11 }

cie1000IpConfig OBJECT IDENTIFIER
    ::= { cie1000IpMibObjects 2 }

cie1000IpConfigGlobals OBJECT IDENTIFIER
    ::= { cie1000IpConfig 1 }

cie1000IpConfigGlobalsMain OBJECT IDENTIFIER
    ::= { cie1000IpConfigGlobals 1 }

cie1000IpConfigGlobalsMainEnableRouting OBJECT-TYPE
    SYNTAX      TruthValue
    MAX-ACCESS  read-write
    STATUS      current
    DESCRIPTION
        "Enable routing."
    ::= { cie1000IpConfigGlobalsMain 1 }

cie1000IpConfigInterfaces OBJECT IDENTIFIER
    ::= { cie1000IpConfig 2 }

cie1000IpConfigInterfacesTable OBJECT-TYPE
    SYNTAX      SEQUENCE OF CIE1000IpConfigInterfacesEntry
    MAX-ACCESS  not-accessible
    STATUS      current
    DESCRIPTION
        "This is the IP interface table. When an IP interface is created it can
         be configured in the other tables found in this MIB."
    ::= { cie1000IpConfigInterfaces 1 }

cie1000IpConfigInterfacesEntry OBJECT-TYPE
    SYNTAX      CIE1000IpConfigInterfacesEntry
    MAX-ACCESS  not-accessible
    STATUS      current
    DESCRIPTION
        "Entries in this table represent IP interfaces created on the system"
    INDEX       { cie1000IpConfigInterfacesIfIndex }
    ::= { cie1000IpConfigInterfacesTable 1 }

CIE1000IpConfigInterfacesEntry ::= SEQUENCE {
    cie1000IpConfigInterfacesIfIndex  CIE1000InterfaceIndex,
    cie1000IpConfigInterfacesAction   CIE1000RowEditorState
}

cie1000IpConfigInterfacesIfIndex OBJECT-TYPE
    SYNTAX      CIE1000InterfaceIndex
    MAX-ACCESS  accessible-for-notify
    STATUS      current
    DESCRIPTION
        "Interface index number."
    ::= { cie1000IpConfigInterfacesEntry 1 }

cie1000IpConfigInterfacesAction OBJECT-TYPE
    SYNTAX      CIE1000RowEditorState
    MAX-ACCESS  read-write
    STATUS      current
    DESCRIPTION
        "Action"
    ::= { cie1000IpConfigInterfacesEntry 100 }

cie1000IpConfigInterfacesTableRowEditor OBJECT IDENTIFIER
    ::= { cie1000IpConfigInterfaces 2 }

cie1000IpConfigInterfacesTableRowEditorIfIndex OBJECT-TYPE
    SYNTAX      CIE1000InterfaceIndex
    MAX-ACCESS  read-write
    STATUS      current
    DESCRIPTION
        "Interface index number."
    ::= { cie1000IpConfigInterfacesTableRowEditor 1 }

cie1000IpConfigInterfacesTableRowEditorAction OBJECT-TYPE
    SYNTAX      CIE1000RowEditorState
    MAX-ACCESS  read-write
    STATUS      current
    DESCRIPTION
        "Action"
    ::= { cie1000IpConfigInterfacesTableRowEditor 100 }

cie1000IpConfigInterfacesIpv4Table OBJECT-TYPE
    SYNTAX      SEQUENCE OF CIE1000IpConfigInterfacesIpv4Entry
    MAX-ACCESS  not-accessible
    STATUS      current
    DESCRIPTION
        "IPv4 interface configuration table. This table enables IPv4 related
         configuration of the corresponding IP interface."
    ::= { cie1000IpConfigInterfaces 3 }

cie1000IpConfigInterfacesIpv4Entry OBJECT-TYPE
    SYNTAX      CIE1000IpConfigInterfacesIpv4Entry
    MAX-ACCESS  not-accessible
    STATUS      current
    DESCRIPTION
        "Each entry in this table represents an IP interface."
    INDEX       { cie1000IpConfigInterfacesIpv4IfIndex }
    ::= { cie1000IpConfigInterfacesIpv4Table 1 }

CIE1000IpConfigInterfacesIpv4Entry ::= SEQUENCE {
    cie1000IpConfigInterfacesIpv4IfIndex                    CIE1000InterfaceIndex,
    cie1000IpConfigInterfacesIpv4Active                     TruthValue,
    cie1000IpConfigInterfacesIpv4EnableDhcpClient           TruthValue,
    cie1000IpConfigInterfacesIpv4Ipv4Address                IpAddress,
    cie1000IpConfigInterfacesIpv4PrefixSize                 Unsigned32,
    cie1000IpConfigInterfacesIpv4DhcpClientFallbackTimeout  Unsigned32
}

cie1000IpConfigInterfacesIpv4IfIndex OBJECT-TYPE
    SYNTAX      CIE1000InterfaceIndex
    MAX-ACCESS  accessible-for-notify
    STATUS      current
    DESCRIPTION
        "Interface index number."
    ::= { cie1000IpConfigInterfacesIpv4Entry 1 }

cie1000IpConfigInterfacesIpv4Active OBJECT-TYPE
    SYNTAX      TruthValue
    MAX-ACCESS  read-write
    STATUS      current
    DESCRIPTION
        "Enable IPv4.
         
         IPv4 can only be enabled if either the DHCP client is enabled, or a
         valid address has been configured."
    ::= { cie1000IpConfigInterfacesIpv4Entry 2 }

cie1000IpConfigInterfacesIpv4EnableDhcpClient OBJECT-TYPE
    SYNTAX      TruthValue
    MAX-ACCESS  read-write
    STATUS      current
    DESCRIPTION
        "Enable IPv4 DHCP client.
         
         Note: the DHCP client can only be enabled if there is no conflict in
         the values of: ipv4Address, prefixSize, and dhcpClientFallbackTimeout."
    ::= { cie1000IpConfigInterfacesIpv4Entry 3 }

cie1000IpConfigInterfacesIpv4Ipv4Address OBJECT-TYPE
    SYNTAX      IpAddress
    MAX-ACCESS  read-write
    STATUS      current
    DESCRIPTION
        "IPv4 address.
         
         Note: Multiple interfaces may not have overlapping networks."
    ::= { cie1000IpConfigInterfacesIpv4Entry 4 }

cie1000IpConfigInterfacesIpv4PrefixSize OBJECT-TYPE
    SYNTAX      Unsigned32
    MAX-ACCESS  read-write
    STATUS      current
    DESCRIPTION
        "Prefix size of the network.
         
         Note: Multiple interfaces may not have overlapping networks."
    ::= { cie1000IpConfigInterfacesIpv4Entry 5 }

cie1000IpConfigInterfacesIpv4DhcpClientFallbackTimeout OBJECT-TYPE
    SYNTAX      Unsigned32
    MAX-ACCESS  read-write
    STATUS      current
    DESCRIPTION
        "DHCP client fallback timer.
         
         If DHCP is disabled then this object has no effect. If DHCP is enabled
         and the fallback timeout value is different from zero, then this timer
         will stop the DHCP process and assign the ipv4Address to the interface
         instead."
    ::= { cie1000IpConfigInterfacesIpv4Entry 6 }

cie1000IpConfigInterfacesIpv6Table OBJECT-TYPE
    SYNTAX      SEQUENCE OF CIE1000IpConfigInterfacesIpv6Entry
    MAX-ACCESS  not-accessible
    STATUS      current
    DESCRIPTION
        "IPv6 interface configuration table. This table enables IPv6 related
         configuration of the corresponding IP interface."
    ::= { cie1000IpConfigInterfaces 4 }

cie1000IpConfigInterfacesIpv6Entry OBJECT-TYPE
    SYNTAX      CIE1000IpConfigInterfacesIpv6Entry
    MAX-ACCESS  not-accessible
    STATUS      current
    DESCRIPTION
        "Each entry in this table represents an IP interface."
    INDEX       { cie1000IpConfigInterfacesIpv6IfIndex }
    ::= { cie1000IpConfigInterfacesIpv6Table 1 }

CIE1000IpConfigInterfacesIpv6Entry ::= SEQUENCE {
    cie1000IpConfigInterfacesIpv6IfIndex      CIE1000InterfaceIndex,
    cie1000IpConfigInterfacesIpv6Active       TruthValue,
    cie1000IpConfigInterfacesIpv6Ipv6Address  InetAddressIPv6,
    cie1000IpConfigInterfacesIpv6PrefixSize   Unsigned32
}

cie1000IpConfigInterfacesIpv6IfIndex OBJECT-TYPE
    SYNTAX      CIE1000InterfaceIndex
    MAX-ACCESS  accessible-for-notify
    STATUS      current
    DESCRIPTION
        "Interface index number."
    ::= { cie1000IpConfigInterfacesIpv6Entry 1 }

cie1000IpConfigInterfacesIpv6Active OBJECT-TYPE
    SYNTAX      TruthValue
    MAX-ACCESS  read-write
    STATUS      current
    DESCRIPTION
        "Enable the static configured IPv6 address.
         
         The static configured IPv6 address can only be configured if a valid
         address has been written into 'ipv6Address' and 'prefixSize'."
    ::= { cie1000IpConfigInterfacesIpv6Entry 2 }

cie1000IpConfigInterfacesIpv6Ipv6Address OBJECT-TYPE
    SYNTAX      InetAddressIPv6
    MAX-ACCESS  read-write
    STATUS      current
    DESCRIPTION
        "Static configured IPv6 address."
    ::= { cie1000IpConfigInterfacesIpv6Entry 3 }

cie1000IpConfigInterfacesIpv6PrefixSize OBJECT-TYPE
    SYNTAX      Unsigned32
    MAX-ACCESS  read-write
    STATUS      current
    DESCRIPTION
        "Prefix size of the network."
    ::= { cie1000IpConfigInterfacesIpv6Entry 4 }

cie1000IpConfigRoutes OBJECT IDENTIFIER
    ::= { cie1000IpConfig 3 }

cie1000IpConfigRoutesIpv4Table OBJECT-TYPE
    SYNTAX      SEQUENCE OF CIE1000IpConfigRoutesIpv4Entry
    MAX-ACCESS  not-accessible
    STATUS      current
    DESCRIPTION
        "This is the IPv4 route configuration table."
    ::= { cie1000IpConfigRoutes 1 }

cie1000IpConfigRoutesIpv4Entry OBJECT-TYPE
    SYNTAX      CIE1000IpConfigRoutesIpv4Entry
    MAX-ACCESS  not-accessible
    STATUS      current
    DESCRIPTION
        "Each entry in this table represents a configured route.
         
         Note: a route may be configured without being active."
    INDEX       { cie1000IpConfigRoutesIpv4NetworkAddress,
                  cie1000IpConfigRoutesIpv4NetworkPrefixSize,
                  cie1000IpConfigRoutesIpv4NextHop }
    ::= { cie1000IpConfigRoutesIpv4Table 1 }

CIE1000IpConfigRoutesIpv4Entry ::= SEQUENCE {
    cie1000IpConfigRoutesIpv4NetworkAddress     IpAddress,
    cie1000IpConfigRoutesIpv4NetworkPrefixSize  Integer32,
    cie1000IpConfigRoutesIpv4NextHop            IpAddress,
    cie1000IpConfigRoutesIpv4Action             CIE1000RowEditorState
}

cie1000IpConfigRoutesIpv4NetworkAddress OBJECT-TYPE
    SYNTAX      IpAddress
    MAX-ACCESS  accessible-for-notify
    STATUS      current
    DESCRIPTION
        "Network address."
    ::= { cie1000IpConfigRoutesIpv4Entry 1 }

cie1000IpConfigRoutesIpv4NetworkPrefixSize OBJECT-TYPE
    SYNTAX      Integer32 (0..32)
    MAX-ACCESS  accessible-for-notify
    STATUS      current
    DESCRIPTION
        "Network prefix size."
    ::= { cie1000IpConfigRoutesIpv4Entry 2 }

cie1000IpConfigRoutesIpv4NextHop OBJECT-TYPE
    SYNTAX      IpAddress
    MAX-ACCESS  accessible-for-notify
    STATUS      current
    DESCRIPTION
        "Next-hop address."
    ::= { cie1000IpConfigRoutesIpv4Entry 3 }

cie1000IpConfigRoutesIpv4Action OBJECT-TYPE
    SYNTAX      CIE1000RowEditorState
    MAX-ACCESS  read-write
    STATUS      current
    DESCRIPTION
        "Action"
    ::= { cie1000IpConfigRoutesIpv4Entry 100 }

cie1000IpConfigRoutesIpv4RowEditor OBJECT IDENTIFIER
    ::= { cie1000IpConfigRoutes 2 }

cie1000IpConfigRoutesIpv4RowEditorNetworkAddress OBJECT-TYPE
    SYNTAX      IpAddress
    MAX-ACCESS  read-write
    STATUS      current
    DESCRIPTION
        "Network address."
    ::= { cie1000IpConfigRoutesIpv4RowEditor 1 }

cie1000IpConfigRoutesIpv4RowEditorNetworkPrefixSize OBJECT-TYPE
    SYNTAX      Integer32 (0..32)
    MAX-ACCESS  read-write
    STATUS      current
    DESCRIPTION
        "Network prefix size."
    ::= { cie1000IpConfigRoutesIpv4RowEditor 2 }

cie1000IpConfigRoutesIpv4RowEditorNextHop OBJECT-TYPE
    SYNTAX      IpAddress
    MAX-ACCESS  read-write
    STATUS      current
    DESCRIPTION
        "Next-hop address."
    ::= { cie1000IpConfigRoutesIpv4RowEditor 3 }

cie1000IpConfigRoutesIpv4RowEditorAction OBJECT-TYPE
    SYNTAX      CIE1000RowEditorState
    MAX-ACCESS  read-write
    STATUS      current
    DESCRIPTION
        "Action"
    ::= { cie1000IpConfigRoutesIpv4RowEditor 100 }

cie1000IpConfigRoutesIpv6Table OBJECT-TYPE
    SYNTAX      SEQUENCE OF CIE1000IpConfigRoutesIpv6Entry
    MAX-ACCESS  not-accessible
    STATUS      current
    DESCRIPTION
        "This is the IPv6 route configuration table."
    ::= { cie1000IpConfigRoutes 3 }

cie1000IpConfigRoutesIpv6Entry OBJECT-TYPE
    SYNTAX      CIE1000IpConfigRoutesIpv6Entry
    MAX-ACCESS  not-accessible
    STATUS      current
    DESCRIPTION
        "Each entry in this table represents a configured route.
         
         Note: a route may be configured without being active."
    INDEX       { cie1000IpConfigRoutesIpv6NetworkAddress,
                  cie1000IpConfigRoutesIpv6NetworkPrefixSize,
                  cie1000IpConfigRoutesIpv6NextHop,
                  cie1000IpConfigRoutesIpv6NextHopInterface }
    ::= { cie1000IpConfigRoutesIpv6Table 1 }

CIE1000IpConfigRoutesIpv6Entry ::= SEQUENCE {
    cie1000IpConfigRoutesIpv6NetworkAddress     InetAddressIPv6,
    cie1000IpConfigRoutesIpv6NetworkPrefixSize  Integer32,
    cie1000IpConfigRoutesIpv6NextHop            InetAddressIPv6,
    cie1000IpConfigRoutesIpv6NextHopInterface   CIE1000InterfaceIndex,
    cie1000IpConfigRoutesIpv6Action             CIE1000RowEditorState
}

cie1000IpConfigRoutesIpv6NetworkAddress OBJECT-TYPE
    SYNTAX      InetAddressIPv6
    MAX-ACCESS  accessible-for-notify
    STATUS      current
    DESCRIPTION
        "Network address."
    ::= { cie1000IpConfigRoutesIpv6Entry 1 }

cie1000IpConfigRoutesIpv6NetworkPrefixSize OBJECT-TYPE
    SYNTAX      Integer32 (0..128)
    MAX-ACCESS  accessible-for-notify
    STATUS      current
    DESCRIPTION
        "Network prefix size."
    ::= { cie1000IpConfigRoutesIpv6Entry 2 }

cie1000IpConfigRoutesIpv6NextHop OBJECT-TYPE
    SYNTAX      InetAddressIPv6
    MAX-ACCESS  accessible-for-notify
    STATUS      current
    DESCRIPTION
        "Next-hop address."
    ::= { cie1000IpConfigRoutesIpv6Entry 3 }

cie1000IpConfigRoutesIpv6NextHopInterface OBJECT-TYPE
    SYNTAX      CIE1000InterfaceIndex
    MAX-ACCESS  accessible-for-notify
    STATUS      current
    DESCRIPTION
        "If the next-hop address is a link-local address, then the interface of
         the link-local address must be specified here. Otherwise this value is
         not used."
    ::= { cie1000IpConfigRoutesIpv6Entry 4 }

cie1000IpConfigRoutesIpv6Action OBJECT-TYPE
    SYNTAX      CIE1000RowEditorState
    MAX-ACCESS  read-write
    STATUS      current
    DESCRIPTION
        "Action"
    ::= { cie1000IpConfigRoutesIpv6Entry 100 }

cie1000IpConfigRoutesIpv6RowEditor OBJECT IDENTIFIER
    ::= { cie1000IpConfigRoutes 4 }

cie1000IpConfigRoutesIpv6RowEditorNetworkAddress OBJECT-TYPE
    SYNTAX      InetAddressIPv6
    MAX-ACCESS  read-write
    STATUS      current
    DESCRIPTION
        "Network address."
    ::= { cie1000IpConfigRoutesIpv6RowEditor 1 }

cie1000IpConfigRoutesIpv6RowEditorNetworkPrefixSize OBJECT-TYPE
    SYNTAX      Integer32 (0..128)
    MAX-ACCESS  read-write
    STATUS      current
    DESCRIPTION
        "Network prefix size."
    ::= { cie1000IpConfigRoutesIpv6RowEditor 2 }

cie1000IpConfigRoutesIpv6RowEditorNextHop OBJECT-TYPE
    SYNTAX      InetAddressIPv6
    MAX-ACCESS  read-write
    STATUS      current
    DESCRIPTION
        "Next-hop address."
    ::= { cie1000IpConfigRoutesIpv6RowEditor 3 }

cie1000IpConfigRoutesIpv6RowEditorNextHopInterface OBJECT-TYPE
    SYNTAX      CIE1000InterfaceIndex
    MAX-ACCESS  read-write
    STATUS      current
    DESCRIPTION
        "If the next-hop address is a link-local address, then the interface of
         the link-local address must be specified here. Otherwise this value is
         not used."
    ::= { cie1000IpConfigRoutesIpv6RowEditor 4 }

cie1000IpConfigRoutesIpv6RowEditorAction OBJECT-TYPE
    SYNTAX      CIE1000RowEditorState
    MAX-ACCESS  read-write
    STATUS      current
    DESCRIPTION
        "Action"
    ::= { cie1000IpConfigRoutesIpv6RowEditor 100 }

cie1000IpStatus OBJECT IDENTIFIER
    ::= { cie1000IpMibObjects 3 }

cie1000IpStatusGlobals OBJECT IDENTIFIER
    ::= { cie1000IpStatus 1 }

cie1000IpStatusGlobalsIpv4NeighbourTable OBJECT-TYPE
    SYNTAX      SEQUENCE OF CIE1000IpStatusGlobalsIpv4NeighbourEntry
    MAX-ACCESS  not-accessible
    STATUS      current
    DESCRIPTION
        "This is the IPv4 neighbour table (ARP)."
    ::= { cie1000IpStatusGlobals 1 }

cie1000IpStatusGlobalsIpv4NeighbourEntry OBJECT-TYPE
    SYNTAX      CIE1000IpStatusGlobalsIpv4NeighbourEntry
    MAX-ACCESS  not-accessible
    STATUS      current
    DESCRIPTION
        "Each entry in this table represents an entry in the underlying operting
         system's ARP table."
    INDEX       { cie1000IpStatusGlobalsIpv4NeighbourIpv4 }
    ::= { cie1000IpStatusGlobalsIpv4NeighbourTable 1 }

CIE1000IpStatusGlobalsIpv4NeighbourEntry ::= SEQUENCE {
    cie1000IpStatusGlobalsIpv4NeighbourIpv4        IpAddress,
    cie1000IpStatusGlobalsIpv4NeighbourMacAddress  MacAddress,
    cie1000IpStatusGlobalsIpv4NeighbourInterface   CIE1000InterfaceIndex
}

cie1000IpStatusGlobalsIpv4NeighbourIpv4 OBJECT-TYPE
    SYNTAX      IpAddress
    MAX-ACCESS  accessible-for-notify
    STATUS      current
    DESCRIPTION
        "IPv4 address."
    ::= { cie1000IpStatusGlobalsIpv4NeighbourEntry 1 }

cie1000IpStatusGlobalsIpv4NeighbourMacAddress OBJECT-TYPE
    SYNTAX      MacAddress
    MAX-ACCESS  read-only
    STATUS      current
    DESCRIPTION
        "MAC address associated with the IP address"
    ::= { cie1000IpStatusGlobalsIpv4NeighbourEntry 2 }

cie1000IpStatusGlobalsIpv4NeighbourInterface OBJECT-TYPE
    SYNTAX      CIE1000InterfaceIndex
    MAX-ACCESS  read-only
    STATUS      current
    DESCRIPTION
        "Interface the neighbour can be reached on."
    ::= { cie1000IpStatusGlobalsIpv4NeighbourEntry 3 }

cie1000IpStatusGlobalsIpv6NeighbourTable OBJECT-TYPE
    SYNTAX      SEQUENCE OF CIE1000IpStatusGlobalsIpv6NeighbourEntry
    MAX-ACCESS  not-accessible
    STATUS      current
    DESCRIPTION
        "This is the IPv6 neighbour table."
    ::= { cie1000IpStatusGlobals 2 }

cie1000IpStatusGlobalsIpv6NeighbourEntry OBJECT-TYPE
    SYNTAX      CIE1000IpStatusGlobalsIpv6NeighbourEntry
    MAX-ACCESS  not-accessible
    STATUS      current
    DESCRIPTION
        "Each entry in this table represents an entry in the underlying operting
         system's nieghbour table."
    INDEX       { cie1000IpStatusGlobalsIpv6NeighbourIpAddress,
                  cie1000IpStatusGlobalsIpv6NeighbourInterfaceQuery }
    ::= { cie1000IpStatusGlobalsIpv6NeighbourTable 1 }

CIE1000IpStatusGlobalsIpv6NeighbourEntry ::= SEQUENCE {
    cie1000IpStatusGlobalsIpv6NeighbourIpAddress       InetAddressIPv6,
    cie1000IpStatusGlobalsIpv6NeighbourInterfaceQuery  Integer32,
    cie1000IpStatusGlobalsIpv6NeighbourMacAddress      MacAddress,
    cie1000IpStatusGlobalsIpv6NeighbourInterface       CIE1000InterfaceIndex
}

cie1000IpStatusGlobalsIpv6NeighbourIpAddress OBJECT-TYPE
    SYNTAX      InetAddressIPv6
    MAX-ACCESS  accessible-for-notify
    STATUS      current
    DESCRIPTION
        "IP address."
    ::= { cie1000IpStatusGlobalsIpv6NeighbourEntry 1 }

cie1000IpStatusGlobalsIpv6NeighbourInterfaceQuery OBJECT-TYPE
    SYNTAX      Integer32 (0..2147483647)
    MAX-ACCESS  accessible-for-notify
    STATUS      current
    DESCRIPTION
        "If 'ipAddress' is a link-local address, then the interface index where
         the host can be reached must be specified here, otherwise set this to
         zero."
    ::= { cie1000IpStatusGlobalsIpv6NeighbourEntry 2 }

cie1000IpStatusGlobalsIpv6NeighbourMacAddress OBJECT-TYPE
    SYNTAX      MacAddress
    MAX-ACCESS  read-only
    STATUS      current
    DESCRIPTION
        "MAC address associated with the IP address"
    ::= { cie1000IpStatusGlobalsIpv6NeighbourEntry 3 }

cie1000IpStatusGlobalsIpv6NeighbourInterface OBJECT-TYPE
    SYNTAX      CIE1000InterfaceIndex
    MAX-ACCESS  read-only
    STATUS      current
    DESCRIPTION
        "Interface the neighbour can be reached on."
    ::= { cie1000IpStatusGlobalsIpv6NeighbourEntry 4 }

cie1000IpStatusInterfaces OBJECT IDENTIFIER
    ::= { cie1000IpStatus 2 }

cie1000IpStatusInterfacesLinkTable OBJECT-TYPE
    SYNTAX      SEQUENCE OF CIE1000IpStatusInterfacesLinkEntry
    MAX-ACCESS  not-accessible
    STATUS      current
    DESCRIPTION
        "This table provides link-layer status information for IP interfaces."
    ::= { cie1000IpStatusInterfaces 1 }

cie1000IpStatusInterfacesLinkEntry OBJECT-TYPE
    SYNTAX      CIE1000IpStatusInterfacesLinkEntry
    MAX-ACCESS  not-accessible
    STATUS      current
    DESCRIPTION
        "Each entry in this table represents an IP interface."
    INDEX       { cie1000IpStatusInterfacesLinkIfIndex }
    ::= { cie1000IpStatusInterfacesLinkTable 1 }

CIE1000IpStatusInterfacesLinkEntry ::= SEQUENCE {
    cie1000IpStatusInterfacesLinkIfIndex           CIE1000InterfaceIndex,
    cie1000IpStatusInterfacesLinkOsInterfaceIndex  Unsigned32,
    cie1000IpStatusInterfacesLinkMtu               Unsigned32,
    cie1000IpStatusInterfacesLinkMacAddress        MacAddress,
    cie1000IpStatusInterfacesLinkUp                TruthValue,
    cie1000IpStatusInterfacesLinkBroadcast         TruthValue,
    cie1000IpStatusInterfacesLinkLoopback          TruthValue,
    cie1000IpStatusInterfacesLinkRunning           TruthValue,
    cie1000IpStatusInterfacesLinkNoarp             TruthValue,
    cie1000IpStatusInterfacesLinkPromisc           TruthValue,
    cie1000IpStatusInterfacesLinkMulticast         TruthValue
}

cie1000IpStatusInterfacesLinkIfIndex OBJECT-TYPE
    SYNTAX      CIE1000InterfaceIndex
    MAX-ACCESS  accessible-for-notify
    STATUS      current
    DESCRIPTION
        "Interface index number."
    ::= { cie1000IpStatusInterfacesLinkEntry 1 }

cie1000IpStatusInterfacesLinkOsInterfaceIndex OBJECT-TYPE
    SYNTAX      Unsigned32
    MAX-ACCESS  read-only
    STATUS      current
    DESCRIPTION
        "Interface index used by the operating system."
    ::= { cie1000IpStatusInterfacesLinkEntry 2 }

cie1000IpStatusInterfacesLinkMtu OBJECT-TYPE
    SYNTAX      Unsigned32
    MAX-ACCESS  read-only
    STATUS      current
    DESCRIPTION
        "MTU for the interface."
    ::= { cie1000IpStatusInterfacesLinkEntry 3 }

cie1000IpStatusInterfacesLinkMacAddress OBJECT-TYPE
    SYNTAX      MacAddress
    MAX-ACCESS  read-only
    STATUS      current
    DESCRIPTION
        "MAC-address of the interface."
    ::= { cie1000IpStatusInterfacesLinkEntry 4 }

cie1000IpStatusInterfacesLinkUp OBJECT-TYPE
    SYNTAX      TruthValue
    MAX-ACCESS  read-only
    STATUS      current
    DESCRIPTION
        "Indicates if the interface is up."
    ::= { cie1000IpStatusInterfacesLinkEntry 5 }

cie1000IpStatusInterfacesLinkBroadcast OBJECT-TYPE
    SYNTAX      TruthValue
    MAX-ACCESS  read-only
    STATUS      current
    DESCRIPTION
        "Indicates if the interface is capable of transmitting broadcast
         traffic."
    ::= { cie1000IpStatusInterfacesLinkEntry 6 }

cie1000IpStatusInterfacesLinkLoopback OBJECT-TYPE
    SYNTAX      TruthValue
    MAX-ACCESS  read-only
    STATUS      current
    DESCRIPTION
        "Indicates if the interface is a loop-back interface."
    ::= { cie1000IpStatusInterfacesLinkEntry 7 }

cie1000IpStatusInterfacesLinkRunning OBJECT-TYPE
    SYNTAX      TruthValue
    MAX-ACCESS  read-only
    STATUS      current
    DESCRIPTION
        "Interface is running (according to the operating system)."
    ::= { cie1000IpStatusInterfacesLinkEntry 8 }

cie1000IpStatusInterfacesLinkNoarp OBJECT-TYPE
    SYNTAX      TruthValue
    MAX-ACCESS  read-only
    STATUS      current
    DESCRIPTION
        "Indicates if the interface will answer to ARP requests."
    ::= { cie1000IpStatusInterfacesLinkEntry 9 }

cie1000IpStatusInterfacesLinkPromisc OBJECT-TYPE
    SYNTAX      TruthValue
    MAX-ACCESS  read-only
    STATUS      current
    DESCRIPTION
        "Indicates if the interface is in promisc mode."
    ::= { cie1000IpStatusInterfacesLinkEntry 10 }

cie1000IpStatusInterfacesLinkMulticast OBJECT-TYPE
    SYNTAX      TruthValue
    MAX-ACCESS  read-only
    STATUS      current
    DESCRIPTION
        "Indicates if the interface supports multicast."
    ::= { cie1000IpStatusInterfacesLinkEntry 11 }

cie1000IpStatusInterfacesIpv4Table OBJECT-TYPE
    SYNTAX      SEQUENCE OF CIE1000IpStatusInterfacesIpv4Entry
    MAX-ACCESS  not-accessible
    STATUS      current
    DESCRIPTION
        "This table provides IPv4 status information for IP interfaces. If an
         interface is configured to use a DHCP client, then the address can be
         found here."
    ::= { cie1000IpStatusInterfaces 2 }

cie1000IpStatusInterfacesIpv4Entry OBJECT-TYPE
    SYNTAX      CIE1000IpStatusInterfacesIpv4Entry
    MAX-ACCESS  not-accessible
    STATUS      current
    DESCRIPTION
        "Each entry in this table represents an IP interface."
    INDEX       { cie1000IpStatusInterfacesIpv4IfIndex,
                  cie1000IpStatusInterfacesIpv4NetworkAddress,
                  cie1000IpStatusInterfacesIpv4NetworkMaskLength }
    ::= { cie1000IpStatusInterfacesIpv4Table 1 }

CIE1000IpStatusInterfacesIpv4Entry ::= SEQUENCE {
    cie1000IpStatusInterfacesIpv4IfIndex            CIE1000InterfaceIndex,
    cie1000IpStatusInterfacesIpv4NetworkAddress     IpAddress,
    cie1000IpStatusInterfacesIpv4NetworkMaskLength  Integer32,
    cie1000IpStatusInterfacesIpv4Broadcast          IpAddress
}

cie1000IpStatusInterfacesIpv4IfIndex OBJECT-TYPE
    SYNTAX      CIE1000InterfaceIndex
    MAX-ACCESS  accessible-for-notify
    STATUS      current
    DESCRIPTION
        "Interface index number."
    ::= { cie1000IpStatusInterfacesIpv4Entry 1 }

cie1000IpStatusInterfacesIpv4NetworkAddress OBJECT-TYPE
    SYNTAX      IpAddress
    MAX-ACCESS  accessible-for-notify
    STATUS      current
    DESCRIPTION
        "IPv4 network address."
    ::= { cie1000IpStatusInterfacesIpv4Entry 2 }

cie1000IpStatusInterfacesIpv4NetworkMaskLength OBJECT-TYPE
    SYNTAX      Integer32 (0..32)
    MAX-ACCESS  accessible-for-notify
    STATUS      current
    DESCRIPTION
        "IPv4 network mask length."
    ::= { cie1000IpStatusInterfacesIpv4Entry 3 }

cie1000IpStatusInterfacesIpv4Broadcast OBJECT-TYPE
    SYNTAX      IpAddress
    MAX-ACCESS  read-only
    STATUS      current
    DESCRIPTION
        "Broadcast address."
    ::= { cie1000IpStatusInterfacesIpv4Entry 4 }

cie1000IpStatusInterfacesDhcpClientV4Table OBJECT-TYPE
    SYNTAX      SEQUENCE OF CIE1000IpStatusInterfacesDhcpClientV4Entry
    MAX-ACCESS  not-accessible
    STATUS      current
    DESCRIPTION
        "This table provides status on the DHCP client running on a given
         interface."
    ::= { cie1000IpStatusInterfaces 3 }

cie1000IpStatusInterfacesDhcpClientV4Entry OBJECT-TYPE
    SYNTAX      CIE1000IpStatusInterfacesDhcpClientV4Entry
    MAX-ACCESS  not-accessible
    STATUS      current
    DESCRIPTION
        "Each entry in this table represents an instance of a DHCP client."
    INDEX       { cie1000IpStatusInterfacesDhcpClientV4IfIndex }
    ::= { cie1000IpStatusInterfacesDhcpClientV4Table 1 }

CIE1000IpStatusInterfacesDhcpClientV4Entry ::= SEQUENCE {
    cie1000IpStatusInterfacesDhcpClientV4IfIndex   CIE1000InterfaceIndex,
    cie1000IpStatusInterfacesDhcpClientV4State     CIE1000IpDhcpClientState,
    cie1000IpStatusInterfacesDhcpClientV4ServerIp  IpAddress
}

cie1000IpStatusInterfacesDhcpClientV4IfIndex OBJECT-TYPE
    SYNTAX      CIE1000InterfaceIndex
    MAX-ACCESS  accessible-for-notify
    STATUS      current
    DESCRIPTION
        "Interface index number."
    ::= { cie1000IpStatusInterfacesDhcpClientV4Entry 1 }

cie1000IpStatusInterfacesDhcpClientV4State OBJECT-TYPE
    SYNTAX      CIE1000IpDhcpClientState
    MAX-ACCESS  read-only
    STATUS      current
    DESCRIPTION
        "State of the DHCP client."
    ::= { cie1000IpStatusInterfacesDhcpClientV4Entry 2 }

cie1000IpStatusInterfacesDhcpClientV4ServerIp OBJECT-TYPE
    SYNTAX      IpAddress
    MAX-ACCESS  read-only
    STATUS      current
    DESCRIPTION
        "IP address of the DHCP server that has provided the DHCP offer."
    ::= { cie1000IpStatusInterfacesDhcpClientV4Entry 3 }

cie1000IpStatusInterfacesIpv6Table OBJECT-TYPE
    SYNTAX      SEQUENCE OF CIE1000IpStatusInterfacesIpv6Entry
    MAX-ACCESS  not-accessible
    STATUS      current
    DESCRIPTION
        "This table provides IPv6 status information for IP interfaces. If an
         interface is configured to use a DHCP client, then the address can be
         found here."
    ::= { cie1000IpStatusInterfaces 4 }

cie1000IpStatusInterfacesIpv6Entry OBJECT-TYPE
    SYNTAX      CIE1000IpStatusInterfacesIpv6Entry
    MAX-ACCESS  not-accessible
    STATUS      current
    DESCRIPTION
        "Each entry in this table represents an IP interface."
    INDEX       { cie1000IpStatusInterfacesIpv6IfIndex,
                  cie1000IpStatusInterfacesIpv6NetworkAddress,
                  cie1000IpStatusInterfacesIpv6NetworkMaskLength }
    ::= { cie1000IpStatusInterfacesIpv6Table 1 }

CIE1000IpStatusInterfacesIpv6Entry ::= SEQUENCE {
    cie1000IpStatusInterfacesIpv6IfIndex            CIE1000InterfaceIndex,
    cie1000IpStatusInterfacesIpv6NetworkAddress     InetAddressIPv6,
    cie1000IpStatusInterfacesIpv6NetworkMaskLength  Integer32,
    cie1000IpStatusInterfacesIpv6Tentative          TruthValue,
    cie1000IpStatusInterfacesIpv6Duplicated         TruthValue,
    cie1000IpStatusInterfacesIpv6Detached           TruthValue,
    cie1000IpStatusInterfacesIpv6Nodad              TruthValue,
    cie1000IpStatusInterfacesIpv6Autoconf           TruthValue
}

cie1000IpStatusInterfacesIpv6IfIndex OBJECT-TYPE
    SYNTAX      CIE1000InterfaceIndex
    MAX-ACCESS  accessible-for-notify
    STATUS      current
    DESCRIPTION
        "Interface index number."
    ::= { cie1000IpStatusInterfacesIpv6Entry 1 }

cie1000IpStatusInterfacesIpv6NetworkAddress OBJECT-TYPE
    SYNTAX      InetAddressIPv6
    MAX-ACCESS  accessible-for-notify
    STATUS      current
    DESCRIPTION
        "IPv6 network address."
    ::= { cie1000IpStatusInterfacesIpv6Entry 2 }

cie1000IpStatusInterfacesIpv6NetworkMaskLength OBJECT-TYPE
    SYNTAX      Integer32 (0..128)
    MAX-ACCESS  accessible-for-notify
    STATUS      current
    DESCRIPTION
        "IPv6 network mask length."
    ::= { cie1000IpStatusInterfacesIpv6Entry 3 }

cie1000IpStatusInterfacesIpv6Tentative OBJECT-TYPE
    SYNTAX      TruthValue
    MAX-ACCESS  read-only
    STATUS      current
    DESCRIPTION
        "An address whose uniqueness on a link is being verified, prior to its
         assignment to an interface. A tentative address is not considered
         assigned to an interface in the usual sense."
    ::= { cie1000IpStatusInterfacesIpv6Entry 4 }

cie1000IpStatusInterfacesIpv6Duplicated OBJECT-TYPE
    SYNTAX      TruthValue
    MAX-ACCESS  read-only
    STATUS      current
    DESCRIPTION
        "Indicates the address duplication is detected by Duplicate Address
         Detection (DAD).
         
         If the address is a link-local address formed from an interface
         identifier based on the hardware address, which is supposed to be
         uniquely assigned (e.g., EUI-64 for an Ethernet interface), IP
         operation on the interface should be disabled."
    ::= { cie1000IpStatusInterfacesIpv6Entry 5 }

cie1000IpStatusInterfacesIpv6Detached OBJECT-TYPE
    SYNTAX      TruthValue
    MAX-ACCESS  read-only
    STATUS      current
    DESCRIPTION
        "Indicates this address is ready to be detached from the link (IPv6
         network)."
    ::= { cie1000IpStatusInterfacesIpv6Entry 6 }

cie1000IpStatusInterfacesIpv6Nodad OBJECT-TYPE
    SYNTAX      TruthValue
    MAX-ACCESS  read-only
    STATUS      current
    DESCRIPTION
        "Indicates this address does not perform Duplicate Address Detection
         (DAD)."
    ::= { cie1000IpStatusInterfacesIpv6Entry 7 }

cie1000IpStatusInterfacesIpv6Autoconf OBJECT-TYPE
    SYNTAX      TruthValue
    MAX-ACCESS  read-only
    STATUS      current
    DESCRIPTION
        "Indicates this address is capable of being retrieved by stateless
         address autoconfiguration."
    ::= { cie1000IpStatusInterfacesIpv6Entry 8 }

cie1000IpStatusRoutes OBJECT IDENTIFIER
    ::= { cie1000IpStatus 3 }

cie1000IpStatusRoutesIpv4Table OBJECT-TYPE
    SYNTAX      SEQUENCE OF CIE1000IpStatusRoutesIpv4Entry
    MAX-ACCESS  not-accessible
    STATUS      current
    DESCRIPTION
        "This table provides IPv4 routing status."
    ::= { cie1000IpStatusRoutes 1 }

cie1000IpStatusRoutesIpv4Entry OBJECT-TYPE
    SYNTAX      CIE1000IpStatusRoutesIpv4Entry
    MAX-ACCESS  not-accessible
    STATUS      current
    DESCRIPTION
        "Each entry in this table represents an IP route in the system's routing
         table."
    INDEX       { cie1000IpStatusRoutesIpv4NetworkAddress,
                  cie1000IpStatusRoutesIpv4NetworkPrefixSize,
                  cie1000IpStatusRoutesIpv4NextHop }
    ::= { cie1000IpStatusRoutesIpv4Table 1 }

CIE1000IpStatusRoutesIpv4Entry ::= SEQUENCE {
    cie1000IpStatusRoutesIpv4NetworkAddress           IpAddress,
    cie1000IpStatusRoutesIpv4NetworkPrefixSize        Integer32,
    cie1000IpStatusRoutesIpv4NextHop                  IpAddress,
    cie1000IpStatusRoutesIpv4DerivedNextHopInterface  CIE1000InterfaceIndex,
    cie1000IpStatusRoutesIpv4FlagUp                   TruthValue,
    cie1000IpStatusRoutesIpv4FlagHost                 TruthValue,
    cie1000IpStatusRoutesIpv4FlagGateway              TruthValue,
    cie1000IpStatusRoutesIpv4OwnerConf                TruthValue,
    cie1000IpStatusRoutesIpv4OwnerDhcp                TruthValue,
    cie1000IpStatusRoutesIpv4OwnerDynamic             TruthValue
}

cie1000IpStatusRoutesIpv4NetworkAddress OBJECT-TYPE
    SYNTAX      IpAddress
    MAX-ACCESS  accessible-for-notify
    STATUS      current
    DESCRIPTION
        "Network address."
    ::= { cie1000IpStatusRoutesIpv4Entry 1 }

cie1000IpStatusRoutesIpv4NetworkPrefixSize OBJECT-TYPE
    SYNTAX      Integer32 (0..32)
    MAX-ACCESS  accessible-for-notify
    STATUS      current
    DESCRIPTION
        "Network prefix size."
    ::= { cie1000IpStatusRoutesIpv4Entry 2 }

cie1000IpStatusRoutesIpv4NextHop OBJECT-TYPE
    SYNTAX      IpAddress
    MAX-ACCESS  accessible-for-notify
    STATUS      current
    DESCRIPTION
        "Next-hop address."
    ::= { cie1000IpStatusRoutesIpv4Entry 3 }

cie1000IpStatusRoutesIpv4DerivedNextHopInterface OBJECT-TYPE
    SYNTAX      CIE1000InterfaceIndex
    MAX-ACCESS  read-only
    STATUS      current
    DESCRIPTION
        "Next-hop interface."
    ::= { cie1000IpStatusRoutesIpv4Entry 4 }

cie1000IpStatusRoutesIpv4FlagUp OBJECT-TYPE
    SYNTAX      TruthValue
    MAX-ACCESS  read-only
    STATUS      current
    DESCRIPTION
        "The route is up."
    ::= { cie1000IpStatusRoutesIpv4Entry 35 }

cie1000IpStatusRoutesIpv4FlagHost OBJECT-TYPE
    SYNTAX      TruthValue
    MAX-ACCESS  read-only
    STATUS      current
    DESCRIPTION
        "The route is forwarding to this host (loop-back)."
    ::= { cie1000IpStatusRoutesIpv4Entry 36 }

cie1000IpStatusRoutesIpv4FlagGateway OBJECT-TYPE
    SYNTAX      TruthValue
    MAX-ACCESS  read-only
    STATUS      current
    DESCRIPTION
        "The route is using a gateway as next-hop, of not set then an interface
         is used."
    ::= { cie1000IpStatusRoutesIpv4Entry 37 }

cie1000IpStatusRoutesIpv4OwnerConf OBJECT-TYPE
    SYNTAX      TruthValue
    MAX-ACCESS  read-only
    STATUS      current
    DESCRIPTION
        "The route is installed as part of the user configuration."
    ::= { cie1000IpStatusRoutesIpv4Entry 67 }

cie1000IpStatusRoutesIpv4OwnerDhcp OBJECT-TYPE
    SYNTAX      TruthValue
    MAX-ACCESS  read-only
    STATUS      current
    DESCRIPTION
        "The route is installed by a DHCP client."
    ::= { cie1000IpStatusRoutesIpv4Entry 68 }

cie1000IpStatusRoutesIpv4OwnerDynamic OBJECT-TYPE
    SYNTAX      TruthValue
    MAX-ACCESS  read-only
    STATUS      current
    DESCRIPTION
        "The route is installed by a routing protocol."
    ::= { cie1000IpStatusRoutesIpv4Entry 69 }

cie1000IpStatusRoutesIpv6Table OBJECT-TYPE
    SYNTAX      SEQUENCE OF CIE1000IpStatusRoutesIpv6Entry
    MAX-ACCESS  not-accessible
    STATUS      current
    DESCRIPTION
        "This table provides IPv6 routing status."
    ::= { cie1000IpStatusRoutes 2 }

cie1000IpStatusRoutesIpv6Entry OBJECT-TYPE
    SYNTAX      CIE1000IpStatusRoutesIpv6Entry
    MAX-ACCESS  not-accessible
    STATUS      current
    DESCRIPTION
        "Each entry in this table represents an IP route in the system's routing
         table."
    INDEX       { cie1000IpStatusRoutesIpv6NetworkAddress,
                  cie1000IpStatusRoutesIpv6NetworkPrefixSize,
                  cie1000IpStatusRoutesIpv6NextHop,
                  cie1000IpStatusRoutesIpv6NextHopInterface }
    ::= { cie1000IpStatusRoutesIpv6Table 1 }

CIE1000IpStatusRoutesIpv6Entry ::= SEQUENCE {
    cie1000IpStatusRoutesIpv6NetworkAddress           InetAddressIPv6,
    cie1000IpStatusRoutesIpv6NetworkPrefixSize        Integer32,
    cie1000IpStatusRoutesIpv6NextHop                  InetAddressIPv6,
    cie1000IpStatusRoutesIpv6NextHopInterface         CIE1000InterfaceIndex,
    cie1000IpStatusRoutesIpv6DerivedNextHopInterface  CIE1000InterfaceIndex,
    cie1000IpStatusRoutesIpv6FlagUp                   TruthValue,
    cie1000IpStatusRoutesIpv6FlagHost                 TruthValue,
    cie1000IpStatusRoutesIpv6FlagGateway              TruthValue,
    cie1000IpStatusRoutesIpv6OwnerConf                TruthValue,
    cie1000IpStatusRoutesIpv6OwnerDhcp                TruthValue,
    cie1000IpStatusRoutesIpv6OwnerDynamic             TruthValue
}

cie1000IpStatusRoutesIpv6NetworkAddress OBJECT-TYPE
    SYNTAX      InetAddressIPv6
    MAX-ACCESS  accessible-for-notify
    STATUS      current
    DESCRIPTION
        "Network address."
    ::= { cie1000IpStatusRoutesIpv6Entry 1 }

cie1000IpStatusRoutesIpv6NetworkPrefixSize OBJECT-TYPE
    SYNTAX      Integer32 (0..128)
    MAX-ACCESS  accessible-for-notify
    STATUS      current
    DESCRIPTION
        "Network prefix size."
    ::= { cie1000IpStatusRoutesIpv6Entry 2 }

cie1000IpStatusRoutesIpv6NextHop OBJECT-TYPE
    SYNTAX      InetAddressIPv6
    MAX-ACCESS  accessible-for-notify
    STATUS      current
    DESCRIPTION
        "Next-hop address."
    ::= { cie1000IpStatusRoutesIpv6Entry 3 }

cie1000IpStatusRoutesIpv6NextHopInterface OBJECT-TYPE
    SYNTAX      CIE1000InterfaceIndex
    MAX-ACCESS  accessible-for-notify
    STATUS      current
    DESCRIPTION
        "If the next-hop address is a link-local address, then the interface of
         the link-local address must be specified here. Otherwise this value is
         not used."
    ::= { cie1000IpStatusRoutesIpv6Entry 4 }

cie1000IpStatusRoutesIpv6DerivedNextHopInterface OBJECT-TYPE
    SYNTAX      CIE1000InterfaceIndex
    MAX-ACCESS  read-only
    STATUS      current
    DESCRIPTION
        "Next-hop interface."
    ::= { cie1000IpStatusRoutesIpv6Entry 5 }

cie1000IpStatusRoutesIpv6FlagUp OBJECT-TYPE
    SYNTAX      TruthValue
    MAX-ACCESS  read-only
    STATUS      current
    DESCRIPTION
        "The route is up."
    ::= { cie1000IpStatusRoutesIpv6Entry 36 }

cie1000IpStatusRoutesIpv6FlagHost OBJECT-TYPE
    SYNTAX      TruthValue
    MAX-ACCESS  read-only
    STATUS      current
    DESCRIPTION
        "The route is forwarding to this host (loop-back)."
    ::= { cie1000IpStatusRoutesIpv6Entry 37 }

cie1000IpStatusRoutesIpv6FlagGateway OBJECT-TYPE
    SYNTAX      TruthValue
    MAX-ACCESS  read-only
    STATUS      current
    DESCRIPTION
        "The route is using a gateway as next-hop, of not set then an interface
         is used."
    ::= { cie1000IpStatusRoutesIpv6Entry 38 }

cie1000IpStatusRoutesIpv6OwnerConf OBJECT-TYPE
    SYNTAX      TruthValue
    MAX-ACCESS  read-only
    STATUS      current
    DESCRIPTION
        "The route is installed as part of the user configuration."
    ::= { cie1000IpStatusRoutesIpv6Entry 68 }

cie1000IpStatusRoutesIpv6OwnerDhcp OBJECT-TYPE
    SYNTAX      TruthValue
    MAX-ACCESS  read-only
    STATUS      current
    DESCRIPTION
        "The route is installed by a DHCP client."
    ::= { cie1000IpStatusRoutesIpv6Entry 69 }

cie1000IpStatusRoutesIpv6OwnerDynamic OBJECT-TYPE
    SYNTAX      TruthValue
    MAX-ACCESS  read-only
    STATUS      current
    DESCRIPTION
        "The route is installed by a routing protocol."
    ::= { cie1000IpStatusRoutesIpv6Entry 70 }

cie1000IpControl OBJECT IDENTIFIER
    ::= { cie1000IpMibObjects 4 }

cie1000IpControlGlobals OBJECT IDENTIFIER
    ::= { cie1000IpControl 1 }

cie1000IpControlGlobalsIpv4NeighbourTableClear OBJECT-TYPE
    SYNTAX      TruthValue
    MAX-ACCESS  read-write
    STATUS      current
    DESCRIPTION
        "Flush the entries in IPv4 ARP cache except for the permanent ones."
    ::= { cie1000IpControlGlobals 1 }

cie1000IpControlGlobalsIpv6NeighbourTableClear OBJECT-TYPE
    SYNTAX      TruthValue
    MAX-ACCESS  read-write
    STATUS      current
    DESCRIPTION
        "Erase all the NDP (Neighbor Discovery Protocol) entries registered in
         IPv6 neighbour cache."
    ::= { cie1000IpControlGlobals 2 }

cie1000IpControlGlobalsIpv4SystemStatisticsClear OBJECT-TYPE
    SYNTAX      CIE1000Unsigned8
    MAX-ACCESS  read-write
    STATUS      current
    DESCRIPTION
        "Clear the system-wide IPv4 traffic statistics."
    ::= { cie1000IpControlGlobals 3 }

cie1000IpControlGlobalsIpv6SystemStatisticsClear OBJECT-TYPE
    SYNTAX      CIE1000Unsigned8
    MAX-ACCESS  read-write
    STATUS      current
    DESCRIPTION
        "Clear the system-wide IPv6 traffic statistics."
    ::= { cie1000IpControlGlobals 4 }

cie1000IpControlInterface OBJECT IDENTIFIER
    ::= { cie1000IpControl 2 }

cie1000IpControlInterfaceDhcpClientTable OBJECT-TYPE
    SYNTAX      SEQUENCE OF CIE1000IpControlInterfaceDhcpClientEntry
    MAX-ACCESS  not-accessible
    STATUS      current
    DESCRIPTION
        "This table provides control facilities to control an instance of the
         DHCP client."
    ::= { cie1000IpControlInterface 1 }

cie1000IpControlInterfaceDhcpClientEntry OBJECT-TYPE
    SYNTAX      CIE1000IpControlInterfaceDhcpClientEntry
    MAX-ACCESS  not-accessible
    STATUS      current
    DESCRIPTION
        "Each entry in this table represents an instance of the DHCP client."
    INDEX       { cie1000IpControlInterfaceDhcpClientIfIndex }
    ::= { cie1000IpControlInterfaceDhcpClientTable 1 }

CIE1000IpControlInterfaceDhcpClientEntry ::= SEQUENCE {
    cie1000IpControlInterfaceDhcpClientIfIndex  CIE1000InterfaceIndex,
    cie1000IpControlInterfaceDhcpClientRestart  TruthValue
}

cie1000IpControlInterfaceDhcpClientIfIndex OBJECT-TYPE
    SYNTAX      CIE1000InterfaceIndex
    MAX-ACCESS  accessible-for-notify
    STATUS      current
    DESCRIPTION
        "Interface index number."
    ::= { cie1000IpControlInterfaceDhcpClientEntry 1 }

cie1000IpControlInterfaceDhcpClientRestart OBJECT-TYPE
    SYNTAX      TruthValue
    MAX-ACCESS  read-write
    STATUS      current
    DESCRIPTION
        "Restart the DHCP client."
    ::= { cie1000IpControlInterfaceDhcpClientEntry 2 }

cie1000IpStatistics OBJECT IDENTIFIER
    ::= { cie1000IpMibObjects 5 }

cie1000IpStatisticsGlobals OBJECT IDENTIFIER
    ::= { cie1000IpStatistics 1 }

cie1000IpStatisticsGlobalsIpv4 OBJECT IDENTIFIER
    ::= { cie1000IpStatisticsGlobals 1 }

cie1000IpStatisticsGlobalsIpv4InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime."
    ::= { cie1000IpStatisticsGlobalsIpv4 1 }

cie1000IpStatisticsGlobalsIpv4HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime."
    ::= { cie1000IpStatisticsGlobalsIpv4 2 }

cie1000IpStatisticsGlobalsIpv4InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime."
    ::= { cie1000IpStatisticsGlobalsIpv4 3 }

cie1000IpStatisticsGlobalsIpv4HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime."
    ::= { cie1000IpStatisticsGlobalsIpv4 4 }

cie1000IpStatisticsGlobalsIpv4InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime."
    ::= { cie1000IpStatisticsGlobalsIpv4 5 }

cie1000IpStatisticsGlobalsIpv4InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime."
    ::= { cie1000IpStatisticsGlobalsIpv4 6 }

cie1000IpStatisticsGlobalsIpv4InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime."
    ::= { cie1000IpStatisticsGlobalsIpv4 7 }

cie1000IpStatisticsGlobalsIpv4InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { cie1000IpStatisticsGlobalsIpv4 8 }

cie1000IpStatisticsGlobalsIpv4InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime."
    ::= { cie1000IpStatisticsGlobalsIpv4 9 }

cie1000IpStatisticsGlobalsIpv4InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime."
    ::= { cie1000IpStatisticsGlobalsIpv4 10 }

cie1000IpStatisticsGlobalsIpv4HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime."
    ::= { cie1000IpStatisticsGlobalsIpv4 11 }

cie1000IpStatisticsGlobalsIpv4ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime."
    ::= { cie1000IpStatisticsGlobalsIpv4 12 }

cie1000IpStatisticsGlobalsIpv4ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { cie1000IpStatisticsGlobalsIpv4 13 }

cie1000IpStatisticsGlobalsIpv4ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime."
    ::= { cie1000IpStatisticsGlobalsIpv4 14 }

cie1000IpStatisticsGlobalsIpv4InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime."
    ::= { cie1000IpStatisticsGlobalsIpv4 15 }

cie1000IpStatisticsGlobalsIpv4InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { cie1000IpStatisticsGlobalsIpv4 16 }

cie1000IpStatisticsGlobalsIpv4HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime."
    ::= { cie1000IpStatisticsGlobalsIpv4 17 }

cie1000IpStatisticsGlobalsIpv4OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime."
    ::= { cie1000IpStatisticsGlobalsIpv4 18 }

cie1000IpStatisticsGlobalsIpv4HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime."
    ::= { cie1000IpStatisticsGlobalsIpv4 19 }

cie1000IpStatisticsGlobalsIpv4OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime."
    ::= { cie1000IpStatisticsGlobalsIpv4 20 }

cie1000IpStatisticsGlobalsIpv4OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime."
    ::= { cie1000IpStatisticsGlobalsIpv4 21 }

cie1000IpStatisticsGlobalsIpv4HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime."
    ::= { cie1000IpStatisticsGlobalsIpv4 22 }

cie1000IpStatisticsGlobalsIpv4OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime."
    ::= { cie1000IpStatisticsGlobalsIpv4 23 }

cie1000IpStatisticsGlobalsIpv4OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime."
    ::= { cie1000IpStatisticsGlobalsIpv4 24 }

cie1000IpStatisticsGlobalsIpv4OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime."
    ::= { cie1000IpStatisticsGlobalsIpv4 25 }

cie1000IpStatisticsGlobalsIpv4OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime."
    ::= { cie1000IpStatisticsGlobalsIpv4 26 }

cie1000IpStatisticsGlobalsIpv4OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime."
    ::= { cie1000IpStatisticsGlobalsIpv4 27 }

cie1000IpStatisticsGlobalsIpv4OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime."
    ::= { cie1000IpStatisticsGlobalsIpv4 28 }

cie1000IpStatisticsGlobalsIpv4HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime."
    ::= { cie1000IpStatisticsGlobalsIpv4 29 }

cie1000IpStatisticsGlobalsIpv4OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime."
    ::= { cie1000IpStatisticsGlobalsIpv4 30 }

cie1000IpStatisticsGlobalsIpv4HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime."
    ::= { cie1000IpStatisticsGlobalsIpv4 31 }

cie1000IpStatisticsGlobalsIpv4InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime."
    ::= { cie1000IpStatisticsGlobalsIpv4 32 }

cie1000IpStatisticsGlobalsIpv4HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime."
    ::= { cie1000IpStatisticsGlobalsIpv4 33 }

cie1000IpStatisticsGlobalsIpv4InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime."
    ::= { cie1000IpStatisticsGlobalsIpv4 34 }

cie1000IpStatisticsGlobalsIpv4HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime."
    ::= { cie1000IpStatisticsGlobalsIpv4 35 }

cie1000IpStatisticsGlobalsIpv4OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime."
    ::= { cie1000IpStatisticsGlobalsIpv4 36 }

cie1000IpStatisticsGlobalsIpv4HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime."
    ::= { cie1000IpStatisticsGlobalsIpv4 37 }

cie1000IpStatisticsGlobalsIpv4OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime."
    ::= { cie1000IpStatisticsGlobalsIpv4 38 }

cie1000IpStatisticsGlobalsIpv4HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime."
    ::= { cie1000IpStatisticsGlobalsIpv4 39 }

cie1000IpStatisticsGlobalsIpv4InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime."
    ::= { cie1000IpStatisticsGlobalsIpv4 40 }

cie1000IpStatisticsGlobalsIpv4HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime."
    ::= { cie1000IpStatisticsGlobalsIpv4 41 }

cie1000IpStatisticsGlobalsIpv4OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime."
    ::= { cie1000IpStatisticsGlobalsIpv4 42 }

cie1000IpStatisticsGlobalsIpv4HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime."
    ::= { cie1000IpStatisticsGlobalsIpv4 43 }

cie1000IpStatisticsGlobalsIpv4DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value."
    ::= { cie1000IpStatisticsGlobalsIpv4 44 }

cie1000IpStatisticsGlobalsIpv4RefreshRate OBJECT-TYPE
    SYNTAX      Unsigned32
    MAX-ACCESS  read-only
    STATUS      current
    DESCRIPTION
        "The minimum reasonable polling interval for this entry. This object
         provides an indication of the minimum amount of time required to update
         the counters in this entry."
    ::= { cie1000IpStatisticsGlobalsIpv4 45 }

cie1000IpStatisticsGlobalsIpv6 OBJECT IDENTIFIER
    ::= { cie1000IpStatisticsGlobals 2 }

cie1000IpStatisticsGlobalsIpv6InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime."
    ::= { cie1000IpStatisticsGlobalsIpv6 1 }

cie1000IpStatisticsGlobalsIpv6HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime."
    ::= { cie1000IpStatisticsGlobalsIpv6 2 }

cie1000IpStatisticsGlobalsIpv6InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime."
    ::= { cie1000IpStatisticsGlobalsIpv6 3 }

cie1000IpStatisticsGlobalsIpv6HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime."
    ::= { cie1000IpStatisticsGlobalsIpv6 4 }

cie1000IpStatisticsGlobalsIpv6InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime."
    ::= { cie1000IpStatisticsGlobalsIpv6 5 }

cie1000IpStatisticsGlobalsIpv6InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime."
    ::= { cie1000IpStatisticsGlobalsIpv6 6 }

cie1000IpStatisticsGlobalsIpv6InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime."
    ::= { cie1000IpStatisticsGlobalsIpv6 7 }

cie1000IpStatisticsGlobalsIpv6InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { cie1000IpStatisticsGlobalsIpv6 8 }

cie1000IpStatisticsGlobalsIpv6InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime."
    ::= { cie1000IpStatisticsGlobalsIpv6 9 }

cie1000IpStatisticsGlobalsIpv6InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime."
    ::= { cie1000IpStatisticsGlobalsIpv6 10 }

cie1000IpStatisticsGlobalsIpv6HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime."
    ::= { cie1000IpStatisticsGlobalsIpv6 11 }

cie1000IpStatisticsGlobalsIpv6ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime."
    ::= { cie1000IpStatisticsGlobalsIpv6 12 }

cie1000IpStatisticsGlobalsIpv6ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { cie1000IpStatisticsGlobalsIpv6 13 }

cie1000IpStatisticsGlobalsIpv6ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime."
    ::= { cie1000IpStatisticsGlobalsIpv6 14 }

cie1000IpStatisticsGlobalsIpv6InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime."
    ::= { cie1000IpStatisticsGlobalsIpv6 15 }

cie1000IpStatisticsGlobalsIpv6InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { cie1000IpStatisticsGlobalsIpv6 16 }

cie1000IpStatisticsGlobalsIpv6HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime."
    ::= { cie1000IpStatisticsGlobalsIpv6 17 }

cie1000IpStatisticsGlobalsIpv6OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime."
    ::= { cie1000IpStatisticsGlobalsIpv6 18 }

cie1000IpStatisticsGlobalsIpv6HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime."
    ::= { cie1000IpStatisticsGlobalsIpv6 19 }

cie1000IpStatisticsGlobalsIpv6OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime."
    ::= { cie1000IpStatisticsGlobalsIpv6 20 }

cie1000IpStatisticsGlobalsIpv6OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime."
    ::= { cie1000IpStatisticsGlobalsIpv6 21 }

cie1000IpStatisticsGlobalsIpv6HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime."
    ::= { cie1000IpStatisticsGlobalsIpv6 22 }

cie1000IpStatisticsGlobalsIpv6OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime."
    ::= { cie1000IpStatisticsGlobalsIpv6 23 }

cie1000IpStatisticsGlobalsIpv6OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime."
    ::= { cie1000IpStatisticsGlobalsIpv6 24 }

cie1000IpStatisticsGlobalsIpv6OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime."
    ::= { cie1000IpStatisticsGlobalsIpv6 25 }

cie1000IpStatisticsGlobalsIpv6OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime."
    ::= { cie1000IpStatisticsGlobalsIpv6 26 }

cie1000IpStatisticsGlobalsIpv6OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime."
    ::= { cie1000IpStatisticsGlobalsIpv6 27 }

cie1000IpStatisticsGlobalsIpv6OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime."
    ::= { cie1000IpStatisticsGlobalsIpv6 28 }

cie1000IpStatisticsGlobalsIpv6HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime."
    ::= { cie1000IpStatisticsGlobalsIpv6 29 }

cie1000IpStatisticsGlobalsIpv6OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime."
    ::= { cie1000IpStatisticsGlobalsIpv6 30 }

cie1000IpStatisticsGlobalsIpv6HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime."
    ::= { cie1000IpStatisticsGlobalsIpv6 31 }

cie1000IpStatisticsGlobalsIpv6InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime."
    ::= { cie1000IpStatisticsGlobalsIpv6 32 }

cie1000IpStatisticsGlobalsIpv6HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime."
    ::= { cie1000IpStatisticsGlobalsIpv6 33 }

cie1000IpStatisticsGlobalsIpv6InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime."
    ::= { cie1000IpStatisticsGlobalsIpv6 34 }

cie1000IpStatisticsGlobalsIpv6HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime."
    ::= { cie1000IpStatisticsGlobalsIpv6 35 }

cie1000IpStatisticsGlobalsIpv6OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime."
    ::= { cie1000IpStatisticsGlobalsIpv6 36 }

cie1000IpStatisticsGlobalsIpv6HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime."
    ::= { cie1000IpStatisticsGlobalsIpv6 37 }

cie1000IpStatisticsGlobalsIpv6OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime."
    ::= { cie1000IpStatisticsGlobalsIpv6 38 }

cie1000IpStatisticsGlobalsIpv6HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime."
    ::= { cie1000IpStatisticsGlobalsIpv6 39 }

cie1000IpStatisticsGlobalsIpv6InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime."
    ::= { cie1000IpStatisticsGlobalsIpv6 40 }

cie1000IpStatisticsGlobalsIpv6HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime."
    ::= { cie1000IpStatisticsGlobalsIpv6 41 }

cie1000IpStatisticsGlobalsIpv6OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime."
    ::= { cie1000IpStatisticsGlobalsIpv6 42 }

cie1000IpStatisticsGlobalsIpv6HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime."
    ::= { cie1000IpStatisticsGlobalsIpv6 43 }

cie1000IpStatisticsGlobalsIpv6DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value."
    ::= { cie1000IpStatisticsGlobalsIpv6 44 }

cie1000IpStatisticsGlobalsIpv6RefreshRate OBJECT-TYPE
    SYNTAX      Unsigned32
    MAX-ACCESS  read-only
    STATUS      current
    DESCRIPTION
        "The minimum reasonable polling interval for this entry. This object
         provides an indication of the minimum amount of time required to update
         the counters in this entry."
    ::= { cie1000IpStatisticsGlobalsIpv6 45 }

cie1000IpStatisticsInterfaces OBJECT IDENTIFIER
    ::= { cie1000IpStatistics 2 }

cie1000IpStatisticsInterfacesLinkTable OBJECT-TYPE
    SYNTAX      SEQUENCE OF CIE1000IpStatisticsInterfacesLinkEntry
    MAX-ACCESS  not-accessible
    STATUS      current
    DESCRIPTION
        "This table provides interface link statistics for a given IP interface."
    ::= { cie1000IpStatisticsInterfaces 1 }

cie1000IpStatisticsInterfacesLinkEntry OBJECT-TYPE
    SYNTAX      CIE1000IpStatisticsInterfacesLinkEntry
    MAX-ACCESS  not-accessible
    STATUS      current
    DESCRIPTION
        "Each entry in this table represents an IP interface."
    INDEX       { cie1000IpStatisticsInterfacesLinkIfIndex }
    ::= { cie1000IpStatisticsInterfacesLinkTable 1 }

CIE1000IpStatisticsInterfacesLinkEntry ::= SEQUENCE {
    cie1000IpStatisticsInterfacesLinkIfIndex        CIE1000InterfaceIndex,
    cie1000IpStatisticsInterfacesLinkInPackets      Counter64,
    cie1000IpStatisticsInterfacesLinkOutPackets     Counter64,
    cie1000IpStatisticsInterfacesLinkInBytes        Counter64,
    cie1000IpStatisticsInterfacesLinkOutBytes       Counter64,
    cie1000IpStatisticsInterfacesLinkInMulticasts   Counter64,
    cie1000IpStatisticsInterfacesLinkOutMulticasts  Counter64,
    cie1000IpStatisticsInterfacesLinkInBroadcasts   Counter64,
    cie1000IpStatisticsInterfacesLinkOutBroadcasts  Counter64
}

cie1000IpStatisticsInterfacesLinkIfIndex OBJECT-TYPE
    SYNTAX      CIE1000InterfaceIndex
    MAX-ACCESS  accessible-for-notify
    STATUS      current
    DESCRIPTION
        "Interface index number."
    ::= { cie1000IpStatisticsInterfacesLinkEntry 1 }

cie1000IpStatisticsInterfacesLinkInPackets OBJECT-TYPE
    SYNTAX      Counter64
    MAX-ACCESS  read-only
    STATUS      current
    DESCRIPTION
        "Number of packets delivered by MAC layer to IP layer."
    ::= { cie1000IpStatisticsInterfacesLinkEntry 2 }

cie1000IpStatisticsInterfacesLinkOutPackets OBJECT-TYPE
    SYNTAX      Counter64
    MAX-ACCESS  read-only
    STATUS      current
    DESCRIPTION
        "Number of packets IP protocols requested be transmitted, including
         those that were discarded or not sent."
    ::= { cie1000IpStatisticsInterfacesLinkEntry 3 }

cie1000IpStatisticsInterfacesLinkInBytes OBJECT-TYPE
    SYNTAX      Counter64
    MAX-ACCESS  read-only
    STATUS      current
    DESCRIPTION
        "Number of octets received on the interface, including framing
         characters."
    ::= { cie1000IpStatisticsInterfacesLinkEntry 4 }

cie1000IpStatisticsInterfacesLinkOutBytes OBJECT-TYPE
    SYNTAX      Counter64
    MAX-ACCESS  read-only
    STATUS      current
    DESCRIPTION
        "Number of octets transmitted out of the interface, including framing
         characters."
    ::= { cie1000IpStatisticsInterfacesLinkEntry 5 }

cie1000IpStatisticsInterfacesLinkInMulticasts OBJECT-TYPE
    SYNTAX      Counter64
    MAX-ACCESS  read-only
    STATUS      current
    DESCRIPTION
        "Number of packets delivered by MAC layer to IP layer that were
         addressed to a MAC multicast address.
         
         For a MAC layer protocol, this includes both Group and Functional
         addresses."
    ::= { cie1000IpStatisticsInterfacesLinkEntry 6 }

cie1000IpStatisticsInterfacesLinkOutMulticasts OBJECT-TYPE
    SYNTAX      Counter64
    MAX-ACCESS  read-only
    STATUS      current
    DESCRIPTION
        "Number of packets addressed to a multicast MAC address that IP
         protocols requested be transmitted, including those that were discarded
         or not sent.
         
         For a MAC layer protocol, this includes both Group and Functional
         addresses."
    ::= { cie1000IpStatisticsInterfacesLinkEntry 7 }

cie1000IpStatisticsInterfacesLinkInBroadcasts OBJECT-TYPE
    SYNTAX      Counter64
    MAX-ACCESS  read-only
    STATUS      current
    DESCRIPTION
        "Number of packets delivered by MAC layer to IP layer that were
         addressed to a MAC broadcast address."
    ::= { cie1000IpStatisticsInterfacesLinkEntry 8 }

cie1000IpStatisticsInterfacesLinkOutBroadcasts OBJECT-TYPE
    SYNTAX      Counter64
    MAX-ACCESS  read-only
    STATUS      current
    DESCRIPTION
        "Number of packets addressed to a broadcast MAC address that IP
         protocols requested be transmitted, including those that were discarded
         or not sent."
    ::= { cie1000IpStatisticsInterfacesLinkEntry 9 }

cie1000IpStatisticsInterfacesIpv4Table OBJECT-TYPE
    SYNTAX      SEQUENCE OF CIE1000IpStatisticsInterfacesIpv4Entry
    MAX-ACCESS  not-accessible
    STATUS      current
    DESCRIPTION
        "This table provides IPv4 related statitics for a given IP interface."
    ::= { cie1000IpStatisticsInterfaces 2 }

cie1000IpStatisticsInterfacesIpv4Entry OBJECT-TYPE
    SYNTAX      CIE1000IpStatisticsInterfacesIpv4Entry
    MAX-ACCESS  not-accessible
    STATUS      current
    DESCRIPTION
        "Each entry in this table represents an IP interface."
    INDEX       { cie1000IpStatisticsInterfacesIpv4IfIndex }
    ::= { cie1000IpStatisticsInterfacesIpv4Table 1 }

CIE1000IpStatisticsInterfacesIpv4Entry ::= SEQUENCE {
    cie1000IpStatisticsInterfacesIpv4IfIndex             CIE1000InterfaceIndex,
    cie1000IpStatisticsInterfacesIpv4InReceives          Unsigned32,
    cie1000IpStatisticsInterfacesIpv4HCInReceives        Counter64,
    cie1000IpStatisticsInterfacesIpv4InOctets            Unsigned32,
    cie1000IpStatisticsInterfacesIpv4HCInOctets          Counter64,
    cie1000IpStatisticsInterfacesIpv4InHdrErrors         Unsigned32,
    cie1000IpStatisticsInterfacesIpv4InNoRoutes          Unsigned32,
    cie1000IpStatisticsInterfacesIpv4InAddrErrors        Unsigned32,
    cie1000IpStatisticsInterfacesIpv4InUnknownProtos     Unsigned32,
    cie1000IpStatisticsInterfacesIpv4InTruncatedPkts     Unsigned32,
    cie1000IpStatisticsInterfacesIpv4InForwDatagrams     Unsigned32,
    cie1000IpStatisticsInterfacesIpv4HCInForwDatagrams   Counter64,
    cie1000IpStatisticsInterfacesIpv4ReasmReqds          Unsigned32,
    cie1000IpStatisticsInterfacesIpv4ReasmOKs            Unsigned32,
    cie1000IpStatisticsInterfacesIpv4ReasmFails          Unsigned32,
    cie1000IpStatisticsInterfacesIpv4InDiscards          Unsigned32,
    cie1000IpStatisticsInterfacesIpv4InDelivers          Unsigned32,
    cie1000IpStatisticsInterfacesIpv4HCInDelivers        Counter64,
    cie1000IpStatisticsInterfacesIpv4OutRequests         Unsigned32,
    cie1000IpStatisticsInterfacesIpv4HCOutRequests       Counter64,
    cie1000IpStatisticsInterfacesIpv4OutNoRoutes         Unsigned32,
    cie1000IpStatisticsInterfacesIpv4OutForwDatagrams    Unsigned32,
    cie1000IpStatisticsInterfacesIpv4HCOutForwDatagrams  Counter64,
    cie1000IpStatisticsInterfacesIpv4OutDiscards         Unsigned32,
    cie1000IpStatisticsInterfacesIpv4OutFragReqds        Unsigned32,
    cie1000IpStatisticsInterfacesIpv4OutFragOKs          Unsigned32,
    cie1000IpStatisticsInterfacesIpv4OutFragFails        Unsigned32,
    cie1000IpStatisticsInterfacesIpv4OutFragCreates      Unsigned32,
    cie1000IpStatisticsInterfacesIpv4OutTransmits        Unsigned32,
    cie1000IpStatisticsInterfacesIpv4HCOutTransmits      Counter64,
    cie1000IpStatisticsInterfacesIpv4OutOctets           Unsigned32,
    cie1000IpStatisticsInterfacesIpv4HCOutOctets         Counter64,
    cie1000IpStatisticsInterfacesIpv4InMcastPkts         Unsigned32,
    cie1000IpStatisticsInterfacesIpv4HCInMcastPkts       Counter64,
    cie1000IpStatisticsInterfacesIpv4InMcastOctets       Unsigned32,
    cie1000IpStatisticsInterfacesIpv4HCInMcastOctets     Counter64,
    cie1000IpStatisticsInterfacesIpv4OutMcastPkts        Unsigned32,
    cie1000IpStatisticsInterfacesIpv4HCOutMcastPkts      Counter64,
    cie1000IpStatisticsInterfacesIpv4OutMcastOctets      Unsigned32,
    cie1000IpStatisticsInterfacesIpv4HCOutMcastOctets    Counter64,
    cie1000IpStatisticsInterfacesIpv4InBcastPkts         Unsigned32,
    cie1000IpStatisticsInterfacesIpv4HCInBcastPkts       Counter64,
    cie1000IpStatisticsInterfacesIpv4OutBcastPkts        Unsigned32,
    cie1000IpStatisticsInterfacesIpv4HCOutBcastPkts      Counter64,
    cie1000IpStatisticsInterfacesIpv4DiscontinuityTime   Counter64,
    cie1000IpStatisticsInterfacesIpv4RefreshRate         Unsigned32
}

cie1000IpStatisticsInterfacesIpv4IfIndex OBJECT-TYPE
    SYNTAX      CIE1000InterfaceIndex
    MAX-ACCESS  accessible-for-notify
    STATUS      current
    DESCRIPTION
        "Interface index number.
         
         This object is only available if the capability object
         'cie1000IpCapabilitiesHasPerInterfaceIpv4Statistics' is True."
    ::= { cie1000IpStatisticsInterfacesIpv4Entry 1 }

cie1000IpStatisticsInterfacesIpv4InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 2 }

cie1000IpStatisticsInterfacesIpv4HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 3 }

cie1000IpStatisticsInterfacesIpv4InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 4 }

cie1000IpStatisticsInterfacesIpv4HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 5 }

cie1000IpStatisticsInterfacesIpv4InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 6 }

cie1000IpStatisticsInterfacesIpv4InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 7 }

cie1000IpStatisticsInterfacesIpv4InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 8 }

cie1000IpStatisticsInterfacesIpv4InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 9 }

cie1000IpStatisticsInterfacesIpv4InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 10 }

cie1000IpStatisticsInterfacesIpv4InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 11 }

cie1000IpStatisticsInterfacesIpv4HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 12 }

cie1000IpStatisticsInterfacesIpv4ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 13 }

cie1000IpStatisticsInterfacesIpv4ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 14 }

cie1000IpStatisticsInterfacesIpv4ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 15 }

cie1000IpStatisticsInterfacesIpv4InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 16 }

cie1000IpStatisticsInterfacesIpv4InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 17 }

cie1000IpStatisticsInterfacesIpv4HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 18 }

cie1000IpStatisticsInterfacesIpv4OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 19 }

cie1000IpStatisticsInterfacesIpv4HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 20 }

cie1000IpStatisticsInterfacesIpv4OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 21 }

cie1000IpStatisticsInterfacesIpv4OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 22 }

cie1000IpStatisticsInterfacesIpv4HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 23 }

cie1000IpStatisticsInterfacesIpv4OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 24 }

cie1000IpStatisticsInterfacesIpv4OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 25 }

cie1000IpStatisticsInterfacesIpv4OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 26 }

cie1000IpStatisticsInterfacesIpv4OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 27 }

cie1000IpStatisticsInterfacesIpv4OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 28 }

cie1000IpStatisticsInterfacesIpv4OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 29 }

cie1000IpStatisticsInterfacesIpv4HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 30 }

cie1000IpStatisticsInterfacesIpv4OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 31 }

cie1000IpStatisticsInterfacesIpv4HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 32 }

cie1000IpStatisticsInterfacesIpv4InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 33 }

cie1000IpStatisticsInterfacesIpv4HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 34 }

cie1000IpStatisticsInterfacesIpv4InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 35 }

cie1000IpStatisticsInterfacesIpv4HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 36 }

cie1000IpStatisticsInterfacesIpv4OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 37 }

cie1000IpStatisticsInterfacesIpv4HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 38 }

cie1000IpStatisticsInterfacesIpv4OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 39 }

cie1000IpStatisticsInterfacesIpv4HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 40 }

cie1000IpStatisticsInterfacesIpv4InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 41 }

cie1000IpStatisticsInterfacesIpv4HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 42 }

cie1000IpStatisticsInterfacesIpv4OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 43 }

cie1000IpStatisticsInterfacesIpv4HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime.
         
         This object is only available if the capability object
         'cie1000IpCapabilitiesHasPerInterfaceIpv4Statistics' is True."
    ::= { cie1000IpStatisticsInterfacesIpv4Entry 44 }

cie1000IpStatisticsInterfacesIpv4DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value.
         
         This object is only available if the capability object
         'cie1000IpCapabilitiesHasPerInterfaceIpv4Statistics' is True."
    ::= { cie1000IpStatisticsInterfacesIpv4Entry 45 }

cie1000IpStatisticsInterfacesIpv4RefreshRate OBJECT-TYPE
    SYNTAX      Unsigned32
    MAX-ACCESS  read-only
    STATUS      current
    DESCRIPTION
        "The minimum reasonable polling interval for this entry. This object
         provides an indication of the minimum amount of time required to update
         the counters in this entry.
         
         This object is only available if the capability object
         'cie1000IpCapabilitiesHasPerInterfaceIpv4Statistics' is True."
    ::= { cie1000IpStatisticsInterfacesIpv4Entry 46 }

cie1000IpStatisticsInterfacesIpv6Table OBJECT-TYPE
    SYNTAX      SEQUENCE OF CIE1000IpStatisticsInterfacesIpv6Entry
    MAX-ACCESS  not-accessible
    STATUS      current
    DESCRIPTION
        "This table provides IPv6 related statitics for a given IP interface."
    ::= { cie1000IpStatisticsInterfaces 3 }

cie1000IpStatisticsInterfacesIpv6Entry OBJECT-TYPE
    SYNTAX      CIE1000IpStatisticsInterfacesIpv6Entry
    MAX-ACCESS  not-accessible
    STATUS      current
    DESCRIPTION
        "Each entry in this table represents an IP interface."
    INDEX       { cie1000IpStatisticsInterfacesIpv6IfIndex }
    ::= { cie1000IpStatisticsInterfacesIpv6Table 1 }

CIE1000IpStatisticsInterfacesIpv6Entry ::= SEQUENCE {
    cie1000IpStatisticsInterfacesIpv6IfIndex             CIE1000InterfaceIndex,
    cie1000IpStatisticsInterfacesIpv6InReceives          Unsigned32,
    cie1000IpStatisticsInterfacesIpv6HCInReceives        Counter64,
    cie1000IpStatisticsInterfacesIpv6InOctets            Unsigned32,
    cie1000IpStatisticsInterfacesIpv6HCInOctets          Counter64,
    cie1000IpStatisticsInterfacesIpv6InHdrErrors         Unsigned32,
    cie1000IpStatisticsInterfacesIpv6InNoRoutes          Unsigned32,
    cie1000IpStatisticsInterfacesIpv6InAddrErrors        Unsigned32,
    cie1000IpStatisticsInterfacesIpv6InUnknownProtos     Unsigned32,
    cie1000IpStatisticsInterfacesIpv6InTruncatedPkts     Unsigned32,
    cie1000IpStatisticsInterfacesIpv6InForwDatagrams     Unsigned32,
    cie1000IpStatisticsInterfacesIpv6HCInForwDatagrams   Counter64,
    cie1000IpStatisticsInterfacesIpv6ReasmReqds          Unsigned32,
    cie1000IpStatisticsInterfacesIpv6ReasmOKs            Unsigned32,
    cie1000IpStatisticsInterfacesIpv6ReasmFails          Unsigned32,
    cie1000IpStatisticsInterfacesIpv6InDiscards          Unsigned32,
    cie1000IpStatisticsInterfacesIpv6InDelivers          Unsigned32,
    cie1000IpStatisticsInterfacesIpv6HCInDelivers        Counter64,
    cie1000IpStatisticsInterfacesIpv6OutRequests         Unsigned32,
    cie1000IpStatisticsInterfacesIpv6HCOutRequests       Counter64,
    cie1000IpStatisticsInterfacesIpv6OutNoRoutes         Unsigned32,
    cie1000IpStatisticsInterfacesIpv6OutForwDatagrams    Unsigned32,
    cie1000IpStatisticsInterfacesIpv6HCOutForwDatagrams  Counter64,
    cie1000IpStatisticsInterfacesIpv6OutDiscards         Unsigned32,
    cie1000IpStatisticsInterfacesIpv6OutFragReqds        Unsigned32,
    cie1000IpStatisticsInterfacesIpv6OutFragOKs          Unsigned32,
    cie1000IpStatisticsInterfacesIpv6OutFragFails        Unsigned32,
    cie1000IpStatisticsInterfacesIpv6OutFragCreates      Unsigned32,
    cie1000IpStatisticsInterfacesIpv6OutTransmits        Unsigned32,
    cie1000IpStatisticsInterfacesIpv6HCOutTransmits      Counter64,
    cie1000IpStatisticsInterfacesIpv6OutOctets           Unsigned32,
    cie1000IpStatisticsInterfacesIpv6HCOutOctets         Counter64,
    cie1000IpStatisticsInterfacesIpv6InMcastPkts         Unsigned32,
    cie1000IpStatisticsInterfacesIpv6HCInMcastPkts       Counter64,
    cie1000IpStatisticsInterfacesIpv6InMcastOctets       Unsigned32,
    cie1000IpStatisticsInterfacesIpv6HCInMcastOctets     Counter64,
    cie1000IpStatisticsInterfacesIpv6OutMcastPkts        Unsigned32,
    cie1000IpStatisticsInterfacesIpv6HCOutMcastPkts      Counter64,
    cie1000IpStatisticsInterfacesIpv6OutMcastOctets      Unsigned32,
    cie1000IpStatisticsInterfacesIpv6HCOutMcastOctets    Counter64,
    cie1000IpStatisticsInterfacesIpv6InBcastPkts         Unsigned32,
    cie1000IpStatisticsInterfacesIpv6HCInBcastPkts       Counter64,
    cie1000IpStatisticsInterfacesIpv6OutBcastPkts        Unsigned32,
    cie1000IpStatisticsInterfacesIpv6HCOutBcastPkts      Counter64,
    cie1000IpStatisticsInterfacesIpv6DiscontinuityTime   Counter64,
    cie1000IpStatisticsInterfacesIpv6RefreshRate         Unsigned32
}

cie1000IpStatisticsInterfacesIpv6IfIndex OBJECT-TYPE
    SYNTAX      CIE1000InterfaceIndex
    MAX-ACCESS  accessible-for-notify
    STATUS      current
    DESCRIPTION
        "Interface index number.
         
         This object is only available if the capability object
         'cie1000IpCapabilitiesHasPerInterfaceIpv6Statistics' is True."
    ::= { cie1000IpStatisticsInterfacesIpv6Entry 1 }

cie1000IpStatisticsInterfacesIpv6InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 2 }

cie1000IpStatisticsInterfacesIpv6HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 3 }

cie1000IpStatisticsInterfacesIpv6InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 4 }

cie1000IpStatisticsInterfacesIpv6HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 5 }

cie1000IpStatisticsInterfacesIpv6InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 6 }

cie1000IpStatisticsInterfacesIpv6InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 7 }

cie1000IpStatisticsInterfacesIpv6InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 8 }

cie1000IpStatisticsInterfacesIpv6InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 9 }

cie1000IpStatisticsInterfacesIpv6InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 10 }

cie1000IpStatisticsInterfacesIpv6InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 11 }

cie1000IpStatisticsInterfacesIpv6HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 12 }

cie1000IpStatisticsInterfacesIpv6ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 13 }

cie1000IpStatisticsInterfacesIpv6ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 14 }

cie1000IpStatisticsInterfacesIpv6ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 15 }

cie1000IpStatisticsInterfacesIpv6InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 16 }

cie1000IpStatisticsInterfacesIpv6InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 17 }

cie1000IpStatisticsInterfacesIpv6HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 18 }

cie1000IpStatisticsInterfacesIpv6OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 19 }

cie1000IpStatisticsInterfacesIpv6HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 20 }

cie1000IpStatisticsInterfacesIpv6OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 21 }

cie1000IpStatisticsInterfacesIpv6OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 22 }

cie1000IpStatisticsInterfacesIpv6HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 23 }

cie1000IpStatisticsInterfacesIpv6OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 24 }

cie1000IpStatisticsInterfacesIpv6OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 25 }

cie1000IpStatisticsInterfacesIpv6OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 26 }

cie1000IpStatisticsInterfacesIpv6OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 27 }

cie1000IpStatisticsInterfacesIpv6OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 28 }

cie1000IpStatisticsInterfacesIpv6OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 29 }

cie1000IpStatisticsInterfacesIpv6HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 30 }

cie1000IpStatisticsInterfacesIpv6OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 31 }

cie1000IpStatisticsInterfacesIpv6HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 32 }

cie1000IpStatisticsInterfacesIpv6InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 33 }

cie1000IpStatisticsInterfacesIpv6HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 34 }

cie1000IpStatisticsInterfacesIpv6InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 35 }

cie1000IpStatisticsInterfacesIpv6HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 36 }

cie1000IpStatisticsInterfacesIpv6OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 37 }

cie1000IpStatisticsInterfacesIpv6HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 38 }

cie1000IpStatisticsInterfacesIpv6OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 39 }

cie1000IpStatisticsInterfacesIpv6HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 40 }

cie1000IpStatisticsInterfacesIpv6InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 41 }

cie1000IpStatisticsInterfacesIpv6HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 42 }

cie1000IpStatisticsInterfacesIpv6OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 43 }

cie1000IpStatisticsInterfacesIpv6HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime.
         
         This object is only available if the capability object
         'cie1000IpCapabilitiesHasPerInterfaceIpv6Statistics' is True."
    ::= { cie1000IpStatisticsInterfacesIpv6Entry 44 }

cie1000IpStatisticsInterfacesIpv6DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value.
         
         This object is only available if the capability object
         'cie1000IpCapabilitiesHasPerInterfaceIpv6Statistics' is True."
    ::= { cie1000IpStatisticsInterfacesIpv6Entry 45 }

cie1000IpStatisticsInterfacesIpv6RefreshRate OBJECT-TYPE
    SYNTAX      Unsigned32
    MAX-ACCESS  read-only
    STATUS      current
    DESCRIPTION
        "The minimum reasonable polling interval for this entry. This object
         provides an indication of the minimum amount of time required to update
         the counters in this entry.
         
         This object is only available if the capability object
         'cie1000IpCapabilitiesHasPerInterfaceIpv6Statistics' is True."
    ::= { cie1000IpStatisticsInterfacesIpv6Entry 46 }

cie1000IpTrap OBJECT IDENTIFIER
    ::= { cie1000IpMibObjects 6 }

cie1000IpTrapInterfacesLinkAdd NOTIFICATION-TYPE
    OBJECTS     { cie1000IpStatusInterfacesLinkIfIndex,
                  cie1000IpStatusInterfacesLinkOsInterfaceIndex,
                  cie1000IpStatusInterfacesLinkMtu,
                  cie1000IpStatusInterfacesLinkMacAddress,
                  cie1000IpStatusInterfacesLinkUp,
                  cie1000IpStatusInterfacesLinkBroadcast,
                  cie1000IpStatusInterfacesLinkLoopback,
                  cie1000IpStatusInterfacesLinkRunning,
                  cie1000IpStatusInterfacesLinkNoarp,
                  cie1000IpStatusInterfacesLinkPromisc,
                  cie1000IpStatusInterfacesLinkMulticast }
    STATUS      current
    DESCRIPTION
        "This trap signals that a row has been added. The index(es) and value(s)
         of the row is included in the trap."

    ::= { cie1000IpTrap 1 }

cie1000IpTrapInterfacesLinkMod NOTIFICATION-TYPE
    OBJECTS     { cie1000IpStatusInterfacesLinkIfIndex,
                  cie1000IpStatusInterfacesLinkOsInterfaceIndex,
                  cie1000IpStatusInterfacesLinkMtu,
                  cie1000IpStatusInterfacesLinkMacAddress,
                  cie1000IpStatusInterfacesLinkUp,
                  cie1000IpStatusInterfacesLinkBroadcast,
                  cie1000IpStatusInterfacesLinkLoopback,
                  cie1000IpStatusInterfacesLinkRunning,
                  cie1000IpStatusInterfacesLinkNoarp,
                  cie1000IpStatusInterfacesLinkPromisc,
                  cie1000IpStatusInterfacesLinkMulticast }
    STATUS      current
    DESCRIPTION
        "This trap signals that one or more of the objects included in the trap
          has been updated."

    ::= { cie1000IpTrap 2 }

cie1000IpTrapInterfacesLinkDel NOTIFICATION-TYPE
    OBJECTS     { cie1000IpStatusInterfacesLinkIfIndex }
    STATUS      current
    DESCRIPTION
        "This trap signals that a row has been deleted. The index(es) of the
         row is included in the trap."

    ::= { cie1000IpTrap 3 }

cie1000IpMibConformance OBJECT IDENTIFIER
    ::= { cie1000IpMib 2 }

cie1000IpMibCompliances OBJECT IDENTIFIER
    ::= { cie1000IpMibConformance 1 }

cie1000IpMibGroups OBJECT IDENTIFIER
    ::= { cie1000IpMibConformance 2 }

cie1000IpCapabilitiesInfoGroup OBJECT-GROUP
    OBJECTS     { cie1000IpCapabilitiesHasIpv4HostCapabilities,
                  cie1000IpCapabilitiesHasIpv6HostCapabilities,
                  cie1000IpCapabilitiesHasIpv4UnicastRoutingCapabilities,
                  cie1000IpCapabilitiesHasIpv4UnicastHwRoutingCapabilities,
                  cie1000IpCapabilitiesHasIpv6UnicastRoutingCapabilities,
                  cie1000IpCapabilitiesHasIpv6UnicastHwRoutingCapabilities,
                  cie1000IpCapabilitiesMaxNumberOfIpInterfaces,
                  cie1000IpCapabilitiesMaxNumberOfStaticRoutes,
                  cie1000IpCapabilitiesNumberOfLpmHardwareEntries,
                  cie1000IpCapabilitiesHasPerInterfaceIpv4Statistics,
                  cie1000IpCapabilitiesHasPerInterfaceIpv6Statistics }
    STATUS      current
    DESCRIPTION
        "A collection of objects."
    ::= { cie1000IpMibGroups 1 }

cie1000IpConfigGlobalsMainInfoGroup OBJECT-GROUP
    OBJECTS     { cie1000IpConfigGlobalsMainEnableRouting }
    STATUS      current
    DESCRIPTION
        "A collection of objects."
    ::= { cie1000IpMibGroups 2 }

cie1000IpConfigInterfacesTableInfoGroup OBJECT-GROUP
    OBJECTS     { cie1000IpConfigInterfacesIfIndex,
                  cie1000IpConfigInterfacesAction }
    STATUS      current
    DESCRIPTION
        "A collection of objects."
    ::= { cie1000IpMibGroups 3 }

cie1000IpConfigInterfacesTableRowEditorInfoGroup OBJECT-GROUP
    OBJECTS     { cie1000IpConfigInterfacesTableRowEditorIfIndex,
                  cie1000IpConfigInterfacesTableRowEditorAction }
    STATUS      current
    DESCRIPTION
        "A collection of objects."
    ::= { cie1000IpMibGroups 4 }

cie1000IpConfigInterfacesIpv4TableInfoGroup OBJECT-GROUP
    OBJECTS     { cie1000IpConfigInterfacesIpv4IfIndex,
                  cie1000IpConfigInterfacesIpv4Active,
                  cie1000IpConfigInterfacesIpv4EnableDhcpClient,
                  cie1000IpConfigInterfacesIpv4Ipv4Address,
                  cie1000IpConfigInterfacesIpv4PrefixSize,
                  cie1000IpConfigInterfacesIpv4DhcpClientFallbackTimeout }
    STATUS      current
    DESCRIPTION
        "A collection of objects."
    ::= { cie1000IpMibGroups 5 }

cie1000IpConfigInterfacesIpv6TableInfoGroup OBJECT-GROUP
    OBJECTS     { cie1000IpConfigInterfacesIpv6IfIndex,
                  cie1000IpConfigInterfacesIpv6Active,
                  cie1000IpConfigInterfacesIpv6Ipv6Address,
                  cie1000IpConfigInterfacesIpv6PrefixSize }
    STATUS      current
    DESCRIPTION
        "A collection of objects."
    ::= { cie1000IpMibGroups 6 }

cie1000IpConfigRoutesIpv4TableInfoGroup OBJECT-GROUP
    OBJECTS     { cie1000IpConfigRoutesIpv4NetworkAddress,
                  cie1000IpConfigRoutesIpv4NetworkPrefixSize,
                  cie1000IpConfigRoutesIpv4NextHop,
                  cie1000IpConfigRoutesIpv4Action }
    STATUS      current
    DESCRIPTION
        "A collection of objects."
    ::= { cie1000IpMibGroups 7 }

cie1000IpConfigRoutesIpv4RowEditorInfoGroup OBJECT-GROUP
    OBJECTS     { cie1000IpConfigRoutesIpv4RowEditorNetworkAddress,
                  cie1000IpConfigRoutesIpv4RowEditorNetworkPrefixSize,
                  cie1000IpConfigRoutesIpv4RowEditorNextHop,
                  cie1000IpConfigRoutesIpv4RowEditorAction }
    STATUS      current
    DESCRIPTION
        "A collection of objects."
    ::= { cie1000IpMibGroups 8 }

cie1000IpConfigRoutesIpv6TableInfoGroup OBJECT-GROUP
    OBJECTS     { cie1000IpConfigRoutesIpv6NetworkAddress,
                  cie1000IpConfigRoutesIpv6NetworkPrefixSize,
                  cie1000IpConfigRoutesIpv6NextHop,
                  cie1000IpConfigRoutesIpv6NextHopInterface,
                  cie1000IpConfigRoutesIpv6Action }
    STATUS      current
    DESCRIPTION
        "A collection of objects."
    ::= { cie1000IpMibGroups 9 }

cie1000IpConfigRoutesIpv6RowEditorInfoGroup OBJECT-GROUP
    OBJECTS     { cie1000IpConfigRoutesIpv6RowEditorNetworkAddress,
                  cie1000IpConfigRoutesIpv6RowEditorNetworkPrefixSize,
                  cie1000IpConfigRoutesIpv6RowEditorNextHop,
                  cie1000IpConfigRoutesIpv6RowEditorNextHopInterface,
                  cie1000IpConfigRoutesIpv6RowEditorAction }
    STATUS      current
    DESCRIPTION
        "A collection of objects."
    ::= { cie1000IpMibGroups 10 }

cie1000IpStatusGlobalsIpv4NeighbourInfoGroup OBJECT-GROUP
    OBJECTS     { cie1000IpStatusGlobalsIpv4NeighbourIpv4,
                  cie1000IpStatusGlobalsIpv4NeighbourMacAddress,
                  cie1000IpStatusGlobalsIpv4NeighbourInterface }
    STATUS      current
    DESCRIPTION
        "A collection of objects."
    ::= { cie1000IpMibGroups 11 }

cie1000IpStatusGlobalsIpv6NeighbourInfoGroup OBJECT-GROUP
    OBJECTS     { cie1000IpStatusGlobalsIpv6NeighbourIpAddress,
                  cie1000IpStatusGlobalsIpv6NeighbourInterfaceQuery,
                  cie1000IpStatusGlobalsIpv6NeighbourMacAddress,
                  cie1000IpStatusGlobalsIpv6NeighbourInterface }
    STATUS      current
    DESCRIPTION
        "A collection of objects."
    ::= { cie1000IpMibGroups 12 }

cie1000IpStatusInterfacesLinkInfoGroup OBJECT-GROUP
    OBJECTS     { cie1000IpStatusInterfacesLinkIfIndex,
                  cie1000IpStatusInterfacesLinkOsInterfaceIndex,
                  cie1000IpStatusInterfacesLinkMtu,
                  cie1000IpStatusInterfacesLinkMacAddress,
                  cie1000IpStatusInterfacesLinkUp,
                  cie1000IpStatusInterfacesLinkBroadcast,
                  cie1000IpStatusInterfacesLinkLoopback,
                  cie1000IpStatusInterfacesLinkRunning,
                  cie1000IpStatusInterfacesLinkNoarp,
                  cie1000IpStatusInterfacesLinkPromisc,
                  cie1000IpStatusInterfacesLinkMulticast }
    STATUS      current
    DESCRIPTION
        "A collection of objects."
    ::= { cie1000IpMibGroups 13 }

cie1000IpStatusInterfacesIpv4InfoGroup OBJECT-GROUP
    OBJECTS     { cie1000IpStatusInterfacesIpv4IfIndex,
                  cie1000IpStatusInterfacesIpv4NetworkAddress,
                  cie1000IpStatusInterfacesIpv4NetworkMaskLength,
                  cie1000IpStatusInterfacesIpv4Broadcast }
    STATUS      current
    DESCRIPTION
        "A collection of objects."
    ::= { cie1000IpMibGroups 14 }

cie1000IpStatusInterfacesDhcpClientV4InfoGroup OBJECT-GROUP
    OBJECTS     { cie1000IpStatusInterfacesDhcpClientV4IfIndex,
                  cie1000IpStatusInterfacesDhcpClientV4State,
                  cie1000IpStatusInterfacesDhcpClientV4ServerIp }
    STATUS      current
    DESCRIPTION
        "A collection of objects."
    ::= { cie1000IpMibGroups 15 }

cie1000IpStatusInterfacesIpv6InfoGroup OBJECT-GROUP
    OBJECTS     { cie1000IpStatusInterfacesIpv6IfIndex,
                  cie1000IpStatusInterfacesIpv6NetworkAddress,
                  cie1000IpStatusInterfacesIpv6NetworkMaskLength,
                  cie1000IpStatusInterfacesIpv6Tentative,
                  cie1000IpStatusInterfacesIpv6Duplicated,
                  cie1000IpStatusInterfacesIpv6Detached,
                  cie1000IpStatusInterfacesIpv6Nodad,
                  cie1000IpStatusInterfacesIpv6Autoconf }
    STATUS      current
    DESCRIPTION
        "A collection of objects."
    ::= { cie1000IpMibGroups 16 }

cie1000IpStatusRoutesIpv4InfoGroup OBJECT-GROUP
    OBJECTS     { cie1000IpStatusRoutesIpv4NetworkAddress,
                  cie1000IpStatusRoutesIpv4NetworkPrefixSize,
                  cie1000IpStatusRoutesIpv4NextHop,
                  cie1000IpStatusRoutesIpv4DerivedNextHopInterface,
                  cie1000IpStatusRoutesIpv4FlagUp,
                  cie1000IpStatusRoutesIpv4FlagHost,
                  cie1000IpStatusRoutesIpv4FlagGateway,
                  cie1000IpStatusRoutesIpv4OwnerConf,
                  cie1000IpStatusRoutesIpv4OwnerDhcp,
                  cie1000IpStatusRoutesIpv4OwnerDynamic }
    STATUS      current
    DESCRIPTION
        "A collection of objects."
    ::= { cie1000IpMibGroups 17 }

cie1000IpStatusRoutesIpv6InfoGroup OBJECT-GROUP
    OBJECTS     { cie1000IpStatusRoutesIpv6NetworkAddress,
                  cie1000IpStatusRoutesIpv6NetworkPrefixSize,
                  cie1000IpStatusRoutesIpv6NextHop,
                  cie1000IpStatusRoutesIpv6NextHopInterface,
                  cie1000IpStatusRoutesIpv6DerivedNextHopInterface,
                  cie1000IpStatusRoutesIpv6FlagUp,
                  cie1000IpStatusRoutesIpv6FlagHost,
                  cie1000IpStatusRoutesIpv6FlagGateway,
                  cie1000IpStatusRoutesIpv6OwnerConf,
                  cie1000IpStatusRoutesIpv6OwnerDhcp,
                  cie1000IpStatusRoutesIpv6OwnerDynamic }
    STATUS      current
    DESCRIPTION
        "A collection of objects."
    ::= { cie1000IpMibGroups 18 }

cie1000IpControlGlobalsInfoGroup OBJECT-GROUP
    OBJECTS     { cie1000IpControlGlobalsIpv4NeighbourTableClear,
                  cie1000IpControlGlobalsIpv6NeighbourTableClear,
                  cie1000IpControlGlobalsIpv4SystemStatisticsClear,
                  cie1000IpControlGlobalsIpv6SystemStatisticsClear }
    STATUS      current
    DESCRIPTION
        "A collection of objects."
    ::= { cie1000IpMibGroups 19 }

cie1000IpControlInterfaceDhcpClientInfoGroup OBJECT-GROUP
    OBJECTS     { cie1000IpControlInterfaceDhcpClientIfIndex,
                  cie1000IpControlInterfaceDhcpClientRestart }
    STATUS      current
    DESCRIPTION
        "A collection of objects."
    ::= { cie1000IpMibGroups 20 }

cie1000IpStatisticsGlobalsIpv4InfoGroup OBJECT-GROUP
    OBJECTS     { cie1000IpStatisticsGlobalsIpv4InReceives,
                  cie1000IpStatisticsGlobalsIpv4HCInReceives,
                  cie1000IpStatisticsGlobalsIpv4InOctets,
                  cie1000IpStatisticsGlobalsIpv4HCInOctets,
                  cie1000IpStatisticsGlobalsIpv4InHdrErrors,
                  cie1000IpStatisticsGlobalsIpv4InNoRoutes,
                  cie1000IpStatisticsGlobalsIpv4InAddrErrors,
                  cie1000IpStatisticsGlobalsIpv4InUnknownProtos,
                  cie1000IpStatisticsGlobalsIpv4InTruncatedPkts,
                  cie1000IpStatisticsGlobalsIpv4InForwDatagrams,
                  cie1000IpStatisticsGlobalsIpv4HCInForwDatagrams,
                  cie1000IpStatisticsGlobalsIpv4ReasmReqds,
                  cie1000IpStatisticsGlobalsIpv4ReasmOKs,
                  cie1000IpStatisticsGlobalsIpv4ReasmFails,
                  cie1000IpStatisticsGlobalsIpv4InDiscards,
                  cie1000IpStatisticsGlobalsIpv4InDelivers,
                  cie1000IpStatisticsGlobalsIpv4HCInDelivers,
                  cie1000IpStatisticsGlobalsIpv4OutRequests,
                  cie1000IpStatisticsGlobalsIpv4HCOutRequests,
                  cie1000IpStatisticsGlobalsIpv4OutNoRoutes,
                  cie1000IpStatisticsGlobalsIpv4OutForwDatagrams,
                  cie1000IpStatisticsGlobalsIpv4HCOutForwDatagrams,
                  cie1000IpStatisticsGlobalsIpv4OutDiscards,
                  cie1000IpStatisticsGlobalsIpv4OutFragReqds,
                  cie1000IpStatisticsGlobalsIpv4OutFragOKs,
                  cie1000IpStatisticsGlobalsIpv4OutFragFails,
                  cie1000IpStatisticsGlobalsIpv4OutFragCreates,
                  cie1000IpStatisticsGlobalsIpv4OutTransmits,
                  cie1000IpStatisticsGlobalsIpv4HCOutTransmits,
                  cie1000IpStatisticsGlobalsIpv4OutOctets,
                  cie1000IpStatisticsGlobalsIpv4HCOutOctets,
                  cie1000IpStatisticsGlobalsIpv4InMcastPkts,
                  cie1000IpStatisticsGlobalsIpv4HCInMcastPkts,
                  cie1000IpStatisticsGlobalsIpv4InMcastOctets,
                  cie1000IpStatisticsGlobalsIpv4HCInMcastOctets,
                  cie1000IpStatisticsGlobalsIpv4OutMcastPkts,
                  cie1000IpStatisticsGlobalsIpv4HCOutMcastPkts,
                  cie1000IpStatisticsGlobalsIpv4OutMcastOctets,
                  cie1000IpStatisticsGlobalsIpv4HCOutMcastOctets,
                  cie1000IpStatisticsGlobalsIpv4InBcastPkts,
                  cie1000IpStatisticsGlobalsIpv4HCInBcastPkts,
                  cie1000IpStatisticsGlobalsIpv4OutBcastPkts,
                  cie1000IpStatisticsGlobalsIpv4HCOutBcastPkts,
                  cie1000IpStatisticsGlobalsIpv4DiscontinuityTime,
                  cie1000IpStatisticsGlobalsIpv4RefreshRate }
    STATUS      current
    DESCRIPTION
        "A collection of objects."
    ::= { cie1000IpMibGroups 21 }

cie1000IpStatisticsGlobalsIpv6InfoGroup OBJECT-GROUP
    OBJECTS     { cie1000IpStatisticsGlobalsIpv6InReceives,
                  cie1000IpStatisticsGlobalsIpv6HCInReceives,
                  cie1000IpStatisticsGlobalsIpv6InOctets,
                  cie1000IpStatisticsGlobalsIpv6HCInOctets,
                  cie1000IpStatisticsGlobalsIpv6InHdrErrors,
                  cie1000IpStatisticsGlobalsIpv6InNoRoutes,
                  cie1000IpStatisticsGlobalsIpv6InAddrErrors,
                  cie1000IpStatisticsGlobalsIpv6InUnknownProtos,
                  cie1000IpStatisticsGlobalsIpv6InTruncatedPkts,
                  cie1000IpStatisticsGlobalsIpv6InForwDatagrams,
                  cie1000IpStatisticsGlobalsIpv6HCInForwDatagrams,
                  cie1000IpStatisticsGlobalsIpv6ReasmReqds,
                  cie1000IpStatisticsGlobalsIpv6ReasmOKs,
                  cie1000IpStatisticsGlobalsIpv6ReasmFails,
                  cie1000IpStatisticsGlobalsIpv6InDiscards,
                  cie1000IpStatisticsGlobalsIpv6InDelivers,
                  cie1000IpStatisticsGlobalsIpv6HCInDelivers,
                  cie1000IpStatisticsGlobalsIpv6OutRequests,
                  cie1000IpStatisticsGlobalsIpv6HCOutRequests,
                  cie1000IpStatisticsGlobalsIpv6OutNoRoutes,
                  cie1000IpStatisticsGlobalsIpv6OutForwDatagrams,
                  cie1000IpStatisticsGlobalsIpv6HCOutForwDatagrams,
                  cie1000IpStatisticsGlobalsIpv6OutDiscards,
                  cie1000IpStatisticsGlobalsIpv6OutFragReqds,
                  cie1000IpStatisticsGlobalsIpv6OutFragOKs,
                  cie1000IpStatisticsGlobalsIpv6OutFragFails,
                  cie1000IpStatisticsGlobalsIpv6OutFragCreates,
                  cie1000IpStatisticsGlobalsIpv6OutTransmits,
                  cie1000IpStatisticsGlobalsIpv6HCOutTransmits,
                  cie1000IpStatisticsGlobalsIpv6OutOctets,
                  cie1000IpStatisticsGlobalsIpv6HCOutOctets,
                  cie1000IpStatisticsGlobalsIpv6InMcastPkts,
                  cie1000IpStatisticsGlobalsIpv6HCInMcastPkts,
                  cie1000IpStatisticsGlobalsIpv6InMcastOctets,
                  cie1000IpStatisticsGlobalsIpv6HCInMcastOctets,
                  cie1000IpStatisticsGlobalsIpv6OutMcastPkts,
                  cie1000IpStatisticsGlobalsIpv6HCOutMcastPkts,
                  cie1000IpStatisticsGlobalsIpv6OutMcastOctets,
                  cie1000IpStatisticsGlobalsIpv6HCOutMcastOctets,
                  cie1000IpStatisticsGlobalsIpv6InBcastPkts,
                  cie1000IpStatisticsGlobalsIpv6HCInBcastPkts,
                  cie1000IpStatisticsGlobalsIpv6OutBcastPkts,
                  cie1000IpStatisticsGlobalsIpv6HCOutBcastPkts,
                  cie1000IpStatisticsGlobalsIpv6DiscontinuityTime,
                  cie1000IpStatisticsGlobalsIpv6RefreshRate }
    STATUS      current
    DESCRIPTION
        "A collection of objects."
    ::= { cie1000IpMibGroups 22 }

cie1000IpStatisticsInterfacesLinkInfoGroup OBJECT-GROUP
    OBJECTS     { cie1000IpStatisticsInterfacesLinkIfIndex,
                  cie1000IpStatisticsInterfacesLinkInPackets,
                  cie1000IpStatisticsInterfacesLinkOutPackets,
                  cie1000IpStatisticsInterfacesLinkInBytes,
                  cie1000IpStatisticsInterfacesLinkOutBytes,
                  cie1000IpStatisticsInterfacesLinkInMulticasts,
                  cie1000IpStatisticsInterfacesLinkOutMulticasts,
                  cie1000IpStatisticsInterfacesLinkInBroadcasts,
                  cie1000IpStatisticsInterfacesLinkOutBroadcasts }
    STATUS      current
    DESCRIPTION
        "A collection of objects."
    ::= { cie1000IpMibGroups 23 }

cie1000IpStatisticsInterfacesIpv4InfoGroup OBJECT-GROUP
    OBJECTS     { cie1000IpStatisticsInterfacesIpv4IfIndex,
                  cie1000IpStatisticsInterfacesIpv4InReceives,
                  cie1000IpStatisticsInterfacesIpv4HCInReceives,
                  cie1000IpStatisticsInterfacesIpv4InOctets,
                  cie1000IpStatisticsInterfacesIpv4HCInOctets,
                  cie1000IpStatisticsInterfacesIpv4InHdrErrors,
                  cie1000IpStatisticsInterfacesIpv4InNoRoutes,
                  cie1000IpStatisticsInterfacesIpv4InAddrErrors,
                  cie1000IpStatisticsInterfacesIpv4InUnknownProtos,
                  cie1000IpStatisticsInterfacesIpv4InTruncatedPkts,
                  cie1000IpStatisticsInterfacesIpv4InForwDatagrams,
                  cie1000IpStatisticsInterfacesIpv4HCInForwDatagrams,
                  cie1000IpStatisticsInterfacesIpv4ReasmReqds,
                  cie1000IpStatisticsInterfacesIpv4ReasmOKs,
                  cie1000IpStatisticsInterfacesIpv4ReasmFails,
                  cie1000IpStatisticsInterfacesIpv4InDiscards,
                  cie1000IpStatisticsInterfacesIpv4InDelivers,
                  cie1000IpStatisticsInterfacesIpv4HCInDelivers,
                  cie1000IpStatisticsInterfacesIpv4OutRequests,
                  cie1000IpStatisticsInterfacesIpv4HCOutRequests,
                  cie1000IpStatisticsInterfacesIpv4OutNoRoutes,
                  cie1000IpStatisticsInterfacesIpv4OutForwDatagrams,
                  cie1000IpStatisticsInterfacesIpv4HCOutForwDatagrams,
                  cie1000IpStatisticsInterfacesIpv4OutDiscards,
                  cie1000IpStatisticsInterfacesIpv4OutFragReqds,
                  cie1000IpStatisticsInterfacesIpv4OutFragOKs,
                  cie1000IpStatisticsInterfacesIpv4OutFragFails,
                  cie1000IpStatisticsInterfacesIpv4OutFragCreates,
                  cie1000IpStatisticsInterfacesIpv4OutTransmits,
                  cie1000IpStatisticsInterfacesIpv4HCOutTransmits,
                  cie1000IpStatisticsInterfacesIpv4OutOctets,
                  cie1000IpStatisticsInterfacesIpv4HCOutOctets,
                  cie1000IpStatisticsInterfacesIpv4InMcastPkts,
                  cie1000IpStatisticsInterfacesIpv4HCInMcastPkts,
                  cie1000IpStatisticsInterfacesIpv4InMcastOctets,
                  cie1000IpStatisticsInterfacesIpv4HCInMcastOctets,
                  cie1000IpStatisticsInterfacesIpv4OutMcastPkts,
                  cie1000IpStatisticsInterfacesIpv4HCOutMcastPkts,
                  cie1000IpStatisticsInterfacesIpv4OutMcastOctets,
                  cie1000IpStatisticsInterfacesIpv4HCOutMcastOctets,
                  cie1000IpStatisticsInterfacesIpv4InBcastPkts,
                  cie1000IpStatisticsInterfacesIpv4HCInBcastPkts,
                  cie1000IpStatisticsInterfacesIpv4OutBcastPkts,
                  cie1000IpStatisticsInterfacesIpv4HCOutBcastPkts,
                  cie1000IpStatisticsInterfacesIpv4DiscontinuityTime,
                  cie1000IpStatisticsInterfacesIpv4RefreshRate }
    STATUS      current
    DESCRIPTION
        "A collection of objects."
    ::= { cie1000IpMibGroups 24 }

cie1000IpStatisticsInterfacesIpv6InfoGroup OBJECT-GROUP
    OBJECTS     { cie1000IpStatisticsInterfacesIpv6IfIndex,
                  cie1000IpStatisticsInterfacesIpv6InReceives,
                  cie1000IpStatisticsInterfacesIpv6HCInReceives,
                  cie1000IpStatisticsInterfacesIpv6InOctets,
                  cie1000IpStatisticsInterfacesIpv6HCInOctets,
                  cie1000IpStatisticsInterfacesIpv6InHdrErrors,
                  cie1000IpStatisticsInterfacesIpv6InNoRoutes,
                  cie1000IpStatisticsInterfacesIpv6InAddrErrors,
                  cie1000IpStatisticsInterfacesIpv6InUnknownProtos,
                  cie1000IpStatisticsInterfacesIpv6InTruncatedPkts,
                  cie1000IpStatisticsInterfacesIpv6InForwDatagrams,
                  cie1000IpStatisticsInterfacesIpv6HCInForwDatagrams,
                  cie1000IpStatisticsInterfacesIpv6ReasmReqds,
                  cie1000IpStatisticsInterfacesIpv6ReasmOKs,
                  cie1000IpStatisticsInterfacesIpv6ReasmFails,
                  cie1000IpStatisticsInterfacesIpv6InDiscards,
                  cie1000IpStatisticsInterfacesIpv6InDelivers,
                  cie1000IpStatisticsInterfacesIpv6HCInDelivers,
                  cie1000IpStatisticsInterfacesIpv6OutRequests,
                  cie1000IpStatisticsInterfacesIpv6HCOutRequests,
                  cie1000IpStatisticsInterfacesIpv6OutNoRoutes,
                  cie1000IpStatisticsInterfacesIpv6OutForwDatagrams,
                  cie1000IpStatisticsInterfacesIpv6HCOutForwDatagrams,
                  cie1000IpStatisticsInterfacesIpv6OutDiscards,
                  cie1000IpStatisticsInterfacesIpv6OutFragReqds,
                  cie1000IpStatisticsInterfacesIpv6OutFragOKs,
                  cie1000IpStatisticsInterfacesIpv6OutFragFails,
                  cie1000IpStatisticsInterfacesIpv6OutFragCreates,
                  cie1000IpStatisticsInterfacesIpv6OutTransmits,
                  cie1000IpStatisticsInterfacesIpv6HCOutTransmits,
                  cie1000IpStatisticsInterfacesIpv6OutOctets,
                  cie1000IpStatisticsInterfacesIpv6HCOutOctets,
                  cie1000IpStatisticsInterfacesIpv6InMcastPkts,
                  cie1000IpStatisticsInterfacesIpv6HCInMcastPkts,
                  cie1000IpStatisticsInterfacesIpv6InMcastOctets,
                  cie1000IpStatisticsInterfacesIpv6HCInMcastOctets,
                  cie1000IpStatisticsInterfacesIpv6OutMcastPkts,
                  cie1000IpStatisticsInterfacesIpv6HCOutMcastPkts,
                  cie1000IpStatisticsInterfacesIpv6OutMcastOctets,
                  cie1000IpStatisticsInterfacesIpv6HCOutMcastOctets,
                  cie1000IpStatisticsInterfacesIpv6InBcastPkts,
                  cie1000IpStatisticsInterfacesIpv6HCInBcastPkts,
                  cie1000IpStatisticsInterfacesIpv6OutBcastPkts,
                  cie1000IpStatisticsInterfacesIpv6HCOutBcastPkts,
                  cie1000IpStatisticsInterfacesIpv6DiscontinuityTime,
                  cie1000IpStatisticsInterfacesIpv6RefreshRate }
    STATUS      current
    DESCRIPTION
        "A collection of objects."
    ::= { cie1000IpMibGroups 25 }

cie1000IpTrapInterfacesLinkAddInfoGroup NOTIFICATION-GROUP
    NOTIFICATIONS { cie1000IpTrapInterfacesLinkAdd }
    STATUS      current
    DESCRIPTION
        "Information group containing a trap."
    ::= { cie1000IpMibGroups 26 }

cie1000IpTrapInterfacesLinkModInfoGroup NOTIFICATION-GROUP
    NOTIFICATIONS { cie1000IpTrapInterfacesLinkMod }
    STATUS      current
    DESCRIPTION
        "Information group containing a trap."
    ::= { cie1000IpMibGroups 27 }

cie1000IpTrapInterfacesLinkDelInfoGroup NOTIFICATION-GROUP
    NOTIFICATIONS { cie1000IpTrapInterfacesLinkDel }
    STATUS      current
    DESCRIPTION
        "Information group containing a trap."
    ::= { cie1000IpMibGroups 28 }

cie1000IpMibCompliance MODULE-COMPLIANCE
    STATUS      current
    DESCRIPTION
        "The compliance statement for the implementation."

    MODULE      -- this module

    MANDATORY-GROUPS { cie1000IpCapabilitiesInfoGroup,
                       cie1000IpConfigGlobalsMainInfoGroup,
                       cie1000IpConfigInterfacesTableInfoGroup,
                       cie1000IpConfigInterfacesTableRowEditorInfoGroup,
                       cie1000IpConfigInterfacesIpv4TableInfoGroup,
                       cie1000IpConfigInterfacesIpv6TableInfoGroup,
                       cie1000IpConfigRoutesIpv4TableInfoGroup,
                       cie1000IpConfigRoutesIpv4RowEditorInfoGroup,
                       cie1000IpConfigRoutesIpv6TableInfoGroup,
                       cie1000IpConfigRoutesIpv6RowEditorInfoGroup,
                       cie1000IpStatusGlobalsIpv4NeighbourInfoGroup,
                       cie1000IpStatusGlobalsIpv6NeighbourInfoGroup,
                       cie1000IpStatusInterfacesLinkInfoGroup,
                       cie1000IpStatusInterfacesIpv4InfoGroup,
                       cie1000IpStatusInterfacesDhcpClientV4InfoGroup,
                       cie1000IpStatusInterfacesIpv6InfoGroup,
                       cie1000IpStatusRoutesIpv4InfoGroup,
                       cie1000IpStatusRoutesIpv6InfoGroup,
                       cie1000IpControlGlobalsInfoGroup,
                       cie1000IpControlInterfaceDhcpClientInfoGroup,
                       cie1000IpStatisticsGlobalsIpv4InfoGroup,
                       cie1000IpStatisticsGlobalsIpv6InfoGroup,
                       cie1000IpStatisticsInterfacesLinkInfoGroup,
                       cie1000IpStatisticsInterfacesIpv4InfoGroup,
                       cie1000IpStatisticsInterfacesIpv6InfoGroup,
                       cie1000IpTrapInterfacesLinkAddInfoGroup,
                       cie1000IpTrapInterfacesLinkModInfoGroup,
                       cie1000IpTrapInterfacesLinkDelInfoGroup }

    ::= { cie1000IpMibCompliances 1 }

END
