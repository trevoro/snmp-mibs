LEFTHAND-NETWORKS-GLOBAL-REG DEFINITIONS ::= BEGIN

-- LeftHand Networks Standard Definitions:
--
-- This file contains definitions which are common to
-- all LeftHand Network products.

IMPORTS
    MODULE-IDENTITY, OBJECT-IDENTITY, enterprises
        FROM SNMPv2-SMI;

--
-- Module definition
--
leftHandNetworksGlobalRegistrationModule MODULE-IDENTITY
    LAST-UPDATED "200106010000Z"
    ORGANIZATION "LeftHand Networks, Inc."
    CONTACT-INFO    
	 "
         Primary Author: Jose Faria

         postal:    6185 Arapahoe Rd.
                    Boulder, CO 80301
         phone:     +1 303 449-4100
         email:     jfaria@lefthandnetworks.com"
    DESCRIPTION
	"This file defines the private LeftHand Networks SNMP MIB extensions."

    ::= { lhnModules 1 }

-- 
-- Private Enterprise Number Definition
--
leftHandNetworks OBJECT-IDENTITY
   STATUS       current
   DESCRIPTION  "The root of the OID sub-tree assigned to LeftHand Networks
                 by the Internet Assigned Numbers Authority (IANA)."
   ::= { enterprises 9804 }
  
--***************************************************************************
--
-- OID Infrastructure Definitions
--
--*************************************************************************** 
lhnRegistrations OBJECT-IDENTITY
   STATUS       current
   DESCRIPTION  "Sub-tree for registrations"
   ::= { leftHandNetworks 1 }
   
lhnGeneric OBJECT-IDENTITY
   STATUS       current
   DESCRIPTION  "Sub-tree for object and event definitions common accross all products"
   ::= { leftHandNetworks 2 }
   
lhnProducts OBJECT-IDENTITY
   STATUS       current
   DESCRIPTION  "Sub-tree for product specific object and event definitions"
   ::= { leftHandNetworks 3 }
   
lhnCapabilities OBJECT-IDENTITY
   STATUS       current
   DESCRIPTION  "Sub-tree for agent profiles"
   ::= { leftHandNetworks 4 }
   
lhnRequirements OBJECT-IDENTITY
   STATUS       current
   DESCRIPTION  "Sub-tree for management application requirements"
   ::= { leftHandNetworks 5 }
   
lhnExperimental OBJECT-IDENTITY
   STATUS       current
   DESCRIPTION  "Sub-tree for experimental definitions"
   ::= { leftHandNetworks 6 }
   
--***************************************************************************
--
-- Registration Definitions
--
--*************************************************************************** 

lhnModules  OBJECT-IDENTITY
   STATUS       current
   DESCRIPTION  "Sub-tree to register the values assigned to modules with the MODULE-IDENTITY construct"
   ::= { lhnRegistrations 1 }
   
lhnNusDevices OBJECT-IDENTITY
   STATUS       current
   DESCRIPTION  "NUS Storage Devices"
   ::= { lhnRegistrations 2 }
   
lhnNusCommon OBJECT-IDENTITY
   STATUS       current
   DESCRIPTION  "NUS Model Devices"
   ::= { lhnNusDevices 1 }
   
--***************************************************************************
--
-- Product MIBs Definitions
--
--*************************************************************************** 

lhnNusDevicesMIBs OBJECT-IDENTITY
   STATUS       current
   DESCRIPTION  "Sub-tree for NUS Devices MIBs"
   ::= { lhnProducts 1 }
   
lhnNusCommonMIB OBJECT-IDENTITY
   STATUS       current
   DESCRIPTION  "Sub-tree for NUS Model 1 objects and events MIBs"
   ::= { lhnNusDevicesMIBs 1 }
   
--
-- The above definitions produce a section of the mib tree that looks
-- like this (including our parent node, printed using the
-- snmptranslate command):
--
--
--   % /usr/local/bin/snmptranslate -M . -m ALL -Tp .iso.org.dod.internet.private.enterprises.leftHandNetworks


END
