-- Based on R2 Voice Inter-Working Functions Specification (Rev 1.0, dated 5/14/97).
-- For Release 2.0, this MIB file, mcm2t1e1.mib, shall replace the existing T1/E1 MIB
-- file, mcmt1e1.mib (Rlse 1.1).
-- 
-- MIB Revision : 1.0 dated 6-2-97
-- Change Desc. : Initial submittal - R. Carmona. 
-- 
-- MIB Revision : 1.1 dated 7-2-97
-- Change Desc. : Add T1E1 Traps - A. Llanes. 
-- 
-- MIB Revision : 1.2 dated 7-8-97
-- Change Desc. : Changed System Status OperStatus enumeration
--                from "unabletosyncup (3)" to "downloadFail (3)"
--                as per Justin Fang's request. - A. Llanes. 
-- 
-- MIB Revision : 1.3 dated 7-11-97
-- Change Desc. : Added LineIndex to all T1/E1 Alarm traps. - B. Jafari
-- 
-- MIB Revision : 1.4 dated 10-7-97
-- Change Desc. : Replaced MPA with 4400, and other minor changes - B. Jafari. 
-- 
-- *** RELEASE 3.0 ***
-- MIB Revision : 1.5 dated 6-23-98
-- Change Desc. : Removed and/or replaced "4400" with "access device"
--				  wherever possible.  Removed the counter reset 
--				  enumeration from the object, 
--				  mcm4400t1e1SysControlActionCmd. -A. Llanes
--
-- MIB Revision : 1.6 dated 7-07-98
-- Change Desc. : Reincorporated counter reset enumeration
--				  for mcm4400t1e1SysControlActionCmd to 
--				  support backward compatibility of 
--				  releases prior to 3.0. -A. Llanes
--
--
-- MIB Revision: 1.7 dated 11-02-98
-- Change Desc.: The Severity Levels were added to the traps. -F. Kottab

MICOM-4400-T1E1-MIB DEFINITIONS ::= BEGIN
	IMPORTS
		TRAP-TYPE
			FROM RFC-1215
		mcmSysAsciiTimeOfDay
			FROM MICOM-SYS-MIB
		Counter
			FROM RFC1155-SMI
		OBJECT-TYPE
			FROM RFC-1212
		DisplayString
			FROM SNMPv2-TC
		micom-oscar
			FROM MICOM-OSCAR-MIB;


-- group OBJECT IDENTIFIERs

	micom-2t1e1			OBJECT IDENTIFIER ::= {micom-oscar 22}
	t1e1-r2-configuration 		OBJECT IDENTIFIER ::= { micom-2t1e1 1}
	t1e1-r2-control	 		OBJECT IDENTIFIER ::= { micom-2t1e1 2}
	t1e1-r2-status			OBJECT IDENTIFIER ::= { micom-2t1e1 3}
	t1e1-r2-statistics 		OBJECT IDENTIFIER ::= { micom-2t1e1 4}


-- *** CONFIGURATION groups/tables ***

-- Note: The following groups contain 2 related groups/tables for all configuration
--       functionality. 
--	 1) The Standard or Operational Parameters (Operational) provide the
--	 SNMP management interface with the access device operational modules.
--	 Objects defined for this interface begin with the 'mcm' prefix.
--	 2) The Configuration Parameters (Configuration) provide the SNMP 
--	 management interface with a stored access device configuration. 
--	 Objects defined for this interface begin with the 'nvm' prefix.
--	


--  Operational Parameter ("mcm") Groups/Tables


--  the T1/E1 Line Configuration Table 
--  (Standard/Operational Parameters)

--  This table provides the T1/E1 line configuration parameters
--  for identifying a T1/E1 line with its corresponding profile. (Operational)

mcm4400t1e1LineCfgTable OBJECT-TYPE
	SYNTAX  SEQUENCE OF Mcm4400t1e1LineCfgEntry
	ACCESS  not-accessible
	STATUS  mandatory
	DESCRIPTION
	  "NAME = ; 
	   DESC = The T1/E1 Line Configuration table. \
		  (Operational);
	   HELP = ;
	   CAPABILITIES = NET_CFG, VPN_CFG;"
	::= { t1e1-r2-configuration 1 }

mcm4400t1e1LineCfgEntry OBJECT-TYPE
	SYNTAX  Mcm4400t1e1LineCfgEntry
	ACCESS  not-accessible
	STATUS  mandatory
	DESCRIPTION
	  "NAME = ; 
	   DESC = An entry in the T1/E1 Line Configuration \
		  table. (Operational);
	   HELP = ;
	   CAPABILITIES = ;"
	INDEX   { mcm4400t1e1LineCfgLineID }
	::= { mcm4400t1e1LineCfgTable 1 }

Mcm4400t1e1LineCfgEntry ::= SEQUENCE {
	mcm4400t1e1LineCfgLineID		INTEGER,
	mcm4400t1e1LineCfgProfileNum		INTEGER
	}

mcm4400t1e1LineCfgLineID OBJECT-TYPE
	SYNTAX	INTEGER {
		local (1),
		network (2)
		}
	ACCESS  read-only
	STATUS  mandatory
	DESCRIPTION
	  "NAME = ;
	   DESC = The T1/E1 line identification specifies which line \
		  is to be configured.  Used as the index to the \
		  T1/E1 Line Configuration table. (Operational);
	   HELP = ;
	   CAPABILITIES = ;"
	::= { mcm4400t1e1LineCfgEntry 1 }

mcm4400t1e1LineCfgProfileNum OBJECT-TYPE
	SYNTAX	INTEGER (1..2)
	ACCESS  read-write
	STATUS  mandatory
	DESCRIPTION
	  "NAME = ; 
	   DESC = The value of this object indicates the profile \
		  to be used to configure the specified T1/E1 \
		  line. (Operational);
	   HELP = 1: expected as default profile for local line. \
		  2: expected as default profile for network line.;
	   CAPABILITIES = ;"
	::= { mcm4400t1e1LineCfgEntry 2 }


--  the T1/E1 Profile Configuration Table 
--  (Standard/Operational Parameters)

--  This table provides the T1/E1 profile configuration parameters.
--  This table is used to configure a profile of T1/E1 line configuration
--  characteristics; of which, a subset may be used for a particular T1/E1
--  line (local or network) to define its configuration. (Operational)

mcm4400t1e1ProfCfgTable OBJECT-TYPE
	SYNTAX  SEQUENCE OF Mcm4400t1e1ProfCfgEntry
	ACCESS  not-accessible
	STATUS  mandatory
	DESCRIPTION
	  "NAME = ; 
	   DESC = The T1/E1 Profile Configuration table. \
		  (Operational);
	   HELP = ;
	   CAPABILITIES = NET_CFG, VPN_CFG;"
	::= { t1e1-r2-configuration 2 }

mcm4400t1e1ProfCfgEntry OBJECT-TYPE
	SYNTAX  Mcm4400t1e1ProfCfgEntry
	ACCESS  not-accessible
	STATUS  mandatory
	DESCRIPTION
	  "NAME = ; 
	   DESC = An entry in the T1/E1 Profile Configuration \
		  table. (Operational);
	   HELP = ;
	   CAPABILITIES = ;"
	INDEX   { mcm4400t1e1ProfCfgProfileNum }
	::= { mcm4400t1e1ProfCfgTable 1 }

Mcm4400t1e1ProfCfgEntry ::= SEQUENCE {
	mcm4400t1e1ProfCfgProfileNum		INTEGER,
	mcm4400t1e1ProfCfgT1FrameFmt		INTEGER,
	mcm4400t1e1ProfCfgT1LineCode		INTEGER,
	mcm4400t1e1ProfCfgE1LineCode		INTEGER,
	mcm4400t1e1ProfCfgIdleCode		INTEGER,
	mcm4400t1e1ProfCfgT1LineBuildOut	INTEGER,
	mcm4400t1e1ProfCfgT1Loopback		INTEGER,
	mcm4400t1e1ProfCfgE1CRC4		INTEGER,
	mcm4400t1e1ProfCfgE1TS16Conn		INTEGER
	}

mcm4400t1e1ProfCfgProfileNum OBJECT-TYPE
	SYNTAX	INTEGER (1..2)
	ACCESS  read-only
	STATUS  mandatory
	DESCRIPTION
	  "NAME = ;
	   DESC = The value of this object indicates the profile \
		  number.  Used as an index to the T1/E1 \
		  Profile Configuration table. (Operational);
	   HELP = ;
	   CAPABILITIES = ;"
	::= { mcm4400t1e1ProfCfgEntry 1 }

mcm4400t1e1ProfCfgT1FrameFmt OBJECT-TYPE
	SYNTAX	INTEGER {
		superFrame (1),
		extendedSuperFrame (2)
		}
	ACCESS  read-write
	STATUS  mandatory
	DESCRIPTION
	  "NAME = ;
	   DESC = The value of this object specifies the T1 \
		  frame format used in the line. (Operational);
	   HELP = ;
	   CAPABILITIES = ;"
	DEFVAL { superFrame }
	::= { mcm4400t1e1ProfCfgEntry 2 }

mcm4400t1e1ProfCfgT1LineCode OBJECT-TYPE
	SYNTAX	INTEGER {
		aMI (1),
		b8ZS (2)
		}
	ACCESS  read-write
	STATUS  mandatory
	DESCRIPTION
	  "NAME = ;
	   DESC = The value of this object specifies the T1 \
		  coding format used in the line. (Operational);
	   HELP = ;
	   CAPABILITIES = ;"
	DEFVAL { aMI }
	::= { mcm4400t1e1ProfCfgEntry 3 }

mcm4400t1e1ProfCfgE1LineCode OBJECT-TYPE
	SYNTAX	INTEGER {
		aMI (1),
		hDB3 (2)
		}
	ACCESS  read-write
	STATUS  mandatory
	DESCRIPTION
	  "NAME = ; 
	   DESC = The value of this object specifies the E1 \
		  coding format used in the line. (Operational);
	   HELP = ;
	   CAPABILITIES = ;"
	DEFVAL { aMI }
	::= { mcm4400t1e1ProfCfgEntry 4 }

mcm4400t1e1ProfCfgIdleCode OBJECT-TYPE
	SYNTAX	INTEGER (0..'ff'h)
	ACCESS  read-write
	STATUS  mandatory
	DESCRIPTION
	  "NAME = ; 
	   DESC = The value of this object specifies the code \
		  to be filled in the line when idle. (Operational);
	   HELP = ;
	   CAPABILITIES = ;"
	DEFVAL {'7f'h }
	::= { mcm4400t1e1ProfCfgEntry 5 }

mcm4400t1e1ProfCfgT1LineBuildOut OBJECT-TYPE
	SYNTAX	INTEGER {
		lessThan110Feet (1),
		lessThan220Feet (2),
		lessThan330Feet (3),
		lessThan440Feet (4),
		externalLBO (5),
		greaterThan665Feet (6),
		lessThan550Feet (7),
		lessThan660Feet (8)
		}
	ACCESS  read-write
	STATUS  mandatory
	DESCRIPTION
	  "NAME = ;
	   DESC = The value of this object specifies the cable \
		  length attached to a local T1 line. (Operational);
	   HELP = ;
	   CAPABILITIES = ;"
	DEFVAL { lessThan110Feet }
	::= { mcm4400t1e1ProfCfgEntry 6 }

mcm4400t1e1ProfCfgT1Loopback OBJECT-TYPE
	SYNTAX	INTEGER {
		disable (1),
		enable (2)
		}
	ACCESS  read-write
	STATUS  mandatory
	DESCRIPTION
	  "NAME = ;
	   DESC = The value of this object specifies whether \
		  to enable or disable the T1 line loopback \
		  to be invoked. (Operational);
	   HELP = 1: expected as default for a local T1 line profile. \
		  2: expected as default for a network T1 line profile.;
	   CAPABILITIES = ;"
	::= { mcm4400t1e1ProfCfgEntry 7 }

mcm4400t1e1ProfCfgE1CRC4 OBJECT-TYPE
	SYNTAX	INTEGER {
		disable (1),
		enable (2)
		}
	ACCESS  read-write
	STATUS  mandatory
	DESCRIPTION
	  "NAME = ;
	   DESC = The value of this object specifies whether \
		  to enable or disable a T1 line CRC4. (Operational);
	   HELP = ;
	   CAPABILITIES = ;"
	DEFVAL { disable }
	::= { mcm4400t1e1ProfCfgEntry 8 }

mcm4400t1e1ProfCfgE1TS16Conn OBJECT-TYPE
	SYNTAX	INTEGER {
		toCAS (1),
		idle (2),
		bypass (3),
		toDataPort1 (4),
		toDataPort2 (5)
		}
	ACCESS  read-write
	STATUS  mandatory
	DESCRIPTION
	  "NAME = ;
	   DESC = The value of this object specifies where the \
		  TS16 goes (for a T1 line). (Operational);
	   HELP = ;
	   CAPABILITIES = ;"
	DEFVAL { toCAS }
	::= { mcm4400t1e1ProfCfgEntry 9 }


--  the T1/E1 DS0 Channel Connection Configuration Table 
--  (Standard/Operational Parameters)

--  This table provides the T1/E1 DS0 channel connection configuration 
--  parameters. (Operational)

mcm4400t1e1DS0ChConnTable OBJECT-TYPE
	SYNTAX  SEQUENCE OF Mcm4400t1e1DS0ChConnEntry
	ACCESS  not-accessible
	STATUS  mandatory
	DESCRIPTION
	  "NAME = ; 
	   DESC = The T1/E1 DS0 Channel Connection \
		  Configuration table.(Operational);
	   HELP = ;
	   CAPABILITIES = NET_CFG, VPN_CFG;"
	::= { t1e1-r2-configuration 3 }

mcm4400t1e1DS0ChConnEntry OBJECT-TYPE
	SYNTAX  Mcm4400t1e1DS0ChConnEntry
	ACCESS  not-accessible
	STATUS  mandatory
	DESCRIPTION
	  "NAME = ; 
	   DESC = An entry in the T1/E1 DS0 Channel \
		  Connection Configuration table. (Operational);
	   HELP = ;
	   CAPABILITIES = ;"
	INDEX   { mcm4400t1e1DS0ChConnLineID,
		mcm4400t1e1DS0ChConnDS0Index }
	::= { mcm4400t1e1DS0ChConnTable 1 }

Mcm4400t1e1DS0ChConnEntry ::= SEQUENCE {
	mcm4400t1e1DS0ChConnLineID		INTEGER,
	mcm4400t1e1DS0ChConnDS0Index		INTEGER,
	mcm4400t1e1DS0ChConnState		INTEGER
	}

mcm4400t1e1DS0ChConnLineID OBJECT-TYPE
	SYNTAX	INTEGER {
		local (1),
		network (2)
		}
	ACCESS  read-only
	STATUS  mandatory
	DESCRIPTION
	  "NAME = ;
	   DESC = The T1/E1 line identification specifies which line \
		  is to be configured.  Used as an index to the \
		  T1/E1 DS0 Channel Connection Configuration \
		  table. (Operational);
	   HELP = ;
	   CAPABILITIES = ;"
	::= { mcm4400t1e1DS0ChConnEntry 1 }

mcm4400t1e1DS0ChConnDS0Index OBJECT-TYPE
	SYNTAX	INTEGER (1..30)
	ACCESS  read-only
	STATUS  mandatory
	DESCRIPTION
	  "NAME = ; 
	   DESC = The T1/E1 DS0 index specifies which time slot \
		  is to be connected.  Used as an index to the \
		  T1/E1 DS0 Channel Connection Configuration \
		  table. (Operational);
	   HELP = For T1, 24 is the maximum.  An error will be \
		  returned for a T1 DS0 index greater than 24.;
	   CAPABILITIES = ;"
	::= { mcm4400t1e1DS0ChConnEntry 2 }

mcm4400t1e1DS0ChConnState OBJECT-TYPE
	SYNTAX	INTEGER {
		idle (1),
		bypassVoice (2),
		bypassData (3),
		toWANPort1 (4),
		toWANPort2 (5),
		toDataPort1 (6),
		toDataPort2 (7),
		toDVMChannelB1 (8),
		toDVMChannelB2 (9),
		toDVMChannelB3 (10),
		toDVMChannelB4 (11),
		toDVMChannelB5 (12),
		toDVMChannelB6 (13),
		toDVMChannelC1 (14),
		toDVMChannelC2 (15),
		toDVMChannelC3 (16),
		toDVMChannelC4 (17),
		toDVMChannelC5 (18),
		toDVMChannelC6 (19),
		toDVMChannelC7 (20),
		toDVMChannelC8 (21),
		toDVMChannelC9 (22),
		toDVMChannelC10 (23),
		toDVMChannelC11 (24),
		toDVMChannelC12 (25),
		toDVMChannelD1 (26),
		toDVMChannelD2 (27),
		toDVMChannelD3 (28),
		toDVMChannelD4 (29),
		toDVMChannelD5 (30),
		toDVMChannelD6 (31),
		toDVMChannelD7 (32),
		toDVMChannelD8 (33),
		toDVMChannelD9 (34),
		toDVMChannelD10 (35),
		toDVMChannelD11 (36),
		toDVMChannelD12 (37)
		}
	ACCESS  read-write
	STATUS  mandatory
	DESCRIPTION
	  "NAME = ; 
	   DESC = The value of this object specifies where the \
		  T1/E1 line channel slot (DS0) is to be connected \
		  to. (Operational);
	   HELP = Note 1: if 2-37 is selected, the previous setting \
		  must be idle, or an error will be returned. \
		  Note 2: if idle is specified and the previous setting \
		  was bypass (voice or data), the corresponding DS0 \
		  in the other line will also be set to idle automatically. \
		  Note 3: if bypass (voice or data) is specified, the \
		  corresponding DS0 in the other line will also be \
		  set to the same bypass mode automatically.;
	   CAPABILITIES = ;"
	::= { mcm4400t1e1DS0ChConnEntry 3 }


--  *** The functional use of the following table may be implemented in a ***
--  *** future NMS implementation.  At this time, the following table has ***
--  *** been commented out of this MIB file implementation.               ***

--  the T1/E1 Group DS0 Connection Configuration Table 
--  (Standard/Operational Parameters)  

--  This table provides the T1/E1 group DS0 connection configuration 
--  parameters. (Operational)  Note that no parallel "nvm" table exists in this 
--  MIB file.

-- mcm4400t1e1GpDS0ConnTable OBJECT-TYPE
--	SYNTAX  SEQUENCE OF Mcm4400t1e1GpDS0ConnEntry
--	ACCESS  not-accessible
--	STATUS  mandatory
--	DESCRIPTION
--	  "NAME = ; 
--	   DESC = The T1/E1 Group DS0 Connection \
--		  Configuration table.(Operational);
--	   HELP = ;
--	   CAPABILITIES = NET_CFG, VPN_CFG;"
--	::= { t1e1-r2-configuration n }

-- mcm4400t1e1GpDS0ConnEntry OBJECT-TYPE
--	SYNTAX  Mcm4400t1e1GpDS0ConnEntry
--	ACCESS  not-accessible
--	STATUS  mandatory
--	DESCRIPTION
--	  "NAME = ; 
--	   DESC = An entry in the T1/E1 Group DS0 \
--		  Connection Configuration table. (Operational);
--	   HELP = ;
--	   CAPABILITIES = ;"
--	INDEX   { mcm4400t1e1GpDS0ConnLineID,
--		mcm4400t1e1GpDS0ConnFromDS0,
--		mcm4400t1e1GpDS0ConnToDS0 }
--	::= { mcm4400t1e1GpDS0ConnTable 1 }

-- Mcm4400t1e1GpDS0ConnEntry ::= SEQUENCE {
--	mcm4400t1e1GpDS0ConnLineID		INTEGER,
--	mcm4400t1e1GpDS0ConnFromDS0		INTEGER,
--	mcm4400t1e1GpDS0ConnToDS0		INTEGER,
--	mcm4400t1e1GpDS0ConnState		INTEGER
--	}

-- mcm4400t1e1GpDS0ConnLineID OBJECT-TYPE
--	SYNTAX	INTEGER {
--		local (1),
--		network (2)
--		}
--	ACCESS  read-only
--	STATUS  mandatory
--	DESCRIPTION
--	  "NAME = ;
--	   DESC = The T1/E1 line identification specifies which line \
--		  is to be configured.  Used as an index to the \
--		  T1/E1 Group DS0 Connection Configuration \
--		  table. (Operational);
--	   HELP = ;
--	   CAPABILITIES = ;"
--	::= { mcm4400t1e1GpDS0ConnEntry 1 }

-- mcm4400t1e1GpDS0ConnFromDS0 OBJECT-TYPE
--	SYNTAX	INTEGER (1..30)
--	ACCESS  read-only
--	STATUS  mandatory
--	DESCRIPTION
--	  "NAME = ; 
--	   DESC = The T1/E1 FromDS0 object specifies the 1st time \
--		  slot of the DS0 group to be connected.  Used as an \
--		  index to the T1/E1 Group DS0 Connection \
--		  Configuration table. (Operational);
--	   HELP = For T1, 24 is the maximum.  An error will be \
--		  returned for a T1 DS0 index greater than 24.;
--	   CAPABILITIES = ;"
--	::= { mcm4400t1e1GpDS0ConnEntry 2 }

-- mcm4400t1e1GpDS0ConnToDS0 OBJECT-TYPE
--	SYNTAX	INTEGER (1..30)
--	ACCESS  read-only
--	STATUS  mandatory
--	DESCRIPTION
--	  "NAME = ; 
--	   DESC = The T1/E1 ToDS0 object specifies the last time \
--		  slot of the DS0 group to be connected.  Used as an \
--		  index to the T1/E1 Group DS0 Connection \
--		  Configuration table. (Operational);
--	   HELP = For T1, 24 is the maximum.  An error will be \
--		  returned for a T1 DS0 index greater than 24.;
--	   CAPABILITIES = ;"
--	::= { mcm4400t1e1GpDS0ConnEntry 3 }

-- mcm4400t1e1GpDS0ConnState OBJECT-TYPE
--	SYNTAX	INTEGER {
--		idle (1),
--		bypassVoice (2),
--		bypassData (3),
--		to4400PrimaryLink (4),
--		to4400BackupLink (5),
--		toDataPort1 (6),
--		toDataPort2 (7),
--		toDVMChannelB1 (8),
--		toDVMChannelB2 (9),
--		toDVMChannelB3 (10),
--		toDVMChannelB4 (11),
--		toDVMChannelB5 (12),
--		toDVMChannelB6 (13),
--		toDVMChannelC1 (14),
--		toDVMChannelC2 (15),
--		toDVMChannelC3 (16),
--		toDVMChannelC4 (17),
--		toDVMChannelC5 (18),
--		toDVMChannelC6 (19),
--		toDVMChannelC7 (20),
--		toDVMChannelC8 (21),
--		toDVMChannelC9 (22),
--		toDVMChannelC10 (23),
--		toDVMChannelC11 (24),
--		toDVMChannelC12 (25),
--		toDVMChannelD1 (26),
--		toDVMChannelD2 (27),
--		toDVMChannelD3 (28),
--		toDVMChannelD4 (29),
--		toDVMChannelD5 (30),
--		toDVMChannelD6 (31),
--		toDVMChannelD7 (32),
--		toDVMChannelD8 (33),
--		toDVMChannelD9 (34),
--		toDVMChannelD10 (35),
--		toDVMChannelD11 (36),
--		toDVMChannelD12 (37)
--		}
--	ACCESS  write-only
--	STATUS  mandatory
--	DESCRIPTION
--	  "NAME = ; 
--	   DESC = The value of this object specifies how the \
--		  T1/E1 group of DS0s are to be connected. \
--		  (Operational);
--	   HELP = 1: all assigned to idle. \
--		  2: all assigned to bypass voice. \
--		  3: all assigned to bypass data. \
--		  4: all assigned to WAN Port 1. \
--		  5: all assigned to WAN Port 2. \
--		  6: all assigned to Data Port 1 (8 DS0s maximum). \
--		  7: all assigned to Data Port 2 (8 DS0s maximum). \
--		  8-37: each DS0 is, in sequence, assigned to \
--		  the next available device.  If no device \
--		  available, it is ignored.;
--	   CAPABILITIES = ;"
--	::= { mcm4400t1e1GpDS0ConnEntry 4 }


--  the T1/E1 Data Port Configuration Table 
--  (Standard/Operational Parameters)

--  This table provides the T1/E1 data port configuration parameters.
--  (Operational)

mcm4400t1e1DPCfgTable OBJECT-TYPE
	SYNTAX  SEQUENCE OF Mcm4400t1e1DPCfgEntry
	ACCESS  not-accessible
	STATUS  mandatory
	DESCRIPTION
	  "NAME = ; 
	   DESC = The T1/E1 Data Port Configuration table. \
		  (Operational);
	   HELP = ;
	   CAPABILITIES = NET_CFG, VPN_CFG;"
	::= { t1e1-r2-configuration 4 }

mcm4400t1e1DPCfgEntry OBJECT-TYPE
	SYNTAX  Mcm4400t1e1DPCfgEntry
	ACCESS  not-accessible
	STATUS  mandatory
	DESCRIPTION
	  "NAME = ; 
	   DESC = An entry in the T1/E1 Data Port \
		  Configuration table. (Operational);
	   HELP = ;
	   CAPABILITIES = ;"
	INDEX   { mcm4400t1e1DPCfgPortNum }
	::= { mcm4400t1e1DPCfgTable 1 }

Mcm4400t1e1DPCfgEntry ::= SEQUENCE {
	mcm4400t1e1DPCfgPortNum			INTEGER,
	mcm4400t1e1DPCfgDataRate		INTEGER,
	mcm4400t1e1DPCfgClock			INTEGER,
	mcm4400t1e1DPCfgDTRCntl			INTEGER,
	mcm4400t1e1DPCfgRTSCntl			INTEGER
	}

mcm4400t1e1DPCfgPortNum OBJECT-TYPE
	SYNTAX	INTEGER {
		port1 (1),
		port2 (2)
		}
	ACCESS  read-only
	STATUS  mandatory
	DESCRIPTION
	  "NAME = ;
	   DESC = The T1/E1 port number specifies which data port \
		  is to be configured.  Used as an index to the \
		  T1/E1 Data Port Configuration table. (Operational);
	   HELP = ;
	   CAPABILITIES = ;"
	::= { mcm4400t1e1DPCfgEntry 1 }

mcm4400t1e1DPCfgDataRate OBJECT-TYPE
	SYNTAX	INTEGER {
		rate64kbps (1),
		rate56kbps (2)
		}
	ACCESS  read-write
	STATUS  mandatory
	DESCRIPTION
	  "NAME = ; 
	   DESC = The value of this object selects the baud rate \
		  for the specified data port. (Operational);
	   HELP = ;
	   CAPABILITIES = ;"
	DEFVAL { rate64kbps }
	::= { mcm4400t1e1DPCfgEntry 2 }

mcm4400t1e1DPCfgClock OBJECT-TYPE
	SYNTAX	INTEGER {
		internalClock (1),
		tailCircuit (2)
		}
	ACCESS  read-write
	STATUS  mandatory
	DESCRIPTION
	  "NAME = ; 
	   DESC = The value of this object selects the clock \
		  source for the specified data port. \
		  (Operational);
	   HELP = ;
	   CAPABILITIES = ;"
	DEFVAL { internalClock }
	::= { mcm4400t1e1DPCfgEntry 3 }

mcm4400t1e1DPCfgDTRCntl OBJECT-TYPE
	SYNTAX	INTEGER {
		normal (1),
		forcedOn (2)
		}
	ACCESS  read-write
	STATUS  mandatory
	DESCRIPTION
	  "NAME = ; 
	   DESC = The value of this object selects the DTR \
		  control for the specified data port. \
		  (Operational);
	   HELP = ;
	   CAPABILITIES = ;"
	DEFVAL { normal }
	::= { mcm4400t1e1DPCfgEntry 4 }

mcm4400t1e1DPCfgRTSCntl OBJECT-TYPE
	SYNTAX	INTEGER {
		normal (1),
		forcedOn (2)
		}
	ACCESS  read-write
	STATUS  mandatory
	DESCRIPTION
	  "NAME = ; 
	   DESC = The value of this object selects the RTS \
		  control for the specified data port. \
		  (Operational);
	   HELP = ;
	   CAPABILITIES = ;"
	DEFVAL { normal }
	::= { mcm4400t1e1DPCfgEntry 5 }


--  the T1/E1 System Configuration Group/Object 
--  (Standard/Operational Parameter)

--  This 'group' provides the T1/E1 system configuration parameter.
--  (Operational)

mcm4400t1e1SysCfgClockSource OBJECT-TYPE
	SYNTAX	INTEGER {
		networkLineExternal (1),
		localLineExternal (2),
		internal (3)
		}
	ACCESS  read-write
	STATUS  mandatory
	DESCRIPTION
	  "NAME = ; 
	   DESC = The value of this object specifies where the \
		  system clock comes from. (Operational);
	   HELP = ;
	   CAPABILITIES = NET_CFG, VPN_CFG;"
	DEFVAL { networkLineExternal }
	::= { t1e1-r2-configuration 5 }



--  "Parallel" Configuration Parameter ("nvm") Groups/Tables


--  the T1/E1 Line Configuration Table 
--  (Configuration Parameters)

--  This table provides the T1/E1 line configuration parameters
--  for identifying a T1/E1 line with its corresponding profile. (Configuration)

nvm4400t1e1LineCfgTable OBJECT-TYPE
	SYNTAX  SEQUENCE OF Nvm4400t1e1LineCfgEntry
	ACCESS  not-accessible
	STATUS  mandatory
	DESCRIPTION
	  "NAME = ; 
	   DESC = The T1/E1 Line Configuration table. \
		  (Configuration);
	   HELP = ;
	   CAPABILITIES = NET_CFG, VPN_CFG;"
	::= { t1e1-r2-configuration 6 }

nvm4400t1e1LineCfgEntry OBJECT-TYPE
	SYNTAX  Nvm4400t1e1LineCfgEntry
	ACCESS  not-accessible
	STATUS  mandatory
	DESCRIPTION
	  "NAME = ; 
	   DESC = An entry in the T1/E1 Line Configuration \
		  table. (Configuration);
	   HELP = ;
	   CAPABILITIES = ;"
	INDEX   { nvm4400t1e1LineCfgLineID }
	::= { nvm4400t1e1LineCfgTable 1 }

Nvm4400t1e1LineCfgEntry ::= SEQUENCE {
	nvm4400t1e1LineCfgLineID		INTEGER,
	nvm4400t1e1LineCfgProfileNum		INTEGER
	}

nvm4400t1e1LineCfgLineID OBJECT-TYPE
	SYNTAX	INTEGER {
		local (1),
		network (2)
		}
	ACCESS  read-only
	STATUS  mandatory
	DESCRIPTION
	  "NAME = ;
	   DESC = The T1/E1 line identification specifies which line \
		  is to be configured.  Used as the index to the \
		  T1/E1 Line Configuration table. (Configuration);
	   HELP = ;
	   CAPABILITIES = ;"
	::= { nvm4400t1e1LineCfgEntry 1 }

nvm4400t1e1LineCfgProfileNum OBJECT-TYPE
	SYNTAX	INTEGER (1..2)
	ACCESS  read-only
	STATUS  mandatory
	DESCRIPTION
	  "NAME = ; 
	   DESC = The value of this object indicates the profile \
		  to be used to configure the specified T1/E1 \
		  line. (Configuration);
	   HELP = 1: expected as default profile for local line. \
		  2: expected as default profile for network line.;
	   CAPABILITIES = ;"
	::= { nvm4400t1e1LineCfgEntry 2 }


--  the T1/E1 Profile Configuration Table 
--  (Configuration Parameters)

--  This table provides the T1/E1 profile configuration parameters.
--  This table is used to view a profile of T1/E1 line configuration
--  characteristics; of which, a subset may be used for a particular T1/E1
--  line (local or network) to define its configuration. (Configuration)

nvm4400t1e1ProfCfgTable OBJECT-TYPE
	SYNTAX  SEQUENCE OF Nvm4400t1e1ProfCfgEntry
	ACCESS  not-accessible
	STATUS  mandatory
	DESCRIPTION
	  "NAME = ; 
	   DESC = The T1/E1 Profile Configuration table. \
		  (Configuration);
	   HELP = ;
	   CAPABILITIES = NET_CFG, VPN_CFG;"
	::= { t1e1-r2-configuration 7 }

nvm4400t1e1ProfCfgEntry OBJECT-TYPE
	SYNTAX  Nvm4400t1e1ProfCfgEntry
	ACCESS  not-accessible
	STATUS  mandatory
	DESCRIPTION
	  "NAME = ; 
	   DESC = An entry in the T1/E1 Profile Configuration \
		  table. (Configuration);
	   HELP = ;
	   CAPABILITIES = ;"
	INDEX   { nvm4400t1e1ProfCfgProfileNum }
	::= { nvm4400t1e1ProfCfgTable 1 }

Nvm4400t1e1ProfCfgEntry ::= SEQUENCE {
	nvm4400t1e1ProfCfgProfileNum		INTEGER,
	nvm4400t1e1ProfCfgT1FrameFmt		INTEGER,
	nvm4400t1e1ProfCfgT1LineCode		INTEGER,
	nvm4400t1e1ProfCfgE1LineCode		INTEGER,
	nvm4400t1e1ProfCfgIdleCode		INTEGER,
	nvm4400t1e1ProfCfgT1LineBuildOut	INTEGER,
	nvm4400t1e1ProfCfgT1Loopback		INTEGER,
	nvm4400t1e1ProfCfgE1CRC4		INTEGER,
	nvm4400t1e1ProfCfgE1TS16Conn		INTEGER
	}

nvm4400t1e1ProfCfgProfileNum OBJECT-TYPE
	SYNTAX	INTEGER (1..2)
	ACCESS  read-only
	STATUS  mandatory
	DESCRIPTION
	  "NAME = ;
	   DESC = The value of this object indicates the profile \
		  number.  Used as an index to the T1/E1 \
		  Profile Configuration table. (Configuration);
	   HELP = ;
	   CAPABILITIES = ;"
	::= { nvm4400t1e1ProfCfgEntry 1 }

nvm4400t1e1ProfCfgT1FrameFmt OBJECT-TYPE
	SYNTAX	INTEGER {
		superFrame (1),
		extendedSuperFrame (2)
		}
	ACCESS  read-only
	STATUS  mandatory
	DESCRIPTION
	  "NAME = ;
	   DESC = The value of this object specifies the T1 \
		  frame format used in the line. (Configuration);
	   HELP = ;
	   CAPABILITIES = ;"
	DEFVAL { superFrame }
	::= { nvm4400t1e1ProfCfgEntry 2 }

nvm4400t1e1ProfCfgT1LineCode OBJECT-TYPE
	SYNTAX	INTEGER {
		aMI (1),
		b8ZS (2)
		}
	ACCESS  read-only
	STATUS  mandatory
	DESCRIPTION
	  "NAME = ;
	   DESC = The value of this object specifies the T1 \
		  coding format used in the line. (Configuration);
	   HELP = ;
	   CAPABILITIES = ;"
	DEFVAL { aMI }
	::= { nvm4400t1e1ProfCfgEntry 3 }

nvm4400t1e1ProfCfgE1LineCode OBJECT-TYPE
	SYNTAX	INTEGER {
		aMI (1),
		hDB3 (2)
		}
	ACCESS  read-only
	STATUS  mandatory
	DESCRIPTION
	  "NAME = ; 
	   DESC = The value of this object specifies the E1 \
		  coding format used in the line. (Configuration);
	   HELP = ;
	   CAPABILITIES = ;"
	DEFVAL { aMI }
	::= { nvm4400t1e1ProfCfgEntry 4 }

nvm4400t1e1ProfCfgIdleCode OBJECT-TYPE
	SYNTAX	INTEGER (0..'ff'h)
	ACCESS  read-only
	STATUS  mandatory
	DESCRIPTION
	  "NAME = ; 
	   DESC = The value of this object specifies the code \
		  to be filled in the line when idle. (Configuration);
	   HELP = ;
	   CAPABILITIES = ;"
	DEFVAL {'7f'h }
	::= { nvm4400t1e1ProfCfgEntry 5 }

nvm4400t1e1ProfCfgT1LineBuildOut OBJECT-TYPE
	SYNTAX	INTEGER {
		lessThan110Feet (1),
		lessThan220Feet (2),
		lessThan330Feet (3),
		lessThan440Feet (4),
		externalLBO (5),
		greaterThan665Feet (6),
		lessThan550Feet (7),
		lessThan660Feet (8)
		}
	ACCESS  read-only
	STATUS  mandatory
	DESCRIPTION
	  "NAME = ;
	   DESC = The value of this object specifies the cable \
		  length attached to a local T1 line. (Configuration);
	   HELP = ;
	   CAPABILITIES = ;"
	DEFVAL { lessThan110Feet }
	::= { nvm4400t1e1ProfCfgEntry 6 }

nvm4400t1e1ProfCfgT1Loopback OBJECT-TYPE
	SYNTAX	INTEGER {
		disable (1),
		enable (2)
		}
	ACCESS  read-only
	STATUS  mandatory
	DESCRIPTION
	  "NAME = ;
	   DESC = The value of this object specifies whether \
		  to enable or disable the T1 line loopback \
		  to be invoked. (Configuration);
	   HELP = 1: expected as default for a local T1 line profile. \
		  2: expected as default for a network T1 line profile.;
	   CAPABILITIES = ;"
	::= { nvm4400t1e1ProfCfgEntry 7 }

nvm4400t1e1ProfCfgE1CRC4 OBJECT-TYPE
	SYNTAX	INTEGER {
		disable (1),
		enable (2)
		}
	ACCESS  read-only
	STATUS  mandatory
	DESCRIPTION
	  "NAME = ;
	   DESC = The value of this object specifies whether \
		  to enable or disable a T1 line CRC4. (Configuration);
	   HELP = ;
	   CAPABILITIES = ;"
	DEFVAL { disable }
	::= { nvm4400t1e1ProfCfgEntry 8 }

nvm4400t1e1ProfCfgE1TS16Conn OBJECT-TYPE
	SYNTAX	INTEGER {
		toCAS (1),
		idle (2),
		bypass (3),
		toDataPort1 (4),
		toDataPort2 (5)
		}
	ACCESS  read-only
	STATUS  mandatory
	DESCRIPTION
	  "NAME = ;
	   DESC = The value of this object specifies where the \
		  TS16 goes (for a T1 line). (Configuration);
	   HELP = ;
	   CAPABILITIES = ;"
	DEFVAL { toCAS }
	::= { nvm4400t1e1ProfCfgEntry 9 }


--  the T1/E1 DS0 Channel Connection Configuration Table 
--  (Configuration Parameters)

--  This table provides the T1/E1 DS0 channel connection configuration 
--  parameters. (Configuration)

nvm4400t1e1DS0ChConnTable OBJECT-TYPE
	SYNTAX  SEQUENCE OF Nvm4400t1e1DS0ChConnEntry
	ACCESS  not-accessible
	STATUS  mandatory
	DESCRIPTION
	  "NAME = ; 
	   DESC = The T1/E1 DS0 Channel Connection \
		  Configuration table.(Configuration);
	   HELP = ;
	   CAPABILITIES = NET_CFG, VPN_CFG;"
	::= { t1e1-r2-configuration 8 }

nvm4400t1e1DS0ChConnEntry OBJECT-TYPE
	SYNTAX  Nvm4400t1e1DS0ChConnEntry
	ACCESS  not-accessible
	STATUS  mandatory
	DESCRIPTION
	  "NAME = ; 
	   DESC = An entry in the T1/E1 DS0 Channel \
		  Connection Configuration table. (Configuration);
	   HELP = ;
	   CAPABILITIES = ;"
	INDEX   { nvm4400t1e1DS0ChConnLineID,
nvm4400t1e1DS0ChConnDS0Index }
	::= { nvm4400t1e1DS0ChConnTable 1 }

Nvm4400t1e1DS0ChConnEntry ::= SEQUENCE {
	nvm4400t1e1DS0ChConnLineID		INTEGER,
	nvm4400t1e1DS0ChConnDS0Index		INTEGER,
	nvm4400t1e1DS0ChConnState		INTEGER
	}

nvm4400t1e1DS0ChConnLineID OBJECT-TYPE
	SYNTAX	INTEGER {
		local (1),
		network (2)
		}
	ACCESS  read-only
	STATUS  mandatory
	DESCRIPTION
	  "NAME = ;
	   DESC = The T1/E1 line identification specifies which line \
		  is to be configured.  Used as an index to the \
		  T1/E1 DS0 Channel Connection Configuration \
		  table. (Configuration);
	   HELP = ;
	   CAPABILITIES = ;"
	::= { nvm4400t1e1DS0ChConnEntry 1 }

nvm4400t1e1DS0ChConnDS0Index OBJECT-TYPE
	SYNTAX	INTEGER (1..30)
	ACCESS  read-only
	STATUS  mandatory
	DESCRIPTION
	  "NAME = ; 
	   DESC = The T1/E1 DS0 index specifies which time slot \
		  is to be connected.  Used as an index to the \
		  T1/E1 DS0 Channel Connection Configuration \
		  table. (Configuration);
	   HELP = For T1, 24 is the maximum.  An error will be \
		  returned for a T1 DS0 index greater than 24.;
	   CAPABILITIES = ;"
	::= { nvm4400t1e1DS0ChConnEntry 2 }

nvm4400t1e1DS0ChConnState OBJECT-TYPE
	SYNTAX	INTEGER {
		idle (1),
		bypassVoice (2),
		bypassData (3),
		toWANPort1 (4),
		toWANPort2 (5),
		toDataPort1 (6),
		toDataPort2 (7),
		toDVMChannelB1 (8),
		toDVMChannelB2 (9),
		toDVMChannelB3 (10),
		toDVMChannelB4 (11),
		toDVMChannelB5 (12),
		toDVMChannelB6 (13),
		toDVMChannelC1 (14),
		toDVMChannelC2 (15),
		toDVMChannelC3 (16),
		toDVMChannelC4 (17),
		toDVMChannelC5 (18),
		toDVMChannelC6 (19),
		toDVMChannelC7 (20),
		toDVMChannelC8 (21),
		toDVMChannelC9 (22),
		toDVMChannelC10 (23),
		toDVMChannelC11 (24),
		toDVMChannelC12 (25),
		toDVMChannelD1 (26),
		toDVMChannelD2 (27),
		toDVMChannelD3 (28),
		toDVMChannelD4 (29),
		toDVMChannelD5 (30),
		toDVMChannelD6 (31),
		toDVMChannelD7 (32),
		toDVMChannelD8 (33),
		toDVMChannelD9 (34),
		toDVMChannelD10 (35),
		toDVMChannelD11 (36),
		toDVMChannelD12 (37)
		}
	ACCESS  read-only
	STATUS  mandatory
	DESCRIPTION
	  "NAME = ; 
	   DESC = The value of this object specifies where the \
		  T1/E1 line channel slot (DS0) is to be connected \
		  to. (Configuration);
	   HELP = Note 1: if 2-37 is selected, the previous setting \
		  must be idle, or an error will be returned. \
		  Note 2: if idle is specified and the previous setting \
		  was bypass (voice or data), the corresponding DS0 \
		  in the other line will also be set to idle automatically. \
		  Note 3: if bypass (voice or data) is specified, the \
		  corresponding DS0 in the other line will also be \
		  set to the same bypass mode automatically.;
	   CAPABILITIES = ;"
	::= { nvm4400t1e1DS0ChConnEntry 3 }


--  the T1/E1 Data Port Configuration Table 
--  (Configuration Parameters)

--  This table provides the T1/E1 data port configuration parameters.
--  (Configuration)

nvm4400t1e1DPCfgTable OBJECT-TYPE
	SYNTAX  SEQUENCE OF Nvm4400t1e1DPCfgEntry
	ACCESS  not-accessible
	STATUS  mandatory
	DESCRIPTION
	  "NAME = ; 
	   DESC = The T1/E1 Data Port Configuration table. \
		  (Configuration);
	   HELP = ;
	   CAPABILITIES = NET_CFG, VPN_CFG;"
	::= { t1e1-r2-configuration 9 }

nvm4400t1e1DPCfgEntry OBJECT-TYPE
	SYNTAX  Nvm4400t1e1DPCfgEntry
	ACCESS  not-accessible
	STATUS  mandatory
	DESCRIPTION
	  "NAME = ; 
	   DESC = An entry in the T1/E1 Data Port \
		  Configuration table. (Configuration);
	   HELP = ;
	   CAPABILITIES = ;"
	INDEX   { nvm4400t1e1DPCfgPortNum }
	::= { nvm4400t1e1DPCfgTable 1 }

Nvm4400t1e1DPCfgEntry ::= SEQUENCE {
	nvm4400t1e1DPCfgPortNum			INTEGER,
	nvm4400t1e1DPCfgDataRate		INTEGER,
	nvm4400t1e1DPCfgClock			INTEGER,
	nvm4400t1e1DPCfgDTRCntl			INTEGER,
	nvm4400t1e1DPCfgRTSCntl			INTEGER
	}

nvm4400t1e1DPCfgPortNum OBJECT-TYPE
	SYNTAX	INTEGER {
		port1 (1),
		port2 (2)
		}
	ACCESS  read-only
	STATUS  mandatory
	DESCRIPTION
	  "NAME = ;
	   DESC = The T1/E1 port number specifies which data port \
		  is to be configured.  Used as an index to the \
		  T1/E1 Data Port Configuration table. (Configuration);
	   HELP = ;
	   CAPABILITIES = ;"
	::= { nvm4400t1e1DPCfgEntry 1 }

nvm4400t1e1DPCfgDataRate OBJECT-TYPE
	SYNTAX	INTEGER {
		rate64kbps (1),
		rate56kbps (2)
		}
	ACCESS  read-only
	STATUS  mandatory
	DESCRIPTION
	  "NAME = ; 
	   DESC = The value of this object selects the baud rate \
		  for the specified data port. (Configuration);
	   HELP = ;
	   CAPABILITIES = ;"
	DEFVAL { rate64kbps }
	::= { nvm4400t1e1DPCfgEntry 2 }

nvm4400t1e1DPCfgClock OBJECT-TYPE
	SYNTAX	INTEGER {
		internalClock (1),
		tailCircuit (2)
		}
	ACCESS  read-only
	STATUS  mandatory
	DESCRIPTION
	  "NAME = ; 
	   DESC = The value of this object selects the clock \
		  source for the specified data port. \
		  (Configuration);
	   HELP = ;
	   CAPABILITIES = ;"
	DEFVAL { internalClock }
	::= { nvm4400t1e1DPCfgEntry 3 }

nvm4400t1e1DPCfgDTRCntl OBJECT-TYPE
	SYNTAX	INTEGER {
		normal (1),
		forcedOn (2)
		}
	ACCESS  read-only
	STATUS  mandatory
	DESCRIPTION
	  "NAME = ; 
	   DESC = The value of this object selects the DTR \
		  control for the specified data port. \
		  (Configuration);
	   HELP = ;
	   CAPABILITIES = ;"
	DEFVAL { normal }
	::= { nvm4400t1e1DPCfgEntry 4 }

nvm4400t1e1DPCfgRTSCntl OBJECT-TYPE
	SYNTAX	INTEGER {
		normal (1),
		forcedOn (2)
		}
	ACCESS  read-only
	STATUS  mandatory
	DESCRIPTION
	  "NAME = ; 
	   DESC = The value of this object selects the RTS \
		  control for the specified data port. \
		  (Configuration);
	   HELP = ;
	   CAPABILITIES = ;"
	DEFVAL { normal }
	::= { nvm4400t1e1DPCfgEntry 5 }


--  the T1/E1 System Configuration Group/Object 
--  (Configuration Parameter)

--  This 'group' provides the T1/E1 system configuration parameter.
--  (Configuration)

nvm4400t1e1SysCfgClockSource OBJECT-TYPE
	SYNTAX	INTEGER {
		networkLineExternal (1),
		localLineExternal (2),
		internal (3)
		}
	ACCESS  read-only
	STATUS  mandatory
	DESCRIPTION
	  "NAME = ; 
	   DESC = The value of this object specifies where the \
		  system clock comes from. (Configuration);
	   HELP = ;
	   CAPABILITIES = NET_CFG, VPN_CFG;"
	DEFVAL { networkLineExternal }
	::= { t1e1-r2-configuration 10 }



-- *** STATUS groups/tables ***

--  Operational Parameter ("mcm") Groups/Tables (note: no parallel "nvm" objects
--  are defined for STATUS parameters.)


--  the T1/E1 Line Status Display Table 

--  This table provides the T1/E1 line status display parameters.

mcm4400t1e1LineStatusTable OBJECT-TYPE
	SYNTAX  SEQUENCE OF Mcm4400t1e1LineStatusEntry
	ACCESS  not-accessible
	STATUS  mandatory
	DESCRIPTION
	  "NAME = ; 
	   DESC = The T1/E1 Line Status Display table. \
	   HELP = ;
	   CAPABILITIES = NET_CFG, VPN_CFG;"
	::= { t1e1-r2-status 1 }

mcm4400t1e1LineStatusEntry OBJECT-TYPE
	SYNTAX  Mcm4400t1e1LineStatusEntry
	ACCESS  not-accessible
	STATUS  mandatory
	DESCRIPTION
	  "NAME = ; 
	   DESC = An entry in the T1/E1 Line Status Display \
		  table.;
	   HELP = ;
	   CAPABILITIES = ;"
	INDEX   { mcm4400t1e1LineStatusLineIndex }
	::= { mcm4400t1e1LineStatusTable 1 }

Mcm4400t1e1LineStatusEntry ::= SEQUENCE {
	mcm4400t1e1LineStatusLineIndex		INTEGER,
	mcm4400t1e1LineStatusInterface		INTEGER,
	mcm4400t1e1LineStatusImpedance		INTEGER,
	mcm4400t1e1LineStatusTestMode		INTEGER,
	mcm4400t1e1LineStatusTestingDS0Ch	INTEGER,
	mcm4400t1e1LineStatusAISAlarm		INTEGER,
	mcm4400t1e1LineStatusRedAlarm		INTEGER,
	mcm4400t1e1LineStatusYellowAlarm	INTEGER,
	mcm4400t1e1LineStatusTS16AIS		INTEGER,
	mcm4400t1e1LineStatusOOSMFAlarm		INTEGER,
	mcm4400t1e1LineStatusMFASAlarm		INTEGER,
	mcm4400t1e1LineStatusFASAlarm		INTEGER,
	mcm4400t1e1LineStatusOOCMFAlarm		INTEGER
	}

mcm4400t1e1LineStatusLineIndex OBJECT-TYPE
	SYNTAX	INTEGER {
		localLine (1),
		networkLine (2)
		}
	ACCESS  read-only
	STATUS  mandatory
	DESCRIPTION
	  "NAME = ;
	   DESC = The T1/E1 line index specifies which line is to \
		  be displayed.  Used as an index to the \
		  T1/E1 Line Status Display table.;
	   HELP = ;
	   CAPABILITIES = ;"
	::= { mcm4400t1e1LineStatusEntry 1 }

mcm4400t1e1LineStatusInterface OBJECT-TYPE
	SYNTAX	INTEGER {
		t1 (1),
		e1 (2)
		}
	ACCESS  read-only
	STATUS  mandatory
	DESCRIPTION
	  "NAME = ;
	   DESC = The value of this object indicates the interface \
		  type as either T1 or E1 for the \
		  T1/E1 Line Status Display table.;
	   HELP = ;
	   CAPABILITIES = ;"
	::= { mcm4400t1e1LineStatusEntry 2 }

mcm4400t1e1LineStatusImpedance OBJECT-TYPE
	SYNTAX	INTEGER {
		line120ohm (1),
		line75ohm (2) 
		}
	ACCESS  read-only
	STATUS  mandatory
	DESCRIPTION
	  "NAME = ; 
	   DESC = The value of this object indicates the impedance \
		  for the specified line.;
	   HELP = ;
	   CAPABILITIES = ;"
	::= { mcm4400t1e1LineStatusEntry 3 }

mcm4400t1e1LineStatusTestMode OBJECT-TYPE
	SYNTAX	INTEGER {
		none (1),
		inLineLoopback (2),
		inChannelLoopback (3),
		inChannelPatternTest (4) 
		}
	ACCESS  read-only
	STATUS  mandatory
	DESCRIPTION
	  "NAME = ; 
	   DESC = The value of this object indicates if the specified \
		  line is in a loopback test mode.;
	   HELP = ;
	   CAPABILITIES = ;"
	::= { mcm4400t1e1LineStatusEntry 4 }

mcm4400t1e1LineStatusTestingDS0Ch OBJECT-TYPE
	SYNTAX	INTEGER (0..30)
	ACCESS  read-only
	STATUS  mandatory
	DESCRIPTION
	  "NAME = ;
	   DESC = The value of this object indicates which DS0 \
		  channel is in channel loopback or channel pattern \
		  test mode now.;
	   HELP = 0: none.\
		  1-30: DS0 channel number.;
	   CAPABILITIES = ;"
	::= { mcm4400t1e1LineStatusEntry 5 }

mcm4400t1e1LineStatusAISAlarm OBJECT-TYPE
	SYNTAX	INTEGER {
		no (1),
		yes (2)
		}
	ACCESS  read-only
	STATUS  mandatory
	DESCRIPTION
	  "NAME = ; 
	   DESC = The value of this object indicates if the AIS \
		  (Alarm Indication Signal) alarm is preset for \
		  the specified line.;
	   HELP = ;
	   CAPABILITIES = ;"
	::= { mcm4400t1e1LineStatusEntry 6 }

mcm4400t1e1LineStatusRedAlarm OBJECT-TYPE
	SYNTAX	INTEGER {
		no (1),
		yes (2)
		}
	ACCESS  read-only
	STATUS  mandatory
	DESCRIPTION
	  "NAME = ; 
	   DESC = The value of this object indicates if the Red \
		  alarm is preset for the specified line.;
	   HELP = ;
	   CAPABILITIES = ;"
	::= { mcm4400t1e1LineStatusEntry 7 }

mcm4400t1e1LineStatusYellowAlarm OBJECT-TYPE
	SYNTAX	INTEGER {
		no (1),
		yes (2),
		notApplicable (3)
		}
	ACCESS  read-only
	STATUS  mandatory
	DESCRIPTION
	  "NAME = ; 
	   DESC = The value of this object indicates if the Yellow \
		  alarm is preset for the specified line.  (Not \
		  applicable in E1.) ;
	   HELP = ;
	   CAPABILITIES = ;"
	::= { mcm4400t1e1LineStatusEntry 8 }

mcm4400t1e1LineStatusTS16AIS OBJECT-TYPE
	SYNTAX	INTEGER {
		no (1),
		yes (2),
		notApplicable (3)
		}
	ACCESS  read-only
	STATUS  mandatory
	DESCRIPTION
	  "NAME = ; 
	   DESC = The value of this object indicates if the TS16 \
		  (Time Slot 16) AIS alarm is preset for the \
		  specified line.  (Not applicable in T1.) ;
	   HELP = ;
	   CAPABILITIES = ;"
	::= { mcm4400t1e1LineStatusEntry 9 }

mcm4400t1e1LineStatusOOSMFAlarm OBJECT-TYPE
	SYNTAX	INTEGER {
		no (1),
		yes (2),
		notApplicable (3)
		}
	ACCESS  read-only
	STATUS  mandatory
	DESCRIPTION
	  "NAME = ; 
	   DESC = The value of this object indicates if the \
		  OOSMF (Out Of Signal Multi-Frame) alarm \
		  is preset for the specified line.  (Not \
		  applicable in T1.) ;
	   HELP = ;
	   CAPABILITIES = ;"
	::= { mcm4400t1e1LineStatusEntry 10 }

mcm4400t1e1LineStatusMFASAlarm OBJECT-TYPE
	SYNTAX	INTEGER {
		no (1),
		yes (2),
		notApplicable (3)
		}
	ACCESS  read-only
	STATUS  mandatory
	DESCRIPTION
	  "NAME = ; 
	   DESC = The value of this object indicates if the \
		  MFAS (Multi-Frame Alignment Signal - \
		  Y bit) alarm is preset for the specified line. \
		  (Not applicable in T1.) ;
	   HELP = ;
	   CAPABILITIES = ;"
	::= { mcm4400t1e1LineStatusEntry 11 }

mcm4400t1e1LineStatusFASAlarm OBJECT-TYPE
	SYNTAX	INTEGER {
		no (1),
		yes (2),
		notApplicable (3)
		}
	ACCESS  read-only
	STATUS  mandatory
	DESCRIPTION
	  "NAME = ; 
	   DESC = The value of this object indicates if the \
		  FAS (Frame Alignment Signal - A bit) \
		  alarm is preset for the specified line. \
		  (Not applicable in T1.) ;
	   HELP = ;
	   CAPABILITIES = ;"
	::= { mcm4400t1e1LineStatusEntry 12 }

mcm4400t1e1LineStatusOOCMFAlarm OBJECT-TYPE
	SYNTAX	INTEGER {
		no (1),
		yes (2),
		notApplicable (3)
		}
	ACCESS  read-only
	STATUS  mandatory
	DESCRIPTION
	  "NAME = ; 
	   DESC = The value of this object indicates if the \
		  OOCMF (Out Of CRC Multi-Frame) \
		  alarm is preset for the specified line. \
		  (Not applicable in T1.) ;
	   HELP = ;
	   CAPABILITIES = ;"
	::= { mcm4400t1e1LineStatusEntry 13 }


--  the T1/E1 System Status Display Group 

--  This group provides the T1/E1 system status display parameters.

mcm4400t1e1SysStatusGroup  OBJECT IDENTIFIER  ::= { t1e1-r2-status 2 }

mcm4400t1e1SysStatusCardType OBJECT-TYPE
	SYNTAX	INTEGER {
		t1SingleLineAccessModule (1),
		t1DualLineAccessModule (2),
		e1SingleLineAccessModule (3),
		e1DualLineAccessModule (4)
		}
	ACCESS  read-only
	STATUS  mandatory
	DESCRIPTION
	  "NAME = ;
	   DESC = The value of this object indicates the T1/E1 \
		  card type.;
	   HELP = 1: TAM1 - network line only. \
		  2: TAM2 - both local and network lines. \
		  3: EAM1 - network line only. \
		  4: EAM2 - both local and network lines.;
	   CAPABILITIES = NET_CFG, VPN_CFG ;"
	::= { mcm4400t1e1SysStatusGroup 1 }

mcm4400t1e1SysStatusOperStatus OBJECT-TYPE
	SYNTAX	INTEGER {
		dead (1),
		aliveButNotReady (2),
		downloadFail (3),
		downloadInProgress (4),
		normal (5)
		}
	ACCESS  read-only
	STATUS  mandatory
	DESCRIPTION
	  "NAME = ;
	   DESC = The value of this object indicates the operation \
		  status of the T1/E1 control unit.;
	   HELP = ;
	   CAPABILITIES = NET_CFG, VPN_CFG ;"
	::= { mcm4400t1e1SysStatusGroup 2 }

mcm4400t1e1SysStatusLEDTest OBJECT-TYPE
	SYNTAX	INTEGER {
		no (1),
		yes (2) 
		}
	ACCESS  read-only
	STATUS  mandatory
	DESCRIPTION
	  "NAME = ; 
	   DESC = The value of this object specifies if the \
		  LED test is in progress.;
	   HELP = ;
	   CAPABILITIES = NET_CFG, VPN_CFG ;"
	::= { mcm4400t1e1SysStatusGroup 3 }

mcm4400t1e1SysStatusSelfTestResults OBJECT-TYPE
	SYNTAX	INTEGER {
		testPassed (1),
		testFailed (2) 
		}
	ACCESS  read-only
	STATUS  mandatory
	DESCRIPTION
	  "NAME = ; 
	   DESC = The value of this object specifies the \
		  results of the T1/E1 self test.;
	   HELP = ;
	   CAPABILITIES = NET_CFG, VPN_CFG ;"
	::= { mcm4400t1e1SysStatusGroup 4 }

mcm4400t1e1SysStatusFlashEPROMSt OBJECT-TYPE
	SYNTAX	INTEGER {
		valid (1),
		erased (2),
		invalidChecksum (3)
		}
	ACCESS  read-only
	STATUS  mandatory
	DESCRIPTION
	  "NAME = ; 
	   DESC = The value of this object specifies the current \
		  state of the flash EPROM in the T1/E1 \
		  access board.;
	   HELP = ;
	   CAPABILITIES = NET_CFG, VPN_CFG ;"
	::= { mcm4400t1e1SysStatusGroup 5 }

mcm4400t1e1SysStatusApplSwID OBJECT-TYPE
	SYNTAX	DisplayString (SIZE (0..15))
	ACCESS  read-only
	STATUS  mandatory
	DESCRIPTION
	  "NAME = ; 
	   DESC = The value of this object indicates the T1/E1 \
		  application software ID (Null terminated string).;
	   HELP = ;
	   CAPABILITIES = NET_CFG, VPN_CFG ;"
	::= { mcm4400t1e1SysStatusGroup 6 }

mcm4400t1e1SysStatusBootSwVer OBJECT-TYPE
	SYNTAX	DisplayString (SIZE (0..15))
	ACCESS  read-only
	STATUS  mandatory
	DESCRIPTION
	  "NAME = ; 
	   DESC = The value of this object indicates the T1/E1 \
		  software version (Null terminated string).;
	   HELP = ;
	   CAPABILITIES = NET_CFG, VPN_CFG ;"
	::= { mcm4400t1e1SysStatusGroup 7 }


--  the T1/E1 Data Port Status Display Table 

--  This table provides the T1/E1 data port status display parameters.

mcm4400t1e1DPStatusTable OBJECT-TYPE
	SYNTAX  SEQUENCE OF Mcm4400t1e1DPStatusEntry
	ACCESS  not-accessible
	STATUS  mandatory
	DESCRIPTION
	  "NAME = ; 
	   DESC = The T1/E1 Data Port Status Display table. \
	   HELP = ;
	   CAPABILITIES = NET_CFG, VPN_CFG;"
	::= { t1e1-r2-status 3 }

mcm4400t1e1DPStatusEntry OBJECT-TYPE
	SYNTAX  Mcm4400t1e1DPStatusEntry
	ACCESS  not-accessible
	STATUS  mandatory
	DESCRIPTION
	  "NAME = ; 
	   DESC = An entry in the T1/E1 Data Port Status \
		  Display table.;
	   HELP = ;
	   CAPABILITIES = ;"
	INDEX   { mcm4400t1e1DPStatusPortNumber }
	::= { mcm4400t1e1DPStatusTable 1 }

Mcm4400t1e1DPStatusEntry ::= SEQUENCE {
	mcm4400t1e1DPStatusPortNumber		INTEGER,
	mcm4400t1e1DPStatusDTRInputSt		INTEGER,
	mcm4400t1e1DPStatusRTSInputSt		INTEGER,
	mcm4400t1e1DPStatusDSROutputSt		INTEGER,
	mcm4400t1e1DPStatusDCDOutputSt		INTEGER,
	mcm4400t1e1DPStatusCTSOutputSt		INTEGER
	}

mcm4400t1e1DPStatusPortNumber OBJECT-TYPE
	SYNTAX	INTEGER {
		port1 (1),
		port2 (2)
		}
	ACCESS  read-only
	STATUS  mandatory
	DESCRIPTION
	  "NAME = ;
	   DESC = The value of this object specifies the data port \
		  number.  Used as the index to the T1/E1 \
		  Data Port Status Display table.;
	   HELP = ;
	   CAPABILITIES = ;"
	::= { mcm4400t1e1DPStatusEntry 1 }

mcm4400t1e1DPStatusDTRInputSt OBJECT-TYPE
	SYNTAX	INTEGER {
		off (1),
		on (2)
		}
	ACCESS  read-only
	STATUS  mandatory
	DESCRIPTION
	  "NAME = ;
	   DESC = The value of this object indicates the current \
		  DTR state for the specified data port.;
	   HELP = ;
	   CAPABILITIES = ;"
	::= { mcm4400t1e1DPStatusEntry 2 }

mcm4400t1e1DPStatusRTSInputSt OBJECT-TYPE
	SYNTAX	INTEGER {
		off (1),
		on (2)
		}
	ACCESS  read-only
	STATUS  mandatory
	DESCRIPTION
	  "NAME = ;
	   DESC = The value of this object indicates the current \
		  RTS state for the specified data port.;
	   HELP = ;
	   CAPABILITIES = ;"
	::= { mcm4400t1e1DPStatusEntry 3 }

mcm4400t1e1DPStatusDSROutputSt OBJECT-TYPE
	SYNTAX	INTEGER {
		off (1),
		on (2)
		}
	ACCESS  read-only
	STATUS  mandatory
	DESCRIPTION
	  "NAME = ;
	   DESC = The value of this object indicates the current \
		  DSR state for the specified data port.;
	   HELP = ;
	   CAPABILITIES = ;"
	::= { mcm4400t1e1DPStatusEntry 4 }

mcm4400t1e1DPStatusDCDOutputSt OBJECT-TYPE
	SYNTAX	INTEGER {
		off (1),
		on (2)
		}
	ACCESS  read-only
	STATUS  mandatory
	DESCRIPTION
	  "NAME = ;
	   DESC = The value of this object indicates the current \
		  DCD state for the specified data port.;
	   HELP = ;
	   CAPABILITIES = ;"
	::= { mcm4400t1e1DPStatusEntry 5 }

mcm4400t1e1DPStatusCTSOutputSt OBJECT-TYPE
	SYNTAX	INTEGER {
		off (1),
		on (2)
		}
	ACCESS  read-only
	STATUS  mandatory
	DESCRIPTION
	  "NAME = ;
	   DESC = The value of this object indicates the current \
		  CTS state for the specified data port.;
	   HELP = ;
	   CAPABILITIES = ;"
	::= { mcm4400t1e1DPStatusEntry 6 }


--  the T1/E1 DS0 Channel Signaling Display Table 

--  This table provides the T1/E1 DS0 channel signaling display parameters.

mcm4400t1e1DS0ChSigTable OBJECT-TYPE
	SYNTAX  SEQUENCE OF Mcm4400t1e1DS0ChSigEntry
	ACCESS  not-accessible
	STATUS  mandatory
	DESCRIPTION
	  "NAME = ; 
	   DESC = The T1/E1 DS0 Channel Signaling Display \
		  table. \
	   HELP = ;
	   CAPABILITIES = NET_CFG, VPN_CFG;"
	::= { t1e1-r2-status 4 }

mcm4400t1e1DS0ChSigEntry OBJECT-TYPE
	SYNTAX  Mcm4400t1e1DS0ChSigEntry
	ACCESS  not-accessible
	STATUS  mandatory
	DESCRIPTION
	  "NAME = ; 
	   DESC = An entry in the T1/E1 DS0 Channel \
		  Signaling Display table.;
	   HELP = ;
	   CAPABILITIES = ;"
	INDEX   { mcm4400t1e1DS0ChSigLineID,
		mcm4400t1e1DS0ChSigDS0Index }
	::= { mcm4400t1e1DS0ChSigTable 1 }

Mcm4400t1e1DS0ChSigEntry ::= SEQUENCE {
	mcm4400t1e1DS0ChSigLineID		INTEGER,
	mcm4400t1e1DS0ChSigDS0Index		INTEGER,
	mcm4400t1e1DS0ChSigInABCDBits		INTEGER,
	mcm4400t1e1DS0ChSigOutABCDBits		INTEGER
	}

mcm4400t1e1DS0ChSigLineID OBJECT-TYPE
	SYNTAX	INTEGER {
		local (1),
		network (2)
		}
	ACCESS  read-only
	STATUS  mandatory
	DESCRIPTION
	  "NAME = ;
	   DESC = The T1/E1 line ID specifies which line is to \
		  be displayed.  Used as an index to the \
		  T1/E1 DS0 Channel Signaling Display table.;
		  
	   HELP = ;
	   CAPABILITIES = ;"
	::= { mcm4400t1e1DS0ChSigEntry 1 }

mcm4400t1e1DS0ChSigDS0Index OBJECT-TYPE
	SYNTAX	INTEGER (1..30)
	ACCESS  read-only
	STATUS  mandatory
	DESCRIPTION
	  "NAME = ;
	   DESC = The DS0 Index specifies which time slot is \
		  to be displayed.  Used as an index to the \
		  T1/E1 DS0 Channel Signaling Display table.;
	   HELP = For T1, 24 is the maximum.  An error will be \
		  returned if a value greater than 24 is selected.;
	   CAPABILITIES = ;"
	::= { mcm4400t1e1DS0ChSigEntry 2 }

mcm4400t1e1DS0ChSigInABCDBits OBJECT-TYPE
	SYNTAX	INTEGER (0..16)
	ACCESS  read-only
	STATUS  mandatory
	DESCRIPTION
	  "NAME = ;
	   DESC = The value of this object indicates the input \
		  ABCD bit pattern.;
	   HELP = ;
	   CAPABILITIES = ;"
	::= { mcm4400t1e1DS0ChSigEntry 3 }

mcm4400t1e1DS0ChSigOutABCDBits OBJECT-TYPE
	SYNTAX	INTEGER (0..16)
	ACCESS  read-only
	STATUS  mandatory
	DESCRIPTION
	  "NAME = ;
	   DESC = The value of this object indicates the output \
		  ABCD bit pattern.;
	   HELP = ;
	   CAPABILITIES = ;"
	::= { mcm4400t1e1DS0ChSigEntry 4 }


--  the T1/E1 Channel Test Results Display Group 

--  This group provides the T1/E1 channel test results display 
--  parameters.

mcm4400t1e1ChTestResultsGroup  OBJECT IDENTIFIER  ::= { t1e1-r2-status 5 }

mcm4400t1e1ChTestResultsLineID OBJECT-TYPE
	SYNTAX	INTEGER {
		local (1),
		network (2),
		none (3)
		}
	ACCESS  read-only
	STATUS  mandatory
	DESCRIPTION
	  "NAME = ;
	   DESC = The line ID specifies which T1/E1 line has \
		  a DS0channel in test mode.;
	   HELP = 3 is returned if no DS0 channel is in test mode.;
	   CAPABILITIES = NET_CFG, VPN_CFG ;"
	::= { mcm4400t1e1ChTestResultsGroup 1 }

mcm4400t1e1ChTestResultsDS0Ch OBJECT-TYPE
	SYNTAX	INTEGER (0..30)
	ACCESS  read-only
	STATUS  mandatory
	DESCRIPTION
	  "NAME = ;
	   DESC = The value of this object specifies which DS0 \
		  channel is in test mode.;
	   HELP = For T1, 24 is the maximum.  Also, 0 will be \
		  returned if no DS0 channels are in test mode.;
	   CAPABILITIES = NET_CFG, VPN_CFG ;"
	::= { mcm4400t1e1ChTestResultsGroup 2 }

mcm4400t1e1ChTestResultsErrorCnt OBJECT-TYPE
	SYNTAX	Counter
	ACCESS  read-only
	STATUS  mandatory
	DESCRIPTION
	  "NAME = ;
	   DESC = The value of this object indicates the number \
		  of errors accumulated since the test had been \
		  started.;
	   HELP = An error can be detected only when in channel \
		  pattern test mode.  Channel loopback will always \
		  be 0.;
	   CAPABILITIES = NET_CFG, VPN_CFG ;"
	::= { mcm4400t1e1ChTestResultsGroup 3 }



-- *** STATISTICS groups/tables ***

--  Operational Parameter ("mcm") Groups/Tables (note: no parallel "nvm" objects
--  are defined for STATISTICS parameters.)


--  the T1/E1 Line Statistics Counters Display Table 

--  This table provides the T1/E1 line statistics counters display 
--  parameters.

mcm4400t1e1LineStatsTable OBJECT-TYPE
	SYNTAX  SEQUENCE OF Mcm4400t1e1LineStatsEntry
	ACCESS  not-accessible
	STATUS  mandatory
	DESCRIPTION
	  "NAME = ; 
	   DESC = The T1/E1 Line Statistics Display table. \
	   HELP = ;
	   CAPABILITIES = NET_CFG, VPN_CFG;"
	::= { t1e1-r2-statistics 1 }

mcm4400t1e1LineStatsEntry OBJECT-TYPE
	SYNTAX  Mcm4400t1e1LineStatsEntry
	ACCESS  not-accessible
	STATUS  mandatory
	DESCRIPTION
	  "NAME = ; 
	   DESC = An entry in the T1/E1 Line Statistics \
		  Display table.;
	   HELP = ;
	   CAPABILITIES = ;"
	INDEX   { mcm4400t1e1LineStatsLineIndex }
	::= { mcm4400t1e1LineStatsTable 1 }

Mcm4400t1e1LineStatsEntry ::= SEQUENCE {
	mcm4400t1e1LineStatsLineIndex		INTEGER,
	mcm4400t1e1LineStatsInterface		INTEGER,
	mcm4400t1e1LineStatsFramingBitError	Counter,
	mcm4400t1e1LineStatsLineCdViolation	Counter,
	mcm4400t1e1LineStatsFarEndBlkError	Counter,
	mcm4400t1e1LineStatsCRCError		Counter,
	mcm4400t1e1LineStatsBufferOverrun	Counter,
	mcm4400t1e1LineStatsBufferUnderrun	Counter,
	mcm4400t1e1LineStatsFrmSyncBitError	Counter,
	mcm4400t1e1LineStatsOutOfFrame		Counter,
	mcm4400t1e1LineStatsTotalFrameSlip	Counter
	}

mcm4400t1e1LineStatsLineIndex OBJECT-TYPE
	SYNTAX	INTEGER {
		localLine (1),
		networkLine (2)
		}
	ACCESS  read-only
	STATUS  mandatory
	DESCRIPTION
	  "NAME = ;
	   DESC = The T1/E1 line index specifies which line is to \
		  be displayed.  Used as an index to the \
		  T1/E1 Line Statistics Display table.;
	   HELP = ;
	   CAPABILITIES = ;"
	::= { mcm4400t1e1LineStatsEntry 1 }

mcm4400t1e1LineStatsInterface OBJECT-TYPE
	SYNTAX	INTEGER {
		t1 (1),
		e1 (2)
		}
	ACCESS  read-only
	STATUS  mandatory
	DESCRIPTION
	  "NAME = ;
	   DESC = The value of this object indicates the interface \
		  type as either T1 or E1 for the \
		  T1/E1 Line Statistics Display table.;
	   HELP = ;
	   CAPABILITIES = ;"
	::= { mcm4400t1e1LineStatsEntry 2 }

mcm4400t1e1LineStatsFramingBitError OBJECT-TYPE
	SYNTAX	Counter
	ACCESS  read-only
	STATUS  mandatory
	DESCRIPTION
	  "NAME = ;
	   DESC = The value of this object indicates the framing \
		  bit errors on the specified line.;
	   HELP = Valid for E1 only.  For T1, 0 will be returned.;
	   CAPABILITIES = ;"
	::= { mcm4400t1e1LineStatsEntry 3 }

mcm4400t1e1LineStatsLineCdViolation OBJECT-TYPE
	SYNTAX	Counter
	ACCESS  read-only
	STATUS  mandatory
	DESCRIPTION
	  "NAME = ;
	   DESC = The value of this object indicates the line \
		  code violations on the specified line.;
	   HELP = ;
	   CAPABILITIES = ;"
	::= { mcm4400t1e1LineStatsEntry 4 }

mcm4400t1e1LineStatsFarEndBlkError OBJECT-TYPE
	SYNTAX	Counter
	ACCESS  read-only
	STATUS  mandatory
	DESCRIPTION
	  "NAME = ;
	   DESC = The value of this object indicates the far \
		  end block errors on the specified line.;
	   HELP = Valid for E1 only.  For T1, 0 will be returned.;
	   CAPABILITIES = ;"
	::= { mcm4400t1e1LineStatsEntry 5 }

mcm4400t1e1LineStatsCRCError OBJECT-TYPE
	SYNTAX	Counter
	ACCESS  read-only
	STATUS  mandatory
	DESCRIPTION
	  "NAME = ;
	   DESC = The value of this object indicates the CRC \
		  errors on the specified line.;
	   HELP = Valid for E1 only.  For T1, 0 will be returned.;
	   CAPABILITIES = ;"
	::= { mcm4400t1e1LineStatsEntry 6 }

mcm4400t1e1LineStatsBufferOverrun OBJECT-TYPE
	SYNTAX	Counter
	ACCESS  read-only
	STATUS  mandatory
	DESCRIPTION
	  "NAME = ;
	   DESC = The value of this object indicates the \
		  buffer overruns on the specified line.;
	   HELP = Valid for E1 only.  For T1, 0 will be returned.;
	   CAPABILITIES = ;"
	::= { mcm4400t1e1LineStatsEntry 7 }

mcm4400t1e1LineStatsBufferUnderrun OBJECT-TYPE
	SYNTAX	Counter
	ACCESS  read-only
	STATUS  mandatory
	DESCRIPTION
	  "NAME = ;
	   DESC = The value of this object indicates the \
		  buffer underruns on the specified line.;
	   HELP = Valid for E1 only.  For T1, 0 will be returned.;
	   CAPABILITIES = ;"
	::= { mcm4400t1e1LineStatsEntry 8 }

mcm4400t1e1LineStatsFrmSyncBitError OBJECT-TYPE
	SYNTAX	Counter
	ACCESS  read-only
	STATUS  mandatory
	DESCRIPTION
	  "NAME = ;
	   DESC = The value of this object indicates the frame \
		  synchronization bit errors on the specified line.;
	   HELP = Valid for T1 only.  For E1, 0 will be returned.;
	   CAPABILITIES = ;"
	::= { mcm4400t1e1LineStatsEntry 9 }

mcm4400t1e1LineStatsOutOfFrame OBJECT-TYPE
	SYNTAX	Counter
	ACCESS  read-only
	STATUS  mandatory
	DESCRIPTION
	  "NAME = ;
	   DESC = The value of this object indicates the out of \
		  frame statistics on the specified line.;
	   HELP = Valid for T1 only.  For E1, 0 will be returned.;
	   CAPABILITIES = ;"
	::= { mcm4400t1e1LineStatsEntry 10 }

mcm4400t1e1LineStatsTotalFrameSlip OBJECT-TYPE
	SYNTAX	Counter
	ACCESS  read-only
	STATUS  mandatory
	DESCRIPTION
	  "NAME = ;
	   DESC = The value of this object indicates the total \
		  frame slips on the specified line.;
	   HELP = Valid for T1 only.  For E1, 0 will be returned.;
	   CAPABILITIES = ;"
	::= { mcm4400t1e1LineStatsEntry 11 }



-- *** CONTROL groups/tables ***

--  Operational Parameter ("mcm") Groups/Tables (note: no parallel "nvm" objects
--  are defined for CONTROL parameters.)


--  the T1/E1 DS0 Channel Test Command Table 

--  This table provides the T1/E1 DS0 channel test commands.

mcm4400t1e1DS0ChTestCmdTable OBJECT-TYPE
	SYNTAX  SEQUENCE OF Mcm4400t1e1DS0ChTestCmdEntry
	ACCESS  not-accessible
	STATUS  mandatory
	DESCRIPTION
	  "NAME = ; 
	   DESC = The T1/E1 DS0 Channel Test Command \
		  table. \
	   HELP = ;
	   CAPABILITIES = NET_OPER, VPN_OPER ;"
	::= { t1e1-r2-control 1 }

mcm4400t1e1DS0ChTestCmdEntry OBJECT-TYPE
	SYNTAX  Mcm4400t1e1DS0ChTestCmdEntry
	ACCESS  not-accessible
	STATUS  mandatory
	DESCRIPTION
	  "NAME = ; 
	   DESC = An entry in the T1/E1 DS0 Channel \
		  Test Command table.;
	   HELP = ;
	   CAPABILITIES = ;"
	INDEX   { mcm4400t1e1DS0ChTestCmdLineID,
		mcm4400t1e1DS0ChTestCmdDS0Index }
	::= { mcm4400t1e1DS0ChTestCmdTable 1 }

Mcm4400t1e1DS0ChTestCmdEntry ::= SEQUENCE {
	mcm4400t1e1DS0ChTestCmdLineID		INTEGER,
	mcm4400t1e1DS0ChTestCmdDS0Index		INTEGER,
	mcm4400t1e1DS0ChTestCmdTstPattern	INTEGER
	}

mcm4400t1e1DS0ChTestCmdLineID OBJECT-TYPE
	SYNTAX	INTEGER {
		local (1),
		network (2)
		}
	ACCESS  read-only
	STATUS  mandatory
	DESCRIPTION
	  "NAME = ;
	   DESC = The T1/E1 line ID specifies which line is to \
		  be tested.  Used as an index to the \
		  T1/E1 DS0 Channel Test Command table.;
	   HELP = ;
	   CAPABILITIES = ;"
	::= { mcm4400t1e1DS0ChTestCmdEntry 1 }

mcm4400t1e1DS0ChTestCmdDS0Index OBJECT-TYPE
	SYNTAX	INTEGER (1..30)
	ACCESS  read-only
	STATUS  mandatory
	DESCRIPTION
	  "NAME = ;
	   DESC = The DS0 Index specifies which time slot is \
		  to be tested.  Used as an index to the \
		  T1/E1 DS0 Channel Test Command table.;
	   HELP = For T1, 24 is the maximum.  An error will be \
		  returned if a value greater than 24 is selected.;
	   CAPABILITIES = ;"
	::= { mcm4400t1e1DS0ChTestCmdEntry 2 }

mcm4400t1e1DS0ChTestCmdTstPattern OBJECT-TYPE
	SYNTAX	INTEGER {
		qrss (1),
		tp511 (2),
		loop (3),
		fixed-E1Only (4)
		}
	ACCESS  write-only
	STATUS  mandatory
	DESCRIPTION
	  "NAME = ; 
	   DESC = Setting this object will initiate various \
		  test pattern testing on the specified T1/E1 \
		  DS0 channel.;
	   HELP = For QRSS, TP511, and Fixed, the T1/E1 \
		  access module will generate and verify the \
		  selected test pattern. \
		  For Loop test, it simply loops the input \
		  data back to the same DS0 channel. \
		  In T1, if 4 is specified, an error will be \
		  returned.;
	   CAPABILITIES = ;"
	::= { mcm4400t1e1DS0ChTestCmdEntry 3 }


--  the T1/E1 Line Test Command Table 

--  This table provides the T1/E1 line test commands.

mcm4400t1e1LineTestCmdTable OBJECT-TYPE
	SYNTAX  SEQUENCE OF Mcm4400t1e1LineTestCmdEntry
	ACCESS  not-accessible
	STATUS  mandatory
	DESCRIPTION
	  "NAME = ; 
	   DESC = The T1/E1 Line Test Command \
		  table. \
	   HELP = ;
	   CAPABILITIES = NET_OPER, VPN_OPER ;"
	::= { t1e1-r2-control 2 }

mcm4400t1e1LineTestCmdEntry OBJECT-TYPE
	SYNTAX  Mcm4400t1e1LineTestCmdEntry
	ACCESS  not-accessible
	STATUS  mandatory
	DESCRIPTION
	  "NAME = ; 
	   DESC = An entry in the T1/E1 Line Test \
		  Command table.;
	   HELP = ;
	   CAPABILITIES = ;"
	INDEX   { mcm4400t1e1LineTestCmdLineID }
	::= { mcm4400t1e1LineTestCmdTable 1 }

Mcm4400t1e1LineTestCmdEntry ::= SEQUENCE {
	mcm4400t1e1LineTestCmdLineID		INTEGER,
	mcm4400t1e1LineTestCmdTstPattern	INTEGER
	}

mcm4400t1e1LineTestCmdLineID OBJECT-TYPE
	SYNTAX	INTEGER {
		local (1),
		network (2)
		}
	ACCESS  read-only
	STATUS  mandatory
	DESCRIPTION
	  "NAME = ;
	   DESC = The T1/E1 line ID specifies which line is to \
		  be tested.  Used as the index to the \
		  T1/E1 Line Test Command table.;
	   HELP = ;
	   CAPABILITIES = ;"
	::= { mcm4400t1e1LineTestCmdEntry 1 }

mcm4400t1e1LineTestCmdTstPattern OBJECT-TYPE
	SYNTAX	INTEGER {
		externalLineLoopback (1),
		externalDigitalLoopback (2),
		internalLineLoopback (3),
		internalDigitalLoopback (4)
		}
	ACCESS  write-only
	STATUS  mandatory
	DESCRIPTION
	  "NAME = ; 
	   DESC = Setting this object will initiate various \
		  tests on the specified T1/E1 line.;
	   HELP = Line Loopback: receiver or transmitter is \
		  connected to transmitter or receiver; respectively. \
		  Digital Loopback: data is stripped off the \
		  DS0 channel and reinserted in the same channel. \
		  External: data coming from the line. \
		  Internal: data going to the line.;
	   CAPABILITIES = ;"
	::= { mcm4400t1e1LineTestCmdEntry 2 }


--  the T1/E1 Data Port Test Command Table 

--  This table provides the T1/E1 data port test commands.

mcm4400t1e1DPTestCmdTable OBJECT-TYPE
	SYNTAX  SEQUENCE OF Mcm4400t1e1DPTestCmdEntry
	ACCESS  not-accessible
	STATUS  mandatory
	DESCRIPTION
	  "NAME = ; 
	   DESC = The T1/E1 Data Port Test Command \
		  table. \
	   HELP = ;
	   CAPABILITIES = NET_OPER, VPN_OPER ;"
	::= { t1e1-r2-control 3 }

mcm4400t1e1DPTestCmdEntry OBJECT-TYPE
	SYNTAX  Mcm4400t1e1DPTestCmdEntry
	ACCESS  not-accessible
	STATUS  mandatory
	DESCRIPTION
	  "NAME = ; 
	   DESC = An entry in the T1/E1 Data Port \
		  Test Command table.;
	   HELP = ;
	   CAPABILITIES = ;"
	INDEX   { mcm4400t1e1DPTestCmdPortNum }
	::= { mcm4400t1e1DPTestCmdTable 1 }

Mcm4400t1e1DPTestCmdEntry ::= SEQUENCE {
	mcm4400t1e1DPTestCmdPortNum		INTEGER,
	mcm4400t1e1DPTestCmdTstPattern		INTEGER
	}

mcm4400t1e1DPTestCmdPortNum OBJECT-TYPE
	SYNTAX	INTEGER {
		dataPort1 (1),
		dataPort2 (2)
		}
	ACCESS  read-only
	STATUS  mandatory
	DESCRIPTION
	  "NAME = ;
	   DESC = The T1/E1 Port Number specifies which data \
		  port is to be tested.  Used as the index to the \
		  T1/E1 Data Port Test Command table.;
	   HELP = ;
	   CAPABILITIES = ;"
	::= { mcm4400t1e1DPTestCmdEntry 1 }

mcm4400t1e1DPTestCmdTstPattern OBJECT-TYPE
	SYNTAX	INTEGER {
		externalLoopback (1),
		internalLoopback (2)
		}
	ACCESS  write-only
	STATUS  mandatory
	DESCRIPTION
	  "NAME = ; 
	   DESC = Setting this object will initiate various \
		  tests on the specified T1/E1 data port.;
	   HELP = External: loop back data coming from the \
		  device attached to the port. \
		  Internal: loop back data coming from the  \
		  DS0 channel.;
	   CAPABILITIES = ;"
	::= { mcm4400t1e1DPTestCmdEntry 2 }


--  the T1/E1 System Control Action Command Group 

--  This object provides the T1/E1 system control/action commands.

mcm4400t1e1SysControlActionCmd OBJECT-TYPE
	SYNTAX	INTEGER {
		testLED (1),
		resetT1E1 (2),
		clearCounter (3),
		download (4),
		stopChannelTest (5),
		stopLineTest (6),
		stopPortTest (7),
		stopLEDTest (8),
		stopAllTests (9)
		}
	ACCESS  write-only
	STATUS  mandatory
	DESCRIPTION
	  "NAME = ; 
	   DESC = Setting this object will perform various \
		  actions on the T1/E1 system. \
		  Note: Starting with software release 3.0, \
		  the enumeration clearCounter (3) is \
		  not supported. The enumeration is included \
		  here only to support backwards compatibility \
		  for software versions prior to release 3.0.; 
	   HELP = 1: initiate LED test. \
		  2: reset T1/E1 module. \
		  3: clear statistics counters. \
		  4: download code. \
		  5: stop DS0 channel test. \
		  6: stop line test. \
		  7: stop port test. \
		  8: stop LED test. \
		  9: stop all tests.;
	   CAPABILITIES = NET_OPER, VPN_OPER ;"
	::= { t1e1-r2-control 4 }


mcm4400T1NoCodeImage TRAP-TYPE
	ENTERPRISE	micom-2t1e1
	VARIABLES	{mcmSysAsciiTimeOfDay}
	DESCRIPTION
	  "NAME = ;
	   DESC = Indicates that the built image doesn't \
		  contain T1 code.\
		  Severity Level: MAJOR.;
	   HELP = The Image loaded does not contain T1 code.\
                  Load a new Image that includes T1 code, or \
                  consult with the System Admin. or Field \
                  Personnel.;"
	::= 1

mcm4400T1DownloadFail TRAP-TYPE
	ENTERPRISE	micom-2t1e1
	VARIABLES	{mcmSysAsciiTimeOfDay}
	DESCRIPTION
	  "NAME = ;
	   DESC = Indicates a failure occurred during the T1 \
		  code download.\
                  Severity Level: MAJOR;
	   HELP = Retry the download. Re-boot the access device and \
                  check if it downloads correctly. Also, verify \
                  the T1 code that is build with access device image \
                  is the right version. If problem persist, consult \
                  your system admin., or field personnel.;"
	::= 2

mcm4400T1OutOfOrder TRAP-TYPE
	ENTERPRISE	micom-2t1e1
	VARIABLES	{mcmSysAsciiTimeOfDay}
	DESCRIPTION
	  "NAME = ;
	   DESC = Indicates the T1 is not responding.\
		  Severity Level: CRITICAL.;
	   HELP = Management frame is out of order. Check for \
                  Framing error. If it does not recover, Please \
                  contact your Sys Admin. or Field personnel.;" 
	::= 3

mcm4400T1OutOfOrderRecovered TRAP-TYPE
	ENTERPRISE	micom-2t1e1
	VARIABLES	{mcmSysAsciiTimeOfDay}
	DESCRIPTION
	  "NAME = ;
	   DESC = Indicates recovery from the T1 out of order condition.\
                  Severity Level: INFORMATIVE.;
	   HELP = T1 is responding. Normal Status Indicator.;"
	::= 4

mcm4400T1FailToSyncUp TRAP-TYPE
	ENTERPRISE	micom-2t1e1
	VARIABLES	{mcmSysAsciiTimeOfDay}
	DESCRIPTION
	  "NAME = ;
	   DESC = Indicates the T1 is unable to sync up.\
                  Severity Level : CRITICAL.;
	   HELP = Check the physical connection locally, and \
                  to the remote device. Possible protocol error. \
                  If problem still persist, contact your \
                  system admin., or field personnel.;"
	::= 5

mcm4400T1FailToSyncUpRecovered TRAP-TYPE
	ENTERPRISE	micom-2t1e1
	VARIABLES	{mcmSysAsciiTimeOfDay}
	DESCRIPTION
	  "NAME = ;
	   DESC = Indicates recovery from the T1 failure \
		  to sync up condition.\
                  Severity Level: INFORMATIVE.;
	   HELP = T1 has recovered. Normal Status Indicator.;"
	::= 6

mcm4400T1AISAlarmSet TRAP-TYPE
	ENTERPRISE	micom-2t1e1
	VARIABLES	{ mcmSysAsciiTimeOfDay, mcm4400t1e1LineStatusLineIndex }
	DESCRIPTION
	  "NAME = ;
	   DESC = Indicates a T1 AIS Alarm condition is present.\
                  Severity Level: CRITICAL.;
	   HELP = Check physical link of the local T1, and the Remote \
                  PBX. Possible Framing error. If problem is not \
                  resolved, contact sys admin., or field personnel.;"
	::= 7

mcm4400T1AISAlarmClear TRAP-TYPE
	ENTERPRISE	micom-2t1e1
	VARIABLES	{ mcmSysAsciiTimeOfDay, mcm4400t1e1LineStatusLineIndex }
	DESCRIPTION
	  "NAME = ;
	   DESC = Indicates a T1 AIS Alarm condition has cleared.\
                  Severity Level: INFORMATIVE.;
	   HELP = T1 AIS Alarm is cleared. Normal Status Indicator.;"
	::= 8 

mcm4400T1RedAlarmSet TRAP-TYPE
	ENTERPRISE	micom-2t1e1
	VARIABLES	{ mcmSysAsciiTimeOfDay, mcm4400t1e1LineStatusLineIndex }
	DESCRIPTION
	  "NAME = ;
	   DESC = Indicates a T1 Red Alarm condition is present.\
                  Severity Level: CRITICAL.;
	   HELP = Check the Physical Connection to remote. \
		  If the Alarm condition is still persistant, \
	          contact your Field Personnel.;"
	::= 9

mcm4400T1RedAlarmClear TRAP-TYPE
	ENTERPRISE	micom-2t1e1
	VARIABLES	{ mcmSysAsciiTimeOfDay, mcm4400t1e1LineStatusLineIndex }
	DESCRIPTION
	  "NAME = ;
	   DESC = Indicates a T1 Red Alarm condition has cleared.\
                  Severity Level: IMFORMATIVE. ;
	   HELP = Red Alarm Cleared. Normal Status Indicator!.;"
	::= 10

mcm4400T1YellowAlarmSet TRAP-TYPE
	ENTERPRISE	micom-2t1e1
	VARIABLES	{ mcmSysAsciiTimeOfDay, mcm4400t1e1LineStatusLineIndex }
	DESCRIPTION
	  "NAME = ;
	   DESC = Indicates a T1 Yellow Alarm condition is present.\
                  Severity Level: MINOR.;
	   HELP = TX or RX side for physical connection may be faulty; \
	          Possible Framing error with Remote device. Run Loopback \
                  test if possible, & determine the problem. If that does not\
                  help, please contact Field Personnel or System admin.;"
	::= 11

mcm4400T1YellowAlarmClear TRAP-TYPE
	ENTERPRISE	micom-2t1e1
	VARIABLES	{ mcmSysAsciiTimeOfDay, mcm4400t1e1LineStatusLineIndex }
	DESCRIPTION
	  "NAME = ;
	   DESC = Indicates a T1 Yellow Alarm condition has cleared.\
                  Severity Level: INFORMATIVE.;
	   HELP = Yellow Alarm is cleared. Normal Status Indicator!.;"
	::= 12

mcm4400E1NoCodeImage TRAP-TYPE
	ENTERPRISE	micom-2t1e1
	VARIABLES	{mcmSysAsciiTimeOfDay}
	DESCRIPTION
	  "NAME = ;
	   DESC = Indicates that the built image doesn't \
		  contain E1 code.\
                  Severity Level: MAJOR.;
	   HELP = The Image loaded does not contain E1 code.\
                  Load a new Image that includes E1 code, or \
                  consult with the System Admin. or Field \
                  Personnel.;"
	::= 13

mcm4400E1DownloadFail TRAP-TYPE
	ENTERPRISE	micom-2t1e1
	VARIABLES	{mcmSysAsciiTimeOfDay}
	DESCRIPTION
	  "NAME = ;
	   DESC = Indicates a failure occurred during the E1 \
		  code download.\
                  Severity Level: MAJOR. ;
	   HELP = Retry the download. Re-boot the access device and \
                  check if it downloads correctly. Also, verify \ 
                  the E1 code that is built with access device \
                  image is the right version. If problem persist, \
                  consult your system admin., or field personnel.;"
	::= 14

mcm4400E1OutOfOrder TRAP-TYPE
	ENTERPRISE	micom-2t1e1
	VARIABLES	{mcmSysAsciiTimeOfDay}
	DESCRIPTION
	  "NAME = ;
	   DESC = Indicates the E1 is not responding.\
                  Severity Level: CRITICAL.;
	   HELP = Management frame is out of order. Check for \
                  Framing error. If it does not recover, Please \
                  contact your Sys Admin. or Field personnel.;"
	::= 15 

mcm4400E1OutOfOrderRecovered TRAP-TYPE
	ENTERPRISE	micom-2t1e1
	VARIABLES	{mcmSysAsciiTimeOfDay}
	DESCRIPTION
	  "NAME = ;
	   DESC = Indicates recovery from the E1 out of order condition.\
                  Severity Level: INFORMATIVE.;
	   HELP = E1 is responding. Normal Status Indicator.;"
	::= 16

mcm4400E1FailToSyncUp TRAP-TYPE
	ENTERPRISE	micom-2t1e1
	VARIABLES	{mcmSysAsciiTimeOfDay}
	DESCRIPTION
	  "NAME = ;
	   DESC = Indicates the E1 is unable to sync up.\
                  Severity Level: CRITICAL.;
	   HELP = Check the physical connection locally, and \
                  to the remote device. Possible protocol error. \
                  If problem still persist, contact your \
                  system admin., or field personnel.;"
	::= 17

mcm4400E1FailToSyncUpRecovered TRAP-TYPE
	ENTERPRISE	micom-2t1e1
	VARIABLES	{mcmSysAsciiTimeOfDay}
	DESCRIPTION
	  "NAME = ;
	   DESC = Indicates recovery from the E1 failure \
		  to sync up condition.\
                  Severity Level: INFORMATIVE.;
	   HELP = E1 has recovered. Normal Status Indicator.;"
	::= 18

mcm4400E1AISAlarmSet TRAP-TYPE
	ENTERPRISE	micom-2t1e1
	VARIABLES	{ mcmSysAsciiTimeOfDay, mcm4400t1e1LineStatusLineIndex }
	DESCRIPTION
	  "NAME = ;
	   DESC = Indicates an E1 AIS Alarm condition is present.\
                  Severity Level: MAJOR.;
	   HELP = Check physical link of the local E1, and the Remote \
                  PBX. Possible Framing error. If problem is not \
                  resolved, contact sys admin., or field personnel.;"
	::= 19

mcm4400E1AISAlarmClear TRAP-TYPE
	ENTERPRISE	micom-2t1e1
	VARIABLES	{ mcmSysAsciiTimeOfDay, mcm4400t1e1LineStatusLineIndex }
	DESCRIPTION
	  "NAME = ;
	   DESC = Indicates an E1 AIS Alarm condition has cleared.\
                  Severity Level: INFORMATIVE. ;
	   HELP = E1 AIS Alarm is cleared. Normal Status Indicator.;"
	::= 20

mcm4400E1RedAlarmSet TRAP-TYPE
	ENTERPRISE	micom-2t1e1
	VARIABLES	{ mcmSysAsciiTimeOfDay, mcm4400t1e1LineStatusLineIndex }
	DESCRIPTION
	  "NAME = ;
	   DESC = Indicates an E1 Red Alarm condition is present.\
                  Severity Level: MAJOR.;
	   HELP = Check the Physical Connection to remote. \
                  Run a loopback test and determine the problem. \
                  If the Alarm condition is still persistant, \
                  contact your Field Personnel.;"
	::= 21

mcm4400E1RedAlarmClear TRAP-TYPE
	ENTERPRISE	micom-2t1e1
	VARIABLES	{ mcmSysAsciiTimeOfDay, mcm4400t1e1LineStatusLineIndex }
	DESCRIPTION
	  "NAME = ;
	   DESC = Indicates an E1 Red Alarm condition has cleared.\
                  Severity Level: INFORMATIVE.;
	   HELP = Red Alarm Cleared. Normal Status Indicator!.;"
	::= 22

mcm4400E1TS16AISAlarmSet TRAP-TYPE
	ENTERPRISE	micom-2t1e1
	VARIABLES	{ mcmSysAsciiTimeOfDay, mcm4400t1e1LineStatusLineIndex }
	DESCRIPTION
	  "NAME = ;
	   DESC = Indicates an E1 TS16 AIS Alarm is present.\
                  Severity Level: MAJOR.;
	   HELP = TX or RX side for physical connection may be faulty; \
		  Possible Framing error with Remote device. Run Loopback \
                  test if possible, & determine the problem. If that does not\
                  help, please contact Field Personnel or System admin.;"
	::= 23

mcm4400E1TS16AISAlarmClear TRAP-TYPE
	ENTERPRISE	micom-2t1e1
	VARIABLES	{ mcmSysAsciiTimeOfDay, mcm4400t1e1LineStatusLineIndex }
	DESCRIPTION
	  "NAME = ;
	   DESC = Indicates an E1 TS16 AIS Alarm has cleared.\
                  Severity Level: INFORMATIVE.;
	   HELP = Alarm is cleared. Normal Status Indicator!.;"
	::= 24

mcm4400E1OOSMFAlarmSet TRAP-TYPE
	ENTERPRISE	micom-2t1e1
	VARIABLES	{ mcmSysAsciiTimeOfDay, mcm4400t1e1LineStatusLineIndex }
	DESCRIPTION
	  "NAME = ;
	   DESC = Indicates an E1 00SMF Alarm is present.\
                  Severity Level: MAJOR.;
	   HELP = Framing error due to signal loss. Run Loopback \
                  test and determine the problem. For further help \
		  contact your Field Personnel.;"
	::= 25

mcm4400E1OOSMFAlarmClear TRAP-TYPE
	ENTERPRISE	micom-2t1e1
	VARIABLES	{ mcmSysAsciiTimeOfDay, mcm4400t1e1LineStatusLineIndex }
	DESCRIPTION
	  "NAME = ;
	   DESC = Indicates an E1 00SMF Alarm has cleared.\
                  Severity Level: INFORMATIVE.;
	   HELP = OOSMF Alarm is cleared. Normal Status Indicator!.;"
	::= 26 

mcm4400E1RemoteYBitAlarmSet TRAP-TYPE
	ENTERPRISE	micom-2t1e1
	VARIABLES	{ mcmSysAsciiTimeOfDay, mcm4400t1e1LineStatusLineIndex }
	DESCRIPTION
	  "NAME = ;
	   DESC = Indicates an E1 Remote Y Bit Alarm is present.\
                  Severity Level: MAJOR.;
	   HELP = Run Loopback test, and determine the condition. \
                  For further help, contact Field Personnel.;"
	::= 27

mcm4400E1RemoteYBitAlarmClear TRAP-TYPE
	ENTERPRISE	micom-2t1e1
	VARIABLES	{ mcmSysAsciiTimeOfDay, mcm4400t1e1LineStatusLineIndex }
	DESCRIPTION
	  "NAME = ;
	   DESC = Indicates an E1 Remote Y Bit Alarm has cleared.\
                  Severity Level: INFORMATIVE.;
	   HELP = Remote YBit Alarm is cleared. Normal Status \
                  Indicator.;"
	::= 28

mcm4400E1RemoteABitAlarmSet TRAP-TYPE
	ENTERPRISE	micom-2t1e1
	VARIABLES	{ mcmSysAsciiTimeOfDay, mcm4400t1e1LineStatusLineIndex }
	DESCRIPTION
	  "NAME = ;
	   DESC = Indicates an E1 Remote A Bit Alarm is present.\
                  Severity Level: MAJOR.;
	   HELP = Possible frame Error. Please run loopback test \
		  and determine the condition. If Alarm \
	          is not cleared, contact your Field Personnel.;"
	::= 29

mcm4400E1RemoteABitAlarmClear TRAP-TYPE
	ENTERPRISE	micom-2t1e1
	VARIABLES	{ mcmSysAsciiTimeOfDay, mcm4400t1e1LineStatusLineIndex }
	DESCRIPTION
	  "NAME = ;
	   DESC = Indicates an E1 Remote Y Bit Alarm has cleared.\
                  Severity Level: INFORMATIVE.;
	   HELP = Alarm is cleared. Normal Status Indicator!.;"
	::= 30

mcm4400E1OOCMFAlarmSet TRAP-TYPE
	ENTERPRISE	micom-2t1e1
	VARIABLES	{ mcmSysAsciiTimeOfDay, mcm4400t1e1LineStatusLineIndex }
	DESCRIPTION
	  "NAME = ;
	   DESC = Indicates an E1 00CMF Alarm is present.\
                  Severity Level: MAJOR.;
	   HELP = CRC multframe alignment is lost. Run loobback \
	          test and determine the problem. For further \
	          help, contact Field Personnel. ;"
	::= 31

mcm4400E1OOCMFAlarmClear TRAP-TYPE
	ENTERPRISE	micom-2t1e1
	VARIABLES	{ mcmSysAsciiTimeOfDay, mcm4400t1e1LineStatusLineIndex }
	DESCRIPTION
	  "NAME = ;
	   DESC = Indicates an E1 00CMF Alarm has cleared.\
                  Severity Level: INFORMATIVE.;
	   HELP = OOCMF Alarm is cleared. Normal Status Indicator.;"
	::= 32

END
