Nortel-Magellan-Passport-DisdnETSIMIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      dataSigChanIndex,
      dataSigChan
   FROM Nortel-Magellan-Passport-DataIsdnMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DisdnETSI Enterprise MIB."

disdnETSIMIB OBJECT IDENTIFIER ::= { passportMIBs 117 }










-- DataSigChan/n ETSI
-- The ETSI component defines the operational characteristics of the 
-- signalling channel's connection to the external equipment.

dataSigChanEtsi OBJECT IDENTIFIER ::= { dataSigChan 10 }



dataSigChanEtsiRowStatusTable OBJECT-TYPE
   SYNTAX     SEQUENCE OF DataSigChanEtsiRowStatusEntry
   ACCESS     not-accessible
   STATUS     mandatory
   DESCRIPTION
     "This entry controls the addition and deletion of 
      dataSigChanEtsi components."
::= { dataSigChanEtsi 1 }

dataSigChanEtsiRowStatusEntry OBJECT-TYPE
   SYNTAX     DataSigChanEtsiRowStatusEntry
   ACCESS     not-accessible
   STATUS     mandatory
   DESCRIPTION
     "A single entry in the table represents a single 
      dataSigChanEtsi component."
   INDEX {
      dataSigChanIndex,
      dataSigChanEtsiIndex }
::= { dataSigChanEtsiRowStatusTable 1 }

DataSigChanEtsiRowStatusEntry ::= SEQUENCE {
   dataSigChanEtsiRowStatus
      RowStatus,
   dataSigChanEtsiComponentName
      DisplayString,
   dataSigChanEtsiStorageType
      StorageType,
   dataSigChanEtsiIndex
      NonReplicated }

dataSigChanEtsiRowStatus OBJECT-TYPE
   SYNTAX     RowStatus 
   ACCESS     read-write
   STATUS     mandatory
   DESCRIPTION
     "This variable is used as the basis for SNMP naming of
      dataSigChanEtsi components.
      These components can be added and deleted."
::= { dataSigChanEtsiRowStatusEntry 1 }

dataSigChanEtsiComponentName OBJECT-TYPE
   SYNTAX     DisplayString 
   ACCESS     read-only
   STATUS     mandatory
   DESCRIPTION
     "This variable provides the component's string name for
      use with the ASCII Console Interface"
::= { dataSigChanEtsiRowStatusEntry 2 }

dataSigChanEtsiStorageType OBJECT-TYPE
   SYNTAX     StorageType 
   ACCESS     read-only
   STATUS     mandatory
   DESCRIPTION
     "This variable represents the storage type value for the
      dataSigChanEtsi tables."
::= { dataSigChanEtsiRowStatusEntry 4 }

dataSigChanEtsiIndex OBJECT-TYPE
   SYNTAX     NonReplicated 
   ACCESS     not-accessible
   STATUS     mandatory
   DESCRIPTION
     "This variable represents the index for the dataSigChanEtsi tables."
::= { dataSigChanEtsiRowStatusEntry 10 }

dataSigChanEtsiL2Table OBJECT-TYPE
   SYNTAX     SEQUENCE OF DataSigChanEtsiL2Entry
   ACCESS     not-accessible
   STATUS     mandatory
   DESCRIPTION
     "This group represents the provisionable Layer 2 attributes of the 
      Q931 CCITT protocol."
::= { dataSigChanEtsi 11 }

dataSigChanEtsiL2Entry OBJECT-TYPE
   SYNTAX     DataSigChanEtsiL2Entry
   ACCESS     not-accessible
   STATUS     mandatory
   DESCRIPTION
     "An entry in the dataSigChanEtsiL2Table."
   INDEX {
      dataSigChanIndex,
      dataSigChanEtsiIndex }
::= { dataSigChanEtsiL2Table 1 }

DataSigChanEtsiL2Entry ::= SEQUENCE {
   dataSigChanEtsiT23
      Unsigned32,
   dataSigChanEtsiT200
      Unsigned32,
   dataSigChanEtsiN200
      Unsigned32,
   dataSigChanEtsiT203
      Unsigned32,
   dataSigChanEtsiN201
      Unsigned32,
   dataSigChanEtsiCircuitSwitchedK
      Unsigned32 }

dataSigChanEtsiT23 OBJECT-TYPE
   SYNTAX     Unsigned32 (1..15)
   ACCESS     read-write
   STATUS     mandatory
   DESCRIPTION
     "This attribute specifies the layer2 enable request timer."
   DEFVAL     { 10 }
::= { dataSigChanEtsiL2Entry 1 }

dataSigChanEtsiT200 OBJECT-TYPE
   SYNTAX     Unsigned32 (1..20)
   ACCESS     read-write
   STATUS     mandatory
   DESCRIPTION
     "This attribute specifies the maximum time between a layer 2 frame 
      and its acknowledgement"
   DEFVAL     { 2 }
::= { dataSigChanEtsiL2Entry 2 }

dataSigChanEtsiN200 OBJECT-TYPE
   SYNTAX     Unsigned32 (1..8)
   ACCESS     read-write
   STATUS     mandatory
   DESCRIPTION
     "This attribute specifies the maximum number of re-transmissions of 
      a layer2 frame."
   DEFVAL     { 3 }
::= { dataSigChanEtsiL2Entry 3 }

dataSigChanEtsiT203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { dataSigChanEtsiL2Entry 4 }

dataSigChanEtsiN201 OBJECT-TYPE
   SYNTAX     Unsigned32 (4..260)
   ACCESS     read-write
   STATUS     mandatory
   DESCRIPTION
     "This attribute specifies the maximum number of octets in an 
      information field."
   DEFVAL     { 260 }
::= { dataSigChanEtsiL2Entry 5 }

dataSigChanEtsiCircuitSwitchedK OBJECT-TYPE
   SYNTAX     Unsigned32 (1..632)
   ACCESS     read-write
   STATUS     mandatory
   DESCRIPTION
     "This attribute specifies the maximum number of frames for B 
      channel use."
   DEFVAL     { 7 }
::= { dataSigChanEtsiL2Entry 6 }

dataSigChanEtsiProvTable OBJECT-TYPE
   SYNTAX     SEQUENCE OF DataSigChanEtsiProvEntry
   ACCESS     not-accessible
   STATUS     mandatory
   DESCRIPTION
     "This group defines the general options of the d-channel signalling 
      link."
::= { dataSigChanEtsi 13 }

dataSigChanEtsiProvEntry OBJECT-TYPE
   SYNTAX     DataSigChanEtsiProvEntry
   ACCESS     not-accessible
   STATUS     mandatory
   DESCRIPTION
     "An entry in the dataSigChanEtsiProvTable."
   INDEX {
      dataSigChanIndex,
      dataSigChanEtsiIndex }
::= { dataSigChanEtsiProvTable 1 }

DataSigChanEtsiProvEntry ::= SEQUENCE {
   dataSigChanEtsiSide
      INTEGER }

dataSigChanEtsiSide OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { dataSigChanEtsiProvEntry 1 }

dataSigChanEtsiOperTable OBJECT-TYPE
   SYNTAX     SEQUENCE OF DataSigChanEtsiOperEntry
   ACCESS     not-accessible
   STATUS     mandatory
   DESCRIPTION
     "This group provides the operational attributes for the signalling 
      protocol."
::= { dataSigChanEtsi 15 }

dataSigChanEtsiOperEntry OBJECT-TYPE
   SYNTAX     DataSigChanEtsiOperEntry
   ACCESS     not-accessible
   STATUS     mandatory
   DESCRIPTION
     "An entry in the dataSigChanEtsiOperTable."
   INDEX {
      dataSigChanIndex,
      dataSigChanEtsiIndex }
::= { dataSigChanEtsiOperTable 1 }

DataSigChanEtsiOperEntry ::= SEQUENCE {
   dataSigChanEtsiActiveChannels
      Unsigned32,
   dataSigChanEtsiPeakActiveChannels
      Unsigned32,
   dataSigChanEtsiDChanStatus
      INTEGER }

dataSigChanEtsiActiveChannels OBJECT-TYPE
   SYNTAX     Unsigned32 (0..128)
   ACCESS     read-only
   STATUS     mandatory
   DESCRIPTION
     "This attribute indicates the number of currently active channels. 
      This includes data and voice channels."
   DEFVAL     { 0 }
::= { dataSigChanEtsiOperEntry 1 }

dataSigChanEtsiPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { dataSigChanEtsiOperEntry 4 }

dataSigChanEtsiDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { dataSigChanEtsiOperEntry 7 }

dataSigChanEtsiToolsTable OBJECT-TYPE
   SYNTAX     SEQUENCE OF DataSigChanEtsiToolsEntry
   ACCESS     not-accessible
   STATUS     mandatory
   DESCRIPTION
     "This group contains a series of operational attributes which turn on 
      and off several kinds of tracing."
::= { dataSigChanEtsi 16 }

dataSigChanEtsiToolsEntry OBJECT-TYPE
   SYNTAX     DataSigChanEtsiToolsEntry
   ACCESS     not-accessible
   STATUS     mandatory
   DESCRIPTION
     "An entry in the dataSigChanEtsiToolsTable."
   INDEX {
      dataSigChanIndex,
      dataSigChanEtsiIndex }
::= { dataSigChanEtsiToolsTable 1 }

DataSigChanEtsiToolsEntry ::= SEQUENCE {
   dataSigChanEtsiTracing
      OCTET STRING }

dataSigChanEtsiTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { dataSigChanEtsiToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

dataSigChanEtsiFramer OBJECT IDENTIFIER ::= { dataSigChanEtsi 2 }



dataSigChanEtsiFramerRowStatusTable OBJECT-TYPE
   SYNTAX     SEQUENCE OF DataSigChanEtsiFramerRowStatusEntry
   ACCESS     not-accessible
   STATUS     mandatory
   DESCRIPTION
     "This entry controls the addition and deletion of 
      dataSigChanEtsiFramer components."
::= { dataSigChanEtsiFramer 1 }

dataSigChanEtsiFramerRowStatusEntry OBJECT-TYPE
   SYNTAX     DataSigChanEtsiFramerRowStatusEntry
   ACCESS     not-accessible
   STATUS     mandatory
   DESCRIPTION
     "A single entry in the table represents a single 
      dataSigChanEtsiFramer component."
   INDEX {
      dataSigChanIndex,
      dataSigChanEtsiIndex,
      dataSigChanEtsiFramerIndex }
::= { dataSigChanEtsiFramerRowStatusTable 1 }

DataSigChanEtsiFramerRowStatusEntry ::= SEQUENCE {
   dataSigChanEtsiFramerRowStatus
      RowStatus,
   dataSigChanEtsiFramerComponentName
      DisplayString,
   dataSigChanEtsiFramerStorageType
      StorageType,
   dataSigChanEtsiFramerIndex
      NonReplicated }

dataSigChanEtsiFramerRowStatus OBJECT-TYPE
   SYNTAX     RowStatus 
   ACCESS     read-only
   STATUS     mandatory
   DESCRIPTION
     "This variable is used as the basis for SNMP naming of
      dataSigChanEtsiFramer components.
      These components cannot be added nor deleted."
::= { dataSigChanEtsiFramerRowStatusEntry 1 }

dataSigChanEtsiFramerComponentName OBJECT-TYPE
   SYNTAX     DisplayString 
   ACCESS     read-only
   STATUS     mandatory
   DESCRIPTION
     "This variable provides the component's string name for
      use with the ASCII Console Interface"
::= { dataSigChanEtsiFramerRowStatusEntry 2 }

dataSigChanEtsiFramerStorageType OBJECT-TYPE
   SYNTAX     StorageType 
   ACCESS     read-only
   STATUS     mandatory
   DESCRIPTION
     "This variable represents the storage type value for the
      dataSigChanEtsiFramer tables."
::= { dataSigChanEtsiFramerRowStatusEntry 4 }

dataSigChanEtsiFramerIndex OBJECT-TYPE
   SYNTAX     NonReplicated 
   ACCESS     not-accessible
   STATUS     mandatory
   DESCRIPTION
     "This variable represents the index for the dataSigChanEtsiFramer tables."
::= { dataSigChanEtsiFramerRowStatusEntry 10 }

dataSigChanEtsiFramerProvTable OBJECT-TYPE
   SYNTAX     SEQUENCE OF DataSigChanEtsiFramerProvEntry
   ACCESS     not-accessible
   STATUS     mandatory
   DESCRIPTION
     "This group contains the base provisioning data for the Framer 
      component. Application or hardware interface specific provisioning 
      data is contained in other provisionable Framer groups."
::= { dataSigChanEtsiFramer 10 }

dataSigChanEtsiFramerProvEntry OBJECT-TYPE
   SYNTAX     DataSigChanEtsiFramerProvEntry
   ACCESS     not-accessible
   STATUS     mandatory
   DESCRIPTION
     "An entry in the dataSigChanEtsiFramerProvTable."
   INDEX {
      dataSigChanIndex,
      dataSigChanEtsiIndex,
      dataSigChanEtsiFramerIndex }
::= { dataSigChanEtsiFramerProvTable 1 }

DataSigChanEtsiFramerProvEntry ::= SEQUENCE {
   dataSigChanEtsiFramerInterfaceName
      Link }

dataSigChanEtsiFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dataSigChanEtsiFramerProvEntry 1 }

dataSigChanEtsiFramerStateTable OBJECT-TYPE
   SYNTAX     SEQUENCE OF DataSigChanEtsiFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dataSigChanEtsiFramer 12 }

dataSigChanEtsiFramerStateEntry OBJECT-TYPE
   SYNTAX     DataSigChanEtsiFramerStateEntry
   ACCESS     not-accessible
   STATUS     mandatory
   DESCRIPTION
     "An entry in the dataSigChanEtsiFramerStateTable."
   INDEX {
      dataSigChanIndex,
      dataSigChanEtsiIndex,
      dataSigChanEtsiFramerIndex }
::= { dataSigChanEtsiFramerStateTable 1 }

DataSigChanEtsiFramerStateEntry ::= SEQUENCE {
   dataSigChanEtsiFramerAdminState
      INTEGER,
   dataSigChanEtsiFramerOperationalState
      INTEGER,
   dataSigChanEtsiFramerUsageState
      INTEGER }

dataSigChanEtsiFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dataSigChanEtsiFramerStateEntry 1 }

dataSigChanEtsiFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dataSigChanEtsiFramerStateEntry 2 }

dataSigChanEtsiFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dataSigChanEtsiFramerStateEntry 3 }

dataSigChanEtsiFramerStatsTable OBJECT-TYPE
   SYNTAX     SEQUENCE OF DataSigChanEtsiFramerStatsEntry
   ACCESS     not-accessible
   STATUS     mandatory
   DESCRIPTION
     "This group contains the operational statistics data for a Framer 
      component."
::= { dataSigChanEtsiFramer 13 }

dataSigChanEtsiFramerStatsEntry OBJECT-TYPE
   SYNTAX     DataSigChanEtsiFramerStatsEntry
   ACCESS     not-accessible
   STATUS     mandatory
   DESCRIPTION
     "An entry in the dataSigChanEtsiFramerStatsTable."
   INDEX {
      dataSigChanIndex,
      dataSigChanEtsiIndex,
      dataSigChanEtsiFramerIndex }
::= { dataSigChanEtsiFramerStatsTable 1 }

DataSigChanEtsiFramerStatsEntry ::= SEQUENCE {
   dataSigChanEtsiFramerFrmToIf
      Unsigned32,
   dataSigChanEtsiFramerFrmFromIf
      Unsigned32,
   dataSigChanEtsiFramerOctetFromIf
      Unsigned32,
   dataSigChanEtsiFramerAborts
      Unsigned32,
   dataSigChanEtsiFramerCrcErrors
      Unsigned32,
   dataSigChanEtsiFramerLrcErrors
      Unsigned32,
   dataSigChanEtsiFramerNonOctetErrors
      Unsigned32,
   dataSigChanEtsiFramerOverruns
      Unsigned32,
   dataSigChanEtsiFramerUnderruns
      Unsigned32,
   dataSigChanEtsiFramerLargeFrmErrors
      Unsigned32 }

dataSigChanEtsiFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { dataSigChanEtsiFramerStatsEntry 1 }

dataSigChanEtsiFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { dataSigChanEtsiFramerStatsEntry 2 }

dataSigChanEtsiFramerOctetFromIf OBJECT-TYPE
   SYNTAX     Unsigned32 (0..4294967295)
   ACCESS     read-only
   STATUS     mandatory
   DESCRIPTION
     "The number of bytes received from the link interface by Framer."
   DEFVAL     { 0 }
::= { dataSigChanEtsiFramerStatsEntry 3 }

dataSigChanEtsiFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { dataSigChanEtsiFramerStatsEntry 4 }

dataSigChanEtsiFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { dataSigChanEtsiFramerStatsEntry 5 }

dataSigChanEtsiFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { dataSigChanEtsiFramerStatsEntry 6 }

dataSigChanEtsiFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { dataSigChanEtsiFramerStatsEntry 7 }

dataSigChanEtsiFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { dataSigChanEtsiFramerStatsEntry 8 }

dataSigChanEtsiFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { dataSigChanEtsiFramerStatsEntry 9 }

dataSigChanEtsiFramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { dataSigChanEtsiFramerStatsEntry 10 }




-- 
-- Version and Compliance statements
-- 



-- Object-Group Statement:
-- A list of all current accessible leaf objects.

-- OBJECTS { dataSigChanEtsiFramerRowStatus,
--           dataSigChanEtsiActiveChannels,
--           dataSigChanEtsiRowStatus,
--           dataSigChanEtsiFramerFrmToIf,
--           dataSigChanEtsiCircuitSwitchedK,
--           dataSigChanEtsiFramerNonOctetErrors,
--           dataSigChanEtsiPeakActiveChannels,
--           dataSigChanEtsiFramerOverruns,
--           dataSigChanEtsiFramerUsageState,
--           dataSigChanEtsiFramerAborts,
--           dataSigChanEtsiFramerComponentName,
--           dataSigChanEtsiN200,
--           dataSigChanEtsiFramerFrmFromIf,
--           dataSigChanEtsiFramerInterfaceName,
--           dataSigChanEtsiComponentName,
--           dataSigChanEtsiT23,
--           dataSigChanEtsiFramerUnderruns,
--           dataSigChanEtsiTracing,
--           dataSigChanEtsiFramerCrcErrors,
--           dataSigChanEtsiStorageType,
--           dataSigChanEtsiFramerOperationalState,
--           dataSigChanEtsiFramerStorageType,
--           dataSigChanEtsiT200,
--           dataSigChanEtsiFramerOctetFromIf,
--           dataSigChanEtsiT203,
--           dataSigChanEtsiDChanStatus,
--           dataSigChanEtsiN201,
--           dataSigChanEtsiFramerAdminState,
--           dataSigChanEtsiSide,
--           dataSigChanEtsiFramerLrcErrors,
--           dataSigChanEtsiFramerLargeFrmErrors }
-- STATUS  mandatory
-- DESCRIPTION
--   "A list of all current accessible leaf objects."

disdnETSIGroup OBJECT IDENTIFIER ::= { disdnETSIMIB 1 }
disdnETSIGroupBE OBJECT IDENTIFIER ::= { disdnETSIGroup 5 }
disdnETSIGroupBE00 OBJECT IDENTIFIER ::= { disdnETSIGroupBE 1 }
disdnETSIGroupBE00A OBJECT IDENTIFIER ::= { disdnETSIGroupBE00 2 }



-- Agent-Capabilities Statement:

-- PRODUCT-RELEASE "Passport Release 7.0 DisdnETSI."
-- STATUS          mandatory
-- DESCRIPTION     "DisdnETSI MIB: MIB Version BE00A,
--                  Software Version BG00S4C."
-- SUPPORTS        Nortel-Magellan-Passport-DisdnETSIMIB
--    INCLUDES     { disdnETSIGroupBE00A }

disdnETSICapabilities OBJECT IDENTIFIER ::= { disdnETSIMIB 3 }
disdnETSICapabilitiesBE OBJECT IDENTIFIER ::= { disdnETSICapabilities 5 }
disdnETSICapabilitiesBE00 OBJECT IDENTIFIER ::= { disdnETSICapabilitiesBE 1 }
disdnETSICapabilitiesBE00A OBJECT IDENTIFIER ::= { disdnETSICapabilitiesBE00 2 }





END
