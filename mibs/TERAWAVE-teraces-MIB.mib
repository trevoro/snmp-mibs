TERAWAVE-teraces-MIB DEFINITIONS ::= BEGIN
        -- Created by sml2mib compiler 
        IMPORTS

	Counter32 FROM SNMPv2-SMI
 enterprises,  OBJECT-TYPE,  Counter,  Gauge,  TimeTicks
        FROM RFC1155-SMI;

terawave OBJECT IDENTIFIER ::=  { enterprises 4513 }

bandwidthGroup OBJECT IDENTIFIER ::=  { terawave 9 }

     -- teraCESConfigTable

teraCESConfigTable OBJECT-TYPE
     SYNTAX SEQUENCE OF TeraCESConfigTableEntryType
     ACCESS not-accessible
     STATUS mandatory
     DESCRIPTION
          " table teraCESConfigTable"
     ::= { bandwidthGroup 1 }

teraCESConfigTableEntry OBJECT-TYPE
          SYNTAX TeraCESConfigTableEntryType
          ACCESS not-accessible
          STATUS mandatory
          DESCRIPTION
               " table entry teraCESConfigTableEntry "
          INDEX {                   atmfCESCbrIndex }
     ::= { teraCESConfigTable 1 }

TeraCESConfigTableEntryType ::= SEQUENCE {
          teraCesSignalling   
             INTEGER,
          teraCesCheckParity   
             INTEGER,
          teraCesTestLine   
             INTEGER,
          teraCesSRTSSize   
             INTEGER (1..511)
}

teraCesSignalling OBJECT-TYPE
          SYNTAX INTEGER
                  {
                  aal1-signalling(1),
                  aal1-no-signalling(2)
                  }
          ACCESS read-write
          STATUS mandatory
          DESCRIPTION
               ""
          ::= { teraCESConfigTableEntry 1 }

teraCesCheckParity OBJECT-TYPE
          SYNTAX INTEGER
                  {
                  aal1-no-parity(1),
                  aal1-parity(2)
                  }
          ACCESS read-write
          STATUS mandatory
          DESCRIPTION
               ""
          ::= { teraCESConfigTableEntry 2 }

teraCesTestLine OBJECT-TYPE
          SYNTAX INTEGER
                  {
                  no-action(1),
                  line-test-relay-off(2),
                  line-test-relay-on(3)
                  }
          ACCESS read-write
          STATUS mandatory
          DESCRIPTION
               ""
          ::= { teraCESConfigTableEntry 3 }

teraCesSRTSSize OBJECT-TYPE
          SYNTAX INTEGER (1..511)
          ACCESS read-write
          STATUS mandatory
          DESCRIPTION
               ""
          ::= { teraCESConfigTableEntry 4 }

     -- teraCESStatTable

teraCESStatTable OBJECT-TYPE
     SYNTAX SEQUENCE OF TeraCESStatTableEntryType
     ACCESS not-accessible
     STATUS mandatory
     DESCRIPTION
          " table teraCESStatTable"
     ::= { bandwidthGroup 2 }

teraCESStatTableEntry OBJECT-TYPE
          SYNTAX TeraCESStatTableEntryType
          ACCESS not-accessible
          STATUS mandatory
          DESCRIPTION
               " table entry teraCESStatTableEntry "
          INDEX {                   atmfCESCbrIndex }
     ::= { teraCESStatTable 1 }

TeraCESStatTableEntryType ::= SEQUENCE {
          teraCESTCellCount   
             Counter32,
          teraCESRLostCellCount   
             Counter32,
          teraCESRReplacedCellCount   
             Counter32
}

teraCESTCellCount OBJECT-TYPE
          SYNTAX Counter32
          ACCESS read-only
          STATUS mandatory
          DESCRIPTION
               ""
          ::= { teraCESStatTableEntry 1 }

teraCESRLostCellCount OBJECT-TYPE
          SYNTAX Counter32
          ACCESS read-only
          STATUS mandatory
          DESCRIPTION
               ""
          ::= { teraCESStatTableEntry 2 }

teraCESRReplacedCellCount OBJECT-TYPE
          SYNTAX Counter32
          ACCESS read-only
          STATUS mandatory
          DESCRIPTION
               ""
          ::= { teraCESStatTableEntry 3 }

     -- teraCESIntervalStatTable

teraCESIntervalStatTable OBJECT-TYPE
     SYNTAX SEQUENCE OF TeraCESIntervalStatTableEntryType
     ACCESS not-accessible
     STATUS mandatory
     DESCRIPTION
          " table teraCESIntervalStatTable"
     ::= { bandwidthGroup 3 }

teraCESIntervalStatTableEntry OBJECT-TYPE
          SYNTAX TeraCESIntervalStatTableEntryType
          ACCESS not-accessible
          STATUS mandatory
          DESCRIPTION
               " table entry teraCESIntervalStatTableEntry "
          INDEX {                   atmfCESCbrIndex,                  teraCESIntervalNumber }
     ::= { teraCESIntervalStatTable 1 }

TeraCESIntervalStatTableEntryType ::= SEQUENCE {
          teraCESIntervalNumber   
             INTEGER (1..96),
          teraCESIntervalTCellCount   
             Counter32,
          teraCESIntervalRLostCellCount   
             Counter32,
          teraCESIntervalRReplacedCellCount   
             Counter32
}

teraCESIntervalNumber OBJECT-TYPE
          SYNTAX INTEGER (1..96)
          ACCESS read-only
          STATUS mandatory
          DESCRIPTION
               ""
          ::= { teraCESIntervalStatTableEntry 1 }

teraCESIntervalTCellCount OBJECT-TYPE
          SYNTAX Counter32
          ACCESS read-only
          STATUS mandatory
          DESCRIPTION
               ""
          ::= { teraCESIntervalStatTableEntry 2 }

teraCESIntervalRLostCellCount OBJECT-TYPE
          SYNTAX Counter32
          ACCESS read-only
          STATUS mandatory
          DESCRIPTION
               ""
          ::= { teraCESIntervalStatTableEntry 3 }

teraCESIntervalRReplacedCellCount OBJECT-TYPE
          SYNTAX Counter32
          ACCESS read-only
          STATUS mandatory
          DESCRIPTION
               ""
          ::= { teraCESIntervalStatTableEntry 4 }

     -- teraCESTotalStatTable

teraCESTotalStatTable OBJECT-TYPE
     SYNTAX SEQUENCE OF TeraCESTotalStatTableEntryType
     ACCESS not-accessible
     STATUS mandatory
     DESCRIPTION
          " table teraCESTotalStatTable"
     ::= { bandwidthGroup 4 }

teraCESTotalStatTableEntry OBJECT-TYPE
          SYNTAX TeraCESTotalStatTableEntryType
          ACCESS not-accessible
          STATUS mandatory
          DESCRIPTION
               " table entry teraCESTotalStatTableEntry "
          INDEX {                   atmfCESCbrIndex }
     ::= { teraCESTotalStatTable 1 }

TeraCESTotalStatTableEntryType ::= SEQUENCE {
          teraCESTotalTCellCount   
             Counter32,
          teraCESTotalRLostCellCount   
             Counter32,
          teraCESTotalRReplacedCellCount   
             Counter32,
          teraCESTotalStatStatus   
             INTEGER
}

teraCESTotalTCellCount OBJECT-TYPE
          SYNTAX Counter32
          ACCESS read-only
          STATUS mandatory
          DESCRIPTION
               ""
          ::= { teraCESTotalStatTableEntry 1 }

teraCESTotalRLostCellCount OBJECT-TYPE
          SYNTAX Counter32
          ACCESS read-only
          STATUS mandatory
          DESCRIPTION
               ""
          ::= { teraCESTotalStatTableEntry 2 }

teraCESTotalRReplacedCellCount OBJECT-TYPE
          SYNTAX Counter32
          ACCESS read-only
          STATUS mandatory
          DESCRIPTION
               ""
          ::= { teraCESTotalStatTableEntry 3 }

teraCESTotalStatStatus OBJECT-TYPE
          SYNTAX INTEGER
                  {
                  ok(1),
                  clear(2)
                  }
          ACCESS read-write
          STATUS mandatory
          DESCRIPTION
               ""
          ::= { teraCESTotalStatTableEntry 4 }

     -- teraAtmfCESIntervalStatsTable

teraAtmfCESIntervalStatsTable OBJECT-TYPE
     SYNTAX SEQUENCE OF TeraAtmfCESIntervalStatsTableEntryType
     ACCESS not-accessible
     STATUS mandatory
     DESCRIPTION
          " table teraAtmfCESIntervalStatsTable"
     ::= { bandwidthGroup 5 }

teraAtmfCESIntervalStatsTableEntry OBJECT-TYPE
          SYNTAX TeraAtmfCESIntervalStatsTableEntryType
          ACCESS not-accessible
          STATUS mandatory
          DESCRIPTION
               " table entry teraAtmfCESIntervalStatsTableEntry "
          INDEX {                   atmfCESCbrIndex,                  teraAtmfCESIntervalNumber }
     ::= { teraAtmfCESIntervalStatsTable 1 }

TeraAtmfCESIntervalStatsTableEntryType ::= SEQUENCE {
          teraAtmfCESIntervalNumber   
             INTEGER (1..96),
          teraAtmfCESIntervalReassCells   
             Counter32,
          teraAtmfCESIntervalHdrErrors   
             Counter32,
          teraAtmfCESIntervalPointerReframes   
             Counter32,
          teraAtmfCESIntervalPointerParityErrors   
             Counter32,
          teraAtmfCESIntervalAal1SeqErrors   
             Counter32,
          teraAtmfCESIntervalLostCells   
             Counter32,
          teraAtmfCESIntervalMisinsertedCells   
             Counter32,
          teraAtmfCESIntervalBufUnderflows   
             Counter32,
          teraAtmfCESIntervalBufOverflows   
             Counter32,
          teraAtmfCESIntervalCellLossStatus   
             INTEGER
}

teraAtmfCESIntervalNumber OBJECT-TYPE
          SYNTAX INTEGER (1..96)
          ACCESS read-only
          STATUS mandatory
          DESCRIPTION
               ""
          ::= { teraAtmfCESIntervalStatsTableEntry 1 }

teraAtmfCESIntervalReassCells OBJECT-TYPE
          SYNTAX Counter32
          ACCESS read-only
          STATUS mandatory
          DESCRIPTION
               ""
          ::= { teraAtmfCESIntervalStatsTableEntry 2 }

teraAtmfCESIntervalHdrErrors OBJECT-TYPE
          SYNTAX Counter32
          ACCESS read-only
          STATUS mandatory
          DESCRIPTION
               ""
          ::= { teraAtmfCESIntervalStatsTableEntry 3 }

teraAtmfCESIntervalPointerReframes OBJECT-TYPE
          SYNTAX Counter32
          ACCESS read-only
          STATUS mandatory
          DESCRIPTION
               ""
          ::= { teraAtmfCESIntervalStatsTableEntry 4 }

teraAtmfCESIntervalPointerParityErrors OBJECT-TYPE
          SYNTAX Counter32
          ACCESS read-only
          STATUS mandatory
          DESCRIPTION
               ""
          ::= { teraAtmfCESIntervalStatsTableEntry 5 }

teraAtmfCESIntervalAal1SeqErrors OBJECT-TYPE
          SYNTAX Counter32
          ACCESS read-only
          STATUS mandatory
          DESCRIPTION
               ""
          ::= { teraAtmfCESIntervalStatsTableEntry 6 }

teraAtmfCESIntervalLostCells OBJECT-TYPE
          SYNTAX Counter32
          ACCESS read-only
          STATUS mandatory
          DESCRIPTION
               ""
          ::= { teraAtmfCESIntervalStatsTableEntry 7 }

teraAtmfCESIntervalMisinsertedCells OBJECT-TYPE
          SYNTAX Counter32
          ACCESS read-only
          STATUS mandatory
          DESCRIPTION
               ""
          ::= { teraAtmfCESIntervalStatsTableEntry 8 }

teraAtmfCESIntervalBufUnderflows OBJECT-TYPE
          SYNTAX Counter32
          ACCESS read-only
          STATUS mandatory
          DESCRIPTION
               ""
          ::= { teraAtmfCESIntervalStatsTableEntry 9 }

teraAtmfCESIntervalBufOverflows OBJECT-TYPE
          SYNTAX Counter32
          ACCESS read-only
          STATUS mandatory
          DESCRIPTION
               ""
          ::= { teraAtmfCESIntervalStatsTableEntry 10 }

teraAtmfCESIntervalCellLossStatus OBJECT-TYPE
          SYNTAX INTEGER
                  {
                  noloss(1),
                  loss(2)
                  }
          ACCESS read-only
          STATUS mandatory
          DESCRIPTION
               ""
          ::= { teraAtmfCESIntervalStatsTableEntry 11 }

     -- teraAtmfCESTotalStatsTable

teraAtmfCESTotalStatsTable OBJECT-TYPE
     SYNTAX SEQUENCE OF TeraAtmfCESTotalStatsTableEntryType
     ACCESS not-accessible
     STATUS mandatory
     DESCRIPTION
          " table teraAtmfCESTotalStatsTable"
     ::= { bandwidthGroup 6 }

teraAtmfCESTotalStatsTableEntry OBJECT-TYPE
          SYNTAX TeraAtmfCESTotalStatsTableEntryType
          ACCESS not-accessible
          STATUS mandatory
          DESCRIPTION
               " table entry teraAtmfCESTotalStatsTableEntry "
          INDEX {                   atmfCESCbrIndex }
     ::= { teraAtmfCESTotalStatsTable 1 }

TeraAtmfCESTotalStatsTableEntryType ::= SEQUENCE {
          teraAtmfCESTotalReassCells   
             Counter32,
          teraAtmfCESTotalHdrErrors   
             Counter32,
          teraAtmfCESTotalPointerReframes   
             Counter32,
          teraAtmfCESTotalPointerParityErrors   
             Counter32,
          teraAtmfCESTotalAal1SeqErrors   
             Counter32,
          teraAtmfCESTotalLostCells   
             Counter32,
          teraAtmfCESTotalMisinsertedCells   
             Counter32,
          teraAtmfCESTotalBufUnderflows   
             Counter32,
          teraAtmfCESTotalBufOverflows   
             Counter32,
          teraAtmfCESTotalCellLossStatus   
             INTEGER,
          teraAtmfCESTotalStatsStatus   
             INTEGER
}

teraAtmfCESTotalReassCells OBJECT-TYPE
          SYNTAX Counter32
          ACCESS read-only
          STATUS mandatory
          DESCRIPTION
               ""
          ::= { teraAtmfCESTotalStatsTableEntry 1 }

teraAtmfCESTotalHdrErrors OBJECT-TYPE
          SYNTAX Counter32
          ACCESS read-only
          STATUS mandatory
          DESCRIPTION
               ""
          ::= { teraAtmfCESTotalStatsTableEntry 2 }

teraAtmfCESTotalPointerReframes OBJECT-TYPE
          SYNTAX Counter32
          ACCESS read-only
          STATUS mandatory
          DESCRIPTION
               ""
          ::= { teraAtmfCESTotalStatsTableEntry 3 }

teraAtmfCESTotalPointerParityErrors OBJECT-TYPE
          SYNTAX Counter32
          ACCESS read-only
          STATUS mandatory
          DESCRIPTION
               ""
          ::= { teraAtmfCESTotalStatsTableEntry 4 }

teraAtmfCESTotalAal1SeqErrors OBJECT-TYPE
          SYNTAX Counter32
          ACCESS read-only
          STATUS mandatory
          DESCRIPTION
               ""
          ::= { teraAtmfCESTotalStatsTableEntry 5 }

teraAtmfCESTotalLostCells OBJECT-TYPE
          SYNTAX Counter32
          ACCESS read-only
          STATUS mandatory
          DESCRIPTION
               ""
          ::= { teraAtmfCESTotalStatsTableEntry 6 }

teraAtmfCESTotalMisinsertedCells OBJECT-TYPE
          SYNTAX Counter32
          ACCESS read-only
          STATUS mandatory
          DESCRIPTION
               ""
          ::= { teraAtmfCESTotalStatsTableEntry 7 }

teraAtmfCESTotalBufUnderflows OBJECT-TYPE
          SYNTAX Counter32
          ACCESS read-only
          STATUS mandatory
          DESCRIPTION
               ""
          ::= { teraAtmfCESTotalStatsTableEntry 8 }

teraAtmfCESTotalBufOverflows OBJECT-TYPE
          SYNTAX Counter32
          ACCESS read-only
          STATUS mandatory
          DESCRIPTION
               ""
          ::= { teraAtmfCESTotalStatsTableEntry 9 }

teraAtmfCESTotalCellLossStatus OBJECT-TYPE
          SYNTAX INTEGER
                  {
                  noloss(1),
                  loss(2)
                  }
          ACCESS read-only
          STATUS mandatory
          DESCRIPTION
               ""
          ::= { teraAtmfCESTotalStatsTableEntry 10 }

teraAtmfCESTotalStatsStatus OBJECT-TYPE
          SYNTAX INTEGER
                  {
                  ok(1),
                  clear(2),
                  clrall(3)
                  }
          ACCESS read-write
          STATUS mandatory
          DESCRIPTION
               ""
          ::= { teraAtmfCESTotalStatsTableEntry 11 }

     -- teraAtmfCESStandard7DayTotalStatsTable

teraAtmfCESStandard7DayTotalStatsTable OBJECT-TYPE
     SYNTAX SEQUENCE OF TeraAtmfCESStandard7DayTotalStatsTableEntryType
     ACCESS not-accessible
     STATUS mandatory
     DESCRIPTION
          " table teraAtmfCESStandard7DayTotalStatsTable"
     ::= { bandwidthGroup 7 }

teraAtmfCESStandard7DayTotalStatsTableEntry OBJECT-TYPE
          SYNTAX TeraAtmfCESStandard7DayTotalStatsTableEntryType
          ACCESS not-accessible
          STATUS mandatory
          DESCRIPTION
               " table entry teraAtmfCESStandard7DayTotalStatsTableEntry "
          INDEX {                   atmfCESCbrIndex,                  teraAtmfCESStandard7DayTotalNumber }
     ::= { teraAtmfCESStandard7DayTotalStatsTable 1 }

TeraAtmfCESStandard7DayTotalStatsTableEntryType ::= SEQUENCE {
          teraAtmfCESStandard7DayTotalNumber   
             INTEGER (1..7),
          teraAtmfCESStandard7DayTotalReassCells   
             Counter32,
          teraAtmfCESStandard7DayTotalHdrErrors   
             Counter32,
          teraAtmfCESStandard7DayTotalPointerReframes   
             Counter32,
          teraAtmfCESStandard7DayTotalPointerParityErrors   
             Counter32,
          teraAtmfCESStandard7DayTotalAal1SeqErrors   
             Counter32,
          teraAtmfCESStandard7DayTotalLostCells   
             Counter32,
          teraAtmfCESStandard7DayTotalMisinsertedCells   
             Counter32,
          teraAtmfCESStandard7DayTotalBufUnderflows   
             Counter32,
          teraAtmfCESStandard7DayTotalBufOverflows   
             Counter32,
          teraAtmfCESStandard7DayTotalCellLossStatus   
             INTEGER,
          teraAtmfCESStandard7DayDayTotalValidData   
             INTEGER
}

teraAtmfCESStandard7DayTotalNumber OBJECT-TYPE
          SYNTAX INTEGER (1..7)
          ACCESS read-only
          STATUS mandatory
          DESCRIPTION
               ""
          ::= { teraAtmfCESStandard7DayTotalStatsTableEntry 1 }

teraAtmfCESStandard7DayTotalReassCells OBJECT-TYPE
          SYNTAX Counter32
          ACCESS read-only
          STATUS mandatory
          DESCRIPTION
               ""
          ::= { teraAtmfCESStandard7DayTotalStatsTableEntry 2 }

teraAtmfCESStandard7DayTotalHdrErrors OBJECT-TYPE
          SYNTAX Counter32
          ACCESS read-only
          STATUS mandatory
          DESCRIPTION
               ""
          ::= { teraAtmfCESStandard7DayTotalStatsTableEntry 3 }

teraAtmfCESStandard7DayTotalPointerReframes OBJECT-TYPE
          SYNTAX Counter32
          ACCESS read-only
          STATUS mandatory
          DESCRIPTION
               ""
          ::= { teraAtmfCESStandard7DayTotalStatsTableEntry 4 }

teraAtmfCESStandard7DayTotalPointerParityErrors OBJECT-TYPE
          SYNTAX Counter32
          ACCESS read-only
          STATUS mandatory
          DESCRIPTION
               ""
          ::= { teraAtmfCESStandard7DayTotalStatsTableEntry 5 }

teraAtmfCESStandard7DayTotalAal1SeqErrors OBJECT-TYPE
          SYNTAX Counter32
          ACCESS read-only
          STATUS mandatory
          DESCRIPTION
               ""
          ::= { teraAtmfCESStandard7DayTotalStatsTableEntry 6 }

teraAtmfCESStandard7DayTotalLostCells OBJECT-TYPE
          SYNTAX Counter32
          ACCESS read-only
          STATUS mandatory
          DESCRIPTION
               ""
          ::= { teraAtmfCESStandard7DayTotalStatsTableEntry 7 }

teraAtmfCESStandard7DayTotalMisinsertedCells OBJECT-TYPE
          SYNTAX Counter32
          ACCESS read-only
          STATUS mandatory
          DESCRIPTION
               ""
          ::= { teraAtmfCESStandard7DayTotalStatsTableEntry 8 }

teraAtmfCESStandard7DayTotalBufUnderflows OBJECT-TYPE
          SYNTAX Counter32
          ACCESS read-only
          STATUS mandatory
          DESCRIPTION
               ""
          ::= { teraAtmfCESStandard7DayTotalStatsTableEntry 9 }

teraAtmfCESStandard7DayTotalBufOverflows OBJECT-TYPE
          SYNTAX Counter32
          ACCESS read-only
          STATUS mandatory
          DESCRIPTION
               ""
          ::= { teraAtmfCESStandard7DayTotalStatsTableEntry 10 }

teraAtmfCESStandard7DayTotalCellLossStatus OBJECT-TYPE
          SYNTAX INTEGER
                  {
                  noloss(1),
                  loss(2)
                  }
          ACCESS read-only
          STATUS mandatory
          DESCRIPTION
               ""
          ::= { teraAtmfCESStandard7DayTotalStatsTableEntry 11 }

teraAtmfCESStandard7DayDayTotalValidData OBJECT-TYPE
          SYNTAX INTEGER
                  {
                  true(1),
                  false(2)
                  }
          ACCESS read-only
          STATUS mandatory
          DESCRIPTION
               ""
          ::= { teraAtmfCESStandard7DayTotalStatsTableEntry 12 }

     -- teraCESTera7DayTotalStatTable

teraCESTera7DayTotalStatTable OBJECT-TYPE
     SYNTAX SEQUENCE OF TeraCESTera7DayTotalStatTableEntryType
     ACCESS not-accessible
     STATUS mandatory
     DESCRIPTION
          " table teraCESTera7DayTotalStatTable"
     ::= { bandwidthGroup 8 }

teraCESTera7DayTotalStatTableEntry OBJECT-TYPE
          SYNTAX TeraCESTera7DayTotalStatTableEntryType
          ACCESS not-accessible
          STATUS mandatory
          DESCRIPTION
               " table entry teraCESTera7DayTotalStatTableEntry "
          INDEX {                   atmfCESCbrIndex,                  teraCESTera7DayTotalNumber }
     ::= { teraCESTera7DayTotalStatTable 1 }

TeraCESTera7DayTotalStatTableEntryType ::= SEQUENCE {
          teraCESTera7DayTotalNumber   
             INTEGER (1..7),
          teraCESTera7DayTotalTCellCount   
             Counter32,
          teraCESTera7DayTotalRLostCellCount   
             Counter32,
          teraCESTera7DayTotalRReplacedCellCount   
             Counter32,
          teraCESTera7DayDayTotalValidData   
             INTEGER
}

teraCESTera7DayTotalNumber OBJECT-TYPE
          SYNTAX INTEGER (1..7)
          ACCESS read-only
          STATUS mandatory
          DESCRIPTION
               ""
          ::= { teraCESTera7DayTotalStatTableEntry 1 }

teraCESTera7DayTotalTCellCount OBJECT-TYPE
          SYNTAX Counter32
          ACCESS read-only
          STATUS mandatory
          DESCRIPTION
               ""
          ::= { teraCESTera7DayTotalStatTableEntry 2 }

teraCESTera7DayTotalRLostCellCount OBJECT-TYPE
          SYNTAX Counter32
          ACCESS read-only
          STATUS mandatory
          DESCRIPTION
               ""
          ::= { teraCESTera7DayTotalStatTableEntry 3 }

teraCESTera7DayTotalRReplacedCellCount OBJECT-TYPE
          SYNTAX Counter32
          ACCESS read-only
          STATUS mandatory
          DESCRIPTION
               ""
          ::= { teraCESTera7DayTotalStatTableEntry 4 }

teraCESTera7DayDayTotalValidData OBJECT-TYPE
          SYNTAX INTEGER
                  {
                  true(1),
                  false(2)
                  }
          ACCESS read-only
          STATUS mandatory
          DESCRIPTION
               ""
          ::= { teraCESTera7DayTotalStatTableEntry 5 }

END
