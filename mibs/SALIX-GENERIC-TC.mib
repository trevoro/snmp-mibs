SALIX-GENERIC-TC DEFINITIONS ::= BEGIN

IMPORTS
         Integer32,            
         MODULE-IDENTITY      FROM SNMPv2-SMI
         
         TEXTUAL-CONVENTION   FROM SNMPv2-TC
         
         salixGeneric         FROM SALIX-MIB;

salixGenericTc MODULE-IDENTITY
     LAST-UPDATED "9810130000Z"
     ORGANIZATION "SALIX Technologies"
     CONTACT-INFO "904 Wind River Lane
                   Suite 101
                   Gaithersburg, MD  20878
                   (301)-417-0017"
     DESCRIPTION  "Contains Generic Textual Conventions for use in 
                   SALIX products"
     ::= { salixGeneric 2 }

InterfaceIndexOrZero ::= TEXTUAL-CONVENTION
       DISPLAY-HINT "d"
       STATUS       current
       DESCRIPTION
               "This textual convention is an extension of the
               InterfaceIndex convention.  The latter defines a
               greater than zero value used to identify an interface
               or interface sub-layer in the managed system.  This
               extension permits the additional value of zero.  the
               value zero is object-specific and must therefore be
               defined as part of the description of any object which
               uses this syntax.  Examples of the usage of zero might
               include situations where interface was unknown, or
               when none or all interfaces need to be referenced."
       SYNTAX       Integer32 (0.. 2147483647)
       
END
