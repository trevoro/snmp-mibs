AVICI-SERVER-MIB DEFINITIONS ::= BEGIN

IMPORTS
   MODULE-IDENTITY, OBJECT-TYPE, Unsigned32, NOTIFICATION-TYPE
      FROM SNMPv2-SMI
   MODULE-COMPLIANCE, OBJECT-GROUP, NOTIFICATION-GROUP
      FROM SNMPv2-CONF
   aviciMibs
      FROM AVICI-SMI
   AviciBayType, AviciSlotType, AviciHighAvailabilityType
      FROM AVICI-TC
   aviciSysTrapDescr
      FROM AVICI-SYSTEM-MIB;

aviciServerMIB MODULE-IDENTITY
   LAST-UPDATED   "001207151500Z"
   ORGANIZATION   "Avici Systems, Inc."
   CONTACT-INFO   "
                  Avici Systems, Inc.
                  101 Billerica Avenue
                  North Billerica, MA 01862-1256
 
                  (978) 964-2000
                  (978) 964-2100 (fax)
 
                  snmp@avici.com"
   DESCRIPTION
      "This MIB module specifies those managed objects that monitor and
       control a route server."
   REVISION      "001207151500Z"
   DESCRIPTION
      "Created MIB module."
   ::= { aviciMibs 9 }

aviciServerObjects       OBJECT IDENTIFIER ::= { aviciServerMIB 1 }

aviciServerGroup         OBJECT IDENTIFIER ::= { aviciServerMIB 2 }

aviciServerNotifications OBJECT IDENTIFIER ::= { aviciServerMIB 3 }

aviciServerNotificationPrefix OBJECT IDENTIFIER ::=
     { aviciServerNotifications 0 }

aviciServerHeartbeatType OBJECT-TYPE
    SYNTAX      AviciHighAvailabilityType
    MAX-ACCESS  accessible-for-notify
    STATUS      current
    DESCRIPTION
        "The type of server heartbeat."
    ::= { aviciServerGroup 1 }


aviciServerTable OBJECT-TYPE
    SYNTAX	SEQUENCE OF AviciServerEntry
    MAX-ACCESS	not-accessible
    STATUS	current
    DESCRIPTION
	"A list of servers, including primary and backup. "
    ::= { aviciServerObjects 1 }

aviciServerEntry OBJECT-TYPE
    SYNTAX	AviciServerEntry
    MAX-ACCESS	not-accessible
    STATUS	current
    DESCRIPTION
	"An entry containing information about a control server."
    INDEX { aviciServerIndex }
    ::= { aviciServerTable 1}

AviciServerEntry ::=
    SEQUENCE {
	aviciServerIndex	  Unsigned32,
        aviciServerBay            AviciBayType,
        aviciServerSlot           AviciSlotType,
	aviciServerState	  AviciHighAvailabilityType,
        aviciServerDomain         INTEGER,
        aviciServerOperStatus     INTEGER
    } 

aviciServerIndex        OBJECT-TYPE
    SYNTAX      Unsigned32 (1..64)
    MAX-ACCESS  read-only
    STATUS      current
    DESCRIPTION
        "The index number of the server."
    ::= { aviciServerEntry 1 }

aviciServerBay        OBJECT-TYPE
    SYNTAX      AviciBayType
    MAX-ACCESS  read-only
    STATUS      current
    DESCRIPTION
        "The bay containing this server."
    ::= { aviciServerEntry 2 }

aviciServerSlot        OBJECT-TYPE
    SYNTAX      AviciSlotType
    MAX-ACCESS  read-only
    STATUS      current
    DESCRIPTION
        "The slot containing this server."
    ::= { aviciServerEntry 3 }

aviciServerState OBJECT-TYPE
   SYNTAX       AviciHighAvailabilityType
   MAX-ACCESS   read-only
   STATUS       current
   DESCRIPTION
       "The current high availability state of the server."
   ::= { aviciServerEntry 4 }

aviciServerDomain OBJECT-TYPE
   SYNTAX       INTEGER {
       upper (1),  -- upper half of a 2+2 bay
       lower (2),  -- lower half of a 2+2 bay
       full  (3)   -- full bay (one or more bays)
       }
   MAX-ACCESS   read-only
   STATUS       current
   DESCRIPTION
       "The domain of this server.  The server can control
        the upper or lower half of a split bay or it can
        control one or more full bays."
   ::= { aviciServerEntry 5 }

aviciServerOperStatus OBJECT-TYPE
   SYNTAX       INTEGER {
       up(1),
       down(2),
       unknown(3),
       misconfigured (4)
       }
   MAX-ACCESS   read-only
   STATUS       current
   DESCRIPTION
       "The current operational state of the server."
   ::= { aviciServerEntry 6 }

--
-- Notifications
--

aviciServerUp     NOTIFICATION-TYPE
   OBJECTS { aviciServerIndex,
             aviciServerBay,
             aviciServerSlot,
             aviciServerState,
             aviciSysTrapDescr
           }
   STATUS	current 
   DESCRIPTION
       "This notification is sent when a route server changes state
        to up."
  ::= { aviciServerNotificationPrefix 1 }

aviciServerDown   NOTIFICATION-TYPE
   OBJECTS { aviciServerIndex,
             aviciServerBay,
             aviciServerSlot,
             aviciServerState,
             aviciSysTrapDescr
           }
   STATUS	current 
   DESCRIPTION
       "This notification is sent when a route server detects that a
        peer server has transitioned down.  If only one route server
        is present, this notification will not be sent."
  ::= { aviciServerNotificationPrefix 2 }

aviciServerHeartbeatUp   NOTIFICATION-TYPE
   OBJECTS { aviciServerIndex,
             aviciServerBay,
             aviciServerSlot,
             aviciServerHeartbeatType,
             aviciSysTrapDescr
           }
   STATUS	current 
   DESCRIPTION
       "This notification is sent when the server heartbeat transitions
        to up."
  ::= { aviciServerNotificationPrefix 3 }

aviciServerHeartbeatDown   NOTIFICATION-TYPE
   OBJECTS { aviciServerIndex,
             aviciServerBay,
             aviciServerSlot,
             aviciServerHeartbeatType,
             aviciSysTrapDescr
           }
   STATUS	current 
   DESCRIPTION
       "This notification is sent when the server heartbeat transitions
        to down."
  ::= { aviciServerNotificationPrefix 4 }

aviciServerMisconfigured   NOTIFICATION-TYPE
   OBJECTS {
             aviciServerIndex,
             aviciServerBay,
             aviciServerSlot,
             aviciSysTrapDescr
            }
   STATUS      current
   DESCRIPTION
       "This notification indicates that a route server is
        misconfigured and must have its configuration
        manually corrected."
   ::= { aviciServerNotificationPrefix 5 }

--
-- Conformance Information
--    

aviciServerMIBConformance OBJECT IDENTIFIER ::= { aviciServerMIB 4 }
aviciServerMIBCompliances OBJECT IDENTIFIER ::= { aviciServerMIBConformance 1 }
aviciServerMIBGroups OBJECT IDENTIFIER ::= { aviciServerMIBConformance 2 }

--
-- Compliance Statements
--

aviciServerMIBCompliance MODULE-COMPLIANCE
    STATUS current
    DESCRIPTION
        "The compliance statement for the aviciServer."
    MODULE
    MANDATORY-GROUPS {
        aviciServerGeneralGroup,
        aviciServerNotificationGroup
    }
    ::= { aviciServerMIBCompliances 1 }

aviciServerGeneralGroup OBJECT-GROUP
    OBJECTS {
        aviciServerHeartbeatType,
        aviciServerIndex,
        aviciServerBay,
        aviciServerSlot,
        aviciServerState,
        aviciServerDomain,
        aviciServerOperStatus

    }
    STATUS     current
    DESCRIPTION
        "Objects for the server."
    ::= { aviciServerMIBGroups 1 }

aviciServerNotificationGroup NOTIFICATION-GROUP
    NOTIFICATIONS {
        aviciServerUp,
        aviciServerDown,
        aviciServerHeartbeatUp,
        aviciServerHeartbeatDown,
        aviciServerMisconfigured
    }
    STATUS     current
    DESCRIPTION
        "Notifications for servers."
    ::= { aviciServerMIBGroups 2 }
END
