BAS-CM-CONFIG-MIB DEFINITIONS ::= BEGIN

IMPORTS
    MODULE-IDENTITY, OBJECT-TYPE, Integer32             FROM SNMPv2-SMI
    TruthValue                                          FROM SNMPv2-TC
    basCmConfig                                         FROM BAS-MIB;

basCmConfigMIB MODULE-IDENTITY
    LAST-UPDATED "9901200000Z"
    ORGANIZATION "Broadband Access Systems, Inc."
    CONTACT-INFO
        " Tech Support
          Broadband Access Systems, Inc.
          201 Forest Street
          Marlborough, MA 01752
          USA

          508-485-8200
          support@basystems.com"
    DESCRIPTION
        "This MIB module defines the configuration MIB objects
        used to create cable modem configuration files. "
    ::= { basCmConfig 1 }

basCmDsFreq OBJECT-TYPE
    SYNTAX      Integer32
    MAX-ACCESS  read-write
    STATUS      current
    DESCRIPTION
        "The receive frequency to be used by the CM. It is an
        override for the channel selected during scanning. This
        is the center frequency of the downstream channel in Hz
        stored as a 32-bit binary number."
    ::= { basCmConfigMIB 1 }

basCmUsChannelId OBJECT-TYPE
    SYNTAX      Integer32
    MAX-ACCESS  read-write
    STATUS      current
    DESCRIPTION
        ""
    ::= { basCmConfigMIB 2 }

basCmNetworkAccess OBJECT-TYPE
    SYNTAX      INTEGER {
                        off(0),
                        on(1)
                }
    MAX-ACCESS  read-write
    STATUS      current
    DESCRIPTION
        ""
    ::= { basCmConfigMIB 3 }

--*****************************************************************************
--* basCmCosTable
--*****************************************************************************

basCmCosTable OBJECT-TYPE
    SYNTAX      SEQUENCE OF BasCmCosEntry
    MAX-ACCESS  not-accessible
    STATUS      current
    DESCRIPTION
        ""
    ::= { basCmConfigMIB 4 }

basCmCosEntry OBJECT-TYPE
    SYNTAX      BasCmCosEntry
    MAX-ACCESS  not-accessible
    STATUS      current
    DESCRIPTION
      ""
    INDEX       { basCmCosClassId }
    ::= {basCmCosTable 1 }

BasCmCosEntry ::= 
    SEQUENCE {
        basCmCosClassId          Integer32,
        basCmCosMaxDsBps         Integer32,
        basCmCosMaxUsBps         Integer32,
        basCmCosUsPriority       INTEGER,
        basCmCosGuaranteedUsBps  Integer32,
        basCmCosMaxUsBurst       Integer32,
        basCmCosBp               INTEGER
    }

basCmCosClassId OBJECT-TYPE
    SYNTAX      Integer32
    MAX-ACCESS  read-write
    STATUS      current
    DESCRIPTION
        ""
    ::= { basCmCosEntry 1 }

basCmCosMaxDsBps OBJECT-TYPE
    SYNTAX      Integer32
    MAX-ACCESS  read-write
    STATUS      current
    DESCRIPTION
        ""
    ::= { basCmCosEntry 2 }

basCmCosMaxUsBps OBJECT-TYPE
    SYNTAX      Integer32
    MAX-ACCESS  read-write
    STATUS      current
    DESCRIPTION
        ""
    ::= { basCmCosEntry 3 }

basCmCosUsPriority OBJECT-TYPE
    SYNTAX      INTEGER {
                        zero(0),
                        one(1),
                        two(2),
                        three(3),
                        four(4),
                        five(5),
                        six(6),
                        seven(7)
                }
    MAX-ACCESS  read-write
    STATUS      current
    DESCRIPTION
        ""
    ::= { basCmCosEntry 4 }

basCmCosGuaranteedUsBps OBJECT-TYPE
    SYNTAX      Integer32
    MAX-ACCESS  read-write
    STATUS      current
    DESCRIPTION
        ""
    ::= { basCmCosEntry 5 }

basCmCosMaxUsBurst OBJECT-TYPE
    SYNTAX      Integer32
    MAX-ACCESS  read-write
    STATUS      current
    DESCRIPTION
        ""
    ::= { basCmCosEntry 6 }

basCmCosBp OBJECT-TYPE
    SYNTAX      INTEGER {
                        disable(0),
                        enable(1)
                }
    MAX-ACCESS  read-write
    STATUS      current
    DESCRIPTION
        ""
    ::= { basCmCosEntry 7 }

--*****************************************************************************
--* basCmCapabilities
--*****************************************************************************

basCmCapabilities OBJECT IDENTIFIER ::= { basCmConfigMIB 5 }

basCmCapConcat OBJECT-TYPE
    SYNTAX      INTEGER {
                        off(0),
                        on(1)
                }
    MAX-ACCESS  read-write
    STATUS      current
    DESCRIPTION
        ""
    ::= { basCmCapabilities 1 }


--*****************************************************************************
--* basSnmpMibObjectTable
--*****************************************************************************

basSnmpMibObjectTable OBJECT-TYPE
    SYNTAX      SEQUENCE OF BasSnmpMibObjectEntry
    MAX-ACCESS  not-accessible
    STATUS      current
    DESCRIPTION
        ""
    ::= { basCmConfigMIB 11 }

basSnmpMibObjectEntry OBJECT-TYPE
    SYNTAX      BasSnmpMibObjectEntry
    MAX-ACCESS  not-accessible
    STATUS      current
    DESCRIPTION
      ""
    INDEX       { basSnmpMibObjectIdx }
    ::= {basSnmpMibObjectTable 1 }

BasSnmpMibObjectEntry ::= 
    SEQUENCE {
        basSnmpMibObjectIdx              Integer32,
        basSnmpMibObjectVarBind          OCTET STRING
    }

basSnmpMibObjectIdx OBJECT-TYPE
    SYNTAX      Integer32
    MAX-ACCESS  read-write
    STATUS      current
    DESCRIPTION
        ""
    ::= { basSnmpMibObjectEntry 1 }

basSnmpMibObjectVarBind OBJECT-TYPE
    SYNTAX      OCTET STRING(SIZE(1..255))
    MAX-ACCESS  read-write
    STATUS      current
    DESCRIPTION
        ""
    ::= { basSnmpMibObjectEntry 2 }

--*****************************************************************************
--* basCpeAddressTable
--*****************************************************************************

basCpeAddressTable OBJECT-TYPE
    SYNTAX      SEQUENCE OF BasCpeAddressEntry
    MAX-ACCESS  not-accessible
    STATUS      current
    DESCRIPTION
        ""
    ::= { basCmConfigMIB 14 }

basCpeAddressEntry OBJECT-TYPE
    SYNTAX      BasCpeAddressEntry
    MAX-ACCESS  not-accessible
    STATUS      current
    DESCRIPTION
      ""
    INDEX       { basCpeAddressIdx }
    ::= {basCpeAddressTable 1 }

BasCpeAddressEntry ::= 
    SEQUENCE {
        basCpeAddressIdx              Integer32,
        basCpeAddressMacAddr          OCTET STRING
    }

basCpeAddressIdx OBJECT-TYPE
    SYNTAX      Integer32
    MAX-ACCESS  read-write
    STATUS      current
    DESCRIPTION
        ""
    ::= { basCpeAddressEntry 1 }

basCpeAddressMacAddr OBJECT-TYPE
    SYNTAX      OCTET STRING(SIZE(6))
    MAX-ACCESS  read-write
    STATUS      current
    DESCRIPTION
        ""
    ::= { basCpeAddressEntry 2 }

--*****************************************************************************
--* basCmBpiSettings
--*****************************************************************************

basCmBpiSettings OBJECT IDENTIFIER ::= { basCmConfigMIB 17 }

basCmBpiAuthWaitTimeout OBJECT-TYPE
    SYNTAX      INTEGER(1..30)
    MAX-ACCESS  read-write
    STATUS      current
    DESCRIPTION
        ""
    ::= { basCmBpiSettings 1 }

basCmBpiReAuthWaitTimeout OBJECT-TYPE
    SYNTAX      INTEGER(1..30)
    MAX-ACCESS  read-write
    STATUS      current
    DESCRIPTION
        ""
    ::= { basCmBpiSettings 2 }

basCmBpiAuthGraceTime OBJECT-TYPE
    SYNTAX      INTEGER(1..1800)
    MAX-ACCESS  read-write
    STATUS      current
    DESCRIPTION
        ""
    ::= { basCmBpiSettings 3 }

basCmBpiOperWaitTimeout OBJECT-TYPE
    SYNTAX      INTEGER(1..10)
    MAX-ACCESS  read-write
    STATUS      current
    DESCRIPTION
        ""
    ::= { basCmBpiSettings 4 }

basCmBpiRekeyWaitTimeout OBJECT-TYPE
    SYNTAX      INTEGER(1..10)
    MAX-ACCESS  read-write
    STATUS      current
    DESCRIPTION
        ""
    ::= { basCmBpiSettings 5 }

basCmBpiTEKGraceTime OBJECT-TYPE
    SYNTAX      INTEGER(5..30)
    MAX-ACCESS  read-write
    STATUS      current
    DESCRIPTION
        ""
    ::= { basCmBpiSettings 6 }

basCmBpiAuthRejectWaitTimeout OBJECT-TYPE
    SYNTAX      INTEGER(1..600)
    MAX-ACCESS  read-write
    STATUS      current
    DESCRIPTION
        ""
    ::= { basCmBpiSettings 7 }

basCmBpiSAMapWaitTimeout OBJECT-TYPE
    SYNTAX      INTEGER(1..10)
    MAX-ACCESS  read-write
    STATUS      current
    DESCRIPTION
        ""
    ::= { basCmBpiSettings 8 }

basCmBpiMaxClockDrift OBJECT-TYPE
    SYNTAX      INTEGER(1..1800)
    MAX-ACCESS  read-write
    STATUS      current
    DESCRIPTION
        ""
    ::= { basCmBpiSettings 9 }

basCmBpiSAMapMaxRetries OBJECT-TYPE
    SYNTAX      INTEGER(0..10)
    MAX-ACCESS  read-write
    STATUS      current
    DESCRIPTION
        ""
    ::= { basCmBpiSettings 10 }


basCmMaxNumCPEs OBJECT-TYPE
    SYNTAX      Integer32
    MAX-ACCESS  read-write
    STATUS      current
    DESCRIPTION
        "The maximum number of CPEs that can be granted access
        through a CM during a CM epoch. The maximum number of
        CPEs MUST be enforced by the CM."
    ::= { basCmConfigMIB 18 }

--*****************************************************************************
--* Make sure the CM MIC and CMTS MIC are last.
--*****************************************************************************

basCmMIC OBJECT-TYPE
    SYNTAX      OCTET STRING(SIZE(16))
    MAX-ACCESS  read-write
    STATUS      current
    DESCRIPTION
        ""
    ::= { basCmConfigMIB 256 }

basCmtsMIC OBJECT-TYPE
    SYNTAX      OCTET STRING(SIZE(16))
    MAX-ACCESS  read-write
    STATUS      current
    DESCRIPTION
        ""
    ::= { basCmConfigMIB 257 }

basCmEndOfMib OBJECT-TYPE
    SYNTAX      Integer32
    MAX-ACCESS  not-accessible
    STATUS      current
    DESCRIPTION
        "This object is used to mark the end of the cable
        modem configuration MIB. Add any new objects before
        this object. Do not add any cable modem configuration
        objects after this object."
    ::= { basCmConfigMIB 258 }

END
