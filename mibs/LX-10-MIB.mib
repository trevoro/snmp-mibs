LX-10-MIB DEFINITIONS ::= BEGIN

 IMPORTS
         enterprises, IpAddress, Counter FROM RFC1155-SMI
         DisplayString, PhysAddress      FROM RFC1213-MIB
         TRAP-TYPE                       FROM RFC-1215
         OBJECT-TYPE                     FROM RFC-1212;

 onstream    OBJECT IDENTIFIER ::= { enterprises 135 }
 lx-10       OBJECT IDENTIFIER ::= { onstream     22 }

 -- groups in FRESNO

 -- The managed objects for DS1 performance are defined in
 -- rfc1406 (Definitions of Managed Objects for the DS1 and E1
 -- Interface Types).

 sys          OBJECT IDENTIFIER ::= { lx-10 1 }

 config       OBJECT IDENTIFIER ::= { lx-10 2 }

 fault        OBJECT IDENTIFIER ::= { lx-10 3 }

 perf         OBJECT IDENTIFIER ::= { lx-10 4 }

 TimeAndDate ::= OCTET STRING (SIZE(6..6))

 -- This data type is used to represent the current system time.
 -- It is composed of 6 data bytes defined as follows:
 --
 -- byte 1 - year   (0..99)
 -- byte 2 - month  (1..12)
 -- byte 3 - day    (1..31)
 -- byte 4 - hour   (0..23)
 -- byte 5 - minute (0..59)
 -- byte 6 - second (0..59)

 -- sys (System Administration) group

 -- General System Information

 sysGenInfo  OBJECT IDENTIFIER ::= { sys 1 }

 sysGenInfoShelfName OBJECT-TYPE
     SYNTAX  DisplayString (SIZE(0..16))
     ACCESS  read-write
     STATUS  mandatory
     DESCRIPTION
             "Name of the managed node."
     ::= { sysGenInfo 1 }

 sysGenInfoCustomerName OBJECT-TYPE
     SYNTAX  DisplayString (SIZE(0..32))
     ACCESS  read-write
     STATUS  mandatory
     DESCRIPTION
             "Name of the organization that uses the managed node."
     ::= { sysGenInfo 2 }

 sysGenInfoPhoneNumber OBJECT-TYPE
     SYNTAX  DisplayString (SIZE(0..32))
     ACCESS  read-write
     STATUS  mandatory
     DESCRIPTION
             "Phone number of the organization that uses
              the managed node."
     ::= { sysGenInfo 3 }

 sysGenInfoMaintenanceContact OBJECT-TYPE
     SYNTAX  DisplayString (SIZE(0..32))
     ACCESS  read-write
     STATUS  mandatory
     DESCRIPTION
             "Maintenance contact of the managed node."
     ::= { sysGenInfo 4 }

 sysGenInfoLocation OBJECT-TYPE
     SYNTAX  DisplayString (SIZE(0..32))
     ACCESS  read-write
     STATUS  mandatory
     DESCRIPTION
             "Location of the managed node."
     ::= { sysGenInfo 5 }

 sysGenInfoAutoLogoutTime OBJECT-TYPE
     SYNTAX  INTEGER (1..99)
     ACCESS  read-write
     STATUS  mandatory
     DESCRIPTION
             "The time a TELNET or VT-100 terminal user can maintain
              a session with the managed node without any keyboard
              action.  Unit: minute"
     DEFVAL  { 10 }
     ::= { sysGenInfo 6 }

 sysGenInfoPassword OBJECT-TYPE
     SYNTAX  OCTET STRING (SIZE(0..16))
     ACCESS  read-write
     STATUS  mandatory
     DESCRIPTION
             "Password required to access the managed node using
              VT-100 terminal or TELNET.  A get request always
              returns a NULL string."
     DEFVAL  { "onstream" }
     ::= { sysGenInfo 7 }

 sysGenInfoShelfId OBJECT-TYPE
     SYNTAX  INTEGER (1..255)
     ACCESS  read-write
     STATUS  mandatory
     DESCRIPTION
             "LX-10 unit identification number required to identify
              and set up the device's role (primary/secondary). This 
              number should be unique among interconnected devices."
     DEFVAL  { 255 }
     ::= { sysGenInfo 8 }

 -- Time and Date

 sysTimeAndDate OBJECT-TYPE
     SYNTAX  TimeAndDate
     ACCESS  read-write
     STATUS  mandatory
     DESCRIPTION
             "Time and date maintained in the managed node."
     ::= { sys 2 }

 -- IP Network Configuration

 sysIpConfig  OBJECT IDENTIFIER ::= { sys 3 }

 -- host interface subgroup
 -- 
 -- The objects in this subgroup includes the information
 -- required by the SNMP managers or TELENT clients to
 -- communicate with the SNMP agent and TELNET server in
 -- the managed node.
 -- 

 sysIpConfigHostInterfaceTable OBJECT-TYPE
     SYNTAX  SEQUENCE OF SysIpConfigHostInterfaceEntry
     ACCESS  not-accessible
     STATUS  mandatory
     DESCRIPTION
             "Table of available host IP interfaces."
     ::= { sysIpConfig 1 }

 sysIpConfigHostInterfaceEntry OBJECT-TYPE
     SYNTAX  SysIpConfigHostInterfaceEntry
     ACCESS  not-accessible
     STATUS  mandatory
     DESCRIPTION
             "Each entry contains the IP address and subnet mask of the
              specified interface and a flag which enables/disables the
              managed node to broadcast its (RIP) routing table through
              the interface."
     INDEX   { sysIpConfigHostInterfaceIndex }
     ::= { sysIpConfigHostInterfaceTable 1 }

 SysIpConfigHostInterfaceEntry ::=
     SEQUENCE {
         sysIpConfigHostInterfaceIndex
             INTEGER,
         sysIpConfigHostInterfaceIpAddress
             IpAddress,
         sysIpConfigHostInterfaceSubnetMask
             IpAddress,
         sysIpConfigHostInterfaceXmtRoutingMsg
             INTEGER
     }

 sysIpConfigHostInterfaceIndex OBJECT-TYPE
     SYNTAX  INTEGER { ethernet (1),
                       slip     (2),
                       nxt1     (3) }
     ACCESS  read-only
     STATUS  mandatory
     DESCRIPTION
             ""
     ::= { sysIpConfigHostInterfaceEntry 1 }

 sysIpConfigHostInterfaceIpAddress OBJECT-TYPE
     SYNTAX  IpAddress
     ACCESS  read-only
     STATUS  mandatory
     DESCRIPTION
             "Host's IP address."
     DEFVAL  { '00000000'h }
     ::= { sysIpConfigHostInterfaceEntry 2 }

 sysIpConfigHostInterfaceSubnetMask OBJECT-TYPE
     SYNTAX  IpAddress
     ACCESS  read-only
     STATUS  mandatory
     DESCRIPTION
             "Host's IP subnet mask."
     DEFVAL  { '00000000'h }
     ::= { sysIpConfigHostInterfaceEntry 3 }

 sysIpConfigHostInterfaceXmtRoutingMsg OBJECT-TYPE
     SYNTAX  INTEGER { disabled (1),
                       enabled  (2) }
     ACCESS  read-write
     STATUS  mandatory
     DESCRIPTION
             "This object controls whether the managed node should
              broadcast its (RIP) routing table through the interface."
     ::= { sysIpConfigHostInterfaceEntry 4 }

 -- default gateway subgroup
 --
 -- The objects in this subgroup are required when there are
 -- trap clients whose network portion of the IP addresses are
 -- not the same as the network portion of the local host's
 -- Ethernet/NxT1 IP addresses.  The SNMP agent in the managed
 -- node depends on the default gateway to route SNMP trap messages
 -- to the trap clients.
 --

 sysIpConfigDefaultGateway OBJECT IDENTIFIER ::= { sysIpConfig 2 }

 sysIpConfigDefaultGatewayIpAddress OBJECT-TYPE
     SYNTAX  IpAddress
     ACCESS  read-write
     STATUS  mandatory
     DESCRIPTION
             "Default gateway's IP address."
     DEFVAL { '00000000'h }
     ::= { sysIpConfigDefaultGateway 1 }

 sysIpConfigDefaultGatewaySubnetMask OBJECT-TYPE
     SYNTAX  IpAddress
     ACCESS  read-write
     STATUS  mandatory
     DESCRIPTION
             "Default gateway's IP subnet mask."
     DEFVAL  { '00000000'h }
     ::= { sysIpConfigDefaultGateway 2 }

 -- trap client table
 --
 -- Each entry in this table contains the information of an SNMP
 -- trap client which receives SNMP traps from the SNMP agent in
 -- the managed node.  If any of the SNMP trap client has different
 -- network address than the host interfaces (Ethernet/NxT1) in the
 -- managed node, it relies on the default gateway to route the trap
 -- messages.  And the IP address and subnet mask in the default
 -- gateway must be properly configured.
 --

 sysIpConfigTrapClientTable OBJECT-TYPE
     SYNTAX  SEQUENCE OF SysIpConfigTrapClientEntry
     ACCESS  not-accessible
     STATUS  mandatory
     DESCRIPTION
             "Trap client table has 4 entries"
     ::= { sysIpConfig 3 }

 sysIpConfigTrapClientEntry OBJECT-TYPE
     SYNTAX  SysIpConfigTrapClientEntry
     ACCESS  not-accessible
     STATUS  mandatory
     DESCRIPTION
             "Each entry contains IP address and port number of
              an SNMP manager which receives traps from the
              managed node."
     INDEX   { sysIpConfigTrapClientIndex }
     ::= { sysIpConfigTrapClientTable 1 }

 SysIpConfigTrapClientEntry ::=
     SEQUENCE {
         sysIpConfigTrapClientIndex
             INTEGER,
         sysIpConfigTrapClientIpAddress
             IpAddress,
         sysIpConfigTrapClientSubnetMask
             IpAddress,
         sysIpConfigTrapClientPortNumber
             INTEGER
     }

 sysIpConfigTrapClientIndex OBJECT-TYPE
     SYNTAX  INTEGER (1..4)
     ACCESS  read-write
     STATUS  mandatory
     DESCRIPTION
             ""
     ::= { sysIpConfigTrapClientEntry 1 }

 sysIpConfigTrapClientIpAddress OBJECT-TYPE
     SYNTAX  IpAddress
     ACCESS  read-write
     STATUS  mandatory
     DESCRIPTION
             "Trap client's IP address."
     DEFVAL  { '00000000'h }
     ::= { sysIpConfigTrapClientEntry 2 }

 sysIpConfigTrapClientSubnetMask OBJECT-TYPE
     SYNTAX  IpAddress
     ACCESS  read-write
     STATUS  mandatory
     DESCRIPTION
             "Trap client's IP subnet mask."
     DEFVAL  { '00000000'h }
     ::= { sysIpConfigTrapClientEntry 3 }

 sysIpConfigTrapClientPortNumber OBJECT-TYPE
     SYNTAX  INTEGER
     ACCESS  read-write
     STATUS  mandatory
     DESCRIPTION
             "Trap client's port number."
     DEFVAL  { 162 }
     ::= { sysIpConfigTrapClientEntry 4 }

 -- SNMP Agent Community Name

 sysIpConfigCommunityName OBJECT-TYPE
     SYNTAX  DisplayString (SIZE(0..64))
     ACCESS  read-write
     STATUS  mandatory
     DESCRIPTION
             "Community name of the managed node.  A get request
              for an instance of this object always returns a
              NULL string."
     DEFVAL  { "onstream" }
     ::= { sysIpConfig 4 }

 -- Management Ethernet MAC address

 sysIpConfigMacAddress OBJECT-TYPE
     SYNTAX  PhysAddress
     ACCESS  read-only
     STATUS  mandatory
     DESCRIPTION
             "MAC-layer address of the management Ethernet port."
     ::= { sysIpConfig 5 }

 -- RS232 Ports Configuration

 sysRs232Table OBJECT-TYPE
     SYNTAX  SEQUENCE OF SysRs232Entry
     ACCESS  not-accessible
     STATUS  mandatory
     DESCRIPTION
             "This table contains 2 rows.  The first row shows the physical
              configuration of the port connected to a VT100 termianl.  The
              second row is used to configure the port which supports SLIP.
              Access to the first row is read-only and access to the second
              row is read-write."
     ::= { sys 4 }

 sysRs232Entry OBJECT-TYPE
     SYNTAX  SysRs232Entry
     ACCESS  not-accessible
     STATUS  mandatory
     DESCRIPTION
             "Each entry contains the attributes of a serial port."
     INDEX   { sysRs232Port }
     ::= { sysRs232Table 1 }

 SysRs232Entry ::=
     SEQUENCE {
         sysRs232Port
             INTEGER,
         sysRs232BaudRate
             INTEGER,
         sysRs232Parity
             INTEGER,
         sysRs232DataBits
             INTEGER,
         sysRs232StopBits
             INTEGER
     }

 sysRs232Port OBJECT-TYPE
     SYNTAX  INTEGER { port-1 (1),
                       port-2 (2) }
     ACCESS  read-only
     STATUS  mandatory
     DESCRIPTION
             "The managed node has 2 serial ports: port 1 and port 2."
     ::= { sysRs232Entry 1 }

 sysRs232BaudRate OBJECT-TYPE
     SYNTAX  INTEGER { br-300   (1),
                       br-1200  (2),
                       br-2400  (3),
                       br-4800  (4),
                       br-9600  (5),
                       br-19200 (6),
                       br-38400 (7) }
     ACCESS  read-write
     STATUS  mandatory
     DESCRIPTION
             "Baud rate.  The instance of this object in port-1
              is read-only."
     DEFVAL { br-9600 }
     ::= { sysRs232Entry 2 }

 sysRs232Parity OBJECT-TYPE
     SYNTAX  INTEGER { none (1),
                       even (2),
                       odd  (3) }
     ACCESS  read-write
     STATUS  mandatory
     DESCRIPTION
             "Parity.  The instance of this object in port-1 is
              read-only."
     DEFVAL { none }
     ::= { sysRs232Entry 3 }

 sysRs232DataBits OBJECT-TYPE
     SYNTAX  INTEGER { db-7 (1),
                       db-8 (2) }
     ACCESS  read-write
     STATUS  mandatory
     DESCRIPTION
             "Number of data bits.  The instance of this object
              in port-1 is read-only."
     DEFVAL { db-8 }
     ::= { sysRs232Entry 4 }

 sysRs232StopBits OBJECT-TYPE
     SYNTAX  INTEGER { sb-1 (1),
                       sb-2 (2) }
     ACCESS  read-write
     STATUS  mandatory
     DESCRIPTION
             "Number of stop bits.  The instance of this object
              in port-1 is read-only."
     DEFVAL { sb-1 }
     ::= { sysRs232Entry 5 }

 -- Firmware Version

 sysMainProcessorFirmwareRev OBJECT-TYPE
     SYNTAX  DisplayString (SIZE(4..10))
     ACCESS  read-only
     STATUS  mandatory
     DESCRIPTION
             "Firmware revision of the management CPU."
     ::= { sys 5 }

 sysPortCardFirmwareRev OBJECT-TYPE
     SYNTAX  DisplayString (SIZE(4..10))
     ACCESS  read-only
     STATUS  mandatory
     DESCRIPTION
             "Firmware revision of the Ethernet (DATA) card."
     ::= { sys 6 }

 -- config (Configuration Management) group

 -- DS1 ports configuration table

 configDs1Table OBJECT-TYPE
     SYNTAX  SEQUENCE OF ConfigDs1Entry
     ACCESS  not-accessible
     STATUS  mandatory
     DESCRIPTION
             "DS1 configuration table."
     ::= { config 1 }

 configDs1Entry OBJECT-TYPE
     SYNTAX  ConfigDs1Entry
     ACCESS  not-accessible
     STATUS  mandatory
     DESCRIPTION
             "Each entry contains the configuration attributes
              for a DS1 port."
     INDEX   { configDs1Port }
     ::= { configDs1Table 1 }

 ConfigDs1Entry ::=
     SEQUENCE {
         configDs1Port
             INTEGER,
         configDs1AdminStatus
             INTEGER,
         configDs1OperStatus
             INTEGER,
         configDs1LBO
             INTEGER,
         configDs1Encoding
             INTEGER,
         configDs1Framing
             INTEGER,
         configDs1XmtAis
             INTEGER
     }

 configDs1Port OBJECT-TYPE
     SYNTAX  INTEGER (1..7)
     ACCESS  read-only
     STATUS  mandatory
     DESCRIPTION
             "DS1 port number."
     ::= { configDs1Entry 1 }

 configDs1AdminStatus OBJECT-TYPE
     SYNTAX  INTEGER { disabled (1),
                       enabled  (2) }
     ACCESS  read-write
     STATUS  mandatory
     DESCRIPTION
             "DS1 administrative status."
     ::= { configDs1Entry 2 }

 configDs1OperStatus OBJECT-TYPE
     SYNTAX  INTEGER { down (1),
                       up   (2) }
     ACCESS  read-only
     STATUS  mandatory
     DESCRIPTION
             "DS1 operational status."
     ::= { configDs1Entry 3 }

 configDs1LBO OBJECT-TYPE
     SYNTAX  INTEGER { dB-0   (1),    -- 0    dB
                       dB-7-5 (2),    -- -7.5 dB
                       dB-15  (3) }   -- -15  dB
     ACCESS  read-write
     STATUS  mandatory
     DESCRIPTION
             "LBO.  This object is not accessible if the
              managed node is the E1 version of LX10."
     ::= { configDs1Entry 4 }

 configDs1Encoding OBJECT-TYPE
     SYNTAX  INTEGER { b8zs (1),
                       ami  (2) }
     ACCESS  read-write
     STATUS  mandatory
     DESCRIPTION
             "Encoding.  This object is not accessible if the
              managed node is the E1 version of LX10."
     ::= { configDs1Entry 5 }

 configDs1Framing OBJECT-TYPE
     SYNTAX  INTEGER { esf (1),
                       d4  (2) }
     ACCESS  read-write
     STATUS  mandatory
     DESCRIPTION
             "Framing format.  This object is not accessible if the
              managed node is the E1 version of LX10."
     ::= { configDs1Entry 6 }

 configDs1XmtAis OBJECT-TYPE
     SYNTAX  INTEGER { disabled (1),
                       enabled  (2) }
     ACCESS  read-write
     STATUS  mandatory
     DESCRIPTION
             "Enable/disable transmit AIS."
     ::= { configDs1Entry 7 }

 -- DS1 Timing Configuration

 configDs1Timing OBJECT-TYPE
     SYNTAX  INTEGER { looped   (1),
                       internal (2) }
     ACCESS  read-write
     STATUS  mandatory
     DESCRIPTION
             "DS1 clock Source."
     ::= { config 2 }

 -- afa (Automatic Frequency Adjustment) management

 configAfa       OBJECT IDENTIFIER ::= { config 3 }

 configAfaActivationRate OBJECT-TYPE
     SYNTAX  INTEGER { a-10-4 (1),
                       a-10-5 (2),
                       a-10-6 (3),
                       a-10-7 (4),
                       a-10-8 (5) }
     ACCESS  read-write
     STATUS  mandatory
     DESCRIPTION
             "AFA activation rate is used by the managed node to
              decide when it will disable the operational status
              of a T1 interface if the interface's BER rate is
              above the selected activation rate for a period
              specified by configAfaActivationTime (see below)."
     ::= { configAfa 1 }

 configAfaActivationTime OBJECT-TYPE
     SYNTAX  INTEGER (1..15)
     ACCESS  read-write
     STATUS  mandatory
     DESCRIPTION
             "See above description.  Unit - minute"
     ::= { configAfa 2 }

 configAfaDeactivationRate OBJECT-TYPE
     SYNTAX  INTEGER { d-10-6 (1),
                       d-10-7 (2),
                       d-10-8 (3),
                       d-10-9 (4) }
     ACCESS  read-write
     STATUS  mandatory
     DESCRIPTION
             "AFA deactivation rate is used by the managed node to
              decide when it will enable the operational status of
              a T1 interface if the interface's BER rate is below the
              selected activation rate for a period specified by
              configAfaDectivationTime (see below)."
     ::= { configAfa 3 }

 configAfaDeactivationTime OBJECT-TYPE
     SYNTAX  INTEGER (15..30)
     ACCESS  read-write
     STATUS  mandatory
     DESCRIPTION
             "See above description.  Unit - minute"
     ::= { configAfa 4 }

 configAfaStatus OBJECT-TYPE
     SYNTAX  INTEGER { disabled (1),
                       enabled  (2) }
     ACCESS  read-write
     STATUS  mandatory
     DESCRIPTION
             "Enable/disable AFA function."
     ::= { configAfa 5 }

 configAfaFarEndLpbkDetect OBJECT-TYPE
     SYNTAX  INTEGER { disabled (1),
                       enabled  (2) }
     ACCESS  read-write
     STATUS  mandatory
     DESCRIPTION
             "This object controls whether AFA will be activated when
              a near end LX-10 detects network loopback in the far end
              LX-10.  If it's disabled, no AFA will be activated because
              of a far end network loopback."
     ::= { configAfa 6 }

 -- port card type

 configPortCardType OBJECT-TYPE
     SYNTAX  INTEGER { hsdp       (1),  -- high speed data port
                       ethernet   (2),  -- ethernet card
                       token-ring (3) } -- token ring card
     ACCESS  read-only
     STATUS  mandatory
     DESCRIPTION
             "There are 3 kinds of cards/port supported by the
              managed node:

              HSDP,
              Ethernet, or
              Token-Ring.

              Only one of them can be installed in the managed node.
              Hsdp is a high speed data port with v.35, rs-422,
              and HSSI interfaces."
     ::= { config 4 }

 -- High Speed Data Port configuration

 configHsdp   OBJECT IDENTIFIER ::= { config 5 }

 configHsdpMode OBJECT-TYPE
     SYNTAX  INTEGER { v-35   (1),
                       rs-422 (2),
                       hssi   (3) }
     ACCESS  read-write
     STATUS  mandatory
     DESCRIPTION
             "Interface type used by HSDP."
     DEFVAL { hssi }
     ::= { configHsdp 1 }

 configHsdpCtsControl OBJECT-TYPE
     SYNTAX  INTEGER { set               (1),
                       no-bandwidth      (2),
                       frequency-change  (3) }
     ACCESS  read-write
     STATUS  mandatory
     DESCRIPTION
             "CTS line control in HSDP.  If the value of an instance of
              this object is set, the CTS line will always be set. If the
              value of an instance of this object is no-bandwidth, the CTS
              line will go low when no bandwidth is available after a hold-off 
              time. If the value of an instance of this object is frequency-
              change, the CTS line will go low for a hold-off time when there 
              is a frequency change."
     ::= { configHsdp 2 }

 configHsdpCtsStatus OBJECT-TYPE
     SYNTAX  INTEGER { clear (1),
                       set   (2) }
     ACCESS  read-only
     STATUS  mandatory
     DESCRIPTION
             "Status of CTS line in HSDP."
     ::= { configHsdp 3 }

 configHsdpTermTimingSource OBJECT-TYPE
     SYNTAX  INTEGER { external (1),
                       internal (2) }
     ACCESS  read-write
     STATUS  mandatory
     DESCRIPTION
             "Terminal timing source in HSDP.  It applies only
              when the value of the instance of configHsdpMode is
              v-35 or rs-422."
     ::= { configHsdp 4 }

 configHsdpTermTiming OBJECT-TYPE
     SYNTAX  INTEGER { normal   (1),
                       inverted (2) }
     ACCESS  read-write
     STATUS  mandatory
     DESCRIPTION
             "Status of terminal timing in HSDP.  It applies only
              when the value of the instance of configHsdpMode is
              v-35 or rs-422."
     ::= { configHsdp 5 }

 configHsdpRecvTiming OBJECT-TYPE
     SYNTAX  INTEGER { normal   (1),
                       inverted (2) }
     ACCESS  read-write
     STATUS  mandatory
     DESCRIPTION
             "Status of receive timing in HSDP.  It applies only
              when the value of the instance of configHsdpMode is
              v-35 or rs-422."
     ::= { configHsdp 6 }

 configHsdpHoldoffSeconds OBJECT-TYPE
     SYNTAX  INTEGER { sec1  (1),
                       sec2  (2),
                       sec3  (3),
                       sec4  (4),
                       sec5  (5) }
     ACCESS  read-write
     STATUS  mandatory
     DESCRIPTION
             "Hold-off time for CA lead. If the hold-off is set at 5 seconds,
              and if the CTS control is sensitive to no-bandwidth, the CTS 
              line will go low after 5 seconds when no bandwidth is available. 
              If the CTS control is sensitive to frequency-change, the CTS 
              line will stay low for 5 seconds when there is a frequency 
              change, and then back to high."
     ::= { configHsdp 7 }

-- HDLC configuration

 configHdlc   OBJECT IDENTIFIER ::= { config 6 }

 configHdlcMode OBJECT-TYPE
     SYNTAX  INTEGER { auto   (1),
                       manual (2) }
     ACCESS  read-write
     STATUS  mandatory
     DESCRIPTION
             "Select the way in which HDLC port will be assigned.
              If mode is manual, the HDLC port is selectable by
              the NMS.  If mode is auto, the 2 LX-10's in the 2
              sides will match their HDLC ports automatically."
     ::= { configHdlc 1 }

 configHdlcLocalPort OBJECT-TYPE
     SYNTAX  INTEGER (0..7)
     ACCESS  read-write
     STATUS  mandatory
     DESCRIPTION
             "Assign one of the DS1 ports as the HDLC port.  If its
              value is 0, no port is asssigned as the HDLC port. "
     ::= { configHdlc 2 }

 configHdlcFarEndPort OBJECT-TYPE
     SYNTAX  INTEGER (0..7)
     ACCESS  read-only
     STATUS  mandatory
     DESCRIPTION
             "The DS1 port currently being used as the HDLC port in
              the far end LX-10."
     ::= { configHdlc 3 }

 -- Inverse Mux Configuration

 configInverseMux OBJECT-TYPE
     SYNTAX  INTEGER { secondary (1),
                       primary   (2) }
     ACCESS  read-write
     STATUS  mandatory
     DESCRIPTION
             "Master/slave relationship of the 2 LX-10E's in the
              point to point connection."
     ::= { config 7 }


 -- Fault Management group

 -- DS1 loopback control for the DS1 interfaces in the managed node

 faultDs1   OBJECT IDENTIFIER ::= { fault 1 }

 faultDs1LoopbackTable OBJECT-TYPE
     SYNTAX  SEQUENCE OF FaultDs1LoopbackEntry
     ACCESS  not-accessible
     STATUS  mandatory
     DESCRIPTION
             "DS1 loopback table for 7 DS1 ports."
     ::= { faultDs1 1 }

 faultDs1LoopbackEntry OBJECT-TYPE
     SYNTAX  FaultDs1LoopbackEntry
     ACCESS  not-accessible
     STATUS  mandatory
     DESCRIPTION
             "Each entry in the table contains the
              loopback status of a DS1 port."
     INDEX   { faultDs1LoopbackPort }
     ::= { faultDs1LoopbackTable 1 }

 FaultDs1LoopbackEntry ::=
     SEQUENCE {
         faultDs1LoopbackPort
             INTEGER,
         faultDs1LoopbackNetworkLoopback
             INTEGER
     }

 faultDs1LoopbackPort OBJECT-TYPE
     SYNTAX  INTEGER (1..7)
     ACCESS  read-only
     STATUS  mandatory
     DESCRIPTION
             "The port number of one of the 7 DS1 ports"
     ::= { faultDs1LoopbackEntry 1 }

 faultDs1LoopbackNetworkLoopback OBJECT-TYPE
     SYNTAX  INTEGER { none (1),
                       card (2),
                       line (3) }
     ACCESS  read-write
     STATUS  mandatory
     DESCRIPTION
             "DS1 loopback is used to control the loopback state of
              one of the 7 DS1 interfaces in the managed node."
     ::= { faultDs1LoopbackEntry 2 }

 faultDs1RemoteLineLoopback OBJECT-TYPE
     SYNTAX  INTEGER { inactive (1),
                       active   (2) }
     ACCESS  read-only
     STATUS  mandatory
     DESCRIPTION
             "This loopback status is controlled by the LA/LB leads
              in the remote node."
     ::= { faultDs1 2 }

 -- LA/LB loopback is the loopback request from the customer
 -- equipment (DTE).  To enable/disable LA/LB loopback, set
 -- faultLaLbLoopbackEnable to "enabled" or "disabled"

 faultDte   OBJECT IDENTIFIER ::= { fault 2 }

 faultDteLaLead OBJECT-TYPE
     SYNTAX  INTEGER { clear (1),
                       set   (2) }
     ACCESS  read-only
     STATUS  mandatory
     DESCRIPTION
             "The state of the LA loopbak lead."
     ::= { faultDte 1 }

 faultDteLbLead OBJECT-TYPE
     SYNTAX  INTEGER { clear (1),
                       set   (2) }
     ACCESS  read-only
     STATUS  mandatory
     DESCRIPTION
             "The state of the LB loopbak lead."
     ::= { faultDte 2 }

 faultDteLaLbTranslation OBJECT-TYPE
     SYNTAX  INTEGER { none        (1),
                       local-line  (2),
                       remote-line (3),
                       dte         (4) }
     ACCESS  read-only
     STATUS  mandatory
     DESCRIPTION
             "The managed node uses the states of the LA and LB
              leads to decide what kind of loopback to perform if
              faultLaLbLoopbackEnable (see below) is ENABLED. The
              meaning of LA and LB leads is as follows:

              loopback         LA-Lead        LB-Lead
              ------------------------------------------------
              none              clear          clear
              local-line         set           clear
              remote-line       clear           set
              dte                set            set
             "
     ::= { faultDte 3 }

 faultDteLaLbLoopbackEnable OBJECT-TYPE
     SYNTAX  INTEGER { disabled (1),
                       enabled  (2) }
     ACCESS  read-write
     STATUS  mandatory
     DESCRIPTION
             "Enable/disable the managed node to use the
              LA and LB lead states to perform loopbaks."
     ::= { faultDte 4 }

 -- Customer loopback and DTE loopback are initiated by
 -- the managed node.

 faultDteCustomerLoopback OBJECT-TYPE
     SYNTAX  INTEGER { disabled (1),
                       enabled  (2) }
     ACCESS  read-write
     STATUS  mandatory
     DESCRIPTION
             "Enable/disable the customer equipment (DTE) to
              perform loopback toward the managed node."
     ::= { faultDte 5 }

 faultDteDteLoopback OBJECT-TYPE
     SYNTAX  INTEGER { disabled (1),
                       enabled  (2) }
     ACCESS  read-write
     STATUS  mandatory
     DESCRIPTION
             "Enable/disable the managed node to perform
              loopback toward the customer equipment (DTE)."
     ::= { faultDte 6 }

 -- alarm group

 faultClearCurrentAlarms OBJECT-TYPE
     SYNTAX  INTEGER
     ACCESS  read-write
     STATUS  mandatory
     DESCRIPTION
             "A set request clears all entries in the current
              alarm table.  A get/get-next request returns 0."
     ::= { fault 3 }

 faultClearHistoryAlarms OBJECT-TYPE
     SYNTAX  INTEGER
     ACCESS  read-write
     STATUS  mandatory
     DESCRIPTION
             "A set request clears all entries in the history
              alarm table.  A get/get-next request returns 0."
     ::= { fault 4 }

 -- current (active) alarm table

 faultCurrentAlarmTable OBJECT-TYPE
     SYNTAX  SEQUENCE OF FaultCurrentAlarmEntry
     ACCESS  not-accessible
     STATUS  mandatory
     DESCRIPTION
             "Current alarm table."
     ::= { fault 5 }

 faultCurrentAlarmEntry OBJECT-TYPE
     SYNTAX  FaultCurrentAlarmEntry
     ACCESS  not-accessible
     STATUS  mandatory
     DESCRIPTION
             "Each entry in the table contains the information of
              a currently active alarm."
     INDEX   { faultCurrentAlarmTag }
     ::= { faultCurrentAlarmTable 1 }

 FaultCurrentAlarmEntry ::=
     SEQUENCE {
	 faultCurrentAlarmTag
	     INTEGER,
         faultCurrentAlarmAlarmType
             INTEGER,
         faultCurrentAlarmSeverity
             INTEGER,
         faultCurrentAlarmCardType
             INTEGER,
         faultCurrentAlarmPortNumber
             INTEGER,
         faultCurrentAlarmSetTime
             TimeAndDate,
         faultCurrentAlarmDescription
             DisplayString
     }

 faultCurrentAlarmTag OBJECT-TYPE
     SYNTAX  INTEGER (1..1000000)
     ACCESS  read-only
     STATUS  mandatory
     DESCRIPTION
             "The tag of the alarm in the current alarm table."
     ::= { faultCurrentAlarmEntry 1 }

 faultCurrentAlarmAlarmType OBJECT-TYPE
     SYNTAX  INTEGER { ds1-net-card-lpbk          (1),
                       ds1-net-line-lpbk          (2),
                       la-lb-dte-lpbk             (3),
                       la-lb-local-lpbk           (4),
                       la-lb-remote-lpbk          (5),
                       remote-line-lpbk           (6),
                       dte-lpbk                   (7),
                       customer-lpbk              (8),
                       dte-clk-loss               (9),
                       hsdc-ga-oof                (10),
                       pll-fail                   (11),
                       card-fail                  (12),
                       ds1-los                    (13),
                       ds1-oof                    (14),
                       ds1-ais                    (15),
                       ds1-yel                    (16),
                       fan1-failed                (17),
                       fan2-failed                (18),
                       trunk-card-config-mismatch (19),
                       cim-card-config-mismatch   (20),
                       cpu-restarted              (21),
                       port-alarms-cleared        (22),
                       all-alarms-cleared         (23),
                       ds1-afa-alarm              (24),
                       alarm-history-cleared      (25),
                       p1-connected-to-p2         (26),
                       p1-connected-to-p3         (27),
                       p1-connected-to-p4         (28),
                       p1-connected-to-p5         (29),
                       p1-connected-to-p6         (30),
                       p1-connected-to-p7         (31),
                       p2-connected-to-p1         (32),
                       p2-connected-to-p3         (33),
                       p2-connected-to-p4         (34),
                       p2-connected-to-p5         (35),
                       p2-connected-to-p6         (36),
                       p2-connected-to-p7         (37),
                       p3-connected-to-p1         (38),
                       p3-connected-to-p2         (39),
                       p3-connected-to-p4         (40),
                       p3-connected-to-p5         (41),
                       p3-connected-to-p6         (42),
                       p3-connected-to-p7         (43),
                       p4-connected-to-p1         (44),
                       p4-connected-to-p2         (45),
                       p4-connected-to-p3         (46),
                       p4-connected-to-p5         (47),
                       p4-connected-to-p6         (48),
                       p4-connected-to-p7         (49),
                       p5-connected-to-p1         (50),
                       p5-connected-to-p2         (51),
                       p5-connected-to-p3         (52),
                       p5-connected-to-p4         (53),
                       p5-connected-to-p6         (54),
                       p5-connected-to-p7         (55),
                       p6-connected-to-p1         (56),
                       p6-connected-to-p2         (57),
                       p6-connected-to-p3         (58),
                       p6-connected-to-p4         (59),
                       p6-connected-to-p5         (60),
                       p6-connected-to-p7         (61),
                       p7-connected-to-p1         (62),
                       p7-connected-to-p2         (63),
                       p7-connected-to-p3         (64),
                       p7-connected-to-p4         (65),
                       p7-connected-to-p5         (66),
                       p7-connected-to-p6         (67),
                       alarm1-in                  (68),
                       alarm2-in                  (69),
                       alarm3-in                  (70),
                       hdlc-unlocked              (71),
                       far-end-loopback           (72),
                       remote-afa                 (73),
                       att-fdl-loopback           (74),
                       inband-loopback            (75),
                       t1-link-down               (76),
                       ports-out-of-sequence      (77) }
     ACCESS  read-only
     STATUS  mandatory
     DESCRIPTION
             "The alarm type of the alarm."
     ::= { faultCurrentAlarmEntry 2 }

 faultCurrentAlarmSeverity OBJECT-TYPE
     SYNTAX  INTEGER { minor (2),
                       major (3) }
     ACCESS  read-only
     STATUS  mandatory
     DESCRIPTION
             "The severity of the alarm."
     ::= { faultCurrentAlarmEntry 3 }

 faultCurrentAlarmCardType OBJECT-TYPE
     SYNTAX  INTEGER { hsdp       (1),  -- high speed data port
                       ethernet   (2),  -- ethernet
                       token-ring (3),  -- token ring
                       ds1        (4) } -- ds1
     ACCESS  read-only
     STATUS  mandatory
     DESCRIPTION
             "The type of the card which caused the alarm."
     ::= { faultCurrentAlarmEntry 4 }

 faultCurrentAlarmPortNumber OBJECT-TYPE
     SYNTAX  INTEGER (0..7)
     ACCESS  read-only
     STATUS  mandatory
     DESCRIPTION
             "The port number of the card which caused the alarm.
              Its value is between 1 and 7 for DS1 ports and 0
              for others."
     ::= { faultCurrentAlarmEntry 5 }

 faultCurrentAlarmSetTime OBJECT-TYPE
     SYNTAX  TimeAndDate
     ACCESS  read-only
     STATUS  mandatory
     DESCRIPTION
             "The time when the alarm was set."
     ::= { faultCurrentAlarmEntry 6 }

 faultCurrentAlarmDescription OBJECT-TYPE
     SYNTAX  DisplayString
     ACCESS  read-only
     STATUS  mandatory
     DESCRIPTION
             "A readable string which describes the alarm.
              Its format is as follows:

              <Level> <Card> <Port> <Alarm Type> <Time Occured>

              'Level' is the alarm severity.  Its value can be 'Info',
              'Major', or 'Minor'.

              'Card' refers to where the alarm was generated.  Its value
              can be 'HSDP', 'ENET', 'TRING', or 'DS1'.

              'Port' refers to which port generated the alarm.  Its value
              can be 1 to 7 for DS1 and 'empty' if no port number can
              be used for an alarm.

              'Alarm Type' is an ASCII string of the alarm type.

              'Time Occured' is the time when the alarm was generated.
             "
     ::= { faultCurrentAlarmEntry 8 }

 -- history alarm table

 faultHistoryAlarmTable OBJECT-TYPE
     SYNTAX  SEQUENCE OF FaultHistoryAlarmEntry
     ACCESS  not-accessible
     STATUS  mandatory
     DESCRIPTION
             "History/Information alarm table."
     ::= { fault 6 }

 faultHistoryAlarmEntry OBJECT-TYPE
     SYNTAX  FaultHistoryAlarmEntry
     ACCESS  not-accessible
     STATUS  mandatory
     DESCRIPTION
             "Each entry in the history alarm table contains either a
              cleared alarm or an information alarm."
     INDEX   { faultHistoryAlarmTag }
     ::= { faultHistoryAlarmTable 1 }

 FaultHistoryAlarmEntry ::=
     SEQUENCE {
	 faultHistoryAlarmTag
	     INTEGER,
         faultHistoryAlarmAlarmType
             INTEGER,
         faultHistoryAlarmSeverity
             INTEGER,
         faultHistoryAlarmCardType
             INTEGER,
         faultHistoryAlarmPortNumber
             INTEGER,
         faultHistoryAlarmSetTime
             TimeAndDate,
         faultHistoryAlarmClearTime
             TimeAndDate,
         faultHistoryAlarmDescription
             DisplayString
     }

 faultHistoryAlarmTag OBJECT-TYPE
     SYNTAX  INTEGER (1..1000000)
     ACCESS  read-only
     STATUS  mandatory
     DESCRIPTION
             "The tag of the alarm in the history alarm table."
     ::= { faultHistoryAlarmEntry 1 }

 faultHistoryAlarmAlarmType OBJECT-TYPE
     SYNTAX  INTEGER { ds1-net-card-lpbk          (1),
                       ds1-net-line-lpbk          (2),
                       la-lb-dte-lpbk             (3),
                       la-lb-local-lpbk           (4),
                       la-lb-remote-lpbk          (5),
                       remote-line-lpbk           (6),
                       dte-lpbk                   (7),
                       customer-lpbk              (8),
                       dte-clk-loss               (9),
                       hsdc-ga-oof                (10),
                       pll-fail                   (11),
                       card-fail                  (12),
                       ds1-los                    (13),
                       ds1-oof                    (14),
                       ds1-ais                    (15),
                       ds1-yel                    (16),
                       fan1-failed                (17),
                       fan2-failed                (18),
                       trunk-card-config-mismatch (19),
                       cim-card-config-mismatch   (20),
                       cpu-restarted              (21),
                       port-alarms-cleared        (22),
                       all-alarms-cleared         (23),
                       ds1-afa-alarm              (24),
                       alarm-history-cleared      (25),
                       p1-connected-to-p2         (26),
                       p1-connected-to-p3         (27),
                       p1-connected-to-p4         (28),
                       p1-connected-to-p5         (29),
                       p1-connected-to-p6         (30),
                       p1-connected-to-p7         (31),
                       p2-connected-to-p1         (32),
                       p2-connected-to-p3         (33),
                       p2-connected-to-p4         (34),
                       p2-connected-to-p5         (35),
                       p2-connected-to-p6         (36),
                       p2-connected-to-p7         (37),
                       p3-connected-to-p1         (38),
                       p3-connected-to-p2         (39),
                       p3-connected-to-p4         (40),
                       p3-connected-to-p5         (41),
                       p3-connected-to-p6         (42),
                       p3-connected-to-p7         (43),
                       p4-connected-to-p1         (44),
                       p4-connected-to-p2         (45),
                       p4-connected-to-p3         (46),
                       p4-connected-to-p5         (47),
                       p4-connected-to-p6         (48),
                       p4-connected-to-p7         (49),
                       p5-connected-to-p1         (50),
                       p5-connected-to-p2         (51),
                       p5-connected-to-p3         (52),
                       p5-connected-to-p4         (53),
                       p5-connected-to-p6         (54),
                       p5-connected-to-p7         (55),
                       p6-connected-to-p1         (56),
                       p6-connected-to-p2         (57),
                       p6-connected-to-p3         (58),
                       p6-connected-to-p4         (59),
                       p6-connected-to-p5         (60),
                       p6-connected-to-p7         (61),
                       p7-connected-to-p1         (62),
                       p7-connected-to-p2         (63),
                       p7-connected-to-p3         (64),
                       p7-connected-to-p4         (65),
                       p7-connected-to-p5         (66),
                       p7-connected-to-p6         (67),
                       alarm1-in                  (68),
                       alarm2-in                  (69),
                       alarm3-in                  (70),
                       hdlc-unlocked              (71),
                       far-end-loopback           (72),
                       remote-afa                 (73),
                       att-fdl-loopback           (74),
                       inband-loopback            (75),
                       t1-link-down               (76),
                       ports-out-of-sequence      (77) }
     ACCESS  read-only
     STATUS  mandatory
     DESCRIPTION
             "The alarm type of the alarm."
     ::= { faultHistoryAlarmEntry 2 }

 faultHistoryAlarmSeverity OBJECT-TYPE
     SYNTAX  INTEGER { info  (1),
                       minor (2),
                       major (3) }
     ACCESS  read-only
     STATUS  mandatory
     DESCRIPTION
             "The severity of the alarm.  Its value can be
              either major or minor for DS1 ports and info
              for others."
     ::= { faultHistoryAlarmEntry 3 }

 faultHistoryAlarmCardType OBJECT-TYPE
     SYNTAX  INTEGER { hsdp       (1),  -- high speed data port
                       ethernet   (2),  -- ethernet
                       token-ring (3),  -- token ring
                       ds1        (4) } -- ds1
     ACCESS  read-only
     STATUS  mandatory
     DESCRIPTION
             "The type of the card which caused the alarm."
     ::= { faultHistoryAlarmEntry 4 }

 faultHistoryAlarmPortNumber OBJECT-TYPE
     SYNTAX  INTEGER (0..7)
     ACCESS  read-only
     STATUS  mandatory
     DESCRIPTION
             "The port number of the card which caused the alarm.
              Its value is between 1 and 7 for DS1 ports and 0
              for others."
     ::= { faultHistoryAlarmEntry 5 }

 faultHistoryAlarmSetTime OBJECT-TYPE
     SYNTAX  TimeAndDate
     ACCESS  read-only
     STATUS  mandatory
     DESCRIPTION
             "The time when the alarm was set."
     ::= { faultHistoryAlarmEntry 6 }

 faultHistoryAlarmClearTime OBJECT-TYPE
     SYNTAX  TimeAndDate
     ACCESS  read-only
     STATUS  mandatory
     DESCRIPTION
             "The time when the alarm was cleared."
     ::= { faultHistoryAlarmEntry 7 }

 faultHistoryAlarmDescription OBJECT-TYPE
     SYNTAX  DisplayString
     ACCESS  read-only
     STATUS  mandatory
     DESCRIPTION
             "A readable string which describes the alarm.
              Its format is as follows:

              <Level> <Card> <Port> <Alarm Type> <Time Occured> <Time Cleared>

              'Level' is the alarm severity.  Its value can be 'Info',
              'Major', or 'Minor'.

              'Card' refers to where the alarm was generated.  Its value
              can be 'HSDP', 'ENET', 'TRING', or 'DS1'.

              'Port' refers to which port generated the alarm.  Its value
              can be 1 to 7 for DS1 and 'empty' if no port number can
              be used for an alarm.

              'Alarm Type' is an ASCII string of the alarm type.

              'Time Occured' is the time when the alarm was generated.

              'Time Cleared' is the time when the alarm was cleared.
             "
     ::= { faultHistoryAlarmEntry 8 }

 perfClearDs1Performance OBJECT-TYPE
     SYNTAX  INTEGER
     ACCESS  read-write
     STATUS  mandatory
     DESCRIPTION
             "A set request clears all DS1 performance monitoring
              data.  A get/get-next request returns 0."
     ::= { perf 1 }


 perfClearEnetPortCardStats OBJECT-TYPE
     SYNTAX  INTEGER
     ACCESS  read-write
     STATUS  mandatory
     DESCRIPTION
             "A set request clears all ethernet port card statistics.
              A get/get-next request returns 0."
     ::= { perf 2 }

 enetPortCardStats OBJECT IDENTIFIER ::= { perf 3 }

 enetPortCardStatsFramesReceived OBJECT-TYPE
     SYNTAX     Counter
     ACCESS     read-only
     STATUS     mandatory
     DESCRIPTION
             "A count of frames received by the ethernet
              port card."
     ::= { enetPortCardStats 1 }

 enetPortCardStatsBytesReceived OBJECT-TYPE
     SYNTAX     Counter
     ACCESS     read-only
     STATUS     mandatory
     DESCRIPTION
             "A count of bytes received by the ethernet
              port card."
     ::= { enetPortCardStats 2 }

 enetPortCardStatsFramesTransmitted OBJECT-TYPE
     SYNTAX     Counter
     ACCESS     read-only
     STATUS     mandatory
     DESCRIPTION
             "A count of frames transmitted on the ethernet
              port card."
     ::= { enetPortCardStats 3 }

 enetPortCardStatsBytesTransmitted OBJECT-TYPE
     SYNTAX     Counter
     ACCESS     read-only
     STATUS     mandatory
     DESCRIPTION
             "A count of bytes transmitted on the ethernet
              port card."
     ::= { enetPortCardStats 4 }

 enetPortCardStatsAlignmentErrors OBJECT-TYPE
     SYNTAX     Counter
     ACCESS     read-only
     STATUS     mandatory
     DESCRIPTION
             "A count of frames received that are not an
              integral number of octets in length and do
              not pass the FCS check.

              The count represented by an instance of this
              object is incremented when the alignmentError
              status is returned by the MAC service to the
              LLC (or other MAC user). Received frames for
              which multiple error conditions obtain are,
              according to the conventions of IEEE 802.3
              Layer Management, counted exclusively according
              to the error status presented to the LLC."
     REFERENCE
            "IEEE 802.3 Layer Management"
     ::= { enetPortCardStats 5 }

 enetPortCardStatsFCSErrors OBJECT-TYPE
     SYNTAX      Counter
     ACCESS      read-only
     STATUS      mandatory
     DESCRIPTION
             "A count of frames received that are an
              integral number of octets in length but do
              not pass the FCS check.

              The count represented by an instance of this
              object is incremented when the frameCheckError
              status is returned by the MAC service to the
              LLC (or other MAC user). Received frames for
              which multiple error conditions obtain are,
              according to the conventions of IEEE 802.3
              Layer Management, counted exclusively according
              to the error status presented to the LLC."
     REFERENCE
             "IEEE 802.3 Layer Management"
     ::= { enetPortCardStats 6 }

 enetPortCardStatsSingleCollisionFrames OBJECT-TYPE
     SYNTAX      Counter
     ACCESS      read-only
     STATUS      mandatory
     DESCRIPTION
             "A count of successfully transmitted frames for
              which transmission is inhibited by exactly one
              collision.
 
              A frame that is counted by an instance of this
              object is not counted by the corresponding
              instance of the enetPortCardStatsMultipleCollisionFrames
              object."
     REFERENCE
             "IEEE 802.3 Layer Management"
     ::= { enetPortCardStats 7 }

 enetPortCardStatsMultipleCollisionFrames OBJECT-TYPE
     SYNTAX      Counter
     ACCESS      read-only
     STATUS      mandatory
     DESCRIPTION
             "A count of successfully transmitted frames for
              which transmission is inhibited by more than
              one collision.

              A frame that is counted by an instance of this
              object is not counted by the corresponding
              instance of the enetPortCardStatsSingleCollisionFrames
              object."
     REFERENCE
             "IEEE 802.3 Layer Management"
     ::= { enetPortCardStats 8 }

 enetPortCardStatsDeferredTransmissions OBJECT-TYPE
     SYNTAX      Counter
     ACCESS      read-only
     STATUS      mandatory
     DESCRIPTION
             "A count of frames for which the first
              transmission attempt is delayed because
              the medium is busy.

              The count represented by an instance of this
              object does not include frames involved in
              collisions."
     REFERENCE
             "IEEE 802.3 Layer Management"
     ::= { enetPortCardStats 9 }

 enetPortCardStatsLateCollisions   OBJECT-TYPE
     SYNTAX      Counter
     ACCESS      read-only
     STATUS      mandatory
     DESCRIPTION
             "The number of times that a collision is
              detected on later than 512 bit-times into
              the transmission of a packet.

              Five hundred and twelve bit-times corresponds
              to 51.2 microseconds on a 10 Mbit/s system. A
              (late) collision included in a count
              represented by an instance of this object is
              also considered as a (generic) collision for
              purposes of other collision-related
              statistics."
     REFERENCE
             "IEEE 802.3 Layer Management"
     ::= { enetPortCardStats 10 }

 enetPortCardStatsExcessiveCollisions   OBJECT-TYPE
     SYNTAX    Counter
     ACCESS    read-only
     STATUS    mandatory
     DESCRIPTION
             "A count of frames for which transmission
              fails due to excessive collisions."
     REFERENCE
             "IEEE 802.3 Layer Management"
     ::= { enetPortCardStats 11 }

 enetPortCardStatsInternalMacTransmitErrors   OBJECT-TYPE
     SYNTAX    Counter
     ACCESS    read-only
     STATUS    mandatory
     DESCRIPTION
             "A count of frames for which transmission fails
              due to an internal MAC sublayer transmit error.
              A frame is only counted by an instance of this
              object if it is not counted by the corresponding
              instance of either the enetPortCardStatsLateCollisions
              object, the enetPortCardStatsExcessiveCollisions
              object, or the enetPortCardStatsCarrierSenseErrors
              object.  The precise meaning of the count represented
              by an instance of this object is implementation-
              specific.  In particular, an instance of this
              object may represent a count of transmission
              errors that are not otherwise counted."
     REFERENCE
             "IEEE 802.3 Layer Management"
     ::= { enetPortCardStats 12 }

 enetPortCardStatsCarrierSenseErrors   OBJECT-TYPE
     SYNTAX    Counter
     ACCESS    read-only
     STATUS    mandatory
     DESCRIPTION
             "The number of times that the carrier sense
              condition was lost or never asserted when
              attempting to transmit a frame.

              The count represented by an instance of this
              object is incremented at most once per
              transmission attempt, even if the carrier sense
              condition fluctuates during a transmission
              attempt."
     REFERENCE
             "IEEE 802.3 Layer Management"
     ::= { enetPortCardStats 13 }

 enetPortCardStatsFrameTooLongs   OBJECT-TYPE
     SYNTAX    Counter
     ACCESS    read-only
     STATUS    mandatory
     DESCRIPTION
             "A count of frames received that exceed the
              maximum permitted frame size.

              The count represented by an instance of this
              object is incremented when the frameTooLong
              status is returned by the MAC service to the
              LLC (or other MAC user). Received frames for
              which multiple error conditions obtain are,
              according to the conventions of IEEE 802.3
              Layer Management, counted exclusively according
              to the error status presented to the LLC."
     REFERENCE
             "IEEE 802.3 Layer Management"
     ::= { enetPortCardStats 14 }


 perfClearNxT1PortStats OBJECT-TYPE
     SYNTAX  INTEGER
     ACCESS  read-write
     STATUS  mandatory
     DESCRIPTION
             "A set request clears all nxt1 port statistics.
              A get/get-next request returns 0."
     ::= { perf 4 }

 nxt1PortStats OBJECT IDENTIFIER ::= { perf 5 }

 nxt1PortStatsFramesReceived OBJECT-TYPE
     SYNTAX     Counter
     ACCESS     read-only
     STATUS     mandatory
     DESCRIPTION
             "A count of frames received by the NxT1 port."
     ::= { nxt1PortStats 1 }

 nxt1PortStatsBytesReceived OBJECT-TYPE
     SYNTAX     Counter
     ACCESS     read-only
     STATUS     mandatory
     DESCRIPTION
             "A count of bytes received by the NxT1 port."
     ::= { nxt1PortStats 2 }

 nxt1PortStatsFramesTransmitted OBJECT-TYPE
     SYNTAX     Counter
     ACCESS     read-only
     STATUS     mandatory
     DESCRIPTION
             "A count of frames transmitted on the NxT1 port."
     ::= { nxt1PortStats 3 }

 nxt1PortStatsBytesTransmitted OBJECT-TYPE
     SYNTAX     Counter
     ACCESS     read-only
     STATUS     mandatory
     DESCRIPTION
             "A count of bytes transmitted on the NxT1 port."
     ::= { nxt1PortStats 4 }

 nxt1PortStatsCrcErrors OBJECT-TYPE
     SYNTAX      Counter
     ACCESS      read-only
     STATUS      mandatory
     DESCRIPTION
             "A count of frames received by the NxT1 port
              that do not pass the CRC check."
     ::= { nxt1PortStats 5 }


 alarmOnReport TRAP-TYPE
     ENTERPRISE lx-10
     VARIABLES  { faultCurrentAlarmAlarmType,
                  faultCurrentAlarmSeverity,
                  faultCurrentAlarmCardType,
                  faultCurrentAlarmPortNumber,
                  faultCurrentAlarmSetTime,
                  faultCurrentAlarmDescription }
     DESCRIPTION
             "LX-10-specific trap sent by the managed node when
              an alarm condition is set."
     ::= 1

 alarmOffReport TRAP-TYPE
     ENTERPRISE lx-10
     VARIABLES  { faultHistoryAlarmAlarmType,
                  faultHistoryAlarmSeverity,
                  faultHistoryAlarmCardType,
                  faultHistoryAlarmPortNumber,
                  faultHistoryAlarmSetTime,
                  faultHistoryAlarmClearTime,
                  faultHistoryAlarmDescription }
     DESCRIPTION
             "LX-10-specific trap sent by the managed node when
              an alarm condition is cleared."
     ::= 2

 END
