-- *****************************************************************
--
-- stn-chassis.mib:  
--      Spring Tide Networks Chassis MIB file.
--
--
--      Copyright (c) 1999, 2000 by Spring Tide Networks, Inc.
--                      ALL RIGHTS RESERVED       
--
-- *****************************************************************

-- MIB Object definitions for Spring Tide Network Chassis 

STN-CHASSIS-MIB DEFINITIONS ::= BEGIN

    IMPORTS
        MODULE-IDENTITY,
        OBJECT-TYPE,
        NOTIFICATION-TYPE, 
        Integer32, 
        TimeTicks
                FROM SNMPv2-SMI

        DisplayString
                FROM SNMPv2-TC

        MODULE-COMPLIANCE, 
        OBJECT-GROUP
                FROM SNMPv2-CONF

        stnSystems,
        stnNotification
                FROM SPRING-TIDE-NETWORKS-SMI

        StnHardwareModuleType,
        StnHardwareSubModuleType,
        StnModuleAdminStatus,
        StnModuleOperStatus,
        StnEngineAdminStatus,
        StnEngineOperStatus,
        StnLedStatus,
        StnPowerStatus,
        StnBatteryStatus,
        StnResourceStatus,
        StnFlashStatus
                FROM SPRING-TIDE-NETWORKS-TC;


    stnChassis       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes the managed objects of the
                         Spring Tide Networks chassis."
        ::= { stnSystems 1 }

    --
    -- Top Level STN Chassis MIB Objects
    --
    stnChassisObjects		OBJECT IDENTIFIER ::= { stnChassis 1 }
    stnChassisMibConformance	OBJECT IDENTIFIER ::= { stnChassis 2 }

    stnChassisVars			OBJECT IDENTIFIER ::= { stnChassisObjects 1 }
    stnModules				OBJECT IDENTIFIER ::= { stnChassisObjects 2 }
    stnLeds					OBJECT IDENTIFIER ::= { stnChassisObjects 3 }
    stnPower				OBJECT IDENTIFIER ::= { stnChassisObjects 4 }
    stnResource				OBJECT IDENTIFIER ::= { stnChassisObjects 5 }

    stnChassisTrapVars		OBJECT IDENTIFIER ::= { stnChassisObjects 100 }


    --
    -- STN Chassis 
    --
    stnChassisSysType OBJECT-TYPE
        SYNTAX          INTEGER {
                            other(1),        -- none of the following
                            stn5000(2)
                        }
        MAX-ACCESS      read-only
        STATUS          current
        DESCRIPTION     "The system type."
        ::= { stnChassisVars 1 }

    stnChassisSysDescr OBJECT-TYPE
        SYNTAX          DisplayString
        MAX-ACCESS      read-only
        STATUS          current
        DESCRIPTION     "The system description."
        ::= { stnChassisVars 2 }

    stnChassisId OBJECT-TYPE
        SYNTAX          DisplayString
        MAX-ACCESS      read-only
        STATUS          current
        DESCRIPTION     "The system ID."
        ::= { stnChassisVars 3 }


    --
    -- STN Slot Module Table
    --
    stnSlotTable OBJECT-TYPE
        SYNTAX          SEQUENCE OF StnSlotEntry
        MAX-ACCESS      not-accessible
        STATUS          current
        DESCRIPTION     "A list of slot and installed module type entries."
        ::= { stnModules 1 }
 
    stnSlotEntry OBJECT-TYPE
        SYNTAX          StnSlotEntry
        MAX-ACCESS      not-accessible
        STATUS          current
        DESCRIPTION     "Entry contains information about a particular 
                         slot."
        INDEX           { stnSlotIndex }
        ::= { stnSlotTable 1 }
 
    StnSlotEntry ::= SEQUENCE {
                stnSlotIndex            Integer32,
                stnModuleType           StnHardwareModuleType,
                stnModulePeer           Integer32,
                stnModuleAdminStatus    StnModuleAdminStatus,
                stnModuleOperStatus     StnModuleOperStatus,
                stnModuleDescr          DisplayString,
                stnModuleLed            StnLedStatus,
                stnSubModules           Integer32
                }

    stnSlotIndex OBJECT-TYPE
        SYNTAX          Integer32
        MAX-ACCESS      read-only
        STATUS          current
        DESCRIPTION     "The slot in which the physical module exists."
        ::= { stnSlotEntry 1 }

    stnModuleType OBJECT-TYPE     
        SYNTAX          StnHardwareModuleType
        MAX-ACCESS      read-only
        STATUS          current
        DESCRIPTION     "The type of module installed in the slot."
        ::= { stnSlotEntry  2 }

    stnModulePeer OBJECT-TYPE
        SYNTAX          Integer32
        MAX-ACCESS      read-only
        STATUS          current
        DESCRIPTION     "Peer module in redundant configuration."
        ::= { stnSlotEntry  3 }

    stnModuleAdminStatus   OBJECT-TYPE
        SYNTAX          StnModuleAdminStatus
        MAX-ACCESS      read-only
        STATUS          current
        DESCRIPTION     "Administrative status of the module."
        ::= { stnSlotEntry  4 }

    stnModuleOperStatus   OBJECT-TYPE
        SYNTAX          StnModuleOperStatus
        MAX-ACCESS      read-only
        STATUS          current
        DESCRIPTION     "Operational status of the module."
        ::= { stnSlotEntry  5 }

    stnModuleDescr OBJECT-TYPE
        SYNTAX          DisplayString
        MAX-ACCESS      read-only
        STATUS          current
        DESCRIPTION     "A descriptive string used to describe 
                         the module type."
        ::= { stnSlotEntry  6 }

    stnModuleLed OBJECT-TYPE
        SYNTAX          StnLedStatus
        MAX-ACCESS      read-only
        STATUS          current
        DESCRIPTION     "Primary LED status of the module."
        ::= { stnSlotEntry  7 }

    stnSubModules OBJECT-TYPE
        SYNTAX          Integer32
        MAX-ACCESS      read-only
        STATUS          current
        DESCRIPTION     "The number of sub-modules attached to this module."
        ::= { stnSlotEntry  8 }


    --
    -- STN Slot Sub-Module Table
    --
    stnSubModuleTable OBJECT-TYPE
        SYNTAX          SEQUENCE OF StnSubModuleEntry
        MAX-ACCESS      not-accessible
        STATUS          current
        DESCRIPTION     "A list of installed sub-module type entries."
        ::= { stnModules 2 }
 
    stnSubModuleEntry OBJECT-TYPE
        SYNTAX          StnSubModuleEntry
        MAX-ACCESS      not-accessible
        STATUS          current
        DESCRIPTION     "Entry contains information about a particular 
                         slot sub-module."
        INDEX           { stnSubModuleSlot, stnSubModuleIndex }
        ::= { stnSubModuleTable 1 }
 
    StnSubModuleEntry ::= SEQUENCE {
                stnSubModuleSlot            Integer32,
                stnSubModuleIndex           Integer32,
                stnSubModuleType            StnHardwareSubModuleType,
                stnSubModulePeer            Integer32,
                stnSubModuleAdminStatus     StnModuleAdminStatus,
                stnSubModuleOperStatus      StnModuleOperStatus,
                stnSubModuleDescr           DisplayString
                }

    stnSubModuleSlot OBJECT-TYPE
        SYNTAX          Integer32
        MAX-ACCESS      read-only
        STATUS          current
        DESCRIPTION     "The chassis slot in which the sub-module 
                        is installed."
        ::= { stnSubModuleEntry 1 }

    stnSubModuleIndex OBJECT-TYPE
        SYNTAX          Integer32
        MAX-ACCESS      read-only
        STATUS          current
        DESCRIPTION     "The engine adapter in which the sub-module 
                        is installed."
        ::= { stnSubModuleEntry 2 }

    stnSubModuleType OBJECT-TYPE     
        SYNTAX          StnHardwareSubModuleType
        MAX-ACCESS      read-only
        STATUS          current
        DESCRIPTION     "The type of sub-module installed in the slot."
        ::= { stnSubModuleEntry  3 }

    stnSubModulePeer OBJECT-TYPE
        SYNTAX          Integer32
        MAX-ACCESS      read-only
        STATUS          current
        DESCRIPTION     "Peer sub-module in redundant configuration."
        ::= { stnSubModuleEntry  4 }

    stnSubModuleAdminStatus   OBJECT-TYPE
        SYNTAX          StnModuleAdminStatus
        MAX-ACCESS      read-only
        STATUS          current
        DESCRIPTION     "Administrative status of the sub-module."
        ::= { stnSubModuleEntry  5 }

    stnSubModuleOperStatus   OBJECT-TYPE
        SYNTAX          StnModuleOperStatus
        MAX-ACCESS      read-only
        STATUS          current
        DESCRIPTION     "Operational status of the sub-module."
        ::= { stnSubModuleEntry  6 }

    stnSubModuleDescr OBJECT-TYPE
        SYNTAX          DisplayString
        MAX-ACCESS      read-only
        STATUS          current
        DESCRIPTION     "A descriptive string used to describe 
                        the sub-module type."
        ::= { stnSubModuleEntry  7 }


    --
    -- STN Engine Table
    --
    stnEngineTable OBJECT-TYPE
        SYNTAX          SEQUENCE OF StnEngineEntry
        MAX-ACCESS      not-accessible
        STATUS          current
        DESCRIPTION     "A list of engine entries."
        ::= { stnModules 3 }
 
    stnEngineEntry OBJECT-TYPE
        SYNTAX          StnEngineEntry
        MAX-ACCESS      not-accessible
        STATUS          current
        DESCRIPTION     "Entry contains information about a particular 
                        engine."
        INDEX           { stnEngineIndex }
        ::= { stnEngineTable 1 }
 
    StnEngineEntry ::= SEQUENCE {
                stnEngineIndex          Integer32,
                stnEngineSlot           Integer32,
                stnEngineCpu            Integer32,
                stnEngineType           INTEGER,
                stnEnginePeer           Integer32,
                stnEngineAdminStatus    StnEngineAdminStatus,
                stnEngineOperStatus     StnEngineOperStatus,
                stnEngineDescr          DisplayString
                }

    stnEngineIndex OBJECT-TYPE
        SYNTAX          Integer32
        MAX-ACCESS      read-only
        STATUS          current
        DESCRIPTION     "A sequence number that identifies a particular engine
                         in the chassis."
        ::= { stnEngineEntry 1 }

    stnEngineSlot OBJECT-TYPE
        SYNTAX          Integer32
        MAX-ACCESS      read-only
        STATUS          current
        DESCRIPTION     "The slot/module in which the engine exists."
        ::= { stnEngineEntry 2 }

    stnEngineCpu OBJECT-TYPE
        SYNTAX          Integer32
        MAX-ACCESS      read-only
        STATUS          current
        DESCRIPTION     "The cpu ID associated with the engine."
        ::= { stnEngineEntry 3 }

    stnEngineType OBJECT-TYPE     
        SYNTAX          INTEGER { 
                    unknown(1), -- not one of the following
                    swc(2),     -- Switch Controller
                    rpe(3),     -- Routing Processor Engine
                    ecf(4),     -- Encryption Compression Forwarding Engine
                    ecf2(5)     -- Encryption Compression Forwarding Engine II
                    }
        MAX-ACCESS      read-only
        STATUS          current
        DESCRIPTION     "The type of engine."
        ::= { stnEngineEntry  4 }

    stnEnginePeer OBJECT-TYPE
        SYNTAX          Integer32
        MAX-ACCESS      read-only
        STATUS          current
        DESCRIPTION     "Peer engine in redundant configuration."
        ::= { stnEngineEntry  5 }

    stnEngineAdminStatus OBJECT-TYPE
        SYNTAX          StnEngineAdminStatus
        MAX-ACCESS      read-only
        STATUS          current
        DESCRIPTION     "Administrative status of the engine."
        ::= { stnEngineEntry  6 }

    stnEngineOperStatus OBJECT-TYPE
        SYNTAX          StnEngineOperStatus
        MAX-ACCESS      read-only
        STATUS          current
        DESCRIPTION     "Operational status of the engine."
        ::= { stnEngineEntry  7 }

    stnEngineDescr OBJECT-TYPE
        SYNTAX          DisplayString
        MAX-ACCESS      read-only
        STATUS          current
        DESCRIPTION     "A descriptive string used to describe 
                         the engine type."
        ::= { stnEngineEntry  8 }


    --
    -- STN System LEDs
    --
    stnLedFanTray OBJECT-TYPE
        SYNTAX          StnLedStatus
        MAX-ACCESS      read-only
        STATUS          current
        DESCRIPTION     "Current status of the chassis fan tray LED."
        ::= { stnLeds  1 }

    stnLedPowerA OBJECT-TYPE
        SYNTAX          StnLedStatus
        MAX-ACCESS      read-only
        STATUS          current
        DESCRIPTION     "Current status of the chassis PowerA LED."
        ::= { stnLeds  2 }

    stnLedPowerB OBJECT-TYPE
        SYNTAX          StnLedStatus
        MAX-ACCESS      read-only
        STATUS          current
        DESCRIPTION     "Current status of the chassis PowerB LED."
        ::= { stnLeds  3 }

    stnLedAlarm OBJECT-TYPE
        SYNTAX          StnLedStatus
        MAX-ACCESS      read-only
        STATUS          current
        DESCRIPTION     "Current status of the chassis Alarm LED."
        ::= { stnLeds  4 }


    --
    -- STN Fan Tray LED Table
    --
    stnFanTrayLedTable OBJECT-TYPE
        SYNTAX          SEQUENCE OF StnFanTrayLedEntry
        MAX-ACCESS      not-accessible
        STATUS          current
        DESCRIPTION     "A list of Fan Tray LED entries."
        ::= { stnLeds 5 }
 
    stnFanTrayLedEntry OBJECT-TYPE
        SYNTAX          StnFanTrayLedEntry
        MAX-ACCESS      not-accessible
        STATUS          current
        DESCRIPTION     "An entry containing information about a particular 
                        Fan Tray LED."
        INDEX           { stnFanTrayLedIndex }
        ::= { stnFanTrayLedTable 1 }
 
    StnFanTrayLedEntry ::= SEQUENCE {
                stnFanTrayLedIndex          Integer32,
                stnFanTrayLedSlotIndex      Integer32,
                stnFanTrayLedStatus         StnLedStatus
                }

    stnFanTrayLedIndex OBJECT-TYPE
        SYNTAX          Integer32
        MAX-ACCESS      read-only
        STATUS          current
        DESCRIPTION     "A sequence number that identifies a particular 
                        Fan Tray LED."
        ::= { stnFanTrayLedEntry 1 }

    stnFanTrayLedSlotIndex OBJECT-TYPE
        SYNTAX          Integer32
        MAX-ACCESS      read-only
        STATUS          current
        DESCRIPTION     "The chassis slot number associated with this 
                        Fan Tray LED."
        ::= { stnFanTrayLedEntry 2 }

    stnFanTrayLedStatus OBJECT-TYPE     
        SYNTAX          StnLedStatus
        MAX-ACCESS      read-only
        STATUS          current
        DESCRIPTION     "The current state of the particular Fan Tray LED."
        ::= { stnFanTrayLedEntry  3 }


    --
    -- STN Port LED Table
    --
    stnPortLedTable OBJECT-TYPE
        SYNTAX          SEQUENCE OF StnPortLedEntry
        MAX-ACCESS      not-accessible
        STATUS          current
        DESCRIPTION     "A list of Port LED entries."
        ::= { stnLeds 6 }
 
    stnPortLedEntry OBJECT-TYPE
        SYNTAX          StnPortLedEntry
        MAX-ACCESS      not-accessible
        STATUS          current
        DESCRIPTION     "An entry containing information about a particular 
                        port LED."
        INDEX           { stnPortLedSlotIndex, stnPortLedPortIndex, stnPortLedIndex }
        ::= { stnPortLedTable 1 }
 
    StnPortLedEntry ::= SEQUENCE {
                stnPortLedSlotIndex      Integer32,
                stnPortLedPortIndex      Integer32,
                stnPortLedIndex          Integer32,
                stnPortLedStatus         StnLedStatus,
                stnPortLedDescr          DisplayString
                }

    stnPortLedSlotIndex OBJECT-TYPE
        SYNTAX          Integer32
        MAX-ACCESS      read-only
        STATUS          current
        DESCRIPTION     "The chassis slot number associated with this 
                        port LED."
        ::= { stnPortLedEntry 1 }

    stnPortLedPortIndex OBJECT-TYPE
        SYNTAX          Integer32
        MAX-ACCESS      read-only
        STATUS          current
        DESCRIPTION     "The chassis port number associated with this 
                        port LED."
        ::= { stnPortLedEntry 2 }

    stnPortLedIndex OBJECT-TYPE
        SYNTAX          Integer32
        MAX-ACCESS      read-only
        STATUS          current
        DESCRIPTION     "The index of this port LED."
        ::= { stnPortLedEntry 3 }

    stnPortLedStatus OBJECT-TYPE     
        SYNTAX          StnLedStatus
        MAX-ACCESS      read-only
        STATUS          current
        DESCRIPTION     "The current state of the port LED."
        ::= { stnPortLedEntry 4 }

    stnPortLedDescr OBJECT-TYPE     
        SYNTAX          DisplayString
        MAX-ACCESS      read-only
        STATUS          current
        DESCRIPTION     "A descriptive string or label associated with the 
                        port LED."
        ::= { stnPortLedEntry 5 }


    --
    -- STN Power Connection Table
    --
    stnPowerTable OBJECT-TYPE
        SYNTAX          SEQUENCE OF StnPowerEntry
        MAX-ACCESS      not-accessible
        STATUS          current
        DESCRIPTION     "A list of power entries."
        ::= { stnPower 1 }
 
    stnPowerEntry OBJECT-TYPE
        SYNTAX          StnPowerEntry
        MAX-ACCESS      not-accessible
        STATUS          current
        DESCRIPTION     "An entry containing information about a particular 
                        power connector."
        INDEX           { stnPowerIndex }
        ::= { stnPowerTable 1 }
 
    StnPowerEntry ::= SEQUENCE {
                stnPowerIndex           Integer32,
                stnPowerStatus          StnPowerStatus,
                stnPowerDescr           DisplayString
                }

    stnPowerIndex OBJECT-TYPE
        SYNTAX          Integer32
        MAX-ACCESS      read-only
        STATUS          current
        DESCRIPTION     "The id associated with this power connector."
        ::= { stnPowerEntry 1 }

    stnPowerStatus OBJECT-TYPE     
        SYNTAX          StnPowerStatus
        MAX-ACCESS      read-only
        STATUS          current
        DESCRIPTION     "The current state of the power source attached
                        to this power connector."
        ::= { stnPowerEntry 2 }

    stnPowerDescr OBJECT-TYPE     
        SYNTAX          DisplayString
        MAX-ACCESS      read-only
        STATUS          current
        DESCRIPTION     "A descriptive string or label associated with the 
                        power connector."
        ::= { stnPowerEntry 3 }


    --
    -- STN Battery Table
    --
    stnBatteryTable OBJECT-TYPE
        SYNTAX        SEQUENCE OF StnBatteryEntry
        MAX-ACCESS    not-accessible
        STATUS        current
        DESCRIPTION   "A list of battery entries."
        ::= { stnPower 2 }
 
    stnBatteryEntry OBJECT-TYPE
        SYNTAX          StnBatteryEntry
        MAX-ACCESS      not-accessible
        STATUS          current
        DESCRIPTION     "An entry containing information about a particular 
                        battery."
        INDEX           { stnBatterySlotIndex }
        ::= { stnBatteryTable 1 }
 
    StnBatteryEntry ::= SEQUENCE {
                stnBatterySlotIndex      Integer32,
                stnBatteryType           Integer32,
                stnBatteryStatus         StnBatteryStatus,
                stnBatteryDescr          DisplayString
                }

    stnBatterySlotIndex OBJECT-TYPE
        SYNTAX          Integer32
        MAX-ACCESS      read-only
        STATUS          current
        DESCRIPTION     "The chassis slot number associated with this battery."
        ::= { stnBatteryEntry 1 }

    stnBatteryType OBJECT-TYPE
        SYNTAX          Integer32
        MAX-ACCESS      read-only
        STATUS          current
        DESCRIPTION     "The physical component using the battery.

                        real-time-clock(1),
                        nvram(2)
                        "
        ::= { stnBatteryEntry 2 }

    stnBatteryStatus OBJECT-TYPE     
        SYNTAX          StnBatteryStatus
        MAX-ACCESS      read-only
        STATUS          current
        DESCRIPTION     "The current state of the battery.
                        
                        unknown(1),     -- none of the following 
                        ok(2),          -- battery power is within the acceptable range
                        low(3)          -- battery power is below the recommended range
                        "
        ::= { stnBatteryEntry 3 }

    stnBatteryDescr OBJECT-TYPE     
        SYNTAX          DisplayString
        MAX-ACCESS      read-only
        STATUS          current
        DESCRIPTION     "A descriptive string or label associated with the 
                        battery."
        ::= { stnBatteryEntry 4 }

	--
    -- STN CPU Utilization Table
    --
    stnCpuUtilizationTable OBJECT-TYPE
        SYNTAX          SEQUENCE OF StnCpuUtilizationEntry
        MAX-ACCESS      not-accessible
        STATUS          current
        DESCRIPTION     "A list of CPU utilization entries."
        ::= { stnResource 1 }
 
    stnCpuUtilizationEntry OBJECT-TYPE
        SYNTAX          StnCpuUtilizationEntry
        MAX-ACCESS      not-accessible
        STATUS          current
        DESCRIPTION     "An entry containing CPU Utilization."
        INDEX           { stnCpuUtilizationIndex }
        ::= { stnCpuUtilizationTable 1 }
 
    StnCpuUtilizationEntry ::= SEQUENCE {
                stnCpuUtilizationIndex      Integer32,
                stnCpuUtilizationCurrent	Integer32,
				stnCpuUtilization5Min		Integer32,
				stnCpuUtilization15Min		Integer32,
				stnCpuUtilization30Min		Integer32
                }

    stnCpuUtilizationIndex OBJECT-TYPE
        SYNTAX          Integer32
        MAX-ACCESS      read-only
        STATUS          current
        DESCRIPTION     "The engine id associated with each CPU."
        ::= { stnCpuUtilizationEntry 1 }

    stnCpuUtilizationCurrent OBJECT-TYPE     
        SYNTAX          Integer32
        MAX-ACCESS      read-only
        STATUS          current
        DESCRIPTION     "The current utilization (%) of the CPU."
        ::= { stnCpuUtilizationEntry 2 }

	stnCpuUtilization5Min OBJECT-TYPE     
        SYNTAX          Integer32
        MAX-ACCESS      read-only
        STATUS          current
        DESCRIPTION     "The past 5 minute utilization (%) of the CPU."
        ::= { stnCpuUtilizationEntry 3 }

	stnCpuUtilization15Min OBJECT-TYPE     
        SYNTAX          Integer32
        MAX-ACCESS      read-only
        STATUS          current
        DESCRIPTION     "The past 15 minute utilization (%) of the CPU."
        ::= { stnCpuUtilizationEntry 4 }

	stnCpuUtilization30Min OBJECT-TYPE     
        SYNTAX          Integer32
        MAX-ACCESS      read-only
        STATUS          current
        DESCRIPTION     "The past 30 minute utilization (%) of the CPU."
        ::= { stnCpuUtilizationEntry 5 }

    --
    -- STN CPU IP Table
    --
    stnCpuIpTable OBJECT-TYPE
        SYNTAX          SEQUENCE OF StnCpuIpEntry
        MAX-ACCESS      not-accessible
        STATUS          current
        DESCRIPTION     "A list of entries describing IP resources on each cpu."
        ::= { stnResource 2 }
 
    stnCpuIpEntry OBJECT-TYPE
        SYNTAX          StnCpuIpEntry
        MAX-ACCESS      not-accessible
        STATUS          current
        DESCRIPTION     "An entry describing IP resources on each cpu."
        INDEX           { stnCpuIpIndex }
        ::= { stnCpuIpTable 1 }
 
    StnCpuIpEntry ::= SEQUENCE {
                stnCpuIpIndex             Integer32,
                stnCpuIpRouteLimit        Integer32,
                stnCpuIpRoutesInUse       Integer32,
                stnCpuIpRoutesBooked      Integer32,
                stnCpuIpFwdProcesses      Integer32,
                stnCpuIpRoutingProcesses  Integer32
                }

    stnCpuIpIndex OBJECT-TYPE
        SYNTAX          Integer32
        MAX-ACCESS      read-only
        STATUS          current
        DESCRIPTION     "The engine id associated with each CPU."
        ::= { stnCpuIpEntry 1 }

    stnCpuIpRouteLimit OBJECT-TYPE
        SYNTAX          Integer32
        MAX-ACCESS      read-only
        STATUS          current
        DESCRIPTION     "The maximum number of ip routes allowed on this cpu."
        ::= { stnCpuIpEntry 2 }

    stnCpuIpRoutesInUse OBJECT-TYPE
        SYNTAX          Integer32
        MAX-ACCESS      read-only
        STATUS          current
        DESCRIPTION     "The number of ip routes currently allocated on this cpu."
        ::= { stnCpuIpEntry 3 }

    stnCpuIpRoutesBooked OBJECT-TYPE
        SYNTAX          Integer32
        MAX-ACCESS      read-only
        STATUS          current
        DESCRIPTION     "The sum of all maximum routing table sizes for all routers on this cpu.
                         Note that when over-subsciption is allowed this number may
                         exceed the actual route limit on this engine."
        ::= { stnCpuIpEntry 4 }

    stnCpuIpFwdProcesses OBJECT-TYPE
        SYNTAX          Integer32
        MAX-ACCESS      read-only
        STATUS          current
        DESCRIPTION     "The number of ip forwarding processes on this engine."
        ::= { stnCpuIpEntry 5 }

    stnCpuIpRoutingProcesses OBJECT-TYPE
        SYNTAX          Integer32
        MAX-ACCESS      read-only
        STATUS          current
        DESCRIPTION     "The number of ip routing processes on this engine."
        ::= { stnCpuIpEntry 6 }

    --
    -- STN Chassis trap support objects.
    --
    stnNotificationCfgChangeTime OBJECT-TYPE
        SYNTAX          TimeTicks
        MAX-ACCESS      read-only
        STATUS          current
        DESCRIPTION     "The time (in hundredths of a second) since the
                        configuration of the system was last changed."
        ::= { stnChassisTrapVars 1 }

    stnNotificationFlashStatus OBJECT-TYPE
        SYNTAX          StnFlashStatus
        MAX-ACCESS      read-only
        STATUS          current
        DESCRIPTION     "The status of the chassis flash module."
        ::= { stnChassisTrapVars 2 }

    stnNotificationModuleTemperature OBJECT-TYPE
        SYNTAX          INTEGER
        MAX-ACCESS      read-only
        STATUS          current
        DESCRIPTION     "The temperature of a specific module."
        ::= { stnChassisTrapVars 3 }


    stnNotificationResourceStatus OBJECT-TYPE
        SYNTAX          StnResourceStatus
        MAX-ACCESS      read-only
        STATUS          current
        DESCRIPTION     "The status of the chassis resources."
        ::= { stnChassisTrapVars 4 }


    --
    -- STN Traps & Notifications 
    --
    stnRedundant NOTIFICATION-TYPE
        OBJECTS         { stnSlotIndex, stnModuleType, stnModuleOperStatus }
        STATUS          current
        DESCRIPTION     "A stnRedundant trap signifies that the agent 
                        entity has detected that the stnModuleOperStatus 
                        object in the STN-CHASSIS-MIB has transitioned to the 
                        up-primary(8) state for one of its modules.
                        The generation of this trap can be controlled by the
                        RedundancyTraps configuration object."
        ::= { stnNotification 1 }

    stnNotRedundant NOTIFICATION-TYPE
        OBJECTS         { stnSlotIndex, stnModuleType, stnModuleOperStatus }
        STATUS          current
        DESCRIPTION     "A stnNotRedundant trap signifies that the agent 
                        entity has detected that the stnModuleOperStatus 
                        object in the STN-CHASSIS-MIB has transitioned to the 
                        up-standalone(6) state for one of its modules.
                        The generation of this trap can be controlled by the
                        RedundancyTraps configuration object."
        ::= { stnNotification 2 }

    stnModuleUp NOTIFICATION-TYPE
        OBJECTS         { stnSlotIndex, stnModuleType, stnModuleOperStatus,
                          stnModuleDescr, stnSubModules }
        STATUS          current
        DESCRIPTION     "A stnModuleUp trap signifies that the agent 
                        entity has detected that the stnModuleOperStatus 
                        object in the STN-CHASSIS-MIB has transitioned to 
                        up-standalone(6), up-standby(7), or 
                        up-primary(8) state for one of its modules.
                        The generation of this trap can be controlled by the
                        ModuleUpTraps configuration object."
        ::= { stnNotification 3 }

    stnModuleDown NOTIFICATION-TYPE
        OBJECTS         { stnSlotIndex, stnModuleType, stnModuleOperStatus,
                          stnModuleDescr, stnSubModules }
        STATUS          current
        DESCRIPTION     "A stnModuleDown trap signifies that the agent 
                        entity has detected that the stnModuleOperStatus 
                        object in the STN-CHASSIS-MIB has transitioned to 
                        the down(3) state for one of its modules.
                        The generation of this trap can be controlled by the
                        ModuleDownTraps configuration object."
        ::= { stnNotification 4 }

    stnSubModuleUp NOTIFICATION-TYPE
        OBJECTS         { stnSubModuleSlot, stnSubModuleIndex, 
                          stnSubModuleType, stnSubModuleOperStatus, 
			  stnSubModuleDescr }
        STATUS          current
        DESCRIPTION     "A stnSubModuleUp trap signifies that the agent 
                        entity has detected that the stnSubModuleOperStatus 
                        object in the STN-CHASSIS-MIB has transitioned to 
                        up-standalone(6), up-standby(7), or 
                        up-primary(8) state for one of its sub-modules.
                        The generation of this trap can be controlled by the
                        SubModuleUpTraps configuration object."
        ::= { stnNotification 5 }

    stnSubModuleDown NOTIFICATION-TYPE
        OBJECTS         { stnSubModuleSlot, stnSubModuleIndex, 
                          stnSubModuleType, stnSubModuleOperStatus,
			  stnSubModuleDescr }
        STATUS          current
        DESCRIPTION     "A stnModuleDown trap signifies that the agent 
                        entity has detected that the stnModuleOperStatus 
                        object in the STN-CHASSIS-MIB has transitioned to 
                        the down(3) state for one of its modules.
                        The generation of this trap can be controlled by the
                        SubModuleDownTraps configuration object."
        ::= { stnNotification 6 }

    stnEngineUp NOTIFICATION-TYPE
        OBJECTS         { stnEngineIndex, stnEngineSlot, stnEngineCpu, 
                          stnEngineType, stnEngineOperStatus }
        STATUS          current
        DESCRIPTION     "A stnEngineUp trap signifies that the agent 
                        entity has detected that the stnEngineOperStatus 
                        object in the STN-CHASSIS-MIB has transitioned to 
                        up-standalone(6), up-standby(7), or 
                        up-primary(8) state for one of its engines.
                        The generation of this trap can be controlled by the
                        EngineUpTraps configuration object."
        ::= { stnNotification 7 }

    stnEngineDown NOTIFICATION-TYPE
        OBJECTS         { stnEngineIndex, stnEngineSlot, stnEngineCpu, 
                          stnEngineType, stnEngineOperStatus }
        STATUS          current
        DESCRIPTION     "A stnEngineDown trap signifies that the agent 
                        entity has detected that the stnEngineOperStatus 
                        object in the STN-CHASSIS-MIB has transitioned to 
                        the down(3) state for one of its engines.
                        The generation of this trap can be controlled by the
                        EngineDownTraps configuration object."
        ::= { stnNotification 8 }

    stnBatteryLow NOTIFICATION-TYPE
        OBJECTS         { stnBatterySlotIndex, stnBatteryType, 
                          stnBatteryStatus }
        STATUS          current
        DESCRIPTION     "A stnBatteryLow trap signifies that the agent 
                        entity has detected that the stnBatteryStatus 
                        object in the STN-CHASSIS-MIB has transitioned to 
                        the low(3) state for one of its batteries.
                        The generation of this trap can be controlled by the
                        BatteryTraps configuration object."
        ::= { stnNotification 9 }

    stnFlashFailure NOTIFICATION-TYPE
        OBJECTS         { stnNotificationFlashStatus }
        STATUS          current
        DESCRIPTION     "A stnFlashFailure trap signifies that the agent 
                        entity has detected that the stnFlashStatus 
                        object in the STN-CHASSIS-MIB has transitioned out 
                        of the ok(2) state to one of the disfunctional states.
                        The generation of this trap can be controlled by the
                        FlashTraps configuration object."
        ::= { stnNotification 10 }

    stnResourceFailure NOTIFICATION-TYPE
        OBJECTS         { stnNotificationResourceStatus }
        STATUS          current
        DESCRIPTION     "A stnResourceFailure trap signifies that the agent 
                        entity has detected that a chassis resource object
                        has transitioned out of the ok(2) state to one of the 
                        alarm states.
                        The generation of this trap can be controlled by the
                        ResourceTraps configuration object."
        ::= { stnNotification 11 }

    stnFailover NOTIFICATION-TYPE
        OBJECTS         { stnSlotIndex, stnModuleType }
        STATUS          current
        DESCRIPTION     "A stnFailover trap signifies that the agent 
                        entity has detected that a stnModule 
                        has transitioned to its redundant stnModule.
                        The generation of this trap can be controlled by the
                        FailoverTraps configuration object."
        ::= { stnNotification 12 }

    stnCfgChange NOTIFICATION-TYPE
        OBJECTS         { stnNotificationCfgChangeTime }
        STATUS          current
        DESCRIPTION     "A stnCfgChange trap signifies that the agent entity 
                        has detected that a configuration modification has 
                        been applied to the device.
                        The generation of this trap can be controlled by the
                        ConfigTraps configuration object."
        ::= { stnNotification 19 }

    stnPowerFailure NOTIFICATION-TYPE
        OBJECTS         { stnPowerIndex, stnPowerStatus }
        STATUS          current
        DESCRIPTION     "A stnPowerFailure trap signifies that the agent 
                        entity has detected that the stnPowerStatus 
                        object in the STN-CHASSIS-MIB has transitioned 
                        out of present(2) state for one of its connections.
                        The generation of this trap can be controlled by the
                        PowerTraps configuration object."
        ::= { stnNotification 55 }

    stnTemperatureFailure NOTIFICATION-TYPE
        OBJECTS         { stnSlotIndex,     stnModuleType,  
                          stnSubModuleType, stnNotificationModuleTemperature }
        STATUS          current
        DESCRIPTION     "A stnTemperatureFailure trap signifies that the agent 
                        entity has detected that a temperature fault has
                        occurred on the indicated module/sub-module.
                        The generation of this trap can be controlled by the
                        TemperatureTraps configuration object."
        ::= { stnNotification 56 }

    --
    -- Conformance Information
    --
    stnChassisMibCompliances OBJECT IDENTIFIER ::= { stnChassisMibConformance 1 }
    stnChassisMibGroups      OBJECT IDENTIFIER ::= { stnChassisMibConformance 2 }


    --
    -- Compliance statements
    --
    stnChassisMibComplianceRev1 MODULE-COMPLIANCE
        STATUS  current 
        DESCRIPTION
                "The compliance statement for entities which implement
                the Spring Tide Networks Chassis MIB."
        MODULE  -- This Module
                MANDATORY-GROUPS { stnChassisMibGroup }
        ::= { stnChassisMibCompliances 1 }


    --
    -- Conformance Units
    --
    stnChassisMibGroup OBJECT-GROUP
        OBJECTS {
                stnChassisSysType,
                stnChassisSysDescr,
                stnChassisId,
                stnSlotIndex,
                stnModuleType,
                stnModulePeer,
                stnModuleAdminStatus,
                stnModuleOperStatus,
                stnModuleDescr,
                stnModuleLed,
                stnSubModules,
                stnSubModuleSlot,
                stnSubModuleIndex,
                stnSubModuleType,
                stnSubModulePeer,
                stnSubModuleAdminStatus,        
                stnSubModuleOperStatus,
                stnSubModuleDescr,
                stnEngineIndex,
                stnEngineSlot,
                stnEngineCpu,
                stnEngineType,
                stnEnginePeer,
                stnEngineAdminStatus,
                stnEngineOperStatus,
                stnEngineDescr,
                stnLedFanTray,
                stnLedPowerA,
                stnLedPowerB,
                stnLedAlarm,
                stnFanTrayLedIndex,
                stnFanTrayLedSlotIndex,
                stnFanTrayLedStatus,
                stnPortLedSlotIndex,
                stnPortLedPortIndex,
                stnPortLedIndex,
                stnPortLedStatus,
                stnPortLedDescr,
                stnPowerIndex,
                stnPowerStatus,
                stnPowerDescr,
                stnBatterySlotIndex,
                stnBatteryType,
                stnBatteryStatus,
                stnBatteryDescr
        }
        STATUS  current
        DESCRIPTION 
                "A collection of STN objects providing chassis information."
        ::= { stnChassisMibGroups 1 }

   
END
