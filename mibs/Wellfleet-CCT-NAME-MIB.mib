Wellfleet-CCT-NAME-MIB DEFINITIONS ::= BEGIN

-- Created by mdl2asn version 3.1
-- Creation date: Wed Aug 30 16:39:06 EDT 1995
-- Modified by Jim Waclawik on 9-31-98

    IMPORTS

      OBJECT-TYPE
        FROM RFC-1212
      DisplayString
        FROM RFC1213-MIB
      wfServices, wfCircuitNameExtension
        FROM Wellfleet-COMMON-MIB;


    wfCircuitNameTable OBJECT-TYPE
        SYNTAX  SEQUENCE OF WfCircuitNameEntry
        ACCESS  not-accessible
        STATUS  mandatory
        DESCRIPTION
                "The table of circuit names"
        ::= { wfServices 3 }

    wfCircuitNameEntry OBJECT-TYPE
        SYNTAX  WfCircuitNameEntry
        ACCESS  not-accessible
        STATUS  mandatory
        DESCRIPTION
                "Entry format for the table of circuit names"
        INDEX   { wfCircuitNumber }
        ::= { wfCircuitNameTable 1 }

    WfCircuitNameEntry ::= SEQUENCE {
            wfCircuitNameDelete
            INTEGER,
            wfCircuitNumber
            INTEGER,
            wfCircuitName
            DisplayString,
            wfCircuitIfType
            INTEGER,
            wfCircuitProtoMap
            OCTET STRING,
            wfCircuitType
            INTEGER,
            wfCircuitRelCctList
            OCTET STRING,
            wfCircuitLineList
            OCTET STRING,
            wfCircuitMultilineName
                DisplayString,
            wfCircuitTdmRes
                INTEGER,
            wfCircuitTdmCctInUse
                INTEGER
        }

    wfCircuitNameDelete OBJECT-TYPE
        SYNTAX  INTEGER {
                create(1),
                delete(2)
            }
        ACCESS  read-write
        STATUS  mandatory
        DESCRIPTION
                "Creation and deletion flag for this record"
        DEFVAL  { create }
        ::= { wfCircuitNameEntry 1 }

    wfCircuitNumber OBJECT-TYPE
        SYNTAX  INTEGER
        ACCESS  read-only
        STATUS  mandatory
        DESCRIPTION
                "circuit number"
        ::= { wfCircuitNameEntry 2 }

    wfCircuitName OBJECT-TYPE
        SYNTAX  DisplayString
        ACCESS  read-write
        STATUS  mandatory
        DESCRIPTION
                "circuit name"
        ::= { wfCircuitNameEntry 3 }

    wfCircuitIfType OBJECT-TYPE
        SYNTAX  INTEGER {
                csmacd(10),
                sync(20),
                t1(30),
                e1(40),
                    token(50),
                fddi(60),
                hssi(70),
                mct1(80),
                ds1e1(90),
                none(100),
                atm(110),
                async(120),
                isdn(130),
                atmz(140),
            bisync(150),
            gre(160),
            ds3e3(170)
            }
        ACCESS  read-write
        STATUS  mandatory
        DESCRIPTION
                "circuit interface type"
        ::= { wfCircuitNameEntry 4 }

    wfCircuitProtoMap OBJECT-TYPE
        SYNTAX  OCTET STRING
        ACCESS  read-write
        STATUS  mandatory
        DESCRIPTION
                "CIRCUIT_PROTO_BRIDGE            1
                CIRCUIT_PROTO_SPANTREE          2
                CIRCUIT_PROTO_IP                3
                CIRCUIT_PROTO_RIP               4
                CIRCUIT_PROTO_EGP               5
                CIRCUIT_PROTO_OSPF              6
                CIRCUIT_PROTO_SNMP              7
                CIRCUIT_PROTO_TFTP              8
                CIRCUIT_PROTO_TCP               9
                CIRCUIT_PROTO_DECNET4           10
                CIRCUIT_PROTO_VINES             11
                CIRCUIT_PROTO_SMDS              12
                CIRCUIT_PROTO_FR                13
                CIRCUIT_PROTO_IPX               14
                CIRCUIT_PROTO_IPX_RIP           15
                CIRCUIT_PROTO_XNS               16
                CIRCUIT_PROTO_XNS_RIP           17
                CIRCUIT_PROTO_AT                18
                CIRCUIT_PROTO_SR                19
                CIRCUIT_PROTO_FR_VC             20
                CIRCUIT_PROTO_PRI_Q             21
                CIRCUIT_PROTO_PPP               22
                CIRCUIT_PROTO_OSI               23
                CIRCUIT_PROTO_LLC2              24
                CIRCUIT_PROTO_LNM               25
                CIRCUIT_PROTO_X25               26
                CIRCUIT_PROTO_ATM               27
                CIRCUIT_PROTO_ATM_VC            28
                CIRCUIT_PROTO_TELNET            29
                CIRCUIT_PROTO_STA               30
                CIRCUIT_PROTO_BGP               31
                CIRCUIT_PROTO_DLS               32
                CIRCUIT_PROTO_RARP              33
                CIRCUIT_PROTO_BOOTP             34
                CIRCUIT_PROTO_LLC2_VC           35
                CIRCUIT_PROTO_AURP              36
                CIRCUIT_PROTO_X25_VC            37
                CIRCUIT_PROTO_DEMAND            38
                CIRCUIT_PROTO_CL_IP             39
                CIRCUIT_PROTO_PROXY             40
                CIRCUIT_PROTO_TELNET_CLIENT     41
                CIRCUIT_PROTO_SW_LAPB           42
                CIRCUIT_PROTO_SR_SPANTREE       43
                CIRCUIT_PROTO_NML               44
                CIRCUIT_PROTO_RDISC             45
                CIRCUIT_PROTO_SDLC              46
                CIRCUIT_PROTO_NBASE             47
                CIRCUIT_PROTO_SWSMDS            48
                CIRCUIT_PROTO_FRSW_CONG         49
                CIRCUIT_PROTO_SW_PROXY          50
                CIRCUIT_PROTO_FRSW              51
                CIRCUIT_PROTO_APPN              52
                CIRCUIT_PROTO_APPN_CP           53
                CIRCUIT_PROTO_ISDN              54
                CIRCUIT_PROTO_LINEMANAGER       55
                CIRCUIT_PROTO_ATM_UNI           56
                CIRCUIT_PROTO_ATM_UNI_VCL       57
                CIRCUIT_PROTO_IGMP              58
                CIRCUIT_PROTO_DVMRP             59
                CIRCUIT_PROTO_NBIP              60
                CIRCUIT_PROTO_FTP               61
                CIRCUIT_PROTO_WCP               62
                CIRCUIT_PROTO_ARP               63
                CIRCUIT_PROTO_ST2               64
                CIRCUIT_PROTO_ATMZ              65
                CIRCUIT_PROTO_ATM_LE            66
                CIRCUIT_PROTO_IPEX              67
                CIRCUIT_PROTO_NLSP              68
                CIRCUIT_PROTO_BGPRS             69
                CIRCUIT_PROTO_CRM               70
                CIRCUIT_PROTO_RR                71
                CIRCUIT_PROTO_NPT               72
                CIRCUIT_PROTO_ATM_SIG           73
                CIRCUIT_PROTO_BOT               74
                CIRCUIT_PROTO_PIM               75
                CIRCUIT_PROTO_NTP               76
                CIRCUIT_PROTO_MIP               77
                CIRCUIT_PROTO_BNX_RSVD_78       78
                CIRCUIT_PROTO_BNX_RSVD_79       79
                CIRCUIT_PROTO_ISDB              80
                CIRCUIT_PROTO_FWALL             81
                CIRCUIT_PROTO_WEP               82
                CIRCUIT_PROTO_BACP              83
                CIRCUIT_PROTO_RADIUS            84
                CIRCUIT_PROTO_IPV6              85
                CIRCUIT_PROTO_RIP6              86
                CIRCUIT_PROTO_AOT               87
                CIRCUIT_PROTO_RSVP              88
                CIRCUIT_PROTO_MOSPF             89
                CIRCUIT_PROTO_PORTMTX           90
                CIRCUIT_PROTO_CONVSTR           91
                CIRCUIT_PROTO_RCMDS             92
                CIRCUIT_PROTO_DNS               93
                CIRCUIT_PROTO_COLUMBO           94
                CIRCUIT_PROTO_NAT               95
                CIRCUIT_PROTO_ASR               96
                CIRCUIT_PROTO_NHRP              97
                CIRCUIT_PROTO_AHB               98
                CIRCUIT_PROTO_HTTP              99
                CIRCUIT_PROTO_FRPT              100
                CIRCUIT_PROTO_FRSVC             101
                CIRCUIT_PROTO_STACLZS           102
                CIRCUIT_PROTO_L2TP              103
                CIRCUIT_PROTO_BNX_RSVD_104      104
                CIRCUIT_PROTO_VCCT              105
                CIRCUIT_PROTO_TAG1Q             106
                CIRCUIT_PROTO_TARP              107
                CIRCUIT_PROTO_MPS               108
                CIRCUIT_PROTO_DHCP              109
                CIRCUIT_PROTO_CAPI              110
                CIRCUIT_PROTO_IPSEC             111
                CIRCUIT_PROTO_MPLS_LDP          112
                CIRCUIT_PROTO_MPLS_MLM          113
                CIRCUIT_PROTO_IISIS             114
                CIRCUIT_PROTO_COPS              115
                CIRCUIT_PROTO_DIFFSERV          116
                CIRCUIT_PROTO_IKE               117
                CIRCUIT_PROTO_VRRP              118
                CIRCUIT_PROTO_WIREDUND          119
                CIRCUIT_PROTO_MLT               120
                CIRCUIT_PROTO_L2TP_CLIENT       121
                CIRCUIT_PROTO_DSQMS             122
                NUMBER_OF_PROTOCOLS             122"
        ::= { wfCircuitNameEntry 5 }

    wfCircuitType OBJECT-TYPE
        SYNTAX  INTEGER {
                normal(1),
                virtual(2),
                master(3),
                clip(4),
                internal(5),
                    gre(6),
                    notrouted(7)
            }
        ACCESS  read-write
        STATUS  mandatory
        DESCRIPTION
                "The circuit type"
        DEFVAL  { normal }
        ::= { wfCircuitNameEntry 6 }

    wfCircuitRelCctList OBJECT-TYPE
        SYNTAX  OCTET STRING
        ACCESS  read-write
        STATUS  mandatory
        DESCRIPTION
                "The related circuit list for this circuit: only valid if
                wfCircuitType is either CIRCUIT_REL_VIRTUAL or CIRCUIT_REL_MASTER"
        ::= { wfCircuitNameEntry 7 }

    wfCircuitLineList OBJECT-TYPE
        SYNTAX  OCTET STRING
        ACCESS  read-write
        STATUS  mandatory
        DESCRIPTION
                "The line info list for this circuit"
        ::= { wfCircuitNameEntry 8 }

    wfCircuitMultilineName OBJECT-TYPE
        SYNTAX  DisplayString
        ACCESS  read-write
        STATUS  mandatory
        DESCRIPTION
                "Name of the multiline that this circuit is. Use the
                 circuit name if this is nil."
        ::= { wfCircuitNameEntry 9 }

    wfCircuitTdmRes OBJECT-TYPE
        SYNTAX  INTEGER {
                    notdmresources(1),
                    switchedh110(2),
                    routedh110(3),
                    cesh110(4)
                }       
        ACCESS  read-write
        STATUS  mandatory
        DESCRIPTION
                "Specifies if, and how, the circuit 
                 utilizes TDM resources.  Normal GAME circuits
                 should have this set to noTdmResources."
        DEFVAL  { notdmresources }
        ::= { wfCircuitNameEntry 10 }

    wfCircuitTdmCctInUse OBJECT-TYPE
        SYNTAX  INTEGER{
                    notinuse(1),
                    inuse(2)
                }
        ACCESS  read-write
        STATUS  mandatory
        DESCRIPTION
                "This field is for TDM Circuit Management use, and
                 it indicates whether this TDM circuit is currently
                 in use.  It is only valid if wfCircuitTdmRes is not 
                 set to (notdmresources)."
        DEFVAL  { notinuse }
        ::= { wfCircuitNameEntry 11 }

    wfLineMappingTable OBJECT-TYPE
        SYNTAX  SEQUENCE OF WfLineMappingEntry
        ACCESS  not-accessible
        STATUS  mandatory
        DESCRIPTION
                "The table of line mappings"
        ::= { wfCircuitNameExtension 1 }

    wfLineMappingEntry OBJECT-TYPE
        SYNTAX  WfLineMappingEntry
        ACCESS  not-accessible
        STATUS  mandatory
        DESCRIPTION
                "Entry format for the table of lines"
        INDEX   { wfLineMappingNumber }
        ::= { wfLineMappingTable 1 }

    WfLineMappingEntry ::= SEQUENCE {
            wfLineMappingDelete
            INTEGER,
            wfLineMappingNumber
            INTEGER,
            wfLineMappingCct
            INTEGER,
            wfLineMappingDef
            OCTET STRING
        }

    wfLineMappingDelete OBJECT-TYPE
        SYNTAX  INTEGER {
                created(1),
                deleted(2)
            }
        ACCESS  read-write
        STATUS  mandatory
        DESCRIPTION
                "Creation and deletion flag for this record"
        DEFVAL  { created }
        ::= { wfLineMappingEntry 1 }

    wfLineMappingNumber OBJECT-TYPE
        SYNTAX  INTEGER
        ACCESS  read-only
        STATUS  mandatory
        DESCRIPTION
                "Unique line number. This number is stored in the physical line entries."
        ::= { wfLineMappingEntry 2 }

    wfLineMappingCct OBJECT-TYPE
        SYNTAX  INTEGER
        ACCESS  read-write
        STATUS  mandatory
        DESCRIPTION
                "Circuit number stored in the physical line entry."
        ::= { wfLineMappingEntry 3 }

    wfLineMappingDef OBJECT-TYPE
        SYNTAX  OCTET STRING
        ACCESS  read-write
        STATUS  mandatory
        DESCRIPTION
                "Identifies which physical line this line maps to."
        ::= { wfLineMappingEntry 4 }

    wfNode      OBJECT IDENTIFIER ::= { wfCircuitNameExtension 2 }

    wfNodeDelete OBJECT-TYPE
        SYNTAX  INTEGER {
                created(1),
                deleted(2)
            }
        ACCESS  read-write
        STATUS  mandatory
        DESCRIPTION
                "Create/Delete parameter. Default is created.
                SM performs a set operation on this
                object in order to create/delete Node base record."
        DEFVAL  { created }
        ::= { wfNode 1 }

    wfNodeProtoMap OBJECT-TYPE
        SYNTAX  OCTET STRING
        ACCESS  read-write
        STATUS  mandatory
        DESCRIPTION
                "The Node-Protocol mask, indicates what protocols are configured
                on the router , for bit numbers see wfCircuitProtomap"
        ::= { wfNode 2 }

    END  -- Wellfleet-CCT-NAME-MIB
