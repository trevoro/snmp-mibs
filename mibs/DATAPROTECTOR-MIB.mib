DATAPROTECTOR-MIB DEFINITIONS ::= BEGIN

IMPORTS
     OBJECT-TYPE FROM RFC-1212
     TRAP-TYPE   FROM RFC-1215
;

-- the path to the root

org            		OBJECT IDENTIFIER ::= { iso 3 }
dod            		OBJECT IDENTIFIER ::= { org 6 }
internet       		OBJECT IDENTIFIER ::= { dod 1 }
private        		OBJECT IDENTIFIER ::= { internet 4 }
enterprises    		OBJECT IDENTIFIER ::= { private 1 }
hp			OBJECT IDENTIFIER ::= { enterprises 11 }
nm			OBJECT IDENTIFIER ::= { hp 2 }
openView		OBJECT IDENTIFIER ::= { nm 17 }
openView-2	OBJECT IDENTIFIER ::= { openView 1 }
openViewTrapVars	OBJECT IDENTIFIER ::= { openView-2 2 }	








dpSourceId OBJECT-TYPE
	SYNTAX	INTEGER	{ dataprotector(1) }  -- is always 1 for Data Protector
	MAX-ACCESS not-accessible
	STATUS	   current
	DESCRIPTION
		"The identifier of the software generating the trap/event.
		 This number is used by HP OpenView software when it sends
		 an event to the OpenView event system.  It identifies
		 which software component sent the event."
	::= { openViewTrapVars 1 }

dpSourceName OBJECT-TYPE
	SYNTAX	OCTET STRING
	MAX-ACCESS not-accessible
	STATUS     current
	DESCRIPTION
		"The machine upon which the event was generated. It
		 identifies for which node the event is generated."
	::= { openViewTrapVars 2 }

dpObjectName OBJECT-TYPE
	SYNTAX	OCTET STRING
	MAX-ACCESS not-accessible
	STATUS     current
	DESCRIPTION
		"The Object identifier associated with the source of the trap/event."
	::= { openViewTrapVars 3 }

dpApplicationName OBJECT-TYPE
	SYNTAX	OCTET STRING
	MAX-ACCESS not-accessible
	STATUS     current
	DESCRIPTION
		"The Application identifier associated with the source of the trap/event."
	::= { openViewTrapVars 4 }

dpSeverity OBJECT-TYPE
	SYNTAX	OCTET STRING
	MAX-ACCESS not-accessible
	STATUS     current
	DESCRIPTION
		"The openView event severity associated with the trap/event."
	::= { openViewTrapVars 5 }

dpMessageText OBJECT-TYPE
	SYNTAX	OCTET STRING
	MAX-ACCESS not-accessible
	STATUS     current
	DESCRIPTION
		"The message text associated with the trap/event."
	::= { openViewTrapVars 6 }

dpDataList OBJECT-TYPE
	SYNTAX	OCTET STRING
	MAX-ACCESS not-accessible
	STATUS     current
	DESCRIPTION
		"A comma separated list of keyword and value pairs."
	::= { openViewTrapVars 7 }



-- the Data Protector Trap definition

dpTrap TRAP-TYPE
	ENTERPRISE	openView-2
	VARIABLES	{
				dpSourceId,
				dpSourceName,
				dpObjectName,
				dpApplicationName,
				dpSeverity,
				dpMessageText,
				dpDataList
			}
	DESCRIPTION
		"A trap with this value identifies Data Protector."
	::= 59047936 




END
