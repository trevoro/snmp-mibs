-- ES-1000 Trunk Switch MIB Ver 0.01                           1999/06/16

TRUNK-MIB

DEFINITIONS ::= BEGIN
    IMPORTS
        enterprises,IpAddress           FROM RFC1155-SMI
        DisplayString                   FROM RFC1213-MIB
        MacAddress                      FROM BRIDGE-MIB
        OBJECT-TYPE                     FROM RFC-1212;
    
    PortList        ::= OCTET STRING(SIZE(4))

    marconi                  OBJECT IDENTIFIER ::= { enterprises 326 }
    systems                  OBJECT IDENTIFIER ::= { marconi 2 }
    external                 OBJECT IDENTIFIER ::= { systems 20 }

    dlink                    OBJECT IDENTIFIER ::= { external 1 }
    dlinkcommon              OBJECT IDENTIFIER ::= { dlink 1 }
    golf                     OBJECT IDENTIFIER ::= { dlink 2 }

    golfproducts             OBJECT IDENTIFIER ::= { golf 1 }
    golfcommon               OBJECT IDENTIFIER ::= { golf 2 }

    marconi-mgmt             OBJECT IDENTIFIER ::= { golfcommon 2 }
    es1000Series             OBJECT IDENTIFIER ::= { marconi-mgmt 24 }

    swPortTrunkPackage      OBJECT IDENTIFIER ::= { es1000Series 6 }
    swSnoopPackage          OBJECT IDENTIFIER ::= { es1000Series 7 }
    swIGMPPackage           OBJECT IDENTIFIER ::= { es1000Series 8 }

    endOfMIB                OBJECT-TYPE
        SYNTAX  INTEGER
        ACCESS  read-only
        STATUS  optional
        ::= { es1000Series 9999 }

    swPortTrunkTable OBJECT-TYPE
        SYNTAX SEQUENCE OF SwPortTrunkEntry
        ACCESS not-accessible
        STATUS mandatory
        DESCRIPTION
            "This table specifys which ports group a set of ports(up to 8)
             into a single logical link."
        ::= { swPortTrunkPackage 1 }

    swPortTrunkEntry OBJECT-TYPE
        SYNTAX SwPortTrunkEntry
        ACCESS not-accessible
        STATUS mandatory
        DESCRIPTION
            "A list of information specifies which ports group a set of 
             ports(up to 8) into a single logical link."
        INDEX  { swPortTrunkIndex }
        ::= { swPortTrunkTable 1 }

    SwPortTrunkEntry ::= 
        SEQUENCE {
            swPortTrunkIndex
                INTEGER,
            swPortTrunkName
                DisplayString,
            swPortTrunkModule
                INTEGER,
            swPortTrunkMasterPort
                INTEGER,
            swPortTrunkMemberNum
                INTEGER,
            swPortTrunkState
                INTEGER
        }

    swPortTrunkIndex OBJECT-TYPE
        SYNTAX INTEGER
        ACCESS read-only
        STATUS mandatory
        DESCRIPTION
            "The index of logical port trunk.The device max support 3 trunk groups.
             The trunk group number depend on the existence of module."
        ::= { swPortTrunkEntry 1 }

    swPortTrunkName OBJECT-TYPE
        SYNTAX DisplayString (SIZE (8))
        ACCESS read-write
        STATUS mandatory
        DESCRIPTION
            "The name of logical port trunk."
        ::= { swPortTrunkEntry 2 }

    swPortTrunkModule OBJECT-TYPE
        SYNTAX INTEGER
        ACCESS read-only
        STATUS mandatory
        DESCRIPTION
            "Indicate which modules include in this Trunk. The value is up to 2."
        ::= { swPortTrunkEntry 3 }

    swPortTrunkMasterPort OBJECT-TYPE
        SYNTAX INTEGER
        ACCESS read-only
        STATUS mandatory
        DESCRIPTION
            "The object indicates the master port number of the port trunk entry.The 
            first port of the trunk is implicitly configured to be the master logical 
            port.When using Port Trunk, you can not configure the other ports of 
            the group except the master port. Their configuration must be same as the
            master port (e.g. speed, duplex, enabled/disabled, flow control, and so on)." 
        ::= { swPortTrunkEntry 4 }

    swPortTrunkMemberNum OBJECT-TYPE
        SYNTAX INTEGER
        ACCESS read-write
        STATUS mandatory
        DESCRIPTION
            "Indicate how many number of ports is included in this Trunk. If
             the trunk is located at expansion module (i.e. es400LinkAggrIndex
             equals to 3) and the module is 100-TX or FX-MTRJ, the maximum number
             of ports in the trunk is 2. The maximum number of ports is 8 for other
             trunks."
        ::= { swPortTrunkEntry 5 }

    
    swPortTrunkState OBJECT-TYPE
        SYNTAX INTEGER {
               other(1),
               disabled(2),
               enabled(3)
               }
        ACCESS read-write
        STATUS mandatory
        DESCRIPTION
            "This object decide the port trunk enabled or disabled."
        ::= { swPortTrunkEntry 6 }

    swSnoopCtrlTable OBJECT-TYPE
        SYNTAX SEQUENCE OF SwSnoopCtrlEntry
        ACCESS not-accessible
        STATUS mandatory
        DESCRIPTION
            "A list of port snooping entries.Port snooping function provide an easy
            way to monitor traffic on any port. In this way any good packets appears
            on the source mirror port also shows up on the target mirror port and 
            doesn't to reconstruct the LAN."
        ::= { swSnoopPackage 1 }

    swSnoopCtrlEntry OBJECT-TYPE
        SYNTAX SwSnoopCtrlEntry
        ACCESS not-accessible
        STATUS mandatory
        DESCRIPTION
            "A list of information provide an easy way to monitor traffic on any port.
            The use can bring a fancy network monitor attaching to any target mirror 
            port and set the port to be monitored as source mirror port. "
        INDEX  { swSnoopIndex }
        ::= { swSnoopCtrlTable 1 }

    SwSnoopCtrlEntry ::= 
        SEQUENCE {
            swSnoopIndex
                INTEGER,
            swSnoopLogicSourcePort
                INTEGER,
            swSnoopLogicTargetPort
                INTEGER,
            swSnoopState
                INTEGER
        }

    swSnoopIndex OBJECT-TYPE
        SYNTAX INTEGER
        ACCESS read-only
        STATUS mandatory
        DESCRIPTION
            "This object indicates the port snooping entry number.There is just only 
            one now."
        ::= { swSnoopCtrlEntry 1 }

    swSnoopLogicSourcePort OBJECT-TYPE
        SYNTAX INTEGER
        ACCESS read-write
        STATUS mandatory
        DESCRIPTION
            "This object indicates the number of port to be sniffed. The port number 
            is the sequential (logical) number which is also applied to bridge MIB,
            etc. For instance, logical port 1~22 is mapped to module 1's 10/100Base-T
            TP ports, port 23~24 is mapped to module 2's 100FX/TX ports, port 25 indicates
            for module 3's Gigabit port, and so on."
        ::= { swSnoopCtrlEntry 2 }

    swSnoopLogicTargetPort OBJECT-TYPE
        SYNTAX INTEGER
        ACCESS read-write
        STATUS mandatory
        DESCRIPTION
            "This object indicates switch which port will sniff another port.
            A trunk port member cannot be configured as a target Snooping port.
            The port number is the sequential (logical) number which is also 
            applied to bridge MIB, etc. For instance, logical port 1~22 is mapped
            to module 1's 10/100Base-T TP ports, port 23~24 is mapped to module
            2's 100FX/TX ports, port 25 indicates for module 3's Gigabit port, and
            so on."
        ::= { swSnoopCtrlEntry 3 }

    swSnoopState OBJECT-TYPE
        SYNTAX INTEGER {
               other(1),
               disable(2),
               enable(3)
               }
        ACCESS read-write
        STATUS mandatory
        DESCRIPTION
            "This object indicates the status of this entry. 

            other(1)   - this entry is currently in use but the conditions under
                         which it will remain so are different from each of the 
                         following values.
            disable(2) - Snoop funtion disable.
            enable(3) -  Snoop funtion enable and Snoop received or transmit
                         packet by snoop source port."
        ::= { swSnoopCtrlEntry 4 }

    swIGMPCtrlTable OBJECT-TYPE
        SYNTAX SEQUENCE OF SwIGMPCtrlEntry
        ACCESS not-accessible
        STATUS mandatory
        DESCRIPTION
            "The table controls the Vlan's IGMP function. Its scale depends on
             current VLAN state (swVlanInfoStatus). If VLAN is disabled or
             in Mac-Base mode, there is only one entry in the table, with
             index 1. If VLAN is in Port-Base or 802.1q mode, the number of
             entries can be up to 12, with index range from 1 to 12."
        ::= { swIGMPPackage 1 }

    swIGMPCtrlEntry OBJECT-TYPE
        SYNTAX SwIGMPCtrlEntry
        ACCESS not-accessible
        STATUS mandatory
        DESCRIPTION
            "The entry in IGMP control table (swIGMPCtrlTable). The entry is
             effective only when IGMP capture switch (swDevIGMPCaptureState)
             is enabled."
        INDEX  { swIGMPCtrlIndex }
        ::= { swIGMPCtrlTable 1 }

    SwIGMPCtrlEntry ::= 
        SEQUENCE {
            swIGMPCtrlIndex
                INTEGER,
            swIGMPCtrlVid
                INTEGER,
            swIGMPCtrlTimer
                INTEGER,
            swIGMPCtrlState
                INTEGER
        }

    swIGMPCtrlIndex OBJECT-TYPE
        SYNTAX INTEGER (1..12)
        ACCESS read-only
        STATUS mandatory
        DESCRIPTION
            "This object indicates the IGMP control entry number.Its scale depends on
             current VLAN state (es400VlanInfoStatus). If VLAN is disabled or in
             Mac-Base mode, there is only one entry in the table, with index 1.
             If VLAN is in Port-Base or 802.1q mode, the number of entries is 12, 
             with index range from 1 to 12."
        ::= { swIGMPCtrlEntry 1 }

    swIGMPCtrlVid OBJECT-TYPE
        SYNTAX INTEGER
        ACCESS read-write
        STATUS mandatory
        DESCRIPTION
            "This object indicates the IGMP control entry's VLAN id. If VLAN is
             disabled or in Mac-Base mode, the Vid is always 0 and cannot be changed
             by management users. If VLAN is in Port-Base mode, the Vid is arranged
             from 1 to 12 , fixed form. If VLAN is in 802.1q mode, the Vid setting 
             can vary from 1 to 4094 by management user, and the Vid in each entry
             must be unique in the IGMP Control Table."
        ::= { swIGMPCtrlEntry 2 }

    swIGMPCtrlTimer OBJECT-TYPE
        SYNTAX INTEGER (30..9999)
        ACCESS read-write
        STATUS mandatory
        DESCRIPTION
            "The timer value for sending IGMP query packet when none 
             was sent by the multicast router in the LAN. The timer works
             in per-VLAN basis. Our device will be activated to send the query
             message if the timer is expired. Please reference RFC2236-1997.
             And it recommends a default of 125 seconds. The timeout value must 
             be at least 30 seconds."
        DEFVAL      { 300 }
        ::= { swIGMPCtrlEntry 3 }

    swIGMPCtrlState OBJECT-TYPE
        SYNTAX INTEGER {
               other(1),
               disable(2),
               enable(3)
               }
        ACCESS read-write
        STATUS mandatory
        DESCRIPTION
            "This object indicates the status of this entry.

            other(1)   - this entry is currently in use but the conditions under
                         which it will remain so are different from each of the 
                         following values.
            disable(2) - IGMP funtion is disabled for this entry.
            enable(3) -  IGMP funtion is enabled for this entry."
        ::= { swIGMPCtrlEntry 4 }

    swIGMPInfoTable OBJECT-TYPE
        SYNTAX SEQUENCE OF SwIGMPInfoEntry
        ACCESS not-accessible
        STATUS mandatory
        DESCRIPTION
            "The table contains the number current IGMP query packets which
             is captured by this device, as well as the IGMP query packets
             sent by the device."
        ::= { swIGMPPackage 2 }

    swIGMPInfoEntry OBJECT-TYPE
        SYNTAX SwIGMPInfoEntry
        ACCESS not-accessible
        STATUS mandatory
        DESCRIPTION
            "Information about current IGMP query information, provided that
             swDevIGMPCaptureState and swIGMPCtrlState of associated VLAN
             entry are all enabled."
        INDEX  { swIGMPInfoIndex }
        ::= { swIGMPInfoTable 1 }

    SwIGMPInfoEntry ::= 
        SEQUENCE {
            swIGMPInfoIndex
                INTEGER,
            swIGMPInfoVid
                INTEGER,
            swIGMPInfoQueryCount
                INTEGER,
            swIGMPInfoTxQueryCount
                INTEGER
        }

    swIGMPInfoIndex OBJECT-TYPE
        SYNTAX INTEGER (1..12)
        ACCESS read-only
        STATUS mandatory
        DESCRIPTION
            "This object indicates the IGMP query information entry number. It could
             be up to 12 entries, depending on current number of VLAN entries."
        ::= { swIGMPInfoEntry 1 }

    swIGMPInfoVid OBJECT-TYPE
        SYNTAX INTEGER
        ACCESS read-only
        STATUS mandatory
        DESCRIPTION
            "This object indicates the Vid of associated IGMP info table entry. It
             follows swIGMPCtrlVid in the associated entry of IGMP control table
             (swIGMPCtrlTable)."
        ::= { swIGMPInfoEntry 2 }

    swIGMPInfoQueryCount OBJECT-TYPE
        SYNTAX INTEGER
        ACCESS read-only
        STATUS mandatory
        DESCRIPTION
            "This object indicates the number of query packets received since the
             IGMP function enabled, in per-VLAN basis."
        ::= { swIGMPInfoEntry 3 }

    swIGMPInfoTxQueryCount OBJECT-TYPE
        SYNTAX INTEGER
        ACCESS read-only
        STATUS mandatory
        DESCRIPTION
            "This object indicates the send count of IGMP query messages, in
             per-VLAN basis. In case of IGMP timer expiration, the switch
             sends IGMP query packets to related VLAN member ports and increment
             this object by 1."
        ::= { swIGMPInfoEntry 4 }

    swIGMPTable OBJECT-TYPE
        SYNTAX SEQUENCE OF SwIGMPEntry
        ACCESS not-accessible
        STATUS mandatory
        DESCRIPTION
            "The table containing current IGMP information which captured by this 
            device, provided that swDevIGMPCaptureState and swIGMPCtrlState of
            associated VLAN entry are all enabled. Note that the priority
            of IGMP table entries is lower than Filtering Table, i.e. if there is a
            table hash collision between the entries of IGMP Table and Filtering Table
            inside the switch H/W address table, then Filtering Table entry overwrite
            the colliding entry of IGMP Table. See swFdbFilterTable description also."
        ::= { swIGMPPackage 3 }

    swIGMPEntry OBJECT-TYPE
        SYNTAX SwIGMPEntry
        ACCESS not-accessible
        STATUS mandatory
        DESCRIPTION
            "Information about current IGMP information which captured by this 
            device , provided that swDevIGMPCaptureState and swIGMPCtrlState of
            associated VLAN entry are all enabled."
        INDEX  { swIGMPVid , swIGMPGroupIpAddr }
        ::= { swIGMPTable 1 }

    SwIGMPEntry ::= 
        SEQUENCE {
            swIGMPVid
                INTEGER,
            swIGMPGroupIpAddr
                IpAddress,
            swIGMPMacAddr
                MacAddress,
            swIGMPPortMap
                PortList,
            swIGMPIpGroupReportCount
                INTEGER
        }

    swIGMPVid OBJECT-TYPE
        SYNTAX INTEGER
        ACCESS read-only
        STATUS mandatory
        DESCRIPTION
            "This object indicates the Vid of individual IGMP table entry. It
             shows the Vid of IGMP report information captured on network."
        ::= { swIGMPEntry 1 }

    swIGMPGroupIpAddr OBJECT-TYPE
        SYNTAX IpAddress
        ACCESS read-only
        STATUS mandatory
        DESCRIPTION
            "This object is identify group ip address which is captured from
            IGMP packet, in per-Vlan basis."
        ::= { swIGMPEntry 2 }

    swIGMPMacAddr OBJECT-TYPE
        SYNTAX MacAddress
        ACCESS read-only
        STATUS mandatory
        DESCRIPTION
            "This object is identify mac address which is corresponding
            to swIGMPGroupIpAddr, in per-Vlan basis.."
        ::= { swIGMPEntry 3 }

    swIGMPPortMap OBJECT-TYPE
        SYNTAX PortList
        ACCESS read-only
        STATUS mandatory
        DESCRIPTION
            "This object indicates which ports are belong to the same multicast 
            group, in per-Vlan basis. Each multicast group has a octect string
            to indicate with port map. The most significant bit represents the
            lowest numbered port, and the least significant bit represents the
            highest numbered port. In module 1 (base module), there are 22 100M
            twisted-pair ports (port 1..22) which is mapped to the PortMap's 
            port 1 to 22 respectively. In module 2 (slot 1 module), there are 2
            100M FX/100 TX (or a single port 100M FX) ports which is mapped to
            the PortMap's port 23,24 respectively (if the module is a single port
            100M FX, it is just mapped to port 23 and port 24 is ignored). Module
            3 (slot 2 module) is a single-port Gigabit Ethernet and it is mapped
            to the PortMap's port 25."
        ::= { swIGMPEntry 4 }

    swIGMPIpGroupReportCount OBJECT-TYPE
        SYNTAX INTEGER
        ACCESS read-only
        STATUS mandatory
        DESCRIPTION
            "This object indicate how much report packet was receive by our
             device corresponding with this entry from IGMP function enabled,
             in per-Vlan basis. ." 
        ::= { swIGMPEntry 5 }

END
