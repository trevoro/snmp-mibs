-- *****************************************************************
-- RBN-PRODUCT-MIB	RedBack Networks Product and Entity Assignments
--
-- Copyright (c) 1998-1999 RedBack Networks, Inc.
-- All rights reserved.
-- 
-- *****************************************************************

RBN-PRODUCT-MIB DEFINITIONS ::= BEGIN

IMPORTS
	MODULE-IDENTITY,
	OBJECT-IDENTITY
		FROM SNMPv2-SMI
	rbnModules,
	rbnProducts,
	rbnEntities
		FROM RBN-SMI;

rbnProductMIB MODULE-IDENTITY
	LAST-UPDATED	"9907081712Z"
	ORGANIZATION	"RedBack Networks, Inc."
	CONTACT-INFO
		"	RedBack Networks, Inc.

		Postal:	1389 Moffett Park Drive
			Sunnyvale, CA  94089-1134
			USA

		 Phone:	+1 408 548 3500
		   Fax: +1 408 548 3599

		E-mail:	mib-info@RedBackNetworks.com"
	DESCRIPTION
		"This management information module contains the
		administrative assignments which are used to
		uniquely identify physical components"
		REVISION	"9907081712Z"
		DESCRIPTION
			"Addition of rbnSMS1800"
	::= { rbnModules 1 }


-- 
-- RedBack Product Assignments
-- 

rbnSMS1000 OBJECT-IDENTITY
	STATUS  current
	DESCRIPTION
		"The definitive identifier of the RedBack Networks
		SMS 1000"
	::= { rbnProducts 1 }

rbnSMS500 OBJECT-IDENTITY
	STATUS  current
	DESCRIPTION
		"The definitive identifier of the RedBack Networks
		SMS 500"
	::= { rbnProducts 2 }

rbnSMS1800 OBJECT-IDENTITY
        STATUS  current
        DESCRIPTION
                "The definitive identifier of the RedBack Networks
                SMS 1800"
        ::= { rbnProducts 3 }



-- 
-- RedBack Entity Assignments
--
-- { rbnEntities 1 } and { rbnEntities 2 } are unassigned

rbnEntityTypeOther OBJECT-IDENTITY
      STATUS  current
      DESCRIPTION
              "The top-level category identifier for entities which
              reside in the ENTITY-MIB PhysicalClass *other*"
      ::= { rbnEntities 1 }

rbnEntityTypeUnknown OBJECT-IDENTITY
      STATUS  current
      DESCRIPTION
              "The top-level category identifier for entities which
              reside in the ENTITY-MIB PhysicalClass *unknown*"
      ::= { rbnEntities 2 }

rbnEntityTypeChassis OBJECT-IDENTITY
      STATUS  current
      DESCRIPTION
              "The top-level category identifier for entities which
              reside in the ENTITY-MIB PhysicalClass *chassis*"
      ::= { rbnEntities 3 }

rbnEntChassisSMS1000 OBJECT-IDENTITY
      STATUS  current
      DESCRIPTION
              "The definitive identifier for the RedBack Networks
              SMS 1000 chassis entity."
      ::= { rbnEntityTypeChassis 1 }

rbnEntChassisSMS500 OBJECT-IDENTITY
      STATUS  current
      DESCRIPTION
              "The definitive identifier for the RedBack Networks
              SMS 500 chassis entity."
      ::= { rbnEntityTypeChassis 2 }

rbnEntChassisSMS1800 OBJECT-IDENTITY
      STATUS  current
      DESCRIPTION
              "The definitive identifier for the RedBack Networks
              SMS 1800 chassis entity."
      ::= { rbnEntityTypeChassis 3 }

rbnEntityTypeBackplane OBJECT-IDENTITY
      STATUS  current
      DESCRIPTION
              "The top-level category identifier for entities which
              reside in the ENTITY-MIB PhysicalClass *backplane*"
      ::= { rbnEntities 4 }

rbnEntBackplaneSMS1000Data OBJECT-IDENTITY
      STATUS  current
      DESCRIPTION
              "The definitive identifier for the RedBack Networks
              SMS 1000 data backplane entity."
      ::= { rbnEntityTypeBackplane 1 }

rbnEntBackplaneSMS1000Power OBJECT-IDENTITY
      STATUS  current
      DESCRIPTION
              "The definitive identifier for the RedBack Networks
              SMS 1000 power backplane entity."
      ::= { rbnEntityTypeBackplane 2 }

rbnEntBackplaneSMS500Data OBJECT-IDENTITY
      STATUS  current
      DESCRIPTION
              "The definitive identifier for the RedBack Networks
              SMS 500 data backplane entity."
      ::= { rbnEntityTypeBackplane 3 }

rbnEntBackplaneSMS500Power OBJECT-IDENTITY
      STATUS  current
      DESCRIPTION
              "The definitive identifier for the RedBack Networks
              SMS 500 power backplane entity."
      ::= { rbnEntityTypeBackplane 4 }

rbnEntBackplaneSMS1800Data OBJECT-IDENTITY
      STATUS  current
      DESCRIPTION
              "The definitive identifier for the RedBack Networks
              SMS 1800 data backplane entity."
      ::= { rbnEntityTypeBackplane 5 }

rbnEntBackplaneSMS1800Power OBJECT-IDENTITY
      STATUS  current
      DESCRIPTION
              "The definitive identifier for the RedBack Networks
              SMS 1800 power backplane entity."
      ::= { rbnEntityTypeBackplane 6 }

rbnEntityTypeContainer OBJECT-IDENTITY
      STATUS  current
      DESCRIPTION
              "The top-level category identifier for entities which
              reside in the ENTITY-MIB PhysicalClass *container*"
      ::= { rbnEntities 5 }

rbnEntContainerSMS1000Data OBJECT-IDENTITY
      STATUS  current
      DESCRIPTION
              "The definitive identifier for the RedBack Networks
              SMS 1000 data container (slot) entity."
      ::= { rbnEntityTypeContainer 1 }

rbnEntContainerSMS1000Power OBJECT-IDENTITY
      STATUS  current
      DESCRIPTION
              "The definitive identifier for the RedBack Networks
              SMS 1000 power container (slot) entity."
      ::= { rbnEntityTypeContainer 2 }

rbnEntContainerSMS500Data OBJECT-IDENTITY
      STATUS  current
      DESCRIPTION
              "The definitive identifier for the RedBack Networks
              SMS 500 data container (slot) entity."
      ::= { rbnEntityTypeContainer 3 }

rbnEntContainerSMS500Power OBJECT-IDENTITY
      STATUS  current
      DESCRIPTION
              "The definitive identifier for the RedBack Networks
              SMS 500 power container (slot) entity."
      ::= { rbnEntityTypeContainer 4 }

rbnEntContainerSMS1800Data OBJECT-IDENTITY
      STATUS  current
      DESCRIPTION
              "The definitive identifier for the RedBack Networks
              SMS 1800 data container (slot) entity."
      ::= { rbnEntityTypeContainer 5 }

rbnEntContainerSMS1800Power OBJECT-IDENTITY
      STATUS  current
      DESCRIPTION
              "The definitive identifier for the RedBack Networks
              SMS 1800 power container (slot) entity."
      ::= { rbnEntityTypeContainer 6 }

rbnEntityTypePowerSupply OBJECT-IDENTITY
      STATUS  current
      DESCRIPTION
              "The top-level category identifier for entities which
              reside in the ENTITY-MIB PhysicalClass *powerSupply*"
      ::= { rbnEntities 6 }

rbnEntPowerSupplyUnknown OBJECT-IDENTITY
      STATUS  current
      DESCRIPTION
              "The identifier use to represent any power supply which
              cannot be definitively identified, probably due to the
              fact that its configuration EEPROM is not valid"
      ::= { rbnEntityTypePowerSupply 1 }

rbnEntPowerSupplySMS1000AC OBJECT-IDENTITY
      STATUS  current
      DESCRIPTION
              "The definitive identifier for the RedBack Networks
              SMS 1000 AC Power Supply, model PS-1K-AC"
      ::= { rbnEntityTypePowerSupply 2 }

rbnEntPowerSupplySMS1000DC OBJECT-IDENTITY
      STATUS  current
      DESCRIPTION
              "The definitive identifier for the RedBack Networks
              SMS 1000 DC Power Supply, model PS-1K-DC"
      ::= { rbnEntityTypePowerSupply 3 }

rbnEntPowerSupplySMS500AC OBJECT-IDENTITY
      STATUS  current
      DESCRIPTION
              "The definitive identifier for the RedBack Networks
              SMS 500 AC Power Supply"
      ::= { rbnEntityTypePowerSupply 4 }

rbnEntPowerSupplySMS500DC OBJECT-IDENTITY
      STATUS  current
      DESCRIPTION
              "The definitive identifier for the RedBack Networks
              SMS 500 DC Power Supply"
      ::= { rbnEntityTypePowerSupply 5 }

rbnEntPowerSupplySMS1800AC OBJECT-IDENTITY
      STATUS  current
      DESCRIPTION
              "The definitive identifier for the RedBack Networks
              SMS 1800 AC Power Supply"
      ::= { rbnEntityTypePowerSupply 6 }

rbnEntPowerSupplySMS1800DC OBJECT-IDENTITY
      STATUS  current
      DESCRIPTION
              "The definitive identifier for the RedBack Networks
              SMS 1800 DC Power Supply"
      ::= { rbnEntityTypePowerSupply 7 }


rbnEntityTypeFan OBJECT-IDENTITY
      STATUS  current
      DESCRIPTION 
              "The top-level category identifier for entities which
              reside in the ENTITY-MIB PhysicalClass *fan*"
      ::= { rbnEntities 7 }

rbnEntityTypeSensor OBJECT-IDENTITY
      STATUS  current
      DESCRIPTION
              "The top-level category identifier for entities which
              reside in the ENTITY-MIB PhysicalClass *sensor*"
      ::= { rbnEntities 8 }

rbnEntityTypeModule OBJECT-IDENTITY
      STATUS  current
      DESCRIPTION
              "The top-level category identifier for entities which
              reside in the ENTITY-MIB PhysicalClass *module*"
      ::= { rbnEntities 9 }

rbnEntModuleUnknown OBJECT-IDENTITY
      STATUS  current
      DESCRIPTION
              "The identifier use to represent any module which
              cannot be definitively identified, probably due
              to the fact that its configuration EEPROM is not
              valid"
      ::= { rbnEntityTypeModule 1 }

rbnEntModuleSMSCE1 OBJECT-IDENTITY
      STATUS  current
      DESCRIPTION
              "The definitive identifier for the RedBack Networks
              SMS Control Engine 1"
      ::= { rbnEntityTypeModule 16 }

rbnEntModuleSMSCE2 OBJECT-IDENTITY
      STATUS  current
      DESCRIPTION
              "The definitive identifier for the RedBack Networks
              SMS Control Engine 2"
      ::= { rbnEntityTypeModule 17 }

rbnEntModuleSMSCE3 OBJECT-IDENTITY
      STATUS  current
      DESCRIPTION
              "The definitive identifier for the RedBack Networks
              SMS Control Engine 3"
      ::= { rbnEntityTypeModule 18 }

rbnEntModuleSMSFE1 OBJECT-IDENTITY
      STATUS  current
      DESCRIPTION 
              "The definitive identifier for the RedBack Networks
              SMS Forwarding Engine 1"
      ::= { rbnEntityTypeModule 10 }

rbnEntModuleSMSFE2 OBJECT-IDENTITY
      STATUS  current
      DESCRIPTION 
              "The definitive identifier for the RedBack Networks
              SMS Forwarding Engine 2"
      ::= { rbnEntityTypeModule 12 }

rbnEntModuleSMSEIM OBJECT-IDENTITY
      STATUS  current
      DESCRIPTION
              "The definitive identifier for the RedBack Networks
              SMS 10/100BaseT Ethernet Interface Module"
      ::= { rbnEntityTypeModule 6 }

rbnEntModuleSMSAIMDS3 OBJECT-IDENTITY
      STATUS  current
      DESCRIPTION
              "The definitive identifier for the RedBack Networks
              SMS ATM DS3 Interface Module"
      ::= { rbnEntityTypeModule 4 }

rbnEntModuleSMSAIMOC3 OBJECT-IDENTITY
      STATUS  current
      DESCRIPTION
              "The definitive identifier for the RedBack Networks
              SMS ATM OC3 Interface Module"
      ::= { rbnEntityTypeModule 3 }

rbnEntModuleSMSPIMDS1 OBJECT-IDENTITY
      STATUS  current
      DESCRIPTION
              "The definitive identifier for the RedBack Networks
              SMS Packet DS1 Interface Module"
      ::= { rbnEntityTypeModule 14 }

rbnEntModuleSMSPIMDS3 OBJECT-IDENTITY
      STATUS  current
      DESCRIPTION
              "The definitive identifier for the RedBack Networks
              SMS Packet DS3 Interface Module"
      ::= { rbnEntityTypeModule 7 }

rbnEntModuleSMSPIMHSSI OBJECT-IDENTITY
      STATUS  current
      DESCRIPTION
              "The definitive identifier for the RedBack Networks
              SMS Packet HSSI Interface Module"
      ::= { rbnEntityTypeModule 9 }
              

      

rbnEntityTypePort OBJECT-IDENTITY
      STATUS  current
      DESCRIPTION 
              "The top-level category identifier for entities which
              reside in the ENTITY-MIB PhysicalClass *port*" 
      ::= { rbnEntities 10 }


rbnEntPortUnknown OBJECT-IDENTITY
      STATUS  current
      DESCRIPTION
              "The identifier use to represent any module which
              cannot be definitively identified, probably due
              to the fact that its configuration EEPROM is not
              valid"
      ::= { rbnEntityTypePort 1 }

rbnEntPortSMSCE1MGMT OBJECT-IDENTITY
      STATUS  current
      DESCRIPTION
              "The definitive identifier for the RedBack Networks
              SMS Control Engine 1, Local Management Port"
      ::= { rbnEntityTypePort 16 }

rbnEntPortSMSCE2MGMT OBJECT-IDENTITY
      STATUS  current
      DESCRIPTION
              "The definitive identifier for the RedBack Networks
              SMS Control Engine 2, Local Management Port"
      ::= { rbnEntityTypePort 17 }

rbnEntPortSMSCE3MGMT OBJECT-IDENTITY
      STATUS  current
      DESCRIPTION
              "The definitive identifier for the RedBack Networks
              SMS Control Engine 3, Local Management Port"
      ::= { rbnEntityTypePort 18 }

rbnEntPortSMSEIM OBJECT-IDENTITY
      STATUS  current
      DESCRIPTION
              "The definitive identifier for the RedBack Networks
              SMS 10/100BaseT Ethernet Interface Port"
      ::= { rbnEntityTypePort 6 }

rbnEntPortSMSAIMDS3 OBJECT-IDENTITY
      STATUS  current
      DESCRIPTION
              "The definitive identifier for the RedBack Networks
              SMS ATM DS3 Interface Port"
      ::= { rbnEntityTypePort 4 }

rbnEntPortSMSAIMOC3 OBJECT-IDENTITY
      STATUS  current
      DESCRIPTION
              "The definitive identifier for the RedBack Networks
              SMS ATM OC3 Interface Port"
      ::= { rbnEntityTypePort 3 }

rbnEntPortSMSPIMDS1 OBJECT-IDENTITY
      STATUS  current
      DESCRIPTION
              "The definitive identifier for the RedBack Networks
              SMS Packet DS1 Interface Port"
      ::= { rbnEntityTypePort 14 }

rbnEntPortSMSPIMDS3 OBJECT-IDENTITY
      STATUS  current
      DESCRIPTION
              "The definitive identifier for the RedBack Networks
              SMS Packet DS3 Interface Port"
      ::= { rbnEntityTypePort 7 }

rbnEntPortSMSPIMHSSI OBJECT-IDENTITY
      STATUS  current
      DESCRIPTION
              "The definitive identifier for the RedBack Networks
              SMS Packet HSSI Interface Port"
      ::= { rbnEntityTypePort 9 }

END
