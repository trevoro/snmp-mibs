--
-- ACC-NC-ALARM-MIB.my
-- MIB generated by MG-SOFT Visual MIB Builder Version 3.0 Build 285
-- Tuesday, August 06, 2002 at 11:20:44
--

	ACC-NC-ALARM-MIB DEFINITIONS ::= BEGIN
 
		IMPORTS
			accNetController			
				FROM ANDOVER-CONTROLS-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI			
			DisplayString, DateAndTime, TruthValue, StorageType, RowStatus			
				FROM SNMPv2-TC;
	
	
		-- 1.3.6.1.4.1.10829.5.2.1
		accAlarmMIB MODULE-IDENTITY 
			LAST-UPDATED "200210300946Z"		-- October 30, 2002 at 09:46 GMT
			ORGANIZATION 
				"Andover Controls Corporation"
			CONTACT-INFO 
				"Technical Support
				Andover Controls Corporation
				300 Brickstone Square
				Andover, MA 01810
				USA
				978-470-0555"
			DESCRIPTION 
				"This MIB module defines MIB objects and notifications which are
				mapped from Andover Controls Continuum Alarms"
			REVISION "200210300946Z"		-- October 30, 2002 at 09:46 GMT
			DESCRIPTION 
				"Revision 1.0"
			::= { accNetController 1 }

		
	
	
--
-- Node definitions
--
	
		-- 1.3.6.1.4.1.10829.5.2.1.1
		alarmListMax OBJECT-TYPE
			SYNTAX Integer32
			MAX-ACCESS read-only
			STATUS current
			DESCRIPTION
				"Maximum number of elements in the Alarm List table
				not including internal alarms, such as Controller Reset,
				Alarm Table Overflow."
			::= { accAlarmMIB 1 }

		
		-- 1.3.6.1.4.1.10829.5.2.1.2
		alarmList OBJECT IDENTIFIER::= { accAlarmMIB 2 }

		
		-- 1.3.6.1.4.1.10829.5.2.1.2.2
		alarmTable OBJECT-TYPE
			SYNTAX SEQUENCE OF AlarmEntry
			MAX-ACCESS not-accessible
			STATUS current
			DESCRIPTION
				"Description."
			::= { alarmList 2 }

		
		-- 1.3.6.1.4.1.10829.5.2.1.2.2.1
		alarmEntry OBJECT-TYPE
			SYNTAX AlarmEntry
			MAX-ACCESS not-accessible
			STATUS current
			DESCRIPTION
				"Description."
			INDEX { alarmIENAD, alarmLink }
			::= { alarmTable 1 }

		
		AlarmEntry ::=
			SEQUENCE { 
				alarmControllerName
					DisplayString,
				alarmInfinetControllerName
					DisplayString,
				alarmPointName
					DisplayString,
				alarmPointDescription
					DisplayString,
				alarmAlarmName
					DisplayString,
				alarmState
					INTEGER,
				alarmAlmTime
					DateAndTime,
			    alarmAlmValue
					DisplayString,
				alarmRtnTime
					DateAndTime,
				alarmRtnValue
					DisplayString,
				alarmIENAD
					OCTET STRING,
				alarmLink
					INTEGER
			 }

		-- 1.3.6.1.4.1.10829.5.2.1.2.2.1.1
		alarmControllerName OBJECT-TYPE
			SYNTAX DisplayString
			MAX-ACCESS read-only
			STATUS current
			DESCRIPTION
				"NetController name upon which this table exists."
			::= { alarmEntry 1 }

		
		-- 1.3.6.1.4.1.10829.5.2.1.2.2.1.2
		alarmInfinetControllerName OBJECT-TYPE
			SYNTAX DisplayString
			MAX-ACCESS read-only
			STATUS current
			DESCRIPTION
				"Infinet controller name upon which the point in alarm resides. This could
				also be null, if the point is on the NetController itself."
			::= { alarmEntry 2 }

		
		-- 1.3.6.1.4.1.10829.5.2.1.2.2.1.3
		alarmPointName OBJECT-TYPE
			SYNTAX DisplayString
			MAX-ACCESS read-only
			STATUS current
			DESCRIPTION
				"Continuum point name."
			::= { alarmEntry 3 }

		
		-- 1.3.6.1.4.1.10829.5.2.1.2.2.1.4
		alarmPointDescription OBJECT-TYPE
			SYNTAX DisplayString
			MAX-ACCESS read-only
			STATUS current
			DESCRIPTION
				"Continuum point description."
			::= { alarmEntry 4 }

		
		-- 1.3.6.1.4.1.10829.5.2.1.2.2.1.5
		alarmAlarmName OBJECT-TYPE
			SYNTAX DisplayString
			MAX-ACCESS read-only
			STATUS current
			DESCRIPTION
				"Continuum alarm name."
			::= { alarmEntry 5 }

		
		-- 1.3.6.1.4.1.10829.5.2.1.2.2.1.6
		alarmState OBJECT-TYPE
			SYNTAX INTEGER
				{
				null(0),
				rtn(1),
				alm(2)
				}
			MAX-ACCESS read-only
			STATUS current
			DESCRIPTION
				"This is the state of the corresponding Continuum alarm as was learned
				from the last alarm transition."
			::= { alarmEntry 6 }
		
		-- 1.3.6.1.4.1.10829.5.2.1.2.2.1.7
		alarmAlmTime OBJECT-TYPE
			SYNTAX DateAndTime
			MAX-ACCESS read-only
			STATUS current
			DESCRIPTION
				"Time stamp when point entered alarm (ALM) state. This could also
				be null, if no transition to ALM occured."
			::= { alarmEntry 7 }
		
		-- 1.3.6.1.4.1.10829.5.2.1.2.2.1.8
		alarmAlmValue OBJECT-TYPE
		  	SYNTAX DisplayString
			MAX-ACCESS read-only
			STATUS current
			DESCRIPTION
				"Value when point went into alarm (ALM) state. This could also
				be null, if no transition to ALM occured."
			::= { alarmEntry 8 }
		
		-- 1.3.6.1.4.1.10829.5.2.1.2.2.1.9
		alarmRtnTime OBJECT-TYPE
			SYNTAX DateAndTime
			MAX-ACCESS read-only
			STATUS current
			DESCRIPTION
				"Time stamp when point returned to normal (RTN) state. This could also
				be null, if no transition to RTN occured."
			::= { alarmEntry 9 }
		
		-- 1.3.6.1.4.1.10829.5.2.1.2.2.1.10
 	    alarmRtnValue OBJECT-TYPE
			SYNTAX DisplayString
			MAX-ACCESS read-only
			STATUS current
			DESCRIPTION
				"Value when point state returned to normal (RTN). This could also
				be null, if no transition to RTN occured."
			::= { alarmEntry 10 }
		
		-- 1.3.6.1.4.1.10829.5.2.1.2.2.1.12
		alarmIENAD OBJECT-TYPE
			SYNTAX OCTET STRING (SIZE (4))
			MAX-ACCESS read-only
			STATUS current
			DESCRIPTION
				"IENAD that identifies point in IE table; 0 for internal alarm."
			::= { alarmEntry 12 }

		
		-- 1.3.6.1.4.1.10829.5.2.1.2.2.1.13
		alarmLink OBJECT-TYPE
			SYNTAX INTEGER (1..8)
			MAX-ACCESS read-only
			STATUS current
			DESCRIPTION
				"Number identifying which Continuum alarm link 1-8; 
				1 for Controller Reset alarm; 2 for Alarm Table Overflow"
			::= { alarmEntry 13 }

		
		-- 1.3.6.1.4.1.10829.5.2.1.3
		alarmTransitionEvent NOTIFICATION-TYPE
			OBJECTS { alarmControllerName, alarmInfinetControllerName, alarmPointName, alarmPointDescription, alarmAlarmName, 
				alarmState, alarmAlmTime, alarmAlmValue, alarmRtnTime, alarmRtnValue }
			STATUS current
			DESCRIPTION 
				"This is the row of the alarm table that is sent as a 
				notification to an SNMP manager."
			::= { accAlarmMIB 3 }
		
-- Agents must support the following MIBs, 
-- groups, and events.
		-- 1.3.6.1.4.1.10829.5.2.1.4
		alarmConformance OBJECT IDENTIFIER::= { accAlarmMIB 4 }

		
		-- 1.3.6.1.4.1.10829.5.2.1.4.1
		alarmCompliances OBJECT IDENTIFIER::= { alarmConformance 1 }

		
		-- 1.3.6.1.4.1.10829.5.2.1.4.1.1
		alarmBasicCompliance MODULE-COMPLIANCE
			STATUS current
			DESCRIPTION 
				"Module Compliance for agent. Agent must support these 
				groups."
			MODULE -- this module
				MANDATORY-GROUPS { alarmGroup, alarmEvents }
			::= { alarmCompliances 1 }

		
		-- 1.3.6.1.4.1.10829.5.2.1.4.2
		alarmGroups OBJECT IDENTIFIER::= { alarmConformance 2 }

		
		-- 1.3.6.1.4.1.10829.5.2.1.4.2.1
		alarmGroup OBJECT-GROUP
			OBJECTS { alarmListMax, alarmControllerName, alarmInfinetControllerName, alarmPointName, 
				alarmPointDescription, alarmAlarmName, alarmState, alarmAlmTime, alarmAlmValue, 
				alarmRtnTime, alarmRtnValue, alarmIENAD, alarmLink }
			STATUS current
			DESCRIPTION 
				"Objects the agent must support."
			::= { alarmGroups 1 }
		
		-- 1.3.6.1.4.1.10829.5.2.1.4.2.2
		alarmEvents NOTIFICATION-GROUP
			NOTIFICATIONS { alarmTransitionEvent }
			STATUS current
			DESCRIPTION 
				"Events the agent must support."
			::= { alarmGroups 2 }

		
	
	END

--
-- ACC-NC-ALARM-MIB.my
--
