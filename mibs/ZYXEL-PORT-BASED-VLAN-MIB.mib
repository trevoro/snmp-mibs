-- ZyXEL Communications Corporation
-- Private Enterprise MIB definition 
  
-- This file describes the ZyXEL Communications Corporation Enterprise MIB.
-- It contains ZyXEL products OIDs, and common managed objects.

-- $Log: ZYXEL-PORT-BASED-VLAN-MIB.mib $ 
-- Revision 1.3  2012/09/19 07:44:00  Kevin 
-- if it's leaf node, revise the vender name from zyxel to zy 
-- Revision 1.2  2012/07/05 06:24:15  Kevin 
-- 1. upgrade from SNMP to SNMPv2  
-- 2. clean warning 
-- Revision 1.1  2012/05/30 07:50:24  Kevin 
-- Initial revision 

ZYXEL-PORT-BASED-VLAN-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelPortBasedVlan MODULE-IDENTITY
		LAST-UPDATED	"201207010000Z"    
		ORGANIZATION "Enterprise Solution ZyXEL"     
		CONTACT-INFO
			""	   
		DESCRIPTION
			"The subtree for port-based VLAN"
		::= { esMgmt 63 }
		
	zyxelPortBasedVlanSetup OBJECT IDENTIFIER ::= { zyxelPortBasedVlan 1 }


                                                            
-- 		zyxelPortBasedVlanTable 

        zyxelPortBasedVlanTable  OBJECT-TYPE
        SYNTAX	SEQUENCE OF ZyxelPortBasedVlanEntry 
        MAX-ACCESS  not-accessible
        STATUS  current
        DESCRIPTION
                 	"The table contains port-based VLAN configuration. "
        ::= { zyxelPortBasedVlanSetup 1 }
        
		zyxelPortBasedVlanEntry  OBJECT-TYPE
        SYNTAX	ZyxelPortBasedVlanEntry 
        MAX-ACCESS	not-accessible
        STATUS	current
        DESCRIPTION    	"An entry contains port-based VLAN configuration. "
        INDEX          	{ dot1dBasePort }
        ::= { zyxelPortBasedVlanTable 1 }

        ZyxelPortBasedVlanEntry ::=
           SEQUENCE {
        	zyPortBasedVlanPorts	OCTET STRING
           }

        zyPortBasedVlanPorts OBJECT-TYPE
        SYNTAX  PortList
        MAX-ACCESS  read-write
        STATUS  current
        DESCRIPTION
                      	"Set port members for each port. This allows packets to be forwarded to these port members. "
        ::= { zyxelPortBasedVlanEntry 1 }
END
