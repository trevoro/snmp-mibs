Wellfleet-PROTOPRI-MIB DEFINITIONS ::= BEGIN

-- Created by mdl2asn version 3.1
-- Creation date: Wed Aug 30 16:46:40 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfProtocolPriorityGroup
        FROM Wellfleet-COMMON-MIB;


    wfProtoPriQTable OBJECT-TYPE
        SYNTAX	SEQUENCE OF WfProtoPriQEntry
        ACCESS	not-accessible
        STATUS	mandatory
        DESCRIPTION
                "Protocol Priority Queue Mib"
        ::= { wfProtocolPriorityGroup 1 }

    wfProtoPriQEntry OBJECT-TYPE
        SYNTAX	WfProtoPriQEntry
        ACCESS	not-accessible
        STATUS	mandatory
        DESCRIPTION
                "entry for each queue the Protocol Priority supports"
        INDEX	{ wfProtoPriPeerAddr,
    		  wfProtoPriClientId,
    		  wfProtoPriQueueNumber }
        ::= { wfProtoPriQTable 1 }

    WfProtoPriQEntry ::= SEQUENCE {
    	    wfProtoPriQueueDelete
    		INTEGER,
    	    wfProtoPriClientId
    		INTEGER,
    	    wfProtoPriQueueNumber
    		INTEGER,
    	    wfProtoPriQueueBandwidthPercent
    		INTEGER,
    	    wfProtoPriQueueHighWaterPkts
    		Gauge,
    	    wfProtoPriQueueTxPkts
    		Counter,
    	    wfProtoPriQueueTotalTxOctets
    		Counter,
    	    wfProtoPriQueueLargePkts
    		Counter,
    	    wfProtoPriQueueClippedPkts
    		Counter,
    	    wfProtoPriPeerAddr
    		IpAddress,
    	    wfProtoPriQueueHighWaterBytes
    		Gauge,
    	    wfProtoPriCCPkts
    		Counter,
    	    wfProtoPriCCOctets
    		Counter,
    	    wfProtoPriCCHighWaterPkts
    		Gauge,
    	    wfProtoPriCCHighWaterBytes
    		Gauge
        }

    wfProtoPriQueueDelete OBJECT-TYPE
        SYNTAX	INTEGER {
    		    created(1),
    		    deleted(2)
    		}
        ACCESS	read-write
        STATUS	mandatory
        DESCRIPTION
                "Create/Delete this Mib entry"
        DEFVAL	{ created }
        ::= { wfProtoPriQEntry 1 }

    wfProtoPriClientId OBJECT-TYPE
        SYNTAX	INTEGER
        ACCESS	read-only
        STATUS	mandatory
        DESCRIPTION
                "Client's number provided by the Client to identify the user"
        ::= { wfProtoPriQEntry 2 }

    wfProtoPriQueueNumber OBJECT-TYPE
        SYNTAX	INTEGER
        ACCESS	read-only
        STATUS	mandatory
        DESCRIPTION
                "Queue number"
        ::= { wfProtoPriQEntry 3 }

    wfProtoPriQueueBandwidthPercent OBJECT-TYPE
        SYNTAX	INTEGER {
    		    default(10)
    		}
        ACCESS	read-write
        STATUS	mandatory
        DESCRIPTION
                "Bandwidth percent alloted for this queue; Sum of
                the bandwidth for all the queues for this peer
                should equal to 100%"
        DEFVAL	{ default }
        ::= { wfProtoPriQEntry 4 }

    wfProtoPriQueueHighWaterPkts OBJECT-TYPE
        SYNTAX	Gauge
        ACCESS	read-only
        STATUS	mandatory
        DESCRIPTION
                "Max number of packets held by this Queue since
                the Queue creation or reset"
        ::= { wfProtoPriQEntry 5 }

    wfProtoPriQueueTxPkts OBJECT-TYPE
        SYNTAX	Counter
        ACCESS	read-only
        STATUS	mandatory
        DESCRIPTION
                "Max number number of packets sent out of this
                Queue(statistics) since creation or
                last reset"
        ::= { wfProtoPriQEntry 6 }

    wfProtoPriQueueTotalTxOctets OBJECT-TYPE
        SYNTAX	Counter
        ACCESS	read-only
        STATUS	mandatory
        DESCRIPTION
                "Max number of bytes sent out of this
                Queue(statistics) since creation or
                last reset"
        ::= { wfProtoPriQEntry 7 }

    wfProtoPriQueueLargePkts OBJECT-TYPE
        SYNTAX	Counter
        ACCESS	read-only
        STATUS	mandatory
        DESCRIPTION
                "Number of packets that exceeded the latency by itself
                but still got sent out; N/A for DLS"
        ::= { wfProtoPriQEntry 8 }

    wfProtoPriQueueClippedPkts OBJECT-TYPE
        SYNTAX	Counter
        ACCESS	read-only
        STATUS	mandatory
        DESCRIPTION
                "Number of packets clipped when Congestion control
                is disabled"
        ::= { wfProtoPriQEntry 9 }

    wfProtoPriPeerAddr OBJECT-TYPE
        SYNTAX	IpAddress
        ACCESS	read-only
        STATUS	mandatory
        DESCRIPTION
                "IP addr for DLS, part of the instance id"
        ::= { wfProtoPriQEntry 10 }

    wfProtoPriQueueHighWaterBytes OBJECT-TYPE
        SYNTAX	Gauge
        ACCESS	read-only
        STATUS	mandatory
        DESCRIPTION
                "Max number of bytes held by this Queue since
                the Queue creation or reset"
        ::= { wfProtoPriQEntry 11 }

    wfProtoPriCCPkts OBJECT-TYPE
        SYNTAX	Counter
        ACCESS	read-only
        STATUS	mandatory
        DESCRIPTION
                "Max number of packets sent by Congestion Control
                Queue in memory(statistics) since creation or
                last reset"
        ::= { wfProtoPriQEntry 12 }

    wfProtoPriCCOctets OBJECT-TYPE
        SYNTAX	Counter
        ACCESS	read-only
        STATUS	mandatory
        DESCRIPTION
                "Max number of bytes sent by Congestion Control
                Queue in memory(statistics) since creation or
                last reset"
        ::= { wfProtoPriQEntry 13 }

    wfProtoPriCCHighWaterPkts OBJECT-TYPE
        SYNTAX	Gauge
        ACCESS	read-only
        STATUS	mandatory
        DESCRIPTION
                "Max number of packets held by Congestion Control
                Queue in memory(statistics) since creation or
                last reset"
        ::= { wfProtoPriQEntry 14 }

    wfProtoPriCCHighWaterBytes OBJECT-TYPE
        SYNTAX	Gauge
        ACCESS	read-only
        STATUS	mandatory
        DESCRIPTION
                "Max number of bytes held by Congestion Control
                Queue in memory(statistics) since creation or
                last reset"
        ::= { wfProtoPriQEntry 15 }

    wfProtoPriFilterTable OBJECT-TYPE
        SYNTAX	SEQUENCE OF WfProtoPriFilterEntry
        ACCESS	not-accessible
        STATUS	mandatory
        DESCRIPTION
                "Protocol Prioritiy Filter Definitions"
        ::= { wfProtocolPriorityGroup 2 }

    wfProtoPriFilterEntry OBJECT-TYPE
        SYNTAX	WfProtoPriFilterEntry
        ACCESS	not-accessible
        STATUS	mandatory
        DESCRIPTION
                "Filter table entry for Protocol Priority"
        INDEX	{ wfProtoPriFilterPeerAddr,
    		  wfProtoPriFilterClientId,
    		  wfProtoPriFilterRuleNumber,
    		  wfProtoPriFilterFragment }
        ::= { wfProtoPriFilterTable 1 }

    WfProtoPriFilterEntry ::= SEQUENCE {
    	    wfProtoPriFilterCreate
    		INTEGER,
    	    wfProtoPriFilterEnable
    		INTEGER,
    	    wfProtoPriFilterState
    		INTEGER,
    	    wfProtoPriFilterCounter
    		Counter,
    	    wfProtoPriFilterDefinition
    		OCTET STRING,
    	    wfProtoPriFilterReserved
    		INTEGER,
    	    wfProtoPriFilterPeerAddr
    		IpAddress,
    	    wfProtoPriFilterClientId
    		INTEGER,
    	    wfProtoPriFilterRuleNumber
    		INTEGER,
    	    wfProtoPriFilterFragment
    		INTEGER,
    	    wfProtoPriFilterName
    		DisplayString
        }

    wfProtoPriFilterCreate OBJECT-TYPE
        SYNTAX	INTEGER {
    		    created(1),
    		    deleted(2)
    		}
        ACCESS	read-write
        STATUS	mandatory
        DESCRIPTION
                "create/delete the filter table"
        DEFVAL	{ created }
        ::= { wfProtoPriFilterEntry 1 }

    wfProtoPriFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule. "
        DEFVAL	{ enabled }
        ::= { wfProtoPriFilterEntry 2 }

    wfProtoPriFilterState OBJECT-TYPE
        SYNTAX	INTEGER {
    		    active(1),
    		    error(2),
    		    inactive(3)
    		}
        ACCESS	read-only
        STATUS	mandatory
        DESCRIPTION
                "Defines the current State of the traffic filter:
                inactive - the rule is not in use.
                active - the rule is being used.
                error - the application detected an error in the rule. "
        DEFVAL	{ inactive }
        ::= { wfProtoPriFilterEntry 3 }

    wfProtoPriFilterCounter OBJECT-TYPE
        SYNTAX	Counter
        ACCESS	read-only
        STATUS	mandatory
        DESCRIPTION
                "counter to keep track how many times this rule got hit"
        ::= { wfProtoPriFilterEntry 4 }

    wfProtoPriFilterDefinition OBJECT-TYPE
        SYNTAX	OCTET STRING
        ACCESS	read-write
        STATUS	mandatory
        DESCRIPTION
                "octect string defining the filter rule"
        ::= { wfProtoPriFilterEntry 5 }

    wfProtoPriFilterReserved OBJECT-TYPE
        SYNTAX	INTEGER
        ACCESS	read-only
        STATUS	mandatory
        DESCRIPTION
                "reserved"
        ::= { wfProtoPriFilterEntry 6 }

    wfProtoPriFilterPeerAddr OBJECT-TYPE
        SYNTAX	IpAddress
        ACCESS	read-only
        STATUS	mandatory
        DESCRIPTION
                "for DLS part of instance id"
        ::= { wfProtoPriFilterEntry 7 }

    wfProtoPriFilterClientId OBJECT-TYPE
        SYNTAX	INTEGER
        ACCESS	read-only
        STATUS	mandatory
        DESCRIPTION
                "unique id for each Client provided by the Client"
        ::= { wfProtoPriFilterEntry 8 }

    wfProtoPriFilterRuleNumber OBJECT-TYPE
        SYNTAX	INTEGER
        ACCESS	read-only
        STATUS	mandatory
        DESCRIPTION
                "rule number"
        ::= { wfProtoPriFilterEntry 9 }

    wfProtoPriFilterFragment OBJECT-TYPE
        SYNTAX	INTEGER
        ACCESS	read-only
        STATUS	mandatory
        DESCRIPTION
                "fragment number"
        ::= { wfProtoPriFilterEntry 10 }

    wfProtoPriFilterName OBJECT-TYPE
        SYNTAX	DisplayString
        ACCESS	read-write
        STATUS	mandatory
        DESCRIPTION
                "name of this rule, provided by the user"
        ::= { wfProtoPriFilterEntry 11 }

    END  -- Wellfleet-PROTOPRI-MIB
