Wellfleet-HWMO-MIB DEFINITIONS ::= BEGIN

-- Created by mdl2asn version 3.1
-- Creation date: Wed Aug 30 16:42:35 EDT 1995


    IMPORTS

      OBJECT-TYPE
        FROM RFC-1212
      wfHardwareConfig
        FROM Wellfleet-COMMON-MIB;


    wfMod		OBJECT IDENTIFIER ::= { wfHardwareConfig 3 }

    wfModState OBJECT-TYPE
        SYNTAX	INTEGER {
    		    init(1)
    		}
        ACCESS	not-accessible
        STATUS	mandatory
        DESCRIPTION
                "State of this record"
        ::= { wfMod 1 }

    wfModSlot OBJECT-TYPE
        SYNTAX	INTEGER
        ACCESS	not-accessible
        STATUS	mandatory
        DESCRIPTION
                "Instance of this record"
        ::= { wfMod 2 }

    wfModIdOpt OBJECT-TYPE
        SYNTAX	INTEGER
        ACCESS	not-accessible
        STATUS	mandatory
        DESCRIPTION
                "actual module ID and Option"
        ::= { wfMod 3 }

    wfModRev OBJECT-TYPE
        SYNTAX	INTEGER
        ACCESS	not-accessible
        STATUS	mandatory
        DESCRIPTION
                "actual module Revision"
        ::= { wfMod 4 }

    wfModProm OBJECT-TYPE
        SYNTAX	INTEGER
        ACCESS	not-accessible
        STATUS	mandatory
        DESCRIPTION
                "module PROM"
        ::= { wfMod 5 }

    wfModMidr OBJECT-TYPE
        SYNTAX	INTEGER
        ACCESS	not-accessible
        STATUS	mandatory
        DESCRIPTION
                "module ID register"
        ::= { wfMod 6 }

    wfModMled OBJECT-TYPE
        SYNTAX	INTEGER
        ACCESS	not-accessible
        STATUS	mandatory
        DESCRIPTION
                "module LED register"
        ::= { wfMod 7 }

    wfModMisr OBJECT-TYPE
        SYNTAX	INTEGER
        ACCESS	not-accessible
        STATUS	mandatory
        DESCRIPTION
                "module MISR register"
        ::= { wfMod 8 }

    wfModSnprom OBJECT-TYPE
        SYNTAX	INTEGER
        ACCESS	not-accessible
        STATUS	mandatory
        DESCRIPTION
                "module SNPROM"
        ::= { wfMod 9 }

    wfModMadr1 OBJECT-TYPE
        SYNTAX	OCTET STRING
        ACCESS	not-accessible
        STATUS	mandatory
        DESCRIPTION
                "SNPROM MAC address connector 1"
        ::= { wfMod 10 }

    wfModMadr2 OBJECT-TYPE
        SYNTAX	OCTET STRING
        ACCESS	not-accessible
        STATUS	mandatory
        DESCRIPTION
                "SNPROM MAC address connector 2"
        ::= { wfMod 11 }

    wfModMadr3 OBJECT-TYPE
        SYNTAX	OCTET STRING
        ACCESS	not-accessible
        STATUS	mandatory
        DESCRIPTION
                "SNPROM MAC address connector 3"
        ::= { wfMod 12 }

    wfModMadr4 OBJECT-TYPE
        SYNTAX	OCTET STRING
        ACCESS	not-accessible
        STATUS	mandatory
        DESCRIPTION
                "SNPROM MAC address connector 4"
        ::= { wfMod 13 }

    wfModLance1 OBJECT-TYPE
        SYNTAX	INTEGER
        ACCESS	not-accessible
        STATUS	mandatory
        DESCRIPTION
                "LANCE line 1"
        ::= { wfMod 14 }

    wfModLance2 OBJECT-TYPE
        SYNTAX	INTEGER
        ACCESS	not-accessible
        STATUS	mandatory
        DESCRIPTION
                "LANCE line 2"
        ::= { wfMod 15 }

    wfModMk50251 OBJECT-TYPE
        SYNTAX	INTEGER
        ACCESS	not-accessible
        STATUS	mandatory
        DESCRIPTION
                "MK5025 line 1"
        ::= { wfMod 16 }

    wfModMk50252 OBJECT-TYPE
        SYNTAX	INTEGER
        ACCESS	not-accessible
        STATUS	mandatory
        DESCRIPTION
                "MK5025 line 2"
        ::= { wfMod 17 }

    wfModMk50253 OBJECT-TYPE
        SYNTAX	INTEGER
        ACCESS	not-accessible
        STATUS	mandatory
        DESCRIPTION
                "MK5025 line 3"
        ::= { wfMod 18 }

    wfModMk50254 OBJECT-TYPE
        SYNTAX	INTEGER
        ACCESS	not-accessible
        STATUS	mandatory
        DESCRIPTION
                "MK5025 line 4"
        ::= { wfMod 19 }

    wfModSicr OBJECT-TYPE
        SYNTAX	INTEGER
        ACCESS	not-accessible
        STATUS	mandatory
        DESCRIPTION
                "SYNC interface control register"
        ::= { wfMod 20 }

    wfModSbrr OBJECT-TYPE
        SYNTAX	INTEGER
        ACCESS	not-accessible
        STATUS	mandatory
        DESCRIPTION
                "SYNC baudrate register"
        ::= { wfMod 21 }

    wfMod8530 OBJECT-TYPE
        SYNTAX	INTEGER
        ACCESS	not-accessible
        STATUS	mandatory
        DESCRIPTION
                "8530 DUART"
        ::= { wfMod 22 }

    wfModCar OBJECT-TYPE
        SYNTAX	INTEGER
        ACCESS	not-accessible
        STATUS	mandatory
        DESCRIPTION
                "CAM assembly register"
        ::= { wfMod 23 }

    wfModDefaA OBJECT-TYPE
        SYNTAX	INTEGER
        ACCESS	not-accessible
        STATUS	mandatory
        DESCRIPTION
                "DEFA A chip"
        ::= { wfMod 24 }

    wfModCamALock OBJECT-TYPE
        SYNTAX	INTEGER
        ACCESS	not-accessible
        STATUS	mandatory
        DESCRIPTION
                "CAM A lock"
        ::= { wfMod 25 }

    wfModCamAUnlock OBJECT-TYPE
        SYNTAX	INTEGER
        ACCESS	not-accessible
        STATUS	mandatory
        DESCRIPTION
                "CAM A unlock"
        ::= { wfMod 26 }

    wfModDefaB OBJECT-TYPE
        SYNTAX	INTEGER
        ACCESS	not-accessible
        STATUS	mandatory
        DESCRIPTION
                "DEFA B chip"
        ::= { wfMod 27 }

    wfModCamBLock OBJECT-TYPE
        SYNTAX	INTEGER
        ACCESS	not-accessible
        STATUS	mandatory
        DESCRIPTION
                "CAM B lock"
        ::= { wfMod 28 }

    wfModCamBUnlock OBJECT-TYPE
        SYNTAX	INTEGER
        ACCESS	not-accessible
        STATUS	mandatory
        DESCRIPTION
                "CAM B unlock"
        ::= { wfMod 29 }

    wfModIlacc1 OBJECT-TYPE
        SYNTAX	INTEGER
        ACCESS	not-accessible
        STATUS	mandatory
        DESCRIPTION
                "ILACC line 1"
        ::= { wfMod 30 }

    wfModIlacc2 OBJECT-TYPE
        SYNTAX	INTEGER
        ACCESS	not-accessible
        STATUS	mandatory
        DESCRIPTION
                "ILACC line 2"
        ::= { wfMod 31 }

    wfModIlacc3 OBJECT-TYPE
        SYNTAX	INTEGER
        ACCESS	not-accessible
        STATUS	mandatory
        DESCRIPTION
                "ILACC line 3"
        ::= { wfMod 32 }

    wfModIlacc4 OBJECT-TYPE
        SYNTAX	INTEGER
        ACCESS	not-accessible
        STATUS	mandatory
        DESCRIPTION
                "ILACC line 4"
        ::= { wfMod 33 }

    wfModTms3801 OBJECT-TYPE
        SYNTAX	INTEGER
        ACCESS	not-accessible
        STATUS	mandatory
        DESCRIPTION
                "TOKEN ring chip line 1"
        ::= { wfMod 34 }

    wfModTms3802 OBJECT-TYPE
        SYNTAX	INTEGER
        ACCESS	not-accessible
        STATUS	mandatory
        DESCRIPTION
                "TOKEN ring chip line 2"
        ::= { wfMod 35 }

    wfModTocr OBJECT-TYPE
        SYNTAX	INTEGER
        ACCESS	not-accessible
        STATUS	mandatory
        DESCRIPTION
                "TOKEN control register"
        ::= { wfMod 36 }

    wfModTsra OBJECT-TYPE
        SYNTAX	INTEGER
        ACCESS	not-accessible
        STATUS	mandatory
        DESCRIPTION
                "TOKEN source route accelerator"
        ::= { wfMod 37 }

    wfModMuxram1 OBJECT-TYPE
        SYNTAX	INTEGER
        ACCESS	not-accessible
        STATUS	mandatory
        DESCRIPTION
                "T1 mux RAM active"
        ::= { wfMod 38 }

    wfModMuxram2 OBJECT-TYPE
        SYNTAX	INTEGER
        ACCESS	not-accessible
        STATUS	mandatory
        DESCRIPTION
                "T1 mux RAM inactive"
        ::= { wfMod 39 }

    wfModTicr OBJECT-TYPE
        SYNTAX	INTEGER
        ACCESS	not-accessible
        STATUS	mandatory
        DESCRIPTION
                "T1 interface control register"
        ::= { wfMod 40 }

    wfModFramer1 OBJECT-TYPE
        SYNTAX	INTEGER
        ACCESS	not-accessible
        STATUS	mandatory
        DESCRIPTION
                "T1 framer line 1"
        ::= { wfMod 41 }

    wfModFramer2 OBJECT-TYPE
        SYNTAX	INTEGER
        ACCESS	not-accessible
        STATUS	mandatory
        DESCRIPTION
                "T1 framer line 2"
        ::= { wfMod 42 }

    wfModFsi1 OBJECT-TYPE
        SYNTAX	INTEGER
        ACCESS	not-accessible
        STATUS	mandatory
        DESCRIPTION
                "FDDI FSI line 1"
        ::= { wfMod 43 }

    wfModMac1 OBJECT-TYPE
        SYNTAX	INTEGER
        ACCESS	not-accessible
        STATUS	mandatory
        DESCRIPTION
                "FDDI MAC line 1"
        ::= { wfMod 44 }

    wfModElmA1 OBJECT-TYPE
        SYNTAX	INTEGER
        ACCESS	not-accessible
        STATUS	mandatory
        DESCRIPTION
                "FDDI ELM A line 1"
        ::= { wfMod 45 }

    wfModElmB1 OBJECT-TYPE
        SYNTAX	INTEGER
        ACCESS	not-accessible
        STATUS	mandatory
        DESCRIPTION
                "FDDI ELM B line 1"
        ::= { wfMod 46 }

    wfModMcr1 OBJECT-TYPE
        SYNTAX	INTEGER
        ACCESS	not-accessible
        STATUS	mandatory
        DESCRIPTION
                "FDDI Module control register line 1"
        ::= { wfMod 47 }

    wfModHssiFsi1 OBJECT-TYPE
        SYNTAX	INTEGER
        ACCESS	not-accessible
        STATUS	mandatory
        DESCRIPTION
                "HSSI FSI line 1"
        ::= { wfMod 48 }

    wfModHssiFsi2 OBJECT-TYPE
        SYNTAX	INTEGER
        ACCESS	not-accessible
        STATUS	mandatory
        DESCRIPTION
                "HSSI FSI line 2"
        ::= { wfMod 49 }

    wfModHssiUga1 OBJECT-TYPE
        SYNTAX	INTEGER
        ACCESS	not-accessible
        STATUS	mandatory
        DESCRIPTION
                "HSSI UGA-330-2 line 1"
        ::= { wfMod 50 }

    wfModHssiUga2 OBJECT-TYPE
        SYNTAX	INTEGER
        ACCESS	not-accessible
        STATUS	mandatory
        DESCRIPTION
                "HSSI UGA-330-2 line 2"
        ::= { wfMod 51 }

    wfModHicr OBJECT-TYPE
        SYNTAX	INTEGER
        ACCESS	not-accessible
        STATUS	mandatory
        DESCRIPTION
                "HSSI Control Register address"
        ::= { wfMod 52 }

    wfModHicrData OBJECT-TYPE
        SYNTAX	INTEGER
        ACCESS	not-accessible
        STATUS	mandatory
        DESCRIPTION
                "HSSI Last value written to the HICR"
        ::= { wfMod 53 }

    wfModHlsr OBJECT-TYPE
        SYNTAX	INTEGER
        ACCESS	not-accessible
        STATUS	mandatory
        DESCRIPTION
                "HSSI Line Status Register address"
        ::= { wfMod 54 }

    wfModHlsrData OBJECT-TYPE
        SYNTAX	INTEGER
        ACCESS	not-accessible
        STATUS	mandatory
        DESCRIPTION
                "HSSI Last value read from HLSR"
        ::= { wfMod 55 }

    wfModMCR0 OBJECT-TYPE
        SYNTAX	INTEGER
        ACCESS	not-accessible
        STATUS	mandatory
        DESCRIPTION
                "Module Control Register 0"
        ::= { wfMod 56 }

    wfModMCR1 OBJECT-TYPE
        SYNTAX	INTEGER
        ACCESS	not-accessible
        STATUS	mandatory
        DESCRIPTION
                "Module Control Register 1"
        ::= { wfMod 57 }

    wfModCcr0 OBJECT-TYPE
        SYNTAX	INTEGER
        ACCESS	not-accessible
        STATUS	mandatory
        DESCRIPTION
                "Command Control Register 0"
        ::= { wfMod 58 }

    wfModCcr1 OBJECT-TYPE
        SYNTAX	INTEGER
        ACCESS	not-accessible
        STATUS	mandatory
        DESCRIPTION
                "Command Control Register 1"
        ::= { wfMod 59 }

    wfModFcr OBJECT-TYPE
        SYNTAX	INTEGER
        ACCESS	not-accessible
        STATUS	mandatory
        DESCRIPTION
                "Framer Command Register"
        ::= { wfMod 60 }

    wfModMar0 OBJECT-TYPE
        SYNTAX	INTEGER
        ACCESS	not-accessible
        STATUS	mandatory
        DESCRIPTION
                "Munich action request 0"
        ::= { wfMod 61 }

    wfModMar1 OBJECT-TYPE
        SYNTAX	INTEGER
        ACCESS	not-accessible
        STATUS	mandatory
        DESCRIPTION
                "Munich action request 1"
        ::= { wfMod 62 }

    wfModBert OBJECT-TYPE
        SYNTAX	INTEGER
        ACCESS	not-accessible
        STATUS	mandatory
        DESCRIPTION
                "BERT Register"
        ::= { wfMod 63 }

    wfModMgbc OBJECT-TYPE
        SYNTAX	INTEGER
        ACCESS	not-accessible
        STATUS	mandatory
        DESCRIPTION
                "Module Global bus-error clear"
        ::= { wfMod 64 }

    wfModClr0 OBJECT-TYPE
        SYNTAX	INTEGER
        ACCESS	not-accessible
        STATUS	mandatory
        DESCRIPTION
                "Clear Munich interrupt 0"
        ::= { wfMod 65 }

    wfModClr1 OBJECT-TYPE
        SYNTAX	INTEGER
        ACCESS	not-accessible
        STATUS	mandatory
        DESCRIPTION
                "Clear Munich interrupt 1"
        ::= { wfMod 66 }

    wfModCclk OBJECT-TYPE
        SYNTAX	INTEGER
        ACCESS	not-accessible
        STATUS	mandatory
        DESCRIPTION
                "Clear external clock interrupt"
        ::= { wfMod 67 }

    wfModCLoopup0 OBJECT-TYPE
        SYNTAX	INTEGER
        ACCESS	not-accessible
        STATUS	mandatory
        DESCRIPTION
                "Clear Port 0 loop up interrupt"
        ::= { wfMod 68 }

    wfModCLoopup1 OBJECT-TYPE
        SYNTAX	INTEGER
        ACCESS	not-accessible
        STATUS	mandatory
        DESCRIPTION
                "Clear Port 1 loop up interrupt"
        ::= { wfMod 69 }

    wfModCLoopdn0 OBJECT-TYPE
        SYNTAX	INTEGER
        ACCESS	not-accessible
        STATUS	mandatory
        DESCRIPTION
                "Clear Port 0 loop down interrupt"
        ::= { wfMod 70 }

    wfModCLoopdn1 OBJECT-TYPE
        SYNTAX	INTEGER
        ACCESS	not-accessible
        STATUS	mandatory
        DESCRIPTION
                "Clear Port 1 loop down interrupt"
        ::= { wfMod 71 }

    wfModDuart OBJECT-TYPE
        SYNTAX	INTEGER
        ACCESS	not-accessible
        STATUS	mandatory
        DESCRIPTION
                "8530 DUART"
        ::= { wfMod 72 }

    wfModLEDC OBJECT-TYPE
        SYNTAX	INTEGER
        ACCESS	not-accessible
        STATUS	mandatory
        DESCRIPTION
                "LED control register"
        ::= { wfMod 73 }

    wfModMadr5 OBJECT-TYPE
        SYNTAX	OCTET STRING
        ACCESS	not-accessible
        STATUS	mandatory
        DESCRIPTION
                "SNPROM MAC address connector 5 - IN Platform"
        ::= { wfMod 74 }

    wfModDefaC OBJECT-TYPE
        SYNTAX	INTEGER
        ACCESS	not-accessible
        STATUS	mandatory
        DESCRIPTION
                "DEFA C chip  - IN Platform"
        ::= { wfMod 75 }

    wfModCamel1 OBJECT-TYPE
        SYNTAX	INTEGER
        ACCESS	not-accessible
        STATUS	mandatory
        DESCRIPTION
                "IFDDI CAMEL line 1"
        ::= { wfMod 76 }

    wfModTms3803 OBJECT-TYPE
        SYNTAX	INTEGER
        ACCESS	not-accessible
        STATUS	mandatory
        DESCRIPTION
                "TOKEN ring chip line 3"
        ::= { wfMod 77 }

    wfModTms3804 OBJECT-TYPE
        SYNTAX	INTEGER
        ACCESS	not-accessible
        STATUS	mandatory
        DESCRIPTION
                "TOKEN ring chip line 4"
        ::= { wfMod 78 }

    wfModMusicSRT1 OBJECT-TYPE
        SYNTAX	INTEGER
        ACCESS	not-accessible
        STATUS	mandatory
        DESCRIPTION
                "Music SRT chip line 1"
        ::= { wfMod 79 }

    wfModMusicSRT2 OBJECT-TYPE
        SYNTAX	INTEGER
        ACCESS	not-accessible
        STATUS	mandatory
        DESCRIPTION
                "Music SRT chip line 2"
        ::= { wfMod 80 }

    wfModMusicSRT3 OBJECT-TYPE
        SYNTAX	INTEGER
        ACCESS	not-accessible
        STATUS	mandatory
        DESCRIPTION
                "Music SRT chip line 3"
        ::= { wfMod 81 }

    wfModMusicSRT4 OBJECT-TYPE
        SYNTAX	INTEGER
        ACCESS	not-accessible
        STATUS	mandatory
        DESCRIPTION
                "Music SRT chip line 4"
        ::= { wfMod 82 }

    wfModClrQ1Reset OBJECT-TYPE
        SYNTAX	INTEGER
        ACCESS	not-accessible
        STATUS	mandatory
        DESCRIPTION
                "Clear QUICC-1 reset"
        ::= { wfMod 83 }

    wfModClrQ2Reset OBJECT-TYPE
        SYNTAX	INTEGER
        ACCESS	not-accessible
        STATUS	mandatory
        DESCRIPTION
                "Clear QUICC-2 reset"
        ::= { wfMod 84 }

    wfModQ1Dram OBJECT-TYPE
        SYNTAX	INTEGER
        ACCESS	not-accessible
        STATUS	mandatory
        DESCRIPTION
                "QUICC-1 DRAM"
        ::= { wfMod 85 }

    wfModQ2Dram OBJECT-TYPE
        SYNTAX	INTEGER
        ACCESS	not-accessible
        STATUS	mandatory
        DESCRIPTION
                "QUICC-2 DRAM"
        ::= { wfMod 86 }

    wfModQ1DPram OBJECT-TYPE
        SYNTAX	INTEGER
        ACCESS	not-accessible
        STATUS	mandatory
        DESCRIPTION
                "QUICC-1 DPRAM"
        ::= { wfMod 87 }

    wfModQ2DPram OBJECT-TYPE
        SYNTAX	INTEGER
        ACCESS	not-accessible
        STATUS	mandatory
        DESCRIPTION
                "QUICC-2 DPRAM"
        ::= { wfMod 88 }

    wfModQ1StickyBit OBJECT-TYPE
        SYNTAX	INTEGER
        ACCESS	not-accessible
        STATUS	mandatory
        DESCRIPTION
                "QUICC-1 Sticky Bit Write Address base"
        ::= { wfMod 89 }

    wfModQ2StickyBit OBJECT-TYPE
        SYNTAX	INTEGER
        ACCESS	not-accessible
        STATUS	mandatory
        DESCRIPTION
                "QUICC-2 Sticky Bit Write Address base"
        ::= { wfMod 90 }

    wfModQ1Int7 OBJECT-TYPE
        SYNTAX	INTEGER
        ACCESS	not-accessible
        STATUS	mandatory
        DESCRIPTION
                "QUICC-1 Interrupt COP high"
        ::= { wfMod 91 }

    wfModQ2Int7 OBJECT-TYPE
        SYNTAX	INTEGER
        ACCESS	not-accessible
        STATUS	mandatory
        DESCRIPTION
                "QUICC-2 Interrupt COP high"
        ::= { wfMod 92 }

    wfModApplyQ1Reset OBJECT-TYPE
        SYNTAX	INTEGER
        ACCESS	not-accessible
        STATUS	mandatory
        DESCRIPTION
                "Apply QUICC-1 reset"
        ::= { wfMod 93 }

    wfModApplyQ2Reset OBJECT-TYPE
        SYNTAX	INTEGER
        ACCESS	not-accessible
        STATUS	mandatory
        DESCRIPTION
                "Apply QUICC-2 reset"
        ::= { wfMod 94 }

    END  -- Wellfleet-HWMO-MIB
