INTEL-ES480-MIB DEFINITIONS ::= BEGIN

--
-- Copyright (C) 2000 Intel Corporation. All rights reserved.
--
-- Notes: Switch MIB for 
--
--   Intel Express 480T Routing Switch
--

	IMPORTS
		enterprises 		FROM RFC1155-SMI
		TEXTUAL-CONVENTION 	FROM SNMPv2-TC;

	--  Organization & Product branches
    
	intel				OBJECT IDENTIFIER ::= { enterprises 343 }
	sysProducts         OBJECT IDENTIFIER ::= { intel 5 }
    switches   			OBJECT IDENTIFIER ::= { sysProducts 1 }
    
	mib2ext	            OBJECT IDENTIFIER ::= { intel 6 }
	es480tAgent         OBJECT IDENTIFIER ::= { mib2ext 60 }

    --
    -- Intel es480t Object ID 
    --    
    es480t				OBJECT IDENTIFIER ::= { switches 15 }


-- ===============================================================================
--
-- Intel es480t MIB Objects
--
        es480tSystem    OBJECT IDENTIFIER ::= { es480tAgent 1 }

END


-- ===========================================================================

--
-- Intel es480t System objects
--
