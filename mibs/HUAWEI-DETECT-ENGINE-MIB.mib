-- ============================================================================
-- Copyright (C) _2012_ by  HUAWEI TECHNOLOGIES. All rights reserved.
--
-- Description:   HUAWEI-DETECT-ENGINE-MIB.mib
-- Reference:
-- Version:       ver 1.0
-- History:       ver 1.0 lijing00201194 2012-08-30 publish
--
-- ============================================================================

HUAWEI-DETECT-ENGINE-MIB DEFINITIONS ::= BEGIN
	IMPORTS
			hwDatacomm
				FROM HUAWEI-MIB
			OBJECT-GROUP, MODULE-COMPLIANCE, NOTIFICATION-GROUP
				FROM SNMPv2-CONF
		    EnabledStatus
                FROM P-BRIDGE-MIB
            InterfaceIndex
                FROM IF-MIB
            SnmpAdminString
                FROM SNMP-FRAMEWORK-MIB
            Integer32, Unsigned32, Counter64, OBJECT-TYPE, MODULE-IDENTITY, NOTIFICATION-TYPE
                FROM SNMPv2-SMI
            DateAndTime, DisplayString, RowStatus, TEXTUAL-CONVENTION, AutonomousType
                FROM SNMPv2-TC;

    hwDetectEngineMIB MODULE-IDENTITY 
			LAST-UPDATED "201208300936Z"		-- Aug 30, 2012 at 09:36 GMT
			ORGANIZATION 
				 "Huawei Technologies Co.,Ltd."
			CONTACT-INFO 
         "Huawei Industrial Base
          Bantian, Longgang
          Shenzhen 518129
          People's Republic of China
          Website: http://www.huawei.com
          Email: support@huawei.com
         "
			DESCRIPTION 
				"The HUAWEI-DETECT-ENGINE-MIB contains objects to configure Logic module,
				including switching logic startup file.
				This MIB module objects can switch logic startup file for NQA-RTP module or OAM module.
				"

			REVISION "201208300936Z"		-- Aug 30, 2012 at 09:36 GMT
			DESCRIPTION
				"ver 1.0"
			::= { hwDatacomm 308 }
   

	-- 1.3.6.1.4.1.2011.5.25.308.1
    hwDetectEngineObject OBJECT IDENTIFIER ::= { hwDetectEngineMIB 1 }
     
    -- 1.3.6.1.4.1.2011.5.25.308.1.1
    hwDetectEngineGlobalObjects OBJECT IDENTIFIER ::= { hwDetectEngineObject 1 }

    -- 1.3.6.1.4.1.2011.5.25.308.1.1.1
	hwDetectEngineOAMEnable OBJECT-TYPE
            SYNTAX EnabledStatus
            MAX-ACCESS read-write
            STATUS current
            DESCRIPTION
                "Globally enable or disable the detect-engine for oam. If the hwDetectEngineOAMEnable is 1, 
                detect-engine for oam is enabled. If the hwDetectEngineOAMEnable is 2, detect-engine for oam is disabled.              
                By default, detect-engine for oam is enabled."                                                                                                                                               
                ::= { hwDetectEngineGlobalObjects 1 }        

    -- 1.3.6.1.4.1.2011.5.25.308.1.1.2
	hwDetectEngineNQAEnable OBJECT-TYPE
            SYNTAX EnabledStatus
            MAX-ACCESS read-write
            STATUS current
            DESCRIPTION
                "Globally enable or disable the detect-engine for nqa-rtp. If the hwDetectEngineNQAEnable 
                is 1, detect-engine for nqa-rtp is enabled. If the hwDetectEngineNQAEnable is 2, detect-engine for nqa-rtp is disabled. 
                By default, detect-engine for nqa-rtp is disabled."   
                ::= { hwDetectEngineGlobalObjects 2 }


	-- 1.3.6.1.4.1.2011.5.25.308.100
		hwDetectEngineConformance OBJECT IDENTIFIER ::= { hwDetectEngineMIB 100 }


	-- 1.3.6.1.4.1.2011.5.25.308.100.1
		hwDetectEngineCompliances OBJECT IDENTIFIER ::= { hwDetectEngineConformance 1 }


	-- 1.3.6.1.4.1.2011.5.25.308.100.1.1
		hwDetectEngineCompliance MODULE-COMPLIANCE
			STATUS current
			DESCRIPTION 
				"Compliance statement for agents that provide full support for 
				hwDetectEngineMIB."
			MODULE -- this module
			MANDATORY-GROUPS { hwDetectEngineGlobalObjectGroup }
			::= { hwDetectEngineCompliances 1 }


    -- 1.3.6.1.4.1.2011.5.25.308.100.2
		hwDetectEngineGroups OBJECT IDENTIFIER ::= { hwDetectEngineConformance 2 }


	-- 1.3.6.1.4.1.2011.5.25.308.100.2.1
		hwDetectEngineGlobalObjectGroup OBJECT-GROUP
			OBJECTS { hwDetectEngineOAMEnable, hwDetectEngineNQAEnable}
			STATUS current
			DESCRIPTION 
				"Group for base trap objects."
			::= { hwDetectEngineGroups 1 }



   END
