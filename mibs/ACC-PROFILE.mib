ACC-PROFILE DEFINITIONS ::= BEGIN

    IMPORTS
	 OBJECT-TYPE, IpAddress, TimeTicks, Gauge, Counter FROM RFC1155-SMI
                      accTrapLogSeqNum FROM ACC-SYSTEM
	accBRG, DisplayString, RowStatus, IfIndex, SmdsAddress
             FROM ACC-MIB;

-- Protocol Independent Filter Profiles Group
accProfile         OBJECT IDENTIFIER ::= { accBRG 46 }
      -- Filter to Profile Mapping Table
      -- Table for mapping named protocol filters to named profiles
      accProfileFilterTable		OBJECT-TYPE
      	SYNTAX			SEQUENCE OF AccProfileFilterEntry
      	ACCESS			not-accessible
      	STATUS			mandatory
      	DESCRIPTION
      	"Filter to Profile Mapping Table"
      ::= { accProfile 1 }
      accProfileFilterEntry		OBJECT-TYPE
      	SYNTAX			AccProfileFilterEntry
      	ACCESS			not-accessible
      	STATUS			mandatory
      	DESCRIPTION
      	"Entry for a filter profile"
        INDEX { accProfileName }
      ::= { accProfileFilterTable 1 }
      AccProfileFilterEntry ::= SEQUENCE {
      		accProfileName	OCTET STRING,
      		accProfileAction	INTEGER,
      		accProfileFiltList	OCTET STRING
      		}
      accProfileName		OBJECT-TYPE
      	SYNTAX			OCTET STRING
      	ACCESS			read-write
      	STATUS			mandatory
      	DESCRIPTION
      	"Filter Profile Name"
      ::= { accProfileFilterEntry 1 }
      accProfileAction		OBJECT-TYPE
      	SYNTAX			INTEGER {
      				add-profile (1),
      				delete-profile (2),
      				add-element (3),
      				delete-element (4)
      			}
      	ACCESS			read-write
      	STATUS			mandatory
      	DESCRIPTION
      	"Action to perform on this table entry.  Add a new profile.  
      	 Delete an existing profile.  Add new elements to a profile.
      	 Delete existing elements from a profile"
      ::= { accProfileFilterEntry 2 }
      accProfileFiltList		OBJECT-TYPE
      	SYNTAX			OCTET STRING
      	ACCESS			read-write
      	STATUS			mandatory
      	DESCRIPTION
      	"Space delimited list of filter names for a profile"
      ::= { accProfileFilterEntry 3 }
      -- Profile to Port Mapping Table
      -- Table for assigning named profiles to interfaces
      accProfilePortTable		OBJECT-TYPE
      	SYNTAX			SEQUENCE OF AccProfilePortEntry
      	ACCESS			not-accessible
      	STATUS			mandatory
      	DESCRIPTION
      	"Profile to Port assignment Table"
      ::= { accProfile 2 }
      accProfilePortEntry		OBJECT-TYPE
      	SYNTAX			AccProfilePortEntry
      	ACCESS			not-accessible
      	STATUS			mandatory
      	DESCRIPTION
      	"Profile to Port assignement"
        INDEX { accProfilePort }
      ::= { accProfilePortTable 1 }
      AccProfilePortEntry ::= SEQUENCE {
      		accProfilePort	INTEGER,
      		accProfilePortAction	INTEGER,
      		accProfileList	OCTET STRING
      		}
      accProfilePort		OBJECT-TYPE
      	SYNTAX			INTEGER
      	ACCESS			read-write
      	STATUS			mandatory
      	DESCRIPTION
      	"IfIndex of port to assign profile to"
      ::= { accProfilePortEntry 1 }
      accProfilePortAction		OBJECT-TYPE
      	SYNTAX			INTEGER {
      				add-profiles(1),
      				delete-profiles(2)
      			}
      	ACCESS			read-write
      	STATUS			mandatory
      	DESCRIPTION
      	"Action to perform. Add or delete profiles"
      ::= { accProfilePortEntry 2 }
      accProfileList		OBJECT-TYPE
      	SYNTAX			OCTET STRING
      	ACCESS			read-write
      	STATUS			mandatory
      	DESCRIPTION
      	"Space delimited list of profile names"
      ::= { accProfilePortEntry 3 }
      -- Global Profile List
      accProfileGlobalList		OBJECT IDENTIFIER ::= { accProfile 3 }
      accProfileGlobalProfiles		OBJECT-TYPE
      	SYNTAX			OCTET STRING
      	ACCESS			read-write
      	STATUS			mandatory
      	DESCRIPTION
      	"Space delimited list of global profiles"
      ::= { accProfileGlobalList 1 }
      accProfileGlobalAction		OBJECT-TYPE
      	SYNTAX			INTEGER {
      				add-profiles(1),
      				delete-profiles(2)
      			}
      	ACCESS			read-write
      	STATUS			mandatory
      	DESCRIPTION
      	"Action to apply on profile list"
      ::= { accProfileGlobalList 2 }

END
