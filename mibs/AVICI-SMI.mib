AVICI-SMI DEFINITIONS ::= BEGIN

IMPORTS
   MODULE-IDENTITY, OBJECT-IDENTITY, enterprises
      FROM SNMPv2-SMI;

avici MODULE-IDENTITY
   LAST-UPDATED   "990330095500Z"
   ORGANIZATION   "Avici Systems, Inc."
   CONTACT-INFO   "
                  Avici Systems, Inc.
                  101 Billerica Avenue
                  North Billerica, MA 01862-1256

                  (978) 964-2000
                  (978) 964-2100 (fax)

                  snmp@avici.com"
   DESCRIPTION
      "This MIB module contains the structure of management information
       for all vendor-specific MIBs authored by Avici Systems, Inc."
   REVISION       "000426173500Z"
   DESCRIPTION
      "Changed arc names, removed unnecessary arcs."
   REVISION       "990330095500Z"
   DESCRIPTION
      "Created MIB module."
   ::= { enterprises 2474 }

aviciMibs OBJECT-IDENTITY
        STATUS current
        DESCRIPTION
            "aviciMibs is the root where Avici Proprietary MIB modules
             are defined."
        ::= { avici 1 }

aviciProducts OBJECT-IDENTITY
        STATUS current
        DESCRIPTION
            "aviciProducts contains the sysObjectID values for all
             Avici products."
        ::= { avici 2 }

aviciExperimental OBJECT-IDENTITY
        STATUS current
        DESCRIPTION
            "aviciExperimental is a temporary place for experimental MIBs."
        ::= { avici 3 }

aviciTypes OBJECT-IDENTITY
        STATUS current
        DESCRIPTION
            "aviciTypes is the root where Avici textual convention MIB
             modules are defined."
        ::= { avici 4 }

END
