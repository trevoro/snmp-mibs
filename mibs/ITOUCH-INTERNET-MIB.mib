-- $Id: it-internet-mib.mib,v 1.5 2001/05/08 13:35:22 sse Exp $
            ITOUCH-INTERNET-MIB DEFINITIONS ::= BEGIN

                    IMPORTS
                            Counter, Gauge, IpAddress
                                    FROM RFC1155-SMI
                            DisplayString, ifIndex,
                            ipNetToMediaNetAddress, ipAdEntAddr
                                    FROM RFC1213-MIB
                            OBJECT-TYPE
                                    FROM RFC-1212
                            iTouch, DateTime, AddressType, TypedAddress
                                    FROM ITOUCH-MIB;

            xInternetDep    OBJECT IDENTIFIER ::= { iTouch 4 }
            xInternet       OBJECT IDENTIFIER ::= { iTouch 10 }

            -- ITouch Internet subgroups

            xIp             OBJECT IDENTIFIER ::= { xInternet 1 }
            xTcp            OBJECT IDENTIFIER ::= { xInternet 2 }
            xSnmpAgent      OBJECT IDENTIFIER ::= { xInternet 3 }
            xDomainResolver OBJECT IDENTIFIER ::= { xInternet 4 }
            xSlip           OBJECT IDENTIFIER ::= { xInternet 5 }
            xTelnet         OBJECT IDENTIFIER ::= { xInternet 6 }
            xTn3270         OBJECT IDENTIFIER ::= { xInternet 7 }
            xKerberos       OBJECT IDENTIFIER ::= { xInternet 8 }
            xPortSecurity   OBJECT IDENTIFIER ::= { xInternet 9 }
            xXremote        OBJECT IDENTIFIER ::= { xInternet 10 }
            xRotary         OBJECT IDENTIFIER ::= { xInternet 11 }
            xEgp            OBJECT IDENTIFIER ::= { xInternet 12 }
            xOspf           OBJECT IDENTIFIER ::= { xInternet 13 }
            xRouterIp       OBJECT IDENTIFIER ::= { xInternet 14 }
            xRouterUdp      OBJECT IDENTIFIER ::= { xInternet 15 }
            xRouterPolicy   OBJECT IDENTIFIER ::= { xInternet 16 }
            -- number 17 reserved
            xRip            OBJECT IDENTIFIER ::= { xInternet 18 }
            xlpd            OBJECT IDENTIFIER ::= { xInternet 19 }
            xSecurID        OBJECT IDENTIFIER ::= { xInternet 20 }
            -- numbers 21, 22 reserved
            xSsh            OBJECT IDENTIFIER ::= { xInternet 23 }


            -- This is a MIB module for all iTouch Communications systems that
            -- implement IP.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the IP group

            -- Implementation of this group is mandatory for all iTouch
            -- systems that implement IP

            ipGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xIp 1 }

            ipGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xIp 2 }

            ipAutoSubnetMask OBJECT-TYPE
                SYNTAX INTEGER { disabled(1), enabled(2) }
                ACCESS read-write
                STATUS deprecated
                DESCRIPTION
                    "A control for automatic determination of subnet 
                    mask.  'disabled' indicates the system must use the 
                    mask as configured by the network manager.  
                    'enabled' indicates that the system is to 
                    automatically change the subnet mask when the 
                    system's Internet address is changed.  Corresponds 
                    directly to SERVER INTERNET SUBNET MASK 
                    AUTOCONFIGURE and the value labeled 'Subnet Mask 
                    Autoconfigure:' in the SERVER INTERNET 
                    CHARACTERISTICS display."
                ::= { xIp 3 }

            ipReassembly OBJECT-TYPE
                SYNTAX INTEGER { disabled(1), enabled(2) }
                ACCESS read-write
                STATUS mandatory
                DESCRIPTION
                    "A control for reassembly of IP fragments.  
                    Corresponds directly to SERVER INTERNET REASSEMBLY 
                    and the value labeled 'Reassembly:' in the SERVER 
                    INTERNET CHARACTERISTICS display."
                ::= { xIp 4 }

            ipFragmentsQueuedHigh OBJECT-TYPE
                SYNTAX Gauge
                ACCESS read-only
                STATUS mandatory
                DESCRIPTION
                    "Highest number of IP fragments queued."
                ::= { xIp 5 }

            ipFragmentsQueuedCurrent OBJECT-TYPE
                SYNTAX Gauge
                ACCESS read-only
                STATUS mandatory
                DESCRIPTION
                    "Current number of IP fragments queued."
                ::= { xIp 6 }

            ipGenAdExtTable OBJECT-TYPE
                SYNTAX SEQUENCE OF IpGenAdExtEntry
                ACCESS not-accessible
                STATUS mandatory
                DESCRIPTION
                    "Table of additional fields indexed by local IP 
                    address.  An entry in this table is created or 
                    deleted when an entry in the MIB-II ipAddrTable is 
                    created or deleted.  Although MIB-II specifies the 
                    ipAddrTable as read-only, iTouch implementations 
                    typically implement it as read-write to support 
                    modification of local IP addresses, network masks, 
                    and such."
                ::= { xIp 7 }

            ipARPTimeout OBJECT-TYPE
                SYNTAX INTEGER (1..255)
                ACCESS read-write
                STATUS mandatory 
                DESCRIPTION
                    "A control to set the length of time in minutes 
                    before an unused ARP entry is purged from the ARP 
                    table. The default is 60 minutes. Corresponds
                    directly to the value labeled 'Translation Table TTL'
                    in the SERVER INTERNET CHARACTERISTICS display."
                ::= { xIp 8 } 

            ipGatewayPingInterval OBJECT-TYPE
                SYNTAX INTEGER (1..300)
                ACCESS read-write
                STATUS mandatory 
                DESCRIPTION
                    "A control to set the interval of time in seconds
                    between successive pings to the primary gateway
                    so as to determine its status.
                    The default is 60 seconds. Corresponds
                    directly to the value labeled 'Gateway Timeout'
                    in the SERVER INTERNET CHARACTERISTICS display."
                ::= { xIp 9 } 

 	ipConfigureBootp OBJECT-TYPE
		SYNTAX INTEGER { disabled(1), enabled(2) }
		ACCESS read-write
		STATUS mandatory
		DESCRIPTION
		    "Control to use the BOOTP protocol upon startup to learn
                     the unit's own internet address, subnet mask, primary and 
                     secondary gateway servers, domain name servers, time 
                     server and domain name."
		DEFVAL { enabled }
		::= { xIp 11 }

            -- the Generic Address Extensions table

            ipGenAdExtEntry OBJECT-TYPE
                SYNTAX IpGenAdExtEntry
                ACCESS not-accessible
                STATUS mandatory
                DESCRIPTION
                    "A particular entry."
                INDEX { ipAdEntAddr }
                ::= { ipGenAdExtTable 1 }

            IpGenAdExtEntry ::=
                SEQUENCE {
                    ipGenAdEntExtType
                        INTEGER,
                    ipGenAdEntExtBroadcast
                        IpAddress
                }

            ipGenAdEntExtType OBJECT-TYPE
                SYNTAX INTEGER { primary(1), rotary(2), slip(3),
                                 ppp(4) }
                ACCESS read-write
                STATUS mandatory
                DESCRIPTION
                    "The way this local IP address is used, which may 
                    imply alternate, more intuitive ways to set it.

                    primary   general purpose for ordinary use
                    rotary    identificaton for rotary selection
                    slip      use for SLIP connection
                    ppp       use for PPP connection
                    "
                DEFVAL { primary }
                ::= { ipGenAdExtEntry 1 }

            ipGenAdEntExtBroadcast OBJECT-TYPE
                SYNTAX IpAddress
                ACCESS read-write
                STATUS mandatory
                DESCRIPTION
                    "Outgoing IP broadcast address associated with this 
                    local address.  Value may be confined to logical 
                    compatibility with associated network mask."
                DEFVAL { 'ffffffff'h }    -- 255.255.255.255
                ::= { ipGenAdExtEntry 2 }


            -- the TCP group

            -- Implementation of this group is mandatory for all iTouch
            -- systems that implement TCP

            -- scalar parameters follow Port table

            -- the TCP Character Port table

            tcpPortTable OBJECT-TYPE
                SYNTAX SEQUENCE OF TcpPortEntry
                ACCESS not-accessible
                STATUS mandatory
                DESCRIPTION
                    "A list of TCP character port entries."
                ::= { xTcp 1 }

            tcpPortEntry OBJECT-TYPE
                SYNTAX TcpPortEntry
                ACCESS not-accessible
                STATUS mandatory
                DESCRIPTION
                    "TCP parameter values for a character port."
                INDEX { tcpPortIndex }
                ::= { tcpPortTable 1 }

            TcpPortEntry ::=
                SEQUENCE {
                    tcpPortIndex
                        INTEGER,
                    tcpPortConnectByAddress
                        INTEGER,
                    tcpPortWindowSize
                        INTEGER,
                    tcpPortKeepAliveLimit
                        INTEGER
                }

            tcpPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tcpPortEntry 1 }

            tcpPortConnectByAddress OBJECT-TYPE
                SYNTAX INTEGER { disabled(1), enabled(2) }
                ACCESS read-write
                STATUS mandatory
                DESCRIPTION
                    "A control for requesting outgoing connection by 
                    internet address.  'disabled' indicates outgoing 
                    connections must be by Domain name.  'enabled' 
                    indicates that outgoing connections may be requested 
                    by internet address.  Corresponds directly to PORT 
                    INTERNET CONNECTIONS and the presence of the label 
                    'Internet Connections' following the label 'Enabled 
                    Characteristics:' in the PORT CHARACTERISTICS 
                    display."
                ::= { tcpPortEntry 2 }

            tcpPortWindowSize OBJECT-TYPE
                SYNTAX INTEGER (64..8192)
                ACCESS read-write
                STATUS mandatory
                DESCRIPTION
                    "Size of the TCP window for TCP connections on the 
                    port.  Corresponds directly to PORT INTERNET TCP 
                    WINDOW SIZE and the value labeled 'TCP Window Size:' 
                    in the PORT ALTERNATE CHARACTERISTICS display."
                ::= { tcpPortEntry 3 }

            tcpPortKeepAliveLimit OBJECT-TYPE
                SYNTAX INTEGER (0..30)
                ACCESS read-write
                STATUS mandatory
                DESCRIPTION
                    "Number of minutes to maintain a TCP connection 
                    without response to keep-alive communication.  A 
                    value of zero indicates no limit."
                ::= { tcpPortEntry 4 }

            -- additional scalar parameters

            tcpResequencing OBJECT-TYPE
                SYNTAX INTEGER { disabled(1), enabled(2) }
                ACCESS read-write
                STATUS mandatory
                DESCRIPTION
                    "A control for keeping TCP messages received 
                    out-of-order to resequence them before using them.   
                    Corresponds directly to SERVER INTERNET TCP 
                    RESEQUENCING and the value labeled 'Resequencing:' 
                    in the SERVER INTERNET CHARACTERISTICS display."
                ::= { xTcp 2 }

            tcpQueuedSegs OBJECT-TYPE
                SYNTAX Gauge
                ACCESS read-only
                STATUS mandatory
                DESCRIPTION
                    "Number of TCP segments in the TCP receive queues.  
                    Corresponds directly to the value labeled 'TCP 
                    Packets Queued:' in the SERVER INTERNET COUNTERS 
                    display."
                ::= { xTcp 3 }

            tcpDiscardSegs OBJECT-TYPE
                SYNTAX Counter
                ACCESS read-only
                STATUS mandatory
                DESCRIPTION
                    "Number of TCP segments discarded due to exceeding 
                    the TCP receive queue limit.  Corresponds directly 
                    to the value labeled 'TCP Packets Discarded:' in the 
                    SERVER INTERNET COUNTERS display."
                ::= { xTcp 4 }

            tcpConnectTimer OBJECT-TYPE
                SYNTAX INTEGER (4..32)
                ACCESS read-write
                STATUS mandatory
                DESCRIPTION
                    "Number of seconds to attempt a TCP connection 
                    without a response from the other side. The default 
                    value is 32 seconds.  Corresponds directly to the 
                    SERVER INTERNET TCP CONNECT TIMER and the value 
                    labeled 'TCP Connect Timer' in the SERVER INTERNET 
                    CHARACTERISTICS display"
                ::= { xTcp 5 }

            tcpLocalPortBase OBJECT-TYPE
                SYNTAX INTEGER (1..32767)
                ACCESS read-write
                STATUS mandatory
                DESCRIPTION
                    "The value for port 0's tcp source port number."
                ::= { xTcp 6 }

            tcpLocalPortIncrement OBJECT-TYPE
                SYNTAX INTEGER (1..1024)
                ACCESS read-write
                STATUS mandatory
                DESCRIPTION
                    "The value by which the tcp source port number
                    increases for each port greater than port 0."
                ::= { xTcp 7 }

            tcpRoutingTblSz OBJECT-TYPE
                SYNTAX INTEGER (64..512)
                ACCESS read-write
                STATUS mandatory 
                DESCRIPTION
                    "A control to set the size of the working routing table.
                    The default is the current size of the table (64)."
                ::= {xTcp 8  } 

            tcpDataSendDelay OBJECT-TYPE
                SYNTAX INTEGER (0..3000)
                ACCESS read-write
                STATUS mandatory 
                DESCRIPTION
                    "A control to delay for the specified number of 10
                     millisecond ticks before sending the userdata string
                     over the telnet connection."
                DEFVAL { 50 }
                ::= {xTcp 9  } 

             tcpAckDelay OBJECT-TYPE
                SYNTAX INTEGER { disabled(1), enabled(2) }
                ACCESS read-write
                STATUS mandatory
                DESCRIPTION
                    "A Control to prevent sending a TCP ACK when we
                     we change TCP window size."
                DEFVAL { disabled }
                ::= {xTcp 10 }

             tcpRetransmitMin OBJECT-TYPE
                SYNTAX INTEGER (600..3000)
                ACCESS read-write
                STATUS mandatory
                DESCRIPTION
                    "Number of milliseconds for the initial TCP Retransmit
                     timer. This is the time at which a TCP session will
                     initially retransmit unacknowledged packets."
                DEFVAL { 640 }
                ::= {xTcp 11 }


             -- the SNMP Agent group

            -- Implementation of this group is mandatory for all iTouch
            -- systems that implement SNMP

            snmpAgentGetCommunity OBJECT-TYPE
                SYNTAX DisplayString (SIZE (0..32))
                ACCESS read-write
                STATUS mandatory
                DESCRIPTION
                    "The SNMP community name allowed to perform 
                    get-requests or get-next requests to this agent.  
                    Use of this value is case-insensitive.  If the size 
                    is 0, the agent does not check the community name 
                    for these operations.  Corresponds directly to 
                    SERVER INTERNET SNMP GET COMMUNITY and the value 
                    labeled 'Get Community:' in the SERVER INTERNET SNMP 
                    CHARACTERISTICS display."
                ::= { xSnmpAgent 1 }

            snmpAgentSetCommunity OBJECT-TYPE
                SYNTAX DisplayString (SIZE (0..32))
                ACCESS read-write
                STATUS mandatory
                DESCRIPTION
                    "The SNMP community name allowed to perform 
                    set-requests to this agent.  Use of this value is 
                    case-insensitive.  If the size is 0, the agent does 
                    not check the community name for these operations.  
                    Corresponds directly to SERVER INTERNET SNMP SET 
                    COMMUNITY and the value labeled 'Set Community:' in 
                    the SERVER INTERNET SNMP CHARACTERISTICS display."
                ::= { xSnmpAgent 2 }

            snmpAgentTrapCommunity OBJECT-TYPE
                SYNTAX DisplayString (SIZE (0..32))
                ACCESS read-write
                STATUS mandatory
                DESCRIPTION
                    "The SNMP community name sent in traps from this 
                    agent.  Use of this value preserves case.  
                    Corresponds directly to SERVER INTERNET SNMP TRAP 
                    COMMUNITY and the value labeled 'Trap Community:' in 
                    the SERVER INTERNET SNMP CHARACTERISTICS display."
                ::= { xSnmpAgent 3 }

            snmpAgentGetClientNumber OBJECT-TYPE
                SYNTAX INTEGER
                ACCESS read-only
                STATUS mandatory
                DESCRIPTION
                    "The number of client source addresses allowed to 
                    perform get-requests or get-next requests to this 
                    agent.  If the value is 0, the agent does not check 
                    source address for these operations.  Corresponds 
                    indirectly to the values labeled 'Get Client n:' in 
                    the SERVER INTERNET SNMP CHARACTERISTICS display."
                ::= { xSnmpAgent 4 }

            snmpAgentSetClientNumber OBJECT-TYPE
                SYNTAX INTEGER
                ACCESS read-only
                STATUS mandatory
                DESCRIPTION
                    "The number of client source addresses allowed to 
                    perform set-requests to this agent.  If the value is 
                    0, the agent does not check source address for these 
                    operations.  Corresponds indirectly to the values 
                    labeled 'Set Client n:' in the SERVER INTERNET SNMP 
                    CHARACTERISTICS display."
                ::= { xSnmpAgent 5 }

            snmpAgentTrapClientNumber OBJECT-TYPE
                SYNTAX INTEGER
                ACCESS read-only
                STATUS mandatory
                DESCRIPTION
                    "The number of client source addresses to which this 
                    agent sends traps.  If the value is 0, the agent 
                    does not perform this operation.  Corresponds 
                    indirectly to the values labeled 'Trap Client n:' in 
                    the SERVER INTERNET SNMP CHARACTERISTICS display."
                ::= { xSnmpAgent 6 }

            -- More individual objects follow 
            -- the Get Client table

            getClientTable OBJECT-TYPE
                SYNTAX SEQUENCE OF GetClientEntry
                ACCESS not-accessible
                STATUS mandatory
                DESCRIPTION
                    "A list of get client entries.  The number of 
                    entries is given by the value of 
                    snmpAgentGetClientNumber."
                ::= { xSnmpAgent 7 }

            getClientEntry OBJECT-TYPE
                SYNTAX GetClientEntry
                ACCESS not-accessible
                STATUS mandatory
                DESCRIPTION
                    "Parameter values for a get client."
                INDEX { getClientIndex }
                ::= { getClientTable 1 }

            GetClientEntry ::=
                SEQUENCE {
                    getClientIndex
                        INTEGER,
                    getClientEntryStatus
                        INTEGER,
                    getClientAddressType
                        AddressType,
                    getClientAddress
                        OCTET STRING
                }

            getClientIndex OBJECT-TYPE
                SYNTAX INTEGER
                ACCESS read-only
                STATUS mandatory
                DESCRIPTION
                    "Identification of a get client entry.  Corresponds 
                    directly to the number in the label 'Get Client n:' 
                    in the SERVER INTERNET SNMP CHARACTERISTICS 
                    display."
                ::= { getClientEntry 1 }

            getClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { getClientEntry 2 }

            getClientAddressType OBJECT-TYPE
                SYNTAX AddressType
                ACCESS read-write
                STATUS mandatory
                DESCRIPTION
                    "The type of network address contained in 
                    getClientAddress.  'unknown' means no address has 
                    been defined.  'other' means no other type value 
                    applies.  'ip' is an Internet IP address.  
                    'ethernet' is an 802.3 MAC address.  If 
                    getClientAddressType does not accompany 
                    getClientAddress in a set request, the default type 
                    is 'ip'.  Corresponds indirectly to the address 
                    value labeled 'Get Client n:' in the SERVER INTERNET 
                    SNMP CHARACTERISTICS display."
                DEFVAL { unknown }
                ::= { getClientEntry 3 }

            getClientAddress OBJECT-TYPE
                SYNTAX OCTET STRING
                ACCESS read-write
                STATUS mandatory
                DESCRIPTION
                    "The client's network address.  If 
                    getClientAddressType does not accompany 
                    getClientAddress in a set request, the default type 
                    is 'ip'.  Corresponds directly to the address value 
                    labeled 'Get Client n:' in the SERVER INTERNET SNMP 
                    CHARACTERISTICS display."
                DEFVAL { "" }  -- zero length
                ::= { getClientEntry 4 }


            -- the Set Client table

            setClientTable OBJECT-TYPE
                SYNTAX SEQUENCE OF SetClientEntry
                ACCESS not-accessible
                STATUS mandatory
                DESCRIPTION
                    "A list of set client entries.  The number of 
                    entries is given by the value of 
                    snmpAgentSetClientNumber."
                ::= { xSnmpAgent 8 }

            setClientEntry OBJECT-TYPE
                SYNTAX SetClientEntry
                ACCESS not-accessible
                STATUS mandatory
                DESCRIPTION
                    "Parameter values for a set client."
                INDEX { setClientIndex }
                ::= { setClientTable 1 }

            SetClientEntry ::=
                SEQUENCE {
                    setClientIndex
                        INTEGER,
                    setClientEntryStatus
                        INTEGER,
                    setClientAddressType
                        AddressType,
                    setClientAddress
                        OCTET STRING
                }

            setClientIndex OBJECT-TYPE
                SYNTAX INTEGER
                ACCESS read-only
                STATUS mandatory
                DESCRIPTION
                    "Identification of a set client entry.  Corresponds 
                    directly to the number in the label 'Set Client n:' 
                    in the SERVER INTERNET SNMP CHARACTERISTICS 
                    display."
                ::= { setClientEntry 1 }

            setClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { setClientEntry 2 }

            setClientAddressType OBJECT-TYPE
                SYNTAX AddressType
                ACCESS read-write
                STATUS mandatory
                DESCRIPTION
                    "The type of network address contained in 
                    setClientAddress.  'unknown' means no address has 
                    been defined.  'other' means no other type value 
                    applies.  'ip' is an Internet IP address.  
                    'ethernet' is an 802.3 MAC address.  If 
                    setClientAddressType does not accompany 
                    setClientAddress in a set request, the default type 
                    is 'ip'.  Corresponds indirectly to the address 
                    value labeled 'Set Client n:' in the SERVER INTERNET 
                    SNMP CHARACTERISTICS display."
                DEFVAL { unknown }
                ::= { setClientEntry 3 }

            setClientAddress OBJECT-TYPE
                SYNTAX OCTET STRING
                ACCESS read-write
                STATUS mandatory
                DESCRIPTION
                    "The client's network address.  When setting this 
                    value, the requester must supply 
                    setClientAddressType.  If setClientAddressType does 
                    not accompany setClientAddress in a set request, the 
                    default type is 'ip'.  Corresponds directly to the 
                    address value labeled 'Set Client n:' in the SERVER 
                    INTERNET SNMP CHARACTERISTICS display."
                DEFVAL { "" }  -- zero length
                ::= { setClientEntry 4 }


            -- the Trap Client table

            trapClientTable OBJECT-TYPE
                SYNTAX SEQUENCE OF TrapClientEntry
                ACCESS not-accessible
                STATUS mandatory
                DESCRIPTION
                    "A list of trap client entries.  The number of 
                    entries is given by the value of 
                    snmpAgentTrapClientNumber."
                ::= { xSnmpAgent 9 }

            trapClientEntry OBJECT-TYPE
                SYNTAX TrapClientEntry
                ACCESS not-accessible
                STATUS mandatory
                DESCRIPTION
                    "Parameter values for a trap client."
                INDEX { trapClientIndex }
                ::= { trapClientTable 1 }

            TrapClientEntry ::=
                SEQUENCE {
                    trapClientIndex
                        INTEGER,
                    trapClientEntryStatus
                        INTEGER,
                    trapClientAddressType
                        AddressType,
                    trapClientAddress
                        OCTET STRING
                }

            trapClientIndex OBJECT-TYPE
                SYNTAX INTEGER
                ACCESS read-only
                STATUS mandatory
                DESCRIPTION
                    "Identification of a trap client entry.  Corresponds 
                    directly to the number in the label 'Trap Client n:' 
                    in the SERVER INTERNET SNMP CHARACTERISTICS 
                    display."
                ::= { trapClientEntry 1 }

            trapClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { trapClientEntry 2 }

            trapClientAddressType OBJECT-TYPE
                SYNTAX AddressType
                ACCESS read-write
                STATUS mandatory
                DESCRIPTION
                    "The type of network address contained in 
                    trapClientAddress.  'unknown' means no address has 
                    been defined.  'other' means no other type value 
                    applies.  'ip' is an Internet IP address.  
                    'ethernet' is an 802.3 MAC address.  If 
                    trapClientAddressType does not accompany 
                    trapClientAddress in a set request, the default type 
                    is 'ip'.  Corresponds indirectly to the address 
                    value labeled 'Trap Client n:' in the SERVER 
                    INTERNET SNMP CHARACTERISTICS display."
                DEFVAL { unknown }
                ::= { trapClientEntry 3 }

            trapClientAddress OBJECT-TYPE
                SYNTAX OCTET STRING
                ACCESS read-write
                STATUS mandatory
                DESCRIPTION
                    "The client's network address.  When setting this 
                    value, the requester must supply 
                    trapClientAddressType.  If trapClientAddressType 
                    does not accompany trapClientAddress in a set 
                    request, the default type is 'ip'.  Corresponds 
                    directly to the address value labeled 'Trap Client 
                    n:' in the SERVER INTERNET SNMP CHARACTERISTICS 
                    display."
                DEFVAL { "" }  -- zero length
                ::= { trapClientEntry 4 }


            -- Additional individual SNMP agent objects

            snmpAgentAuthFailureAddress OBJECT-TYPE
                SYNTAX TypedAddress
                ACCESS read-only
                STATUS mandatory
                DESCRIPTION
                    "The address of the client to most recently fail 
                    SNMP authorization."
                ::= { xSnmpAgent 10 }

            snmpAgentCommunityAuthenticationAlways OBJECT-TYPE
                SYNTAX INTEGER { disabled(1), enabled(2) }
                ACCESS read-write
                STATUS mandatory
                DESCRIPTION
                  "When enabled, indicates that community string authentication
                   is done always for Gets, Sets, and GetNexts. When disabled,
                   community string authentication is done once; but bypassed
                   on subsequent Gets, Sets or GetNexts from the same address."
                DEFVAL { enabled }
                ::= { xSnmpAgent 14 }


            -- the Domain Resolver group

            -- Implementation of this group is mandatory for all iTouch
            -- systems that implement Domain name resolution

            domainResolverSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { xDomainResolver 1 }

            domainResolverAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { xDomainResolver 2 }

            domainResolverAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { xDomainResolver 3 }

            domainResolverTtl OBJECT-TYPE
                SYNTAX INTEGER (0..168)
                ACCESS read-write
                STATUS mandatory
                DESCRIPTION
                    "The number of hours to keep received Domain 
                    information.  Corresponds directly to SERVER 
                    INTERNET DOMAIN TTL and the value labeled ' Domain 
                    TTL:' in the SERVER INTERNET CHARACTERISTICS 
                    display."
                ::= { xDomainResolver 4 }

            domainResolverNameNumber OBJECT-TYPE
                SYNTAX INTEGER
                ACCESS read-only
                STATUS mandatory
                DESCRIPTION
                    "The number of Domain name mappings in this system's 
                    name cache."
                ::= { xDomainResolver 5 }


            -- the Name table

            nameTable OBJECT-TYPE
                SYNTAX SEQUENCE OF NameEntry
                ACCESS not-accessible
                STATUS mandatory
                DESCRIPTION
                    "A list of Domain name entries.  The number of 
                    entries is given by the value of 
                    domainResolverNameNumber."
                ::= { xDomainResolver 6 }

            nameEntry OBJECT-TYPE
                SYNTAX NameEntry
                ACCESS not-accessible
                STATUS mandatory
                DESCRIPTION
                    "Parameter values for a Domain name."
                INDEX { nameName, nameAddress }
                ::= { nameTable 1 }

            NameEntry ::=
                SEQUENCE {
                    nameName
                        DisplayString,
                    nameAddress
                        IpAddress,
                    nameStatus
                        INTEGER,
                    nameSource
                        INTEGER,
                    nameTtl
                        INTEGER
                }

            nameName OBJECT-TYPE
                SYNTAX DisplayString (SIZE (1..50))
                ACCESS read-only
                STATUS mandatory
                DESCRIPTION
                    "A fully qualified domain name.  Corresponds 
                    directly to the value labeled 'Domain Name' in the 
                    DOMAIN display."
                ::= { nameEntry 1 }

            nameAddress OBJECT-TYPE
                SYNTAX IpAddress
                ACCESS read-only
                STATUS mandatory
                DESCRIPTION
                    "An Internet address corresponding to the Domain 
                    name.  Corresponds directly to the value labeled 
                    'Internet Address' in the DOMAIN display."
                ::= { nameEntry 2 }

            nameStatus OBJECT-TYPE
                SYNTAX INTEGER { invalid(1), valid(2) }
                ACCESS read-write
                STATUS mandatory
                DESCRIPTION
                    "The status of the entry.  Set to 'invalid' to 
                    remove the entry, which corresponds directly to the 
                    PURGE DOMAIN command.  Actual removal of the entry 
                    is implementation specific."
                ::= { nameEntry 3 }

            nameSource OBJECT-TYPE
                SYNTAX INTEGER { manager(1), primary(2), secondary(3),
                                 rwho(4) }
                ACCESS read-only
                STATUS mandatory
                DESCRIPTION
                    "Source of this entry.  The value meanings are:

                    local       defined by manager (LOCAL)
                    primary     obtained from a primary name server
                    secondary   obtained from a secondary name server
                    rwho        obtained from rwho

                    Corresponds directly to the value labeled 'Source' 
                    in the DOMAIN display."
                ::= { nameEntry 4 }

            nameTtl OBJECT-TYPE
                SYNTAX INTEGER
                ACCESS read-only
                STATUS mandatory
                DESCRIPTION
                    "The number of minutes remaining in the entry's time 
                    to live.  Corresponds directly to the value labeled 
                    'TTL' in the DOMAIN display."
                ::= { nameEntry 5 }


            domainResolverPpp OBJECT IDENTIFIER ::= { xDomainResolver 7 }
            
            domainResolverPppPrimaryServer OBJECT-TYPE
                SYNTAX IpAddress
                ACCESS read-write
                STATUS mandatory
                DESCRIPTION
                    "The internet address of the primary Domain Name Server to
                     use in PPP IPCP negotiations. A value of 0.0.0.0 indicates
                     no address. Corresponds directly to the value labeled 
                     'Primary WINS Address:' in the SERVER INTERNET
                     CHARACTERISTICS display."
                ::= { domainResolverPpp 1 }

            domainResolverPppSecondaryServer OBJECT-TYPE
                SYNTAX IpAddress
                ACCESS read-write
                STATUS mandatory
                DESCRIPTION
                    "The internet address of the secondary Domain Name Server to
                     use in PPP IPCP negotiations. A value of 0.0.0.0 indicates
                     no address. Corresponds directly to the value labeled 
                     'Secondary WINS Address:' in the SERVER INTERNET
                     CHARACTERISTICS display."
                ::= { domainResolverPpp 2 }


            -- the SLIP group

            -- Implementation of this group is mandatory for all iTouch
            -- systems that implement SLIP ports

            slipTable OBJECT-TYPE
                SYNTAX SEQUENCE OF SlipEntry
                ACCESS not-accessible
                STATUS mandatory
                DESCRIPTION
                    "A list of SLIP character port entries."
                ::= { xSlip 1 }

            slipEntry OBJECT-TYPE
                SYNTAX SlipEntry
                ACCESS not-accessible
                STATUS mandatory
                DESCRIPTION
                    "Parameter values for a SLIP port."
                INDEX { slipIndex }
                ::= { slipTable 1 }

            SlipEntry ::=
                SEQUENCE {
                    slipIndex
                        INTEGER,
                    slipState
                        INTEGER,
                    slipLocalAddress
                        IpAddress,
                    slipRemoteAddress
                        IpAddress,
                    slipMask
                        IpAddress,
                    slipPortPacketsReceived
                        Counter,
                    slipPortPacketsSent
                        Counter,
                    slipPortPacketsDiscarded
                        Counter,
                    slipPortPacketLengthErrors
                        Counter,
                    slipPortPacketChecksumErrors
                        Counter,
                    slipNetworkPacketsReceived
                        Counter,
                    slipNetworkPacketsSent
                        Counter,
                    slipNetworkPacketsDiscarded
                        Counter
                }

            slipIndex OBJECT-TYPE
                SYNTAX INTEGER
                ACCESS read-only
                STATUS mandatory
                DESCRIPTION
                    "An index value that uniquely identifies a port that 
                    can run SLIP.  The port identified by a particular 
                    value of this index is the same port as identified 
                    by charPortIndex in the Proposed Standard Internet 
                    Character MIB."
                ::= { slipEntry 1 }

            slipState OBJECT-TYPE
                SYNTAX INTEGER { off(1), on(2), compressed(3) }
                ACCESS read-write
                STATUS mandatory
                DESCRIPTION
                    "A control indicating whether SLIP is in operation 
                    on the port.  Corresponds directly to PORT INTERNET 
                    SLIP and the value labeled 'SLIP' in the PORT 
                    CHARACTERISTICS display."
                ::= { slipEntry 2 }

            slipLocalAddress OBJECT-TYPE
                SYNTAX IpAddress
                ACCESS read-write
                STATUS mandatory
                DESCRIPTION
                    "The IP address assigned to the port.  Corresponds 
                    directly to PORT SLIP ADDRESS and the value labeled 
                    'SLIP Address:' in the PORT ALTERNATE 
                    CHARACTERISTICS display."
                ::= { slipEntry 3 }

            slipRemoteAddress OBJECT-TYPE
                SYNTAX IpAddress
                ACCESS read-write
                STATUS mandatory
                DESCRIPTION
                    "The IP address of the remote system attached to the 
                    port.  Corresponds directly to PORT SLIP REMOTE and 
                    the value labeled 'Remote SLIP Address:' in the PORT 
                    ALTERNATE CHARACTERISTICS display."
                ::= { slipEntry 4 }

            slipMask OBJECT-TYPE
                SYNTAX IpAddress
                ACCESS read-write
                STATUS mandatory
                DESCRIPTION
                    "The subnet mask to use for SLIP operation on the 
                    port.  Corresponds directly to PORT SLIP MASK and 
                    the value labeled 'SLIP Mask:' in the PORT ALTERNATE 
                    CHARACTERISTICS display."
                ::= { slipEntry 5 }

            slipPortPacketsReceived OBJECT-TYPE
                SYNTAX Counter
                ACCESS read-only
                STATUS mandatory
                DESCRIPTION
                    "The number of SLIP packets received from the port.  
                    Corresponds directly to the value labeled 'Serial 
                    Packets Received:' in the PORT COUNTERS display."
                ::= { slipEntry 6 }

            slipPortPacketsSent OBJECT-TYPE
                SYNTAX Counter
                ACCESS read-only
                STATUS mandatory
                DESCRIPTION
                    "The number of SLIP packets sent to the port.  
                    Corresponds directly to the value labeled 'Serial 
                    Packets Sent:' in the PORT COUNTERS display."
                ::= { slipEntry 7 }

            slipPortPacketsDiscarded OBJECT-TYPE
                SYNTAX Counter
                ACCESS read-only
                STATUS mandatory
                DESCRIPTION
                    "The number of SLIP packets received from the port 
                    and discarded.  Corresponds directly to the value 
                    labeled 'Serial Packets Discarded:' in the PORT 
                    COUNTERS display."
                ::= { slipEntry 8 }

            slipPortPacketLengthErrors OBJECT-TYPE
                SYNTAX Counter
                ACCESS read-only
                STATUS mandatory
                DESCRIPTION
                    "The number of SLIP packets received from the port 
                    with an incorrect number of bytes.  Corresponds 
                    directly to the value labeled 'Serial Packet Length 
                    Errors:' in the PORT COUNTERS display."
                ::= { slipEntry 9 }

            slipPortPacketChecksumErrors OBJECT-TYPE
                SYNTAX Counter
                ACCESS read-only
                STATUS mandatory
                DESCRIPTION
                    "The number of SLIP packets received from the port 
                    with an invalid checksum.  Corresponds directly to 
                    the value labeled 'Serial Packet Checksum Errors:' 
                    in the PORT COUNTERS display."
                ::= { slipEntry 10 }

            slipNetworkPacketsReceived OBJECT-TYPE
                SYNTAX Counter
                ACCESS read-only
                STATUS mandatory
                DESCRIPTION
                    "The number of SLIP packets received from the 
                    network for this port.  Corresponds directly to the 
                    value labeled 'Network Packets Received:' in the 
                    PORT COUNTERS display."
                ::= { slipEntry 11 }

            slipNetworkPacketsSent OBJECT-TYPE
                SYNTAX Counter
                ACCESS read-only
                STATUS mandatory
                DESCRIPTION
                    "The number of SLIP packets sent to the network from 
                    this port.  Corresponds directly to the value 
                    labeled 'Network Packets Sent:' in the PORT COUNTERS 
                    display."
                ::= { slipEntry 12 }

            slipNetworkPacketsDiscarded OBJECT-TYPE
                SYNTAX Counter
                ACCESS read-only
                STATUS mandatory
                DESCRIPTION
                    "The number of SLIP packets received from the 
                    network for this port and discarded.  Corresponds 
                    directly to the value labeled 'Network Packets 
                    Discarded:' in the PORT COUNTERS display."
                ::= { slipEntry 13 }


            -- the Telnet group

            -- Implementation of this group is mandatory for all iTouch
            -- systems that implement Telnet

            -- the Telnet Character Port table

            -- Ports in this table are either serial or parallel

            telnetPortTable OBJECT-TYPE
                SYNTAX SEQUENCE OF TelnetPortEntry
                ACCESS not-accessible
                STATUS mandatory
                DESCRIPTION
                    "A list of Telnet character port entries."
                ::= { xTelnet 1 }

            telnetPortEntry OBJECT-TYPE
                SYNTAX TelnetPortEntry
                ACCESS not-accessible
                STATUS mandatory
                DESCRIPTION
                    "Telnet parameter values for a character port."
                INDEX { telnetPortIndex }
                ::= { telnetPortTable 1 }

            TelnetPortEntry ::=
                SEQUENCE {
                    telnetPortIndex
                        INTEGER,
                    telnetPortIncomingTcpPort
                        INTEGER,
                    telnetPortOutgoingTcpPort
                        INTEGER,
                    telnetPortNewlineTranslation
                        INTEGER,
                    telnetPortTerminalType
                        DisplayString,
                    telnetPortEorReflection
                        INTEGER,
                    telnetPortBinaryMode
                        INTEGER,
                    telnetPortSendLocation
                        INTEGER,
                    telnetPortClientLocation
                        DisplayString,
                    telnetPortPassiveSendLocation
                        INTEGER
                }

            telnetPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetPortEntry 1 }

            telnetPortIncomingTcpPort OBJECT-TYPE
                SYNTAX INTEGER (1..32767)
                ACCESS read-write
                STATUS mandatory
                DESCRIPTION
                    "The TCP port number offered for incoming 
                    connections to this character port.  Corresponds 
                    directly to PORT TELNET REMOTE PORT and the value 
                    labeled 'Remote Port:' in the PORT TELNET 
                    CHARACTERISTICS display."
                ::= { telnetPortEntry 2 }

            telnetPortOutgoingTcpPort OBJECT-TYPE
                SYNTAX INTEGER
                ACCESS read-write
                STATUS mandatory
                DESCRIPTION
                    "The TCP port number used by default for outgoing 
                    connections from this character port.  Corresponds 
                    directly to PORT TELNET DEFAULT PORT and the value 
                    labeled 'Default Port:' in the PORT TELNET 
                    CHARACTERISTICS display."
                ::= { telnetPortEntry 3 }

            telnetPortNewlineTranslation OBJECT-TYPE
                SYNTAX INTEGER { none(1), cr(2), crNull(3), 
                                crLf(4), std(5), lfToCrLf(6) }
                ACCESS read-write
                STATUS mandatory
                DESCRIPTION
                    "Translation to apply to newline sequences (CR/NULL 
                    or CR/LF) received from the network, before sending 
                    the newline to the character port.  The value 
                    indicates the sequence sent to the character port, 
                    with 'none' meaning no translation.  The lfToCrLf 
                    value converts the newline character LF received
                    from the network to a CR/LF.  Corresponds
                    directly to PORT TELNET NEWLINE FILTERING and the 
                    value labeled 'Newline Filtering:' in the PORT 
                    TELNET CHARACTERISTICS display."
                ::= { telnetPortEntry 4 }

            telnetPortTerminalType OBJECT-TYPE
                SYNTAX DisplayString (SIZE (0..21))
                ACCESS read-write
                STATUS mandatory
                DESCRIPTION
                    "The terminal type character string for Telnet 
                    negotiations.  Corresponds directly to PORT TELNET 
                    TERMINALTYPE and the value labeled 'TerminalType:' 
                    in the PORT TELNET CHARACTERISTICS display."
                ::= { telnetPortEntry 5 }

            telnetPortEorReflection OBJECT-TYPE
                SYNTAX INTEGER { disabled(1), enabled(2) }
                ACCESS read-write
                STATUS mandatory
                DESCRIPTION
                    "Control for end-of-record handshake.  Corresponds 
                    directly to PORT TELNET EOR REFLECTION and the value 
                    labeled 'EOR Reflection:' in the PORT TELNET 
                    CHARACTERISTICS display."
                ::= { telnetPortEntry 6 }

            telnetPortBinaryMode OBJECT-TYPE
                SYNTAX INTEGER { flowControl(1), complete(2),
                                 disabled(3) }
                ACCESS read-write
                STATUS mandatory
                DESCRIPTION
                    "Control for operation of Telnet binary mode.  The 
                    value meanings are:

                    disabled      refuse binary mode negotiation
                                  (INTERACTIVE)
                    flowControl   pass all but XON and XOFF (PASTHRU)
                    complete      pass all characters (PASSALL)

                    Corresponds directly to PORT TELNET BINARY SESSION 
                    MODE and the value labeled 'Binary Session Mode:' in 
                    the PORT TELNET CHARACTERISTICS display."
                ::= { telnetPortEntry 7 }

            telnetPortSendLocation OBJECT-TYPE
                SYNTAX INTEGER { disabled(1), enabled(2) }
                ACCESS read-write
                STATUS mandatory
                DESCRIPTION
                    "A control indicating whether a Telnet session will 
                    initiate negotiation of the Send Location option. 
                    Corresponds directly to the PORT TELNET LOCATION and 
                    the value labeled 'Location' in the PORT TELNET 
                    CHARACTERISTICS display."
                ::= { telnetPortEntry 8 }

            telnetPortClientLocation OBJECT-TYPE
                SYNTAX DisplayString (SIZE (0..50))
                ACCESS read-only
                STATUS mandatory
                DESCRIPTION
                    "The location of the Telnet client port. Corresponds 
                    directly to the value labeled 'Telnet Client 
                    Location' in the SESSION display."
                ::= { telnetPortEntry 9 }
         
            telnetPortPassiveSendLocation OBJECT-TYPE
                SYNTAX INTEGER { disabled(1), enabled(2) }
                ACCESS read-write
                STATUS mandatory
                DESCRIPTION
                    "A control indicating whether a Telnet session will 
                    passively respond to negotiation of the Send Location
                    option. When disabled and telnetPortSendLocation is 
                    disabled, we will refuse to negotiate this option.
                    When telnetPortSendLocation is enabled, it takes 
                    precedence. Corresponds directly to the value labeled
                    'Passive Location' in the PORT TELNET CHARACTERISTICS
                    display."
                DEFVAL { enabled }
                ::= { telnetPortEntry 10 }
            

            -- the Telnet Serial Character Port table

            telnetSerialPortTable OBJECT-TYPE
                SYNTAX SEQUENCE OF TelnetSerialPortEntry
                ACCESS not-accessible
                STATUS mandatory
                DESCRIPTION
                    "A list of Telnet character port entries."
                ::= { xTelnet 2 }

            telnetSerialPortEntry OBJECT-TYPE
                SYNTAX TelnetSerialPortEntry
                ACCESS not-accessible
                STATUS mandatory
                DESCRIPTION
                    "Telnet parameter values for a character port."
                INDEX { telnetSerialPortIndex }
                ::= { telnetSerialPortTable 1 }

            TelnetSerialPortEntry ::=
                SEQUENCE {
                    telnetSerialPortIndex
                        INTEGER,
                    telnetSerialPortOptionDisplay
                        INTEGER,
                    telnetSerialPortCsiEscape
                        INTEGER,
                    telnetSerialPortEchoMode
                        INTEGER,
                    telnetSerialPortNewlineMode
                        INTEGER,
                    telnetSerialPortTransmitMode
                        INTEGER,
                    telnetSerialPortTransmitCharacterTimes
                        INTEGER,
                    telnetSerialPortAbortOutputCharacter
                        INTEGER,
                    telnetSerialPortAttentionCharacter
                        INTEGER,
                    telnetSerialPortEraseKeyCharacter
                        INTEGER,
                    telnetSerialPortEraseLineCharacter
                        INTEGER,
                    telnetSerialPortInterruptCharacter
                        INTEGER,
                    telnetSerialPortQueryCharacter
                        INTEGER,
                    telnetSerialPortSynchronizeCharacter
                        INTEGER,
                    telnetSerialPortUrgentBreak
                        INTEGER,
                    telnetSerialPortRs491
                        INTEGER,
                    telnetSerialPortTransmitBufferedTime
                        INTEGER,
                    telnetSerialPortInterpretInterruptAsBreak
                        INTEGER,
                    telnetSerialPortPass8d
                        INTEGER,
                    telnetSerialPortComControlClient
                        INTEGER,
                    telnetSerialPortComControlServer
                        INTEGER,
                    telnetSerialPortComControlServerRaisesDtr
                        INTEGER,
                    telnetSerialPortComControlClientTogglesDtr
                        INTEGER
                }

            telnetSerialPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetSerialPortEntry 1 }

            telnetSerialPortOptionDisplay OBJECT-TYPE
                SYNTAX INTEGER { disabled(1), enabled(2) }
                ACCESS read-write
                STATUS mandatory
                DESCRIPTION
                    "Control for display of Telnet option negotiations.  
                    Corresponds directly to PORT TELNET OPTION DISPLAY 
                    and the value labeled 'Option Display:' in the PORT 
                    TELNET CHARACTERISTICS display."
                ::= { telnetSerialPortEntry 2 }

            telnetSerialPortCsiEscape OBJECT-TYPE
                SYNTAX INTEGER { disabled(1), enabled(2) }
                ACCESS read-write
                STATUS mandatory
                DESCRIPTION
                    "Control for translation of 8-bit escape sequences 
                    received from the character port to 7-bit 
                    equivalents before transmission to the remote 
                    partner.  Corresponds directly to PORT TELNET CSI 
                    ESCAPE and the value labeled 'CSI Escape:' in the 
                    PORT TELNET CHARACTERISTICS display."
                ::= { telnetSerialPortEntry 3 }

            telnetSerialPortEchoMode OBJECT-TYPE
                SYNTAX INTEGER { local(1), remote(2), disabled(3), passive(4),
                                  character(5), line(6), noecho(7) }
                ACCESS read-write
                STATUS mandatory
                DESCRIPTION
                    "Control for who echoes characters that come from 
                    the character port.  The value meanings are:

                    local    terminal server echoes locally
                    remote   remote system echoes
                    disabled don't default to local echo
                    passive  don't initiate negotiating of echo
                    character initiate remote echo and suppress go ahead
                    line     reject remote echo and reject suppress go ahead
                    noecho   will not initiate echo, but will negotiate it

                    Corresponds directly to PORT TELNET ECHO MODE and 
                    the value labeled 'Echo Mode:' in the PORT TELNET 
                    CHARACTERISTICS display."
                ::= { telnetSerialPortEntry 4 }

            telnetSerialPortNewlineMode OBJECT-TYPE
                SYNTAX INTEGER { crNull(1), crLf(2), verbatim(3) }
                ACCESS read-write
                STATUS mandatory
                DESCRIPTION
                    "Translation to apply to newline (carriage return) 
                    received from the character port, before sending the 
                    newline to the remote partner.  The correspondence 
                    to command keywords is 'crNull' to NULL, 'crLF' to 
                    LINEFEED, and 'verbatim' to NOTHING (that is, no 
                    translation).  Corresponds directly to PORT TELNET 
                    NEWLINE and the value labeled 'Newline:' in the PORT 
                    TELNET CHARACTERISTICS display."
                ::= { telnetSerialPortEntry 5 }

            telnetSerialPortTransmitMode OBJECT-TYPE
                SYNTAX INTEGER { immediate(1), buffered(2), timed(3), controlchar(4) }
                ACCESS read-write
                STATUS mandatory
                DESCRIPTION
                    "Criterion for deciding to send to the remote 
                    partner characters received from the character port.  
                    Corresponds directly to PORT TELNET TRANSMIT and the 
                    value labeled 'Transmit:' in the PORT TELNET 
                    CHARACTERISTICS display."
                ::= { telnetSerialPortEntry 6 }

            telnetSerialPortTransmitCharacterTimes OBJECT-TYPE
                SYNTAX INTEGER (0..255)
                ACCESS read-write
                STATUS mandatory
                DESCRIPTION
                    "Number of character times to wait before 
                    transmitting when telnetSerialPortTransmitMode value 
                    is 'timed'.  Corresponds directly to PORT TELNET 
                    TRANSMIT IDLETIME and the value labeled 'Transmit:  
                    Idle Time -' in the PORT TELNET CHARACTERISTICS 
                    display. This object may only be set to values 1..255.
                    A value of 0 may be read if telnetSerialPortTransmitMode
                    has a value of immediate or buffered"
                ::= { telnetSerialPortEntry 7 }

            telnetSerialPortAbortOutputCharacter OBJECT-TYPE
                SYNTAX INTEGER (0..255)
                ACCESS read-write
                STATUS mandatory
                DESCRIPTION
                    "Character input from the character port to cause 
                    aborting output.  The value 0 indicates no character 
                    has this effect.  Corresponds directly to PORT 
                    TELNET ABORT OUTPUT and the value labeled 'Abort 
                    Output Character:' in the PORT TELNET 
                    CHARACTERISTICS display."
                ::= { telnetSerialPortEntry 8 }

            telnetSerialPortAttentionCharacter OBJECT-TYPE
                SYNTAX INTEGER (0..255)
                ACCESS read-write
                STATUS mandatory
                DESCRIPTION
                    "Character input from the character port to cause an 
                    attention notification to the remote partner.  The 
                    value 0 indicates no character has this effect.  
                    Corresponds directly to PORT TELNET ATTENTION and 
                    the value labeled 'Attention Character:' in the PORT 
                    TELNET CHARACTERISTICS display."
                ::= { telnetSerialPortEntry 9 }

            telnetSerialPortEraseKeyCharacter OBJECT-TYPE
                SYNTAX INTEGER (0..255)
                ACCESS read-write
                STATUS mandatory
                DESCRIPTION
                    "Character input from the character port to cause 
                    erasure of the previous input character.  The value 
                    0 indicates no character has this effect.  
                    Corresponds directly to PORT TELNET ERASE CHARACTER 
                    and the value labeled 'Erase Keystroke Character:' 
                    in the PORT TELNET CHARACTERISTICS display."
                ::= { telnetSerialPortEntry 10 }

            telnetSerialPortEraseLineCharacter OBJECT-TYPE
                SYNTAX INTEGER (0..255)
                ACCESS read-write
                STATUS mandatory
                DESCRIPTION
                    "Character input from the character port to cause 
                    erasure of the previous line of input.  The value 0 
                    indicates no character has this effect.  Corresponds 
                    directly to PORT TELNET ERASE LINE and the value 
                    labeled 'Erase Line Character:' in the PORT TELNET 
                    CHARACTERISTICS display."
                ::= { telnetSerialPortEntry 11 }

            telnetSerialPortInterruptCharacter OBJECT-TYPE
                SYNTAX INTEGER (0..255)
                ACCESS read-write
                STATUS mandatory
                DESCRIPTION
                    "Character input from the character port to cause 
                    sending an interrupt notification to the remote 
                    partner.  The value 0 indicates no character has 
                    this effect.  Corresponds directly to PORT TELNET 
                    INTERRUPT and the value labeled 'Interrupt 
                    Character:' in the PORT TELNET CHARACTERISTICS 
                    display."
                ::= { telnetSerialPortEntry 12 }

            telnetSerialPortQueryCharacter OBJECT-TYPE
                SYNTAX INTEGER (0..255)
                ACCESS read-write
                STATUS mandatory
                DESCRIPTION
                    "Character input from the character port to cause 
                    sending a status query to the remote partner.  The 
                    value 0 indicates no character has this effect.  
                    Corresponds directly to PORT TELNET QUERY and the 
                    value labeled 'Query Character:' in the PORT TELNET 
                    CHARACTERISTICS display."
                ::= { telnetSerialPortEntry 13 }

            telnetSerialPortSynchronizeCharacter OBJECT-TYPE
                SYNTAX INTEGER (0..255)
                ACCESS read-write
                STATUS mandatory
                DESCRIPTION
                    "Character input from the character port to cause 
                    sending a synchronization attempt to the remote 
                    partner.  The value 0 indicates no character has 
                    this effect.  Corresponds directly to PORT TELNET 
                    SYNCHRONIZE and the value labeled 'Synchronize 
                    Character:' in the PORT TELNET CHARACTERISTICS 
                    display."
                ::= { telnetSerialPortEntry 14 }

            telnetSerialPortUrgentBreak OBJECT-TYPE
                SYNTAX INTEGER { disabled(1), enabled(2) }
                ACCESS read-write
                STATUS mandatory
                DESCRIPTION
                    "Control for encoding breaks as Telnet urgent data.  
                    Corresponds directly to PORT TELNET URGENT BREAK and 
                    the value labeled 'Urgent Break:' in the PORT TELNET 
                    CHARACTERISTICS display."
                ::= { telnetSerialPortEntry 15 }

            telnetSerialPortRs491 OBJECT-TYPE
                SYNTAX INTEGER { disabled(1), enabled(2) }
                ACCESS read-write
                STATUS mandatory 
                DESCRIPTION
                   "A control to enable RS491 protocol processing on a port."
                DEFVAL  { disabled }
                ::= { telnetSerialPortEntry 16 }

            telnetSerialPortTransmitBufferedTime OBJECT-TYPE
                SYNTAX INTEGER (30..1500)
                ACCESS read-write
                STATUS mandatory
                DESCRIPTION
                   "Number of milliseconds to wait before transmitting
                    when telnetSerialPortTransmitMode value is 'timed'.
                    Corresponds directly to PORT TELNET TRANSMIT BUFFERED
                    and the value labeled 'Transmit: Buff Time -' in the
                    PORT TELNET CHARACTERISTICS display. This object may
                    only be set to values 30..1500. A value of 0 may be
                    read if telnetSerialPortTransmitMode has a value of
                    immediate, idletime or controlchar"
                DEFVAL   { 80 }
                ::= { telnetSerialPortEntry 17 }

            telnetSerialPortInterpretInterruptAsBreak OBJECT-TYPE
                SYNTAX INTEGER { enabled(1), disabled(2) }
                ACCESS read-write
                STATUS mandatory
                DESCRIPTION
                    "Control to interpret a Telnet Interrupt Character coming
                     from the network as a Telnet Break Character, and to send
                     a break out the serial port. This control is necessary 
                     for those devices which can send Telnet Interrupt but not
                     Telnet Break. Corresponds directly to the presence of 
                     'Telnet Interrupts Interpreted as Break' under the label 
                     'Enabled Characteristics' in the PORT TELNET 
                     CHARACTERISTICS display."
                DEFVAL { disabled }
                ::= { telnetSerialPortEntry 18 }

            telnetSerialPortPass8d OBJECT-TYPE
                SYNTAX INTEGER { enabled(1), disabled(2) }
                ACCESS read-write
                STATUS mandatory
                DESCRIPTION
                    "Control to pass unaltered the hexadecimal character '8D'.
                     This control is added to ensure that this character will
                     pass through directly in a session with 8-bit characters
                     and parity odd or even.  Corresponds directly to the 
                     presence of 'Telnet Pass 8D' under the label 'Enabled
                     Characteristics' in the PORT TELNET CHARACTERISTICS 
                     display."
                DEFVAL { disabled }
                ::= { telnetSerialPortEntry 19 }

            telnetSerialPortComControlClient OBJECT-TYPE
                SYNTAX INTEGER { enabled(1), disabled(2) }
                ACCESS read-write
                STATUS mandatory
                DESCRIPTION
                    "Control to begin Telnet comport control option negotiations
                     as a client when a Telnet session is initiated. The comport
                     control option enables a port to do outbound modem dialing
                     on a Telnet connection. Corresponds to the value labeled
                     'Client:' in the PORT TELNET COMPORTCONTROL CHARACTERISTICS
                     display."
                DEFVAL { disabled }
                ::= { telnetSerialPortEntry 20 }

            telnetSerialPortComControlServer OBJECT-TYPE
                SYNTAX INTEGER { enabled(1), disabled(2) }
                ACCESS read-write
                STATUS mandatory
                DESCRIPTION
                    "Control to begin Telnet comport control option negotiations
                     as a server when a Telnet session is initiated. Corresponds
                     to the value labeled 'Server:' in the PORT TELNET 
                     COMPORTCONTROL CHARACTERISTICS display."
                DEFVAL { disabled }
                ::= { telnetSerialPortEntry 21 }
 
            telnetSerialPortComControlServerRaisesDtr OBJECT-TYPE
                SYNTAX INTEGER { enabled(1), disabled(2) }
                ACCESS read-write
                STATUS mandatory
                DESCRIPTION
                    "Control for the client to request that the server raises
                     its DTR signal on the port at the begining of the Telnet 
                     connection. Corresponds to the value labeled 'Server 
                     Raises DTR:' in the PORT TELNET COMPORTCONTROL
                     CHARACTERISTICS display."
                DEFVAL { disabled }
                ::= { telnetSerialPortEntry 22 }
 
            telnetSerialPortComControlClientTogglesDtr OBJECT-TYPE
                SYNTAX INTEGER { enabled(1), disabled(2) }
                ACCESS read-write
                STATUS mandatory
                DESCRIPTION
                    "Control to respond to the server's notification that its 
                     DCD has come high (or low)  by raising (or lowering) DTR
                     accordingly on the local port. Corresponds to the value 
                     labeled 'Client Toggles DTR:' in the PORT TELNET 
                     COMPORTCONTROL CHARACTERISTICS display."
                DEFVAL { disabled }
                ::= { telnetSerialPortEntry 23 }
 

               


            -- the tn3270 group

            -- Implementation of this group is mandatory for all iTouch
            -- systems that implement tn3270

            tn3270DeviceNumber OBJECT-TYPE
                SYNTAX INTEGER
                ACCESS read-only
                STATUS mandatory
                DESCRIPTION
                    "The number of entries in the tn3270 Device table."
                ::= { xTn3270 1 }

            tn3270LanguageNumber OBJECT-TYPE
                SYNTAX INTEGER
                ACCESS read-only
                STATUS mandatory
                DESCRIPTION
                    "The number of entries in the tn3270 Language 
                    table."
                ::= { xTn3270 2 }

            tn3270PortKeymapStatus OBJECT-TYPE
                SYNTAX INTEGER { disabled(1), enabled(2) }
                ACCESS read-write
                STATUS mandatory
                DESCRIPTION
                    "Control for individual ports to create their own 
                    keymaps.  Corresponds directly to SERVER TN3270 PORT 
                    KEYMAPS and the value labeled 'Port Keymaps:' in the 
                    SERVER TN3270 display."
                ::= { xTn3270 3 }


            -- The tn3270 Device table

            tn3270DeviceTable OBJECT-TYPE
                SYNTAX SEQUENCE OF Tn3270DeviceEntry
                ACCESS not-accessible
                STATUS mandatory
                DESCRIPTION
                    "A list of tn3270 terminal device entries."
                ::= { xTn3270 4 }

            tn3270DeviceEntry OBJECT-TYPE
                SYNTAX Tn3270DeviceEntry
                ACCESS not-accessible
                STATUS mandatory
                DESCRIPTION
                    "Tn3270 parameter values for a terminal device 
                    entry."
                INDEX { tn3270DeviceName }
                ::= { tn3270DeviceTable 1 }

            Tn3270DeviceEntry ::=
                SEQUENCE {
                    tn3270DeviceName
                        DisplayString,
                    tn3270DeviceStatus
                        INTEGER,
                    tn3270DeviceType
                        DisplayString,
                    tn3270Device3278Model
                        INTEGER,
                    tn3270DeviceKeyNumber
                        INTEGER,
                    tn3270DeviceScreenNumber
                        INTEGER
                }

            tn3270DeviceName OBJECT-TYPE
                SYNTAX DisplayString (SIZE (1..8))
                ACCESS read-only
                STATUS mandatory
                DESCRIPTION
                    "The name of a generic terminal device.  Corresponds 
                    directly to SERVER TN3270 DEVICE and the value 
                    labeled 'Device Name:' in the SERVER TN3270 DEVICE 
                    display."
                ::= { tn3270DeviceEntry 1 }

            tn3270DeviceStatus OBJECT-TYPE
                SYNTAX INTEGER { invalid(1), valid(2) }
                ACCESS read-write
                STATUS mandatory
                DESCRIPTION
                    "Status of this entry.  Setting the value to 
                    'invalid' invalidates the entry, corresponding 
                    directly to the PURGE SERVER TN3270 DEVICE command.  
                    It is an implementation-specific matter as to 
                    whether the agent removes an invalidated entry from 
                    the table. If a new device table entry is added to
                    the table, the agent will copy the VT100 table as
                    a default. If one plans to add a new table entry, one
                    should not remove the VT100 entry."
                DEFVAL { valid }
                ::= { tn3270DeviceEntry 2 }

            tn3270DeviceType OBJECT-TYPE
                SYNTAX DisplayString (SIZE (0..21))
                ACCESS read-write
                STATUS mandatory
                DESCRIPTION
                    "The terminal type character string for use when 
                    tn3270DeviceTn3270Type is insufficient.  Corresponds 
                    directly to SERVER TN3270 DEVICE TERMINALTYPE and 
                    the value labeled 'TerminalType:' in the SERVER 
                    TN3270 DEVICE display."
                DEFVAL { "VT100" }
                ::= { tn3270DeviceEntry 3 }

            tn3270Device3278Model OBJECT-TYPE
                SYNTAX INTEGER { model2(1), model5(2) }
                ACCESS read-write
                STATUS mandatory
                DESCRIPTION
                    "The 3278 model for the device.  Corresponds 
                    directly to SERVER TN3270 DEVICE 3278Model and the 
                    value labeled '3278Model:' in the SERVER TN3270 
                    DEVICE display."
                DEFVAL { model2 }
                ::= { tn3270DeviceEntry 4 }

            tn3270DeviceKeyNumber OBJECT-TYPE
                SYNTAX INTEGER
                ACCESS read-only
                STATUS mandatory
                DESCRIPTION
                    "The number of Key table entries for this device."
                DEFVAL { 70 }
                ::= { tn3270DeviceEntry 5 }

            tn3270DeviceScreenNumber OBJECT-TYPE
                SYNTAX INTEGER
                ACCESS read-only
                STATUS mandatory
                DESCRIPTION
                    "The number of Screen table entries for this 
                    device."
                DEFVAL { 24 }
                ::= { tn3270DeviceEntry 6 }


            -- The Key table

            tn3270KeyTable OBJECT-TYPE
                SYNTAX SEQUENCE OF Tn3270KeyEntry
                ACCESS not-accessible
                STATUS mandatory
                DESCRIPTION
                    "A list of tn3270 key entries by device."
                ::= { xTn3270 5 }

            tn3270KeyEntry OBJECT-TYPE
                SYNTAX Tn3270KeyEntry
                ACCESS not-accessible
                STATUS mandatory
                DESCRIPTION
                    "Tn3270 parameter values for a key entry for a 
                    device."
                INDEX { tn3270KeyDeviceName, tn3270KeyName }
                ::= { tn3270KeyTable 1 }

            Tn3270KeyEntry ::=
                SEQUENCE {
                    tn3270KeyDeviceName
                        DisplayString,
                    tn3270KeyName
                        INTEGER,
                    tn3270KeyStatus
                        INTEGER,
                    tn3270KeyCharacterSequence
                        OCTET STRING,
                    tn3270KeyDescription
                        DisplayString
                }

            tn3270KeyDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270KeyEntry 1 }

            tn3270KeyName OBJECT-TYPE
                SYNTAX INTEGER { newline(1), tab(2), backtab(3),
                                 cursorup(4), cursorleft(5),
                                 cursorright(6), cursordown(7),
                                 home(8), delete(9), eraseeof(10),
                                 eraseinput(11), insert(12),
                                 flushinput(13), refresh(14),
                                 centsign(15), duplicate(16),
                                 fieldmark(17), scroll(18),
                                 status(19), reset(20),
                                 fastleft(21), fastright(22),
                                 showkeys(23), print(24),
                                 pf1(39), pf2(40), pf3(41),
                                 pf4(42), pf5(43), pf6(44),
                                 pf7(45), pf8(46), pf9(47), pf10(48),
                                 pf11(49), pf12(50), pf13(51),
                                 pf14(52), pf15(53), pf16(54),
                                 pf17(55), pf18(56), pf19(57),
                                 pf20(58), pf21(59), pf22(60),
                                 pf23(61), pf24(62), pa1(63),
                                 pa2(64), pa3(65), sysreq(66),
                                 enter(67), clear(68), cursorsel(69),
                                 test(70) }
                ACCESS read-only
                STATUS mandatory
                DESCRIPTION
                    "The key name to which this entry applies.  
                    Corresponds directly to the key portion of SERVER 
                    TN3270 DEVICE KEYMAP and the value labeled 
                    '3270-key' in the 'Keymap:' section of the SERVER 
                    TN3270 DEVICE display."
                ::= { tn3270KeyEntry 2 }

            tn3270KeyStatus OBJECT-TYPE
                SYNTAX INTEGER { invalid(1), valid(2) }
                ACCESS read-write
                STATUS deprecated
                DESCRIPTION
                    "Status of this entry.  Setting the value to 
                    'invalid' invalidates the entry.  It is an 
                    implementation-specific matter as to whether the 
                    agent removes an invalidated entry from the table."
                DEFVAL { valid }
                ::= { tn3270KeyEntry 3 }

            tn3270KeyCharacterSequence OBJECT-TYPE
                SYNTAX OCTET STRING (SIZE (0..8))
                ACCESS read-write
                STATUS mandatory
                DESCRIPTION
                    "The ASCII character sequence for the key.  
                    Corresponds directly to the escape-sequence portion 
                    of SERVER TN3270 DEVICE KEYMAP and the value labeled 
                    'KeyCode' in the 'Keymap:' section of the SERVER 
                    TN3270 DEVICE display."
                ::= { tn3270KeyEntry 4 }

            tn3270KeyDescription OBJECT-TYPE
                SYNTAX DisplayString (SIZE (0..5))
                ACCESS read-write
                STATUS mandatory
                DESCRIPTION
                    "Descriptive text for the key.  Corresponds directly 
                    to the description portion of SERVER TN3270 DEVICE 
                    KEYMAP and the value labeled 'Description' in the 
                    SERVER TN3270 DEVICE display."
                ::= { tn3270KeyEntry 5 }


            -- The Screen Action table

            tn3270ScreenTable OBJECT-TYPE
                SYNTAX SEQUENCE OF Tn3270ScreenEntry
                ACCESS not-accessible
                STATUS mandatory
                DESCRIPTION
                    "A list of tn3270 screen action entries by device."
                ::= { xTn3270 6 }

            tn3270ScreenEntry OBJECT-TYPE
                SYNTAX Tn3270ScreenEntry
                ACCESS not-accessible
                STATUS mandatory
                DESCRIPTION
                    "Tn3270 parameter values for a screen action entry 
                    for a device."
                INDEX { tn3270ScreenDeviceName, tn3270ScreenActionName }
                ::= { tn3270ScreenTable 1 }

            Tn3270ScreenEntry ::=
                SEQUENCE {
                    tn3270ScreenDeviceName
                        DisplayString,
                    tn3270ScreenActionName
                        INTEGER,
                    tn3270ScreenStatus
                        INTEGER,
                    tn3270ScreenCharacterSequence
                        OCTET STRING
                }

            tn3270ScreenDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270ScreenEntry 1 }

            tn3270ScreenActionName OBJECT-TYPE
                SYNTAX INTEGER { eraseeol(1), clearscr(2),
                                 movecursor(3), col132(4), col80(5),
                                 beep(6), charset(7), boldon(8),
                                 boldoff(9), blinkon(10),
                                 blinkoff(11), underscoreon(12),
                                 underscoreoff(13), reverseon(14),
                                 reverseoff(15),
                                 colorBlue(16), colorRed(17),
                                 colorPink(18), colorGreen(19),
                                 colorTurquoise(20),
                                 colorYellow(21), colorWhite(22),
                                 status1(26), status2(27),
                                 reset1(28), reset2(29),
                                 reset3(30), reset4(31),
                                 base(32), sgr(33) }
                ACCESS read-only
                STATUS mandatory
                DESCRIPTION
                    "The screen action to which this entry applies.  
                    Corresponds directly to the action portion of SERVER 
                    TN3270 DEVICE SCREENMAP and the value labeled 
                    'Terminal Function' in the 'Screenmap: section of 
                    the SERVER TN3270 DEVICE display."
                ::= { tn3270ScreenEntry 2 }

            tn3270ScreenStatus OBJECT-TYPE
                SYNTAX INTEGER { invalid(1), valid(2) }
                ACCESS read-write
                STATUS deprecated
                DESCRIPTION
                    "Status of this entry.  Setting the value to 
                    'invalid' invalidates the entry.  It is an 
                    implementation-specific matter as to whether the 
                    agent removes an invalidated entry from the table."
                DEFVAL { valid }
                ::= { tn3270ScreenEntry 3 }

            tn3270ScreenCharacterSequence OBJECT-TYPE
                SYNTAX OCTET STRING (SIZE (0..15))
                ACCESS read-write
                STATUS mandatory
                DESCRIPTION
                    "The ASCII character sequence for the screen action.  
                    Some actions may have a lesser length limit.  
                    Corresponds directly to the escape-sequence portion 
                    of SERVER TN3270 DEVICE SCREENMAP and the value 
                    labeled 'HexCode' in the 'Screenmap: section of the 
                    SERVER TN3270 DEVICE display."
                ::= { tn3270ScreenEntry 4 }


            -- The Language table

            tn3270LanguageTable OBJECT-TYPE
                SYNTAX SEQUENCE OF Tn3270LanguageEntry
                ACCESS not-accessible
                STATUS mandatory
                DESCRIPTION
                    "A list of tn3270 language entries."
                ::= { xTn3270 7 }

            tn3270LanguageEntry OBJECT-TYPE
                SYNTAX Tn3270LanguageEntry
                ACCESS not-accessible
                STATUS mandatory
                DESCRIPTION
                    "Tn3270 parameter values for a language entry."
                INDEX { tn3270LanguageName }
                ::= { tn3270LanguageTable 1 }

            Tn3270LanguageEntry ::=
                SEQUENCE {
                    tn3270LanguageName
                        DisplayString,
                    tn3270LanguageStatus
                        INTEGER
                }

            tn3270LanguageName OBJECT-TYPE
                SYNTAX DisplayString (SIZE (1..8))
                ACCESS read-only
                STATUS mandatory
                DESCRIPTION
                    "The name of language for character translation 
                    tables.  Corresponds directly to SERVER TN3270 
                    LANGUAGE and the value labeled 'Language Name:' in 
                    the SERVER LANGUAGE display."
                ::= { tn3270LanguageEntry 1 }

            tn3270LanguageStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table.
                    If a new device table entry is added to the table,
                    the agent will copy the USENGLSH table as the default." 
                DEFVAL { valid }
                ::= { tn3270LanguageEntry 2 }


            -- The Language EBCDIC to ASCII table

            eToALanguageTable OBJECT-TYPE
                SYNTAX SEQUENCE OF EToALanguageEntry
                ACCESS not-accessible
                STATUS mandatory
                DESCRIPTION
                    "A list of language EBCDIC to ASCII conversion 
                    entries."
                ::= { xTn3270 8 }

            eToALanguageEntry OBJECT-TYPE
                SYNTAX EToALanguageEntry
                ACCESS not-accessible
                STATUS mandatory
                DESCRIPTION
                    "EBCDIC to ASCII parameter values for a language 
                    entry."
                INDEX { eToALanguageName, eToAOffset }
                ::= { eToALanguageTable 1 }

            EToALanguageEntry ::=
                SEQUENCE {
                    eToALanguageName
                        DisplayString,
                    eToAOffset
                        INTEGER,
                    eToAValue
                        INTEGER
                }

            eToALanguageName OBJECT-TYPE
                SYNTAX DisplayString (SIZE (1..8))
                ACCESS read-only
                STATUS mandatory
                DESCRIPTION
                    "The name of language from the language table."
                ::= { eToALanguageEntry 1 }

            eToAOffset OBJECT-TYPE
                SYNTAX INTEGER (65..256)
                ACCESS read-only
                STATUS mandatory
                DESCRIPTION
                    "EBCDIC character offset plus one, that is, the 
                    value 1 corresponds to an operational offset of 0.  
                    Corresponds directly to the offset portion of SERVER 
                    TN3270 LANGUAGE and the hexadecimal labels around 
                    the conversion table labeled 'EBCDIC to ASCII' in 
                    the SERVER LANGUAGE display."
                ::= { eToALanguageEntry 2 }

            eToAValue OBJECT-TYPE
                SYNTAX INTEGER (32..255)
                ACCESS read-write
                STATUS mandatory
                DESCRIPTION
                    "ASCII character value for the EBCDIC offset.  
                    Corresponds directly to the value portion of SERVER 
                    TN3270 LANGUAGE and the values in the conversion 
                    table labeled 'EBCDIC to ASCII' in the SERVER 
                    LANGUAGE display."
                ::= { eToALanguageEntry 3 }


            -- The Language ASCII to EBCDIC table

            aToELanguageTable OBJECT-TYPE
                SYNTAX SEQUENCE OF AToELanguageEntry
                ACCESS not-accessible
                STATUS mandatory
                DESCRIPTION
                    "A list of language ASCII to EBCDIC conversion 
                    entries."
                ::= { xTn3270 9 }

            aToELanguageEntry OBJECT-TYPE
                SYNTAX AToELanguageEntry
                ACCESS not-accessible
                STATUS mandatory
                DESCRIPTION
                    "ASCII to EBCDIC parameter values for a language 
                    entry."
                INDEX { aToELanguageName, aToEOffset }
                ::= { aToELanguageTable 1 }

            AToELanguageEntry ::=
                SEQUENCE {
                    aToELanguageName
                        DisplayString,
                    aToEOffset
                        INTEGER,
                    aToEValue
                        INTEGER
                }

            aToELanguageName OBJECT-TYPE
                SYNTAX DisplayString (SIZE (1..8))
                ACCESS read-only
                STATUS mandatory
                DESCRIPTION
                    "The name of language from the language table."
                ::= { aToELanguageEntry 1 }

            aToEOffset OBJECT-TYPE
                SYNTAX INTEGER (33..256)
                ACCESS read-only
                STATUS mandatory
                DESCRIPTION
                    "ASCII character offset plus one, that is, the value 
                    1 corresponds to an operational offset of 0.  
                    Corresponds directly to the offset portion of SERVER 
                    TN3270 LANGUAGE and the hexadecimal labels around 
                    the conversion table labeled 'ASCII to EBCDIC' in 
                    the SERVER LANGUAGE display."
                ::= { aToELanguageEntry 2 }

            aToEValue OBJECT-TYPE
                SYNTAX INTEGER (0..255)
                ACCESS read-write
                STATUS mandatory
                DESCRIPTION
                    "EBCDIC character value for the ASCII offset.  
                    Corresponds directly to the value portion of SERVER 
                    TN3270 LANGUAGE and the values in the conversion 
                    table labeled 'ASCII to EBCDIC' in the SERVER 
                    LANGUAGE display."
                ::= { aToELanguageEntry 3 }


            -- the tn3270 Port table

            tn3270PortTable OBJECT-TYPE
                SYNTAX SEQUENCE OF Tn3270PortEntry
                ACCESS not-accessible
                STATUS mandatory
                DESCRIPTION
                    "A list of tn3270 character port entries."
                ::= { xTn3270 10 }

            tn3270PortEntry OBJECT-TYPE
                SYNTAX Tn3270PortEntry
                ACCESS not-accessible
                STATUS mandatory
                DESCRIPTION
                    "Parameter values for a tn3270 port."
                INDEX { tn3270PortIndex }
                ::= { tn3270PortTable 1 }

            Tn3270PortEntry ::=
                SEQUENCE {
                    tn3270PortIndex
                        INTEGER,
                    tn3270PortDeviceName
                        DisplayString,
                    tn3270PortLanguageName
                        DisplayString,
                    tn3270PortExtendedAttributes
                        INTEGER,
                    tn3270PortEorNegotiation
                        INTEGER,
                    tn3270PortErrorLock
                        INTEGER,
                    tn3270PortPrinterPort
                        INTEGER,
                    tn3270PortOutgoingTcpPort
                        INTEGER,
                    tn3270PortSpaceInsert
                        INTEGER,
                    tn3270PortTypeAhead
                        INTEGER,
                    tn3270PrefixKeyMap
                        INTEGER,
                    tn3270PortScanner
                        INTEGER
                }

            tn3270PortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tn3270PortEntry 1 }

            tn3270PortDeviceName OBJECT-TYPE
                SYNTAX DisplayString (SIZE (0..8))
                ACCESS read-write
                STATUS mandatory
                DESCRIPTION
                    "The name of a generic terminal device from the 
                    tn3270 device table.  Corresponds directly to PORT 
                    TELNET TN3270 DEVICE and the value labeled 'Tn3270 
                    Device:' in the PORT TELNET display."
                ::= { tn3270PortEntry 2 }

            tn3270PortLanguageName OBJECT-TYPE
                SYNTAX DisplayString (SIZE (0..8))
                ACCESS read-write
                STATUS mandatory
                DESCRIPTION
                    "The name of language from the tn3270 language 
                    table.  Corresponds directly to PORT TELNET TN3270 
                    LANGUAGE and the value labeled 'Tn3270 Language:' in 
                    the PORT TELNET display."
                ::= { tn3270PortEntry 3 }

            tn3270PortExtendedAttributes OBJECT-TYPE
                SYNTAX INTEGER { disabled(1), enabled(2) }
                ACCESS read-write
                STATUS mandatory
                DESCRIPTION
                    "A control indicating that certain 3270 extended 
                    attributes are supported on the port.  Corresponds 
                    directly to PORT TELNET TN3270 XTDATTRS and the 
                    label 'Tn3270 XtdAttrs' following the label 'Enabled 
                    Characteristics' in the PORT TELNET display."
                ::= { tn3270PortEntry 4 }

            tn3270PortEorNegotiation OBJECT-TYPE
                SYNTAX INTEGER { disabled(1), enabled(2) }
                ACCESS read-write
                STATUS mandatory
                DESCRIPTION
                    "A control for negotiation of the Telnet EOR option 
                    when establishing a tn3270 session on the port.  
                    Corresponds directly to PORT TELNET TN3270 EOR and 
                    the label 'Tn3270 EOR' following the label 'Enabled 
                    Characteristics' in the PORT TELNET display."
                ::= { tn3270PortEntry 5 }

            tn3270PortErrorLock OBJECT-TYPE
                SYNTAX INTEGER { disabled(1), enabled(2) }
                ACCESS read-write
                STATUS mandatory
                DESCRIPTION
                    "A control for requiring use the RESET key when the 
                    host reports an error during a tn3270 session on the 
                    port.  Corresponds directly to PORT TELNET TN3270 
                    ERRORLOCK and the label 'Tn3270 ErrorLock' following 
                    the label 'Enabled Characteristics' in the PORT 
                    TELNET display."
                ::= { tn3270PortEntry 6 }

            tn3270PortPrinterPort OBJECT-TYPE
                SYNTAX INTEGER
                ACCESS read-write
                STATUS mandatory
                DESCRIPTION
                    "The port number of the tn3270 printer.  Corresponds 
                    directly to PORT TELNET TN3270 PRINTER and the value 
                    labeled 'Tn3270 Printer:' in the PORT TELNET 
                    display."
                ::= { tn3270PortEntry 7 }

            tn3270PortOutgoingTcpPort OBJECT-TYPE
                SYNTAX INTEGER (1..32767)
                ACCESS read-write
                STATUS mandatory
                DESCRIPTION
                    "The TCP port which is used for a TN3270 session when
                     connecting to a remote host from this serial port. 
                     Corresponds directly to the value labeled 'Tn3270 Default 
                     Port:' in the PORT TELNET CHARACTERISTICS display."
                DEFVAL { 23 }
                ::= { tn3270PortEntry 8 }
           
          tn3270PortSpaceInsert OBJECT-TYPE
            SYNTAX INTEGER { disabled(1), enabled(2) }
            ACCESS read-write
            STATUS mandatory
            DESCRIPTION
                "Control to allow insert mode within a space filled field, and
                 write characters over EBCDIC spaces.  Corresponds directly to
                 the presence of 'Tn3270 Space_Insert' under the label 'Enabled
                 Characteristics' in the PORT TELNET CHARACTERISTICS display."
            DEFVAL { disabled }
            ::= { tn3270PortEntry 9 }
           
          tn3270PortTypeAhead OBJECT-TYPE
            SYNTAX INTEGER { disabled(1), enabled(2) }
            ACCESS read-write  
            STATUS mandatory
            DESCRIPTION
                "Control to permit typing ahead in a tn3270 session prior to
                 receiving a response from the host for the previous command
                 entered. Corresponds directly to the presence of
                 'Tn3270 TypeAhead' under the label 'Enabled Characteristics'
                 in the PORT TELNET CHARACTERISTICS display."
            DEFVAL { enabled }
            ::= { tn3270PortEntry 10 }

          tn3270PrefixKeyMap OBJECT-TYPE
            SYNTAX INTEGER { disabled(1), enabled(2) }
            ACCESS read-write
            STATUS mandatory
            DESCRIPTION
                "Control to prepend a prefix function to another function key.
                 When the operator hits the key the prepended function(s) and
                 then the main function for the key are transmitted to the host.
                 Corresponds directly to the presence of 'Tn3270 PrefixKeyMap'
                 under the label 'Enabled Characteristics' in the PORT
                 TELNET CHARACTERISTICS display."
            DEFVAL { disabled  }
            ::= { tn3270PortEntry 11 }

          tn3270PortScanner OBJECT-TYPE
            SYNTAX INTEGER { disabled(1), enabled(2) }
            ACCESS read-write
            STATUS mandatory
            DESCRIPTION
                "Indicates that this is a tn3270 scanner port. Corresponds
                 directly to the presence of 'Tn3270 SCANNER' under the
                 label 'Enabled Characteristics' in the PORT TELNET
                 CHARACTERISTICS display."
            DEFVAL { disabled  }
            ::= { tn3270PortEntry 12 }



            -- the Kerberos group

            -- Implementation of this group is mandatory for all iTouch
            -- systems that implement a Kerberos client

            kerbStatus OBJECT-TYPE
                SYNTAX INTEGER { none(1), login(2) }
                ACCESS read-write
                STATUS mandatory
                DESCRIPTION
                    "A control indicating the level of Kerberos 
                    operation on the system.  Corresponds directly to 
                    SERVER KERBEROS STATUS and the value labeled 
                    'Kerberos Security:' in the SERVER KERBEROS 
                    display."
                ::= { xKerberos 1 }

            kerbRealm OBJECT-TYPE
                SYNTAX DisplayString (SIZE (0..40))
                ACCESS read-write
                STATUS mandatory
                DESCRIPTION
                    "The Kerberos realm with which the kerbServerName1 
                    and kerbServerName2 are associated.  Corresponds 
                    directly to SERVER KERBEROS REALM and the value 
                    labeled 'Kerberos Realm:' in the SERVER KERBEROS 
                    display."
                ::= { xKerberos 2 }

            kerbQueryLimit OBJECT-TYPE
                SYNTAX INTEGER (1..16)
                ACCESS read-write
                STATUS mandatory
                DESCRIPTION
                    "The maximum number of attempts the system can make 
                    when trying to verify a Kerberos ID.  Corresponds 
                    directly to SERVER KERBEROS QUERY LIMIT and the 
                    value labeled 'Kerberos Query Limit:' in the SERVER 
                    KERBEROS display."
                ::= { xKerberos 3 }

            kerbMasterName OBJECT-TYPE
                SYNTAX DisplayString (SIZE (0..50))
                ACCESS read-write
                STATUS mandatory
                DESCRIPTION
                    "The Domain name of the Kerberos master host system, 
                    which holds the Kerberos database.  Corresponds 
                    directly to SERVER KERBEROS MASTER and the value 
                    labeled 'Kerberos Master:' in the SERVER KERBEROS 
                    display."
                ::= { xKerberos 4 }

            kerbServerName1 OBJECT-TYPE
                SYNTAX DisplayString (SIZE (0..50))
                ACCESS read-write
                STATUS mandatory
                DESCRIPTION
                    "The Domain name of the first Kerberos server to try 
                    when the system verifys a Kerberos ID.  Corresponds 
                    directly to SERVER KERBEROS PRIMARY SERVER and the 
                    value labeled 'Kerberos Primary Server:' in the 
                    SERVER KERBEROS display."
                ::= { xKerberos 5 }

            kerbServerName2 OBJECT-TYPE
                SYNTAX DisplayString (SIZE (0..50))
                ACCESS read-write
                STATUS mandatory
                DESCRIPTION
                    "The Domain name of the Kerberos server to try when 
                    the system verifys a Kerberos ID and cannot reach 
                    the Kerberos primary server.  Corresponds directly 
                    to SERVER KERBEROS SECONDARY SERVER and the value 
                    labeled 'Kerberos Secondary Server:' in the SERVER 
                    KERBEROS display."
                ::= { xKerberos 6 }

            kerbInsecureLogins OBJECT-TYPE
                SYNTAX Counter
                ACCESS read-only
                STATUS mandatory
                DESCRIPTION
                    "The number of user logins on ports for which 
                    Kerberos user verification is not enabled.  
                    Corresponds directly to the value labeled 'Logins 
                    without Kerberos:' in the SERVER KERBEROS display."
                ::= { xKerberos 7 }

            kerbSecureLogins OBJECT-TYPE
                SYNTAX Counter
                ACCESS read-only
                STATUS mandatory
                DESCRIPTION
                    "The number of successful user logins on ports for 
                    which Kerberos user verification is enabled.  
                    Corresponds directly to the value labeled 
                    'Successful Logins:' in the SERVER KERBEROS 
                    display."
                ::= { xKerberos 8 }

            kerbSecureLoginsFailed OBJECT-TYPE
                SYNTAX Counter
                ACCESS read-only
                STATUS mandatory
                DESCRIPTION
                    "The number of verification failures due to 
                    incorrect ID or password for attempted user logins 
                    on ports for which Kerberos user verification is 
                    enabled.  Corresponds directly to the value labeled 
                    'Unsuccessful Logins:' in the SERVER KERBEROS 
                    display."
                ::= { xKerberos 9 }

            kerbPasswordChangeFailed OBJECT-TYPE
                SYNTAX Counter
                ACCESS read-only
                STATUS mandatory
                DESCRIPTION
                    "The number of user failures to change their 
                    Kerberos password due to invalid old password or new 
                    password verification.  Corresponds directly to the 
                    value labeled 'Password Change Failures:' in the 
                    SERVER KERBEROS display."
                ::= { xKerberos 10 }

            kerbError OBJECT-TYPE
                SYNTAX INTEGER
                ACCESS read-only
                STATUS mandatory
                DESCRIPTION
                    "The error number of the most recent 
                    Kerberos-related failure.  Corresponds directly to 
                    the value labeled 'Last Kerberos Error:' in the 
                    SERVER KERBEROS display.  For a list of error 
                    numbers and their meanings, consult relevant iTouch 
                    or Kerberos documentation."
                ::= { xKerberos 11 }

            kerbErrorTime OBJECT-TYPE
                SYNTAX DateTime
                ACCESS read-only
                STATUS mandatory
                DESCRIPTION
                    "The date and time that kerbError was last updated.  
                    Corresponds directly to the value labeled 
                    'Occurred:' in the SERVER KERBEROS display."
                ::= { xKerberos 12 }

            kerbMasterAccess OBJECT-TYPE
                SYNTAX Counter
                ACCESS read-only
                STATUS mandatory
                DESCRIPTION
                    "The number of times the system successfully 
                    accessed the Kerberos master host.  Corresponds 
                    directly to the value labeled 'Attempts to access:', 
                    'Master', and 'Successful:' in the SERVER KERBEROS 
                    display."
                ::= { xKerberos 13 }

            kerbMasterAccessFailed OBJECT-TYPE
                SYNTAX Counter
                ACCESS read-only
                STATUS mandatory
                DESCRIPTION
                    "The number of times the system failed access to the 
                    Kerberos master host.  Corresponds directly to the 
                    value labeled 'Attempts to access:', 'Master', and 
                    'Unsuccessful:' in the SERVER KERBEROS display."
                ::= { xKerberos 14 }

            kerbServerAccess1 OBJECT-TYPE
                SYNTAX Counter
                ACCESS read-only
                STATUS mandatory
                DESCRIPTION
                    "The number of times the system successfully 
                    accessed the Kerberos primary server.  Corresponds 
                    directly to the value labeled 'Attempts to access:', 
                    'Server1', and 'Successful:' in the SERVER KERBEROS 
                    display."
                ::= { xKerberos 15 }

            kerbServerAccessFailed1 OBJECT-TYPE
                SYNTAX Counter
                ACCESS read-only
                STATUS mandatory
                DESCRIPTION
                    "The number of times the system failed access to the 
                    Kerberos primary server.  Corresponds directly to 
                    the value labeled 'Attempts to access:', 'Server1', 
                    and 'Unsuccessful:' in the SERVER KERBEROS 
                    display."
                ::= { xKerberos 16 }

            kerbServerAccess2 OBJECT-TYPE
                SYNTAX Counter
                ACCESS read-only
                STATUS mandatory
                DESCRIPTION
                    "The number of times the system successfully 
                    accessed the Kerberos secondary server.  Corresponds 
                    directly to the value labeled 'Attempts to access:', 
                    'Server2', and 'Successful:' in the SERVER KERBEROS 
                    display."
                ::= { xKerberos 17 }

            kerbServerAccessFailed2 OBJECT-TYPE
                SYNTAX Counter
                ACCESS read-only
                STATUS mandatory
                DESCRIPTION
                    "The number of times the system failed access to the 
                    Kerberos secondary server.  Corresponds directly to 
                    the value labeled 'Attempts to access:', 'Server2', 
                    and 'Unsuccessful:' in the SERVER KERBEROS 
                    display."
                ::= { xKerberos 18 }

            -- additional scalar values below


            -- the Kerberos Port table

            kerbPortTable OBJECT-TYPE
                SYNTAX SEQUENCE OF KerbPortEntry
                ACCESS not-accessible
                STATUS mandatory
                DESCRIPTION
                    "A list of Kerberos character port entries."
                ::= { xKerberos 19 }

            kerbPortEntry OBJECT-TYPE
                SYNTAX KerbPortEntry
                ACCESS not-accessible
                STATUS mandatory
                DESCRIPTION
                    "Parameter values for a Kerberos port."
                INDEX { kerbPortIndex }
                ::= { kerbPortTable 1 }

            KerbPortEntry ::=
                SEQUENCE {
                    kerbPortIndex
                        INTEGER,
                    kerbPortStatus
                        INTEGER
                }

            kerbPortIndex OBJECT-TYPE
                SYNTAX INTEGER
                ACCESS read-only
                STATUS mandatory
                DESCRIPTION
                    "An index value that uniquely identifies a port 
                    could relate to Kerberos.  The port identified by a 
                    particular value of this index is the same port as 
                    identified by charPortIndex in the Proposed Standard 
                    Internet Character MIB."
                ::= { kerbPortEntry 1 }

            kerbPortStatus OBJECT-TYPE
                SYNTAX INTEGER { none(1), login(2) }
                ACCESS read-write
                STATUS mandatory
                DESCRIPTION
                    "A control indicating the level of Kerberos 
                    operation on the port.  Corresponds directly to PORT 
                    KERBEROS and the value 'Kerberos' following the 
                    label 'Enabled Characteristics' in the PORT 
                    CHARACTERISTICS display."
                ::= { kerbPortEntry 2 }

            -- additional scalars

            kerbServerPort OBJECT-TYPE
                SYNTAX INTEGER { standardPort(88), experimentalPort(750) }
                ACCESS read-write
                STATUS mandatory
                DESCRIPTION
                    "The UDP port number on the Kerberos server where
                    Kerberos messages are sent."
                ::= { xKerberos 20 }


            -- the Port Security group

            -- Implementation of this group is mandatory for all iTouch
            -- systems that implement Internet port security

            psEntryNumber OBJECT-TYPE
                SYNTAX INTEGER
                ACCESS read-only
                STATUS mandatory
                DESCRIPTION
                    "The number of security entries in this system's 
                    port security table with psEntryStatus of 'valid'."
                ::= { xPortSecurity 1 }

            psEntryNumberLimit OBJECT-TYPE
                SYNTAX INTEGER
                ACCESS read-only
                STATUS mandatory
                DESCRIPTION
                    "The maximum number of security entries in this 
                    system's port security table."
                ::= { xPortSecurity 2 }

            psEntryInvalidIndex OBJECT-TYPE
                SYNTAX INTEGER
                ACCESS read-only
                STATUS mandatory
                DESCRIPTION
                    "A value of psEntryIndex for an entry that has 
                    psEntryStatus of 'invalid'.  A management station 
                    may choose this value when adding a new entry.  
                    Collisions between independent management stations 
                    simultaneously using the same number are beyond the 
                    scope of this document."
                ::= { xPortSecurity 3 }


            -- the Port Security table

            psPortTable OBJECT-TYPE
                SYNTAX SEQUENCE OF PsPortEntry
                ACCESS not-accessible
                STATUS mandatory
                DESCRIPTION
                    "A list of port security character port entries."
                ::= { xPortSecurity 4 }

            psPortEntry OBJECT-TYPE
                SYNTAX PsPortEntry
                ACCESS not-accessible
                STATUS mandatory
                DESCRIPTION
                    "Port security parameter values for a port."
                INDEX { psPortIndex }
                ::= { psPortTable 1 }

            PsPortEntry ::=
                SEQUENCE {
                    psPortIndex
                        INTEGER,
                    psPortDefaultInboundAccess
                        INTEGER,
                    psPortDefaultOutboundAccess
                        INTEGER,
                    psClrInternetSecurity
                        INTEGER
                }

            psPortIndex OBJECT-TYPE
                SYNTAX INTEGER
                ACCESS read-only
                STATUS mandatory
                DESCRIPTION
                    "An index value that uniquely identifies a port for 
                    security purposes.  The port identified by a 
                    particular value of this index is the same port as 
                    identified by charPortIndex in the Proposed Standard 
                    Internet Character MIB."
                ::= { psPortEntry 1 }

            psPortDefaultInboundAccess OBJECT-TYPE
                SYNTAX INTEGER { allow(1), deny(2) }
                ACCESS read-write
                STATUS mandatory
                DESCRIPTION
                    "The default access to the port for incoming TCP 
                    connections.  Corresponds directly to PORT INTERNET 
                    SECURITY DEFAULT INBOUND and the value labeled 
                    'Inbound Default:' in the PORT INTERNET SECURITY 
                    display."
                ::= { psPortEntry 2 }

            psPortDefaultOutboundAccess OBJECT-TYPE
                SYNTAX INTEGER { allow(1), deny(2) }
                ACCESS read-write
                STATUS mandatory
                DESCRIPTION
                    "The default access to the port for outgoing TCP 
                    connections.  Corresponds directly to PORT INTERNET 
                    SECURITY DEFAULT OUTBOUND and the value labeled 
                    'Outbound Default:' in the PORT INTERNET SECURITY 
                    display."
                ::= { psPortEntry 3 }

            psClrInternetSecurity OBJECT-TYPE
                SYNTAX INTEGER { disabled(1), enabled(2) }
                ACCESS read-write
                STATUS mandatory
                DESCRIPTION
                   "A control for if the internet security entries for this
                   port will be cleared upon port logout. The default is
                   disabled."
                ::={ psPortEntry 4 }

            -- the Port Security table

            psTable OBJECT-TYPE
                SYNTAX SEQUENCE OF PsEntry
                ACCESS not-accessible
                STATUS mandatory
                DESCRIPTION
                    "A list of port security entries."
                ::= { xPortSecurity 5 }

            psEntry OBJECT-TYPE
                SYNTAX PsEntry
                ACCESS not-accessible
                STATUS mandatory
                DESCRIPTION
                    "Port security parameter values for an entry for a 
                    port."
                INDEX { psEntryIndex }
                ::= { psTable 1 }

            PsEntry ::=
                SEQUENCE {
                    psEntryIndex
                        INTEGER,
                    psEntryStatus
                        INTEGER,
                    psEntryAddress
                        IpAddress,
                    psEntryMask
                        IpAddress,
                    psEntryAccess
                        INTEGER,
                    psEntryDirection
                        INTEGER,
                    psEntryPortMap
                        OCTET STRING
                }

            psEntryIndex OBJECT-TYPE
                SYNTAX INTEGER
                ACCESS read-only
                STATUS mandatory
                DESCRIPTION
                    "A small, numeric distinguisher for port security 
                    entries.  When adding a new entry, the client should 
                    specify an unused value, such as 
                    psEntryInvalidIndex.  Corresponds directly to the 
                    value labeled 'Entry' in the SERVER INTERNET 
                    SECURITY display."
                ::= { psEntry 1 }

            psEntryStatus OBJECT-TYPE
                SYNTAX INTEGER { invalid(1), valid(2) }
                ACCESS read-write
                STATUS mandatory
                DESCRIPTION
                    "Status of this entry.  Setting the value to 
                    'invalid' invalidates the entry, corresponding 
                    directly to the CLEAR INTERNET SECURITY command.  It 
                    is an implementation-specific matter as to whether 
                    the agent removes an invalidated entry from the 
                    table. Setting this object to 'valid' has no effect.
                    When creating a new instance, one must set 
                    psEntryAddress, psEntryMask, psEntryAccess,
                    psEntryDirection and psEntryPortList for the new
                    instance in the same physical set request. Furthermore,
                    if one wishes to change an entry, one must first
                    delete it and then add it with its new values."
                DEFVAL { valid }
                ::= { psEntry 2 }

            psEntryAddress OBJECT-TYPE
                SYNTAX IpAddress
                ACCESS read-write
                STATUS mandatory
                DESCRIPTION
                    "The IP address to which the entry pertains.  
                    Corresponds directly to the PORT INTERNET SECURITY 
                    internet address and the value labeled 'Internet 
                    Address' in the SERVER INTERNET SECURITY display."
                ::= { psEntry 3 }

            psEntryMask OBJECT-TYPE
                SYNTAX IpAddress
                ACCESS read-write
                STATUS mandatory
                DESCRIPTION
                    "The mask applied to psEntryAddress when making a 
                    security check based on this entry.  Corresponds 
                    directly to PORT INTERNET SECURITY MASK and the 
                    value labeled 'Security Mask' in the SERVER INTERNET 
                    SECURITY display."
                ::= { psEntry 4 }

            psEntryAccess OBJECT-TYPE
                SYNTAX INTEGER { allow(1), deny(2) }
                ACCESS read-write
                STATUS mandatory
                DESCRIPTION
                    "The access to the port for TCP connections when 
                    making a security check based on this entry.  
                    Corresponds directly to PORT INTERNET SECURITY ALLOW 
                    or DENY and the value labeled 'Access' in the SERVER 
                    INTERNET SECURITY display."
                ::= { psEntry 5 }

            psEntryDirection OBJECT-TYPE
                SYNTAX INTEGER { inbound(1), outbound(2) }
                ACCESS read-write
                STATUS mandatory
                DESCRIPTION
                    "The direction of TCP connections to which this 
                    entry applies.  Corresponds directly to PORT 
                    INTERNET SECURITY INBOUND or OUTBOUND and the value 
                    labeled 'Direction' in the SERVER INTERNET SECURITY 
                    display."
                ::= { psEntry 6 }

            psEntryPortMap OBJECT-TYPE
                SYNTAX OCTET STRING
                ACCESS read-write
                STATUS mandatory
                DESCRIPTION
                    "The list of character ports to which this entry 
                    applies.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to PORT INTERNET SECURITY and 
                    the value labeled 'Ports' in the SERVER INTERNET 
                    SECURITY display."
                ::= { psEntry 7 }


            -- the XREMOTE group

            -- Implementation of this group is mandatory for all iTouch
            -- systems that implement XREMOTE

            xremoteServerName1 OBJECT-TYPE
                SYNTAX DisplayString (SIZE (0..50))
                ACCESS read-write
                STATUS mandatory
                DESCRIPTION
                    "The Domain name of the first XREMOTE font server to 
                    try for downloading fonts.  Corresponds directly to 
                    SERVER XREMOTE PRIMARY SERVER and the value labeled 
                    'Xremote Primary Font Server:' in the SERVER XREMOTE 
                    display."
                ::= { xXremote 1 }

            xremoteServerName2 OBJECT-TYPE
                SYNTAX DisplayString (SIZE (0..50))
                ACCESS read-write
                STATUS mandatory
                DESCRIPTION
                    "The Domain name of the XREMOTE font server to try 
                    for downloading fonts and the primary font server 
                    does not respond.  Corresponds directly to SERVER 
                    XREMOTE SECONDARY SERVER and the value labeled 
                    'Xremote Secondary Font Server:' in the SERVER 
                    XREMOTE display."
                ::= { xXremote 2 }

            xremoteServerAccess1 OBJECT-TYPE
                SYNTAX Counter
                ACCESS read-only
                STATUS mandatory
                DESCRIPTION
                    "The number of times the system successfully 
                    accessed the XREMOTE primary font server.  
                    Corresponds directly to the value labeled 'Attempts 
                    to access:', 'Server1', and 'Successful:' in the 
                    SERVER XREMOTE display."
                ::= { xXremote 3 }

            xremoteServerAccessFailed1 OBJECT-TYPE
                SYNTAX Counter
                ACCESS read-only
                STATUS mandatory
                DESCRIPTION
                    "The number of times the system failed access to the 
                    XREMOTE primary font server.  Corresponds directly 
                    to the value labeled 'Attempts to access:', 
                    'Server1', and 'Unsuccessful:' in the SERVER XREMOTE 
                    display."
                ::= { xXremote 4 }

            xremoteServerAccess2 OBJECT-TYPE
                SYNTAX Counter
                ACCESS read-only
                STATUS mandatory
                DESCRIPTION
                    "The number of times the system successfully 
                    accessed the XREMOTE secondary font server.  
                    Corresponds directly to the value labeled 'Attempts 
                    to access:', 'Server2', and 'Successful:' in the 
                    SERVER XREMOTE display."
                ::= { xXremote 5 }

            xremoteServerAccessFailed2 OBJECT-TYPE
                SYNTAX Counter
                ACCESS read-only
                STATUS mandatory
                DESCRIPTION
                    "The number of times the system failed access to the 
                    XREMOTE secondary font server.  Corresponds directly 
                    to the value labeled 'Attempts to access:', 
                    'Server2', and 'Unsuccessful:' in the SERVER XREMOTE 
                    display."
                ::= { xXremote 6 }

            xremoteSessions OBJECT-TYPE
                SYNTAX Gauge
                ACCESS read-only
                STATUS mandatory
                DESCRIPTION
                    "The number of connected XREMOTE sessions.  
                    Corresponds directly to the value labeled 'Current 
                    Number of Xremote Sessions:' in the SERVER XREMOTE 
                    display."
                ::= { xXremote 7 }

            -- Additional individual objects follow port table


            -- the XREMOTE Port table

            xremotePortTable OBJECT-TYPE
                SYNTAX SEQUENCE OF XremotePortEntry
                ACCESS not-accessible
                STATUS mandatory
                DESCRIPTION
                    "A list of XREMOTE character port entries."
                ::= { xXremote 8 }

            xremotePortEntry OBJECT-TYPE
                SYNTAX XremotePortEntry
                ACCESS not-accessible
                STATUS mandatory
                DESCRIPTION
                    "XREMOTE parameter values for a port."
                INDEX { xremotePortIndex }
                ::= { xremotePortTable 1 }

            XremotePortEntry ::=
                SEQUENCE {
                    xremotePortIndex
                        INTEGER,
                    xremotePortXremote
                        INTEGER,
                    xremotePortXdmQuery
                        INTEGER,
                    xremotePortXdmHost
                        DisplayString
                }

            xremotePortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { xremotePortEntry 1 }

            xremotePortXremote OBJECT-TYPE
                SYNTAX INTEGER { disabled(1), enabled(2) }
                ACCESS read-write
                STATUS mandatory
                DESCRIPTION
                    "Control for use of XREMOTE on the port.  
                    Corresponds directly to PORT XREMOTE and the 
                    presence of the label 'Xremote' following the label 
                    'Enabled Characteristics:' in the PORT 
                    CHARACTERISTICS display."
                ::= { xremotePortEntry 2 }

            xremotePortXdmQuery OBJECT-TYPE
                SYNTAX INTEGER { specific(1), broadcast(2),
                                 indirect(3) }
                ACCESS read-write
                STATUS mandatory
                DESCRIPTION
                    "The type of query message issued by a port when 
                    searching for an X Display Manager (XDM). 
                    Corresponds directly to the PORT XDM QUERY and the 
                    'XDM Query:' in the PORT ALTERNATE CHARACTERISTICS 
                    display"
                ::= { xremotePortEntry 3 }

            xremotePortXdmHost OBJECT-TYPE
                SYNTAX DisplayString (SIZE (0..50))
                ACCESS read-write
                STATUS mandatory
                DESCRIPTION
                    "The Domain name or Internet address of the X 
                    Display Manager (XDM) for a port. Corresponds 
                    directly to the PORT XDM HOST and the 'XDM Host:' in 
                    the PORT ALTERNATE CHARACTERISTICS display"
                ::= { xremotePortEntry 4 }

            -- Additional individual objects

            xremoteServerClients OBJECT-TYPE
                SYNTAX Gauge
                ACCESS read-only
                STATUS mandatory
                DESCRIPTION
                    "The number of active X clients.  Corresponds 
                    directly to the value labeled 'Current Number of 
                    XClients:' in the SERVER XREMOTE display."
                ::= { xXremote 9 }


            -- the Rotary group

            -- Implementation of this group is mandatory for all iTouch
            -- systems that implement rotaries

            rotaryNumber OBJECT-TYPE
                SYNTAX INTEGER
                ACCESS read-only
                STATUS mandatory
                DESCRIPTION
                    "The number of entries in the Rotary  table."
                ::= { xRotary 1 }


            -- The Rotary  table

            rotaryTable OBJECT-TYPE
                SYNTAX SEQUENCE OF RotaryEntry
                ACCESS not-accessible
                STATUS mandatory
                DESCRIPTION
                    "A list of rotary  entries."
                ::= { xRotary 2 }

            rotaryEntry OBJECT-TYPE
                SYNTAX RotaryEntry
                ACCESS not-accessible
                STATUS mandatory
                DESCRIPTION
                    "Parameter values for a rotary."
                INDEX { rotaryAddress }
                ::= { rotaryTable 1 }

            RotaryEntry ::=
                SEQUENCE {
                    rotaryAddress
                        IpAddress,
                    rotaryStatus
                        INTEGER,
                    rotaryPortMap
                        OCTET STRING
                }

            rotaryAddress OBJECT-TYPE
                SYNTAX IpAddress
                ACCESS read-only
                STATUS mandatory
                DESCRIPTION
                    "The internet address to be recognized as a rotary.  
                    Corresponds directly to the ip-address portion of 
                    SERVER INTERNET ROTARY and the value labeled 
                    'Internet Address' in the SERVER INTERNET ROTARY 
                    display."
                ::= { rotaryEntry 1 }

            rotaryStatus OBJECT-TYPE
                SYNTAX INTEGER { invalid(1), valid(2) }
                ACCESS read-write
                STATUS mandatory
                DESCRIPTION
                    "Status of this entry.  Setting the value to 
                    'invalid' invalidates the entry, corresponding 
                    directly to the CLEAR SERVER INTERNET ROTARY 
                    command.  It is an implementation-specific matter as 
                    to whether the agent removes an invalidated entry 
                    from the table. Setting the value to 'valid' in 
                    conjunction with a new rotaryAddress will add a 
                    new entry to the table. When adding a new entry,
                    one should also specify a rotaryPortMap as the DEFVAL
                    of 0..0 for rotaryPortMap is meaningless."
                DEFVAL { valid }
                ::= { rotaryEntry 2 }

            rotaryPortMap OBJECT-TYPE
                SYNTAX OCTET STRING
                ACCESS read-write
                STATUS mandatory
                DESCRIPTION
                    "The list of character ports that compose the 
                    rotary.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to port-list portion of SERVER 
                    INTERNET ROTARY and the value labeled 'Ports' in the 
                    SERVER INTERNET ROTARY display."
                DEFVAL { "" }  -- zero length
                ::= { rotaryEntry 3 }


            -- the EGP group

            -- Implementation of this group is mandatory for all iTouch
            -- systems that implement EGP

            egpRouting OBJECT-TYPE
                SYNTAX INTEGER { disabled(1), enabled(2) }
                ACCESS read-write
                STATUS mandatory
                DESCRIPTION
                    "Control for EGP routing services."
                ::= { xEgp 1 }

            egpStatus OBJECT-TYPE
                SYNTAX INTEGER { active(1), noMemory(2), noIpRouting(3),
                                 noEgpRouting(4), noNeighbors(5),
                                 noAS(6) }
                ACCESS read-only
                STATUS mandatory
                DESCRIPTION
                    "Status of the EGP routing services indicating why 
                    it is not running."
                ::= { xEgp 2 }

            egpNbrTable OBJECT-TYPE
                SYNTAX SEQUENCE OF EgpNbrEntry
                ACCESS not-accessible
                STATUS mandatory
                DESCRIPTION
                    "The EGP neighbor table."
                ::= { xEgp 3 }

            egpNbrEntry OBJECT-TYPE
                SYNTAX EgpNbrEntry
                ACCESS not-accessible
                STATUS mandatory
                DESCRIPTION
                    "Information about this entity's relationship with a 
                    particular EGP neighbor."
                INDEX { egpNbrAddr }
                ::= { egpNbrTable 1 }

            EgpNbrEntry ::=
                SEQUENCE {
                    egpNbrAddr
                        IpAddress,
                    egpNbrIntervalDead
                        INTEGER,
                    egpNbrStatus
                        INTEGER
                }

            egpNbrAddr OBJECT-TYPE
                SYNTAX IpAddress
                ACCESS read-only
                STATUS mandatory
                DESCRIPTION
                    "The IP address of this entry's EGP neighbor."
                ::= { egpNbrEntry 1 }

            egpNbrIntervalDead OBJECT-TYPE
                SYNTAX INTEGER (0..65535)
                ACCESS read-write
                STATUS mandatory
                DESCRIPTION
                    "The interval upon entering the cease or idle state 
                    before automatically assuming a Start Event has 
                    occured.  If a neighbor does not respond within 5 
                    minutes, a Stop Event will automatically occur.  The 
                    interval is in hundredths of seconds."
                DEFVAL { 30000 }
                ::= { egpNbrEntry 2 }

            egpNbrStatus OBJECT-TYPE
                SYNTAX INTEGER { invalid(1), valid(2) }
                ACCESS read-write
                STATUS mandatory
                DESCRIPTION
                    "The status of the entry for this neighbor.  Set to 
                    'invalid' to remove the entry."
                DEFVAL { valid }
                ::= { egpNbrEntry 3 }


            -- the OSPF group

            -- Implementation of this group is mandatory for all iTouch
            -- systems that implement OSPF

            ospfAutoConfigure OBJECT-TYPE
                SYNTAX INTEGER { disabled(1), enabled(2) }
                ACCESS read-write
                STATUS mandatory
                DESCRIPTION
                    "Control whether OSPF will automatically configure 
                    itself."
                ::= { xOspf 1 }

            ospfStatus OBJECT-TYPE
                SYNTAX INTEGER { active(1), noMemory(2), noIpRouting(3),
                                 noOspfRouting(4), noAreas(5),
                                 noInterfaces(6), noRtrId(7), 
                                 noBackBoneAndVirtualInterfaces(8),
                                 noBackBoneAndInterface(9),
                                 noBackBone(10) }
                ACCESS read-only
                STATUS mandatory
                DESCRIPTION
                    "Status of the OSPF routing services indicating why 
                    it is not running."
                ::= { xOspf 2 }

            -- the OSPF Interface Metric table

            ospfIfMtrcTable OBJECT-TYPE
                SYNTAX SEQUENCE OF OspfIfMtrcEntry
                ACCESS not-accessible
                STATUS mandatory
                DESCRIPTION
                    "The TOS metrics for a non-virtual interface 
                    identified by the interface index."
                ::= { xOspf 3 }

            ospfIfMtrcEntry OBJECT-TYPE
                SYNTAX OspfIfMtrcEntry
                ACCESS not-accessible
                STATUS mandatory
                DESCRIPTION
                    "A particular TOS metric for a non-virtual interface 
                    identified by the interface index."
                INDEX { ospfIfMtrcIpAddress, ospfIfMtrcAddressLessIf,
                        ospfIfMtrcTos }
                ::= { ospfIfMtrcTable 1 }

            OspfIfMtrcEntry ::=
                SEQUENCE {
                    ospfIfMtrcIpAddress
                        IpAddress,
                    ospfIfMtrcAddressLessIf
                        INTEGER,
                    ospfIfMtrcTos
                        INTEGER,
                    ospfIfMtrcCostActual
                        INTEGER
                }

            ospfIfMtrcIpAddress OBJECT-TYPE
                SYNTAX IpAddress
                ACCESS read-only
                STATUS mandatory
                DESCRIPTION
                    "Same as ospfIfMetricIpAddress in OSPF MIB, the IP 
                    address of this OSPF interface."
                REFERENCE
                    "OSPF Version 2 Management Information Base, RFC 
                    1253"
                ::= { ospfIfMtrcEntry 1 }

            ospfIfMtrcAddressLessIf OBJECT-TYPE
                SYNTAX INTEGER
                ACCESS read-only
                STATUS mandatory
                DESCRIPTION
                    "Same as ospfIfMetricAddressLessIf in OSPF MIB, for 
                    the purpose of easing the instancing of addressed 
                    and addressless interfaces.  This variable takes the 
                    value 0 on interfaces with IP Addresses, and the 
                    value of ifIndex for interfaces having no IP 
                    Address."
                REFERENCE
                    "OSPF Version 2 Management Information Base, RFC 
                    1253"
                ::= { ospfIfMtrcEntry 2 }

            ospfIfMtrcTos OBJECT-TYPE
                SYNTAX INTEGER ( 1..16 )
                ACCESS read-only
                STATUS mandatory
                DESCRIPTION
                    "Same as ospfIfMetricTOS in OSPF MIB, the type of 
                    service metric being referenced."
                REFERENCE
                    "OSPF Version 2 Management Information Base, RFC 
                    1253"
                ::= { ospfIfMtrcEntry 3 }

            ospfIfMtrcCostActual OBJECT-TYPE
                SYNTAX INTEGER ( 1..65535 )
                ACCESS read-only
                STATUS mandatory
                DESCRIPTION
                    "The actual cost of the metric in case it was set to 
                    auto."
                ::= { ospfIfMtrcEntry 4 }

            -- the OSPF Interface table

            ospfXIfTable OBJECT-TYPE
                SYNTAX SEQUENCE OF OspfXIfEntry
                ACCESS not-accessible
                STATUS mandatory
                DESCRIPTION
                    "The TOS metrics for a non-virtual interface 
                    identified by the interface index."
                ::= { xOspf 4 }

            ospfXIfEntry OBJECT-TYPE
                SYNTAX OspfXIfEntry
                ACCESS not-accessible
                STATUS mandatory
                DESCRIPTION
                    "Interface parameters for OSPF."
                INDEX { ospfXIfIpAddress, ospfXIfAddressLessIf }
                ::= { ospfXIfTable 1 }

            OspfXIfEntry ::=
                SEQUENCE {
                    ospfXIfIpAddress
                        IpAddress,
                    ospfXIfAddressLessIf
                        INTEGER,
                    ospfXIfTypeActual
                        INTEGER,
                    ospfXIfStatus
                        INTEGER
                }

            ospfXIfIpAddress OBJECT-TYPE
                SYNTAX IpAddress
                ACCESS read-only
                STATUS mandatory
                DESCRIPTION
                    "Same as ospfIfIpAddress in OSPF MIB, the IP address 
                    of this OSPF interface."
                REFERENCE
                    "OSPF Version 2 Management Information Base, RFC 
                    1253"
                ::= { ospfXIfEntry 1 }

            ospfXIfAddressLessIf OBJECT-TYPE
                SYNTAX INTEGER
                ACCESS read-only
                STATUS mandatory
                DESCRIPTION
                    "Same as ospfIfAddressLessIf in OSPF MIB, for the 
                    purpose of easing the instancing of addressed and 
                    addressless interfaces.  This variable takes the 
                    value 0 on interfaces with IP Addresses, and the 
                    value of ifIndex for interfaces having no IP 
                    Address."
                REFERENCE
                    "OSPF Version 2 Management Information Base, RFC 
                    1253"
                ::= { ospfXIfEntry 2 }

            ospfXIfTypeActual OBJECT-TYPE
                SYNTAX INTEGER { broadcast(1), nonbroadcast(2),
                                 pointToPoint(3) }
                ACCESS read-only
                STATUS mandatory
                DESCRIPTION
                    "The interface type."
                ::= { ospfXIfEntry 3 }

            ospfXIfStatus OBJECT-TYPE
                SYNTAX INTEGER { invalid(1), valid(2) }
                ACCESS read-write
                STATUS mandatory
                DESCRIPTION
                    "The status of the interface entry, including the 
                    entry in the standard OSPF MIB.  Set to 'invalid' to 
                    remove the entry."
                DEFVAL { valid }
                ::= { ospfXIfEntry 4 }

            -- the OSPF Area table

            ospfXAreaTable OBJECT-TYPE
                SYNTAX SEQUENCE OF OspfXAreaEntry
                ACCESS not-accessible
                STATUS mandatory
                DESCRIPTION
                    "Parameters for an OSPF area."
                ::= { xOspf 5 }

            ospfXAreaEntry OBJECT-TYPE
                SYNTAX OspfXAreaEntry
                ACCESS not-accessible
                STATUS mandatory
                DESCRIPTION
                    "An area entry."
                INDEX { ospfXAreaId }
                ::= { ospfXAreaTable 1 }

            OspfXAreaEntry ::=
                SEQUENCE {
                    ospfXAreaId
                        IpAddress,
                    ospfXAreaStatus
                        INTEGER
                }

            ospfXAreaId OBJECT-TYPE
                SYNTAX IpAddress
                ACCESS read-only
                STATUS mandatory
                DESCRIPTION
                    "Same as ospfAreaId in OSPF MIB, the ID of the 
                    area."
                REFERENCE
                    "OSPF Version 2 Management Information Base, RFC 
                    1253"
                ::= { ospfXAreaEntry 1 }

            ospfXAreaStatus OBJECT-TYPE
                SYNTAX INTEGER { invalid(1), valid(2) }
                ACCESS read-write
                STATUS mandatory
                DESCRIPTION
                    "The status of the area entry, including the entry 
                    in the standard OSPF MIB.  Set to 'invalid' to 
                    remove the entry."
                DEFVAL { valid }
                ::= { ospfXAreaEntry 2 }


            -- the Router IP group

            -- Implementation of this group is mandatory for all iTouch
            -- systems that implement IP and do through routing

            ipAdExtTable OBJECT-TYPE
                SYNTAX SEQUENCE OF IpAdExtEntry
                ACCESS not-accessible
                STATUS mandatory
                DESCRIPTION
                    "Table of additional fields indexed by local IP 
                    address.  An entry in this table is created or 
                    deleted when an entry in the ipAddrTable is created 
                    or deleted."
                ::= { xRouterIp 1 }

            ipAdExtEntry OBJECT-TYPE
                SYNTAX IpAdExtEntry
                ACCESS not-accessible
                STATUS mandatory
                DESCRIPTION
                    "A particular entry."
                INDEX { ipAdEntExtAddress }
                ::= { ipAdExtTable 1 }

            IpAdExtEntry ::=
                SEQUENCE {
                    ipAdEntExtAddress
                        IpAddress,
                    ipAdEntExtProxyArp
                        INTEGER,
                    ipAdEntExtRip
                        INTEGER
                }

            ipAdEntExtAddress OBJECT-TYPE
                SYNTAX IpAddress
                ACCESS read-only
                STATUS mandatory
                DESCRIPTION
                    "Same as ipAdEntAddr, a local address representing a 
                    network connection."
                ::= { ipAdExtEntry 1 }

            ipAdEntExtProxyArp OBJECT-TYPE
                SYNTAX INTEGER { enabled(2), disabled(1) }   
                ACCESS read-write
                STATUS mandatory
                DESCRIPTION
                    "Controls whether proxy ARP is active for this local 
                    address."
                DEFVAL { disabled }
                ::= { ipAdExtEntry 2 }

            ipAdEntExtRip OBJECT-TYPE
                SYNTAX INTEGER { enabled(2), disabled(1) }   
                ACCESS read-only
                STATUS deprecated
                DESCRIPTION
                    "Controls whether RIP as a router discovery protocol 
                    is active for this local address."
                DEFVAL { disabled }
                ::= { ipAdExtEntry 3 }


            -- the IP Router Interface table

            ipRouterIfTable OBJECT-TYPE
                SYNTAX SEQUENCE OF IpRouterIfEntry
                ACCESS not-accessible
                STATUS mandatory
                DESCRIPTION
                    "Table of IP router values indexed by interface."
                ::= { xRouterIp 2 }

            ipRouterIfEntry OBJECT-TYPE
                SYNTAX IpRouterIfEntry
                ACCESS not-accessible
                STATUS mandatory
                DESCRIPTION
                    "A particular entry."
                INDEX { ipRouterIfIndex }
                ::= { ipRouterIfTable 1 }

            IpRouterIfEntry ::=
                SEQUENCE {
                    ipRouterIfIndex
                        INTEGER,
                    ipRouterIfProtocolPriority
                        INTEGER,
                    ipRouterIfMTU
                        INTEGER,
                    ipRouterIfRDP
                        INTEGER,
                    ipRouterIfArpPacketsIn
                        Counter,
                    ipRouterIfArpPacketsOut
                        Counter,
                    ipRouterIfPacketsIn
                        Counter,
                    ipRouterIfPacketsOut
                        Counter,
                    ipRouterIfForwardsIn
                        Counter,
                    ipRouterIfForwardsOut
                        Counter
                }

            ipRouterIfIndex OBJECT-TYPE
                SYNTAX INTEGER
                ACCESS read-only
                STATUS mandatory
                DESCRIPTION
                    "The index of the interface; same as IfIndex."
                ::= { ipRouterIfEntry 1 }

            ipRouterIfProtocolPriority OBJECT-TYPE
                SYNTAX INTEGER { low(1), medium(3), high(5) }
                ACCESS read-write
                STATUS mandatory
                DESCRIPTION
                    "The priority at which all Internet routed packets 
                    will be placed on the WAN output queue."
                DEFVAL { medium }
                ::= { ipRouterIfEntry 2 }

            ipRouterIfMTU OBJECT-TYPE
                SYNTAX INTEGER (128..65535)
                ACCESS read-write
                STATUS mandatory
                DESCRIPTION
                    "The size of the largest datagram that IP can
                     transmit on this interface.  The default value
                     is actually hardware dependent."
                DEFVAL { 1500 }
                ::= { ipRouterIfEntry 3 }

            ipRouterIfRDP OBJECT-TYPE
                SYNTAX INTEGER { enabled(1), disabled(2) }
                ACCESS read-write
                STATUS mandatory
                DESCRIPTION
                    "Control for whether the router side of the Router 
                    Discovery Protocol is running on this interface."
                DEFVAL { disabled }
                ::= { ipRouterIfEntry 4 }

            ipRouterIfArpPacketsIn OBJECT-TYPE
                SYNTAX Counter
                ACCESS read-only
                STATUS mandatory
                DESCRIPTION
                    "The number of ARP packets received on this 
                    interface."
                ::= { ipRouterIfEntry 5 }

            ipRouterIfArpPacketsOut OBJECT-TYPE
                SYNTAX Counter
                ACCESS read-only
                STATUS mandatory
                DESCRIPTION
                    "The number of ARP packets sent on this interface."
                ::= { ipRouterIfEntry 6 }

            ipRouterIfPacketsIn OBJECT-TYPE
                SYNTAX Counter
                ACCESS read-only
                STATUS mandatory
                DESCRIPTION
                    "The number of IP packets received on this 
                    interface."
                ::= { ipRouterIfEntry 7 }

            ipRouterIfPacketsOut OBJECT-TYPE
                SYNTAX Counter
                ACCESS read-only
                STATUS mandatory
                DESCRIPTION
                    "The number of IP packets sent on this interface."
                ::= { ipRouterIfEntry 8 }

            ipRouterIfForwardsIn OBJECT-TYPE
                SYNTAX Counter
                ACCESS read-only
                STATUS mandatory
                DESCRIPTION
                    "The number of IP packets received on this interface 
                    that were forwarded."
                ::= { ipRouterIfEntry 9 }

            ipRouterIfForwardsOut OBJECT-TYPE
                SYNTAX Counter
                ACCESS read-only
                STATUS mandatory
                DESCRIPTION
                    "The number of IP packets sent on this interface 
                    that were forwarded."
                ::= { ipRouterIfEntry 10 }


            -- the IP Router Traffic subgroup

            -- Implementation of this subgroup is mandatory for all
            -- iTouch IP router systems that implement traffic
            -- monitoring

            xIpTraffic   OBJECT IDENTIFIER ::= { xRouterIp 3 }

            ipTrafficSort OBJECT-TYPE
                SYNTAX INTEGER { ready(1), execute(2) }
                ACCESS read-write
                STATUS mandatory
                DESCRIPTION
                    "Setting to 'execute' causes the most recent traffic 
                    information to be sorted into the ipTrafficTable. 
                    The sorting precedence is: decreasing percentage, 
                    increasing destination address, increasing source 
                    address, and increasing interface number.  Setting 
                    to 'ready' has no effect."
                ::= { xIpTraffic 1 }

            -- Note:  additional individual objects follow table

            ipTrafficTable OBJECT-TYPE
                SYNTAX SEQUENCE OF IpTrafficEntry
                ACCESS not-accessible
                STATUS mandatory
                DESCRIPTION
                    "A list of traffic entries, sorted in the order 
                    specified by ipTrafficSort."
                ::= { xIpTraffic 2 }

            ipTrafficEntry OBJECT-TYPE
                SYNTAX IpTrafficEntry
                ACCESS not-accessible
                STATUS mandatory
                DESCRIPTION
                    "A traffic entry."
                INDEX { ipTrafficIndex }
                ::= { ipTrafficTable 1 }

            IpTrafficEntry ::=
                SEQUENCE {
                    ipTrafficIndex
                        INTEGER,
                    ipTrafficPercent
                         INTEGER,
                    ipTrafficDstAddr
                        IpAddress,
                    ipTrafficSrcAddr
                        IpAddress,
                    ipTrafficProtocol
                         INTEGER,
                    ipTrafficDstPort
                         INTEGER,
                    ipTrafficSrcPort
                         INTEGER,
                    ipTrafficIf
                        INTEGER

                }

            ipTrafficIndex OBJECT-TYPE
                SYNTAX INTEGER
                ACCESS read-only
                STATUS mandatory
                DESCRIPTION
                    "Identification of this traffic entry."
                ::= { ipTrafficEntry 1 }

            ipTrafficPercent OBJECT-TYPE
                SYNTAX INTEGER 
                ACCESS read-only
                STATUS mandatory
                DESCRIPTION
                    "The percentage of total traffic that this traffic 
                    entry represents, in tenths of a percent."
                ::= { ipTrafficEntry 2 }

            ipTrafficDstAddr OBJECT-TYPE
                SYNTAX IpAddress
                ACCESS read-only
                STATUS mandatory
                DESCRIPTION
                    "The destination IP address of the traffic entry."
                ::= { ipTrafficEntry 3 }

            ipTrafficSrcAddr OBJECT-TYPE
                SYNTAX IpAddress
                ACCESS read-only
                STATUS mandatory
                DESCRIPTION
                    "The source IP address of the traffic entry."
                ::= { ipTrafficEntry 4 }

            ipTrafficProtocol OBJECT-TYPE
                SYNTAX INTEGER ( 0..255 )
                ACCESS read-only
                STATUS mandatory
                DESCRIPTION
                    "The IP protocol type of the traffic entry."
                ::= { ipTrafficEntry 5 }

            ipTrafficDstPort OBJECT-TYPE
                SYNTAX INTEGER ( 0..65535 )
                ACCESS read-only
                STATUS mandatory
                DESCRIPTION
                    "The destination TCP/UDP port of the traffic 
                    entry."
                ::= { ipTrafficEntry 6 }

            ipTrafficSrcPort OBJECT-TYPE
                SYNTAX INTEGER ( 0..65535 )
                ACCESS read-only
                STATUS mandatory
                DESCRIPTION
                    "The source TCP/UDP port of the traffic entry."
                ::= { ipTrafficEntry 7 }

            ipTrafficIf OBJECT-TYPE
                SYNTAX INTEGER
                ACCESS read-only
                STATUS mandatory
                DESCRIPTION
                    "The inbound interface to which the traffic entry 
                    applies.  This value is the same as IfIndex."
                ::= { ipTrafficEntry 8 }

            -- additional individual objects

            ipTrafficMonitoring OBJECT-TYPE
                SYNTAX INTEGER { enabled(1), disabled(2) }
                ACCESS read-write
                STATUS mandatory
                DESCRIPTION
                    "Control for whether the router side of the Router 
                    Discovery Protocol is running on this interface."
                ::= { xIpTraffic 3 }

            -- IP Net to Media table extension

            xIpNetToMediaTable OBJECT-TYPE
                SYNTAX SEQUENCE OF XIpNetToMediaEntry
                ACCESS not-accessible
                STATUS mandatory
                DESCRIPTION
                    "iTouch extensions to the IP Address Translation 
                    Table."
                ::= { xRouterIp 4 }

            xIpNetToMediaEntry OBJECT-TYPE
                SYNTAX XIpNetToMediaEntry
                ACCESS not-accessible
                STATUS mandatory
                DESCRIPTION
                    "Entry parameters."
                INDEX { ifIndex, ipNetToMediaNetAddress }
                ::= { xIpNetToMediaTable 1 }

            XIpNetToMediaEntry ::=
                SEQUENCE {
                    xIpNetToMediaCircuit
                        INTEGER,
                    xIpNetToMediaReverseArp
                        INTEGER
                }

            xIpNetToMediaCircuit OBJECT-TYPE
                SYNTAX INTEGER
                ACCESS read-write
                STATUS mandatory
                DESCRIPTION
                    "An additional identifier for the circuit (i.e. 
                    Frame Relay DLCI or X.25 VC) which the entry 
                    extends."
                ::= { xIpNetToMediaEntry 1 }

            xIpNetToMediaReverseArp OBJECT-TYPE
                SYNTAX INTEGER { disabled(1), enabled(2) }
                ACCESS read-write
                STATUS mandatory
                DESCRIPTION
                    "Whether reverse ARP is supported on this entry."
                ::= { xIpNetToMediaEntry 2 }


            -- the Router UDP group

            -- Implementation of this group is mandatory for all iTouch
            -- systems that implement UDP and do through routing

            -- Individual objects follow the UDP Port table

            -- the UDP Broadcast Server table

            udpBcstServerTable OBJECT-TYPE
                SYNTAX SEQUENCE OF UdpBcstServerEntry
                ACCESS not-accessible
                STATUS mandatory
                DESCRIPTION
                    "Table of servers to whom UDP broadcast messages 
                    will be forwarded."
                ::= { xRouterUdp 1 }

            udpBcstServerEntry OBJECT-TYPE
                SYNTAX UdpBcstServerEntry
                ACCESS not-accessible
                STATUS mandatory
                DESCRIPTION
                    "A particular entry."
                INDEX { udpBcstServerAddress }
                ::= { udpBcstServerTable 1 }

            UdpBcstServerEntry ::=
                SEQUENCE {
                    udpBcstServerAddress
                        IpAddress,
                    udpBcstServerStatus
                        INTEGER
                }

            udpBcstServerAddress OBJECT-TYPE
                SYNTAX IpAddress
                ACCESS read-only
                STATUS mandatory
                DESCRIPTION
                    "Internet address of the server."
                ::= { udpBcstServerEntry 1 }

            udpBcstServerStatus OBJECT-TYPE
                SYNTAX INTEGER { invalid(1), valid(2) }
                ACCESS read-write
                STATUS mandatory
                DESCRIPTION
                    "The status of the server.  Set to 'invalid' to 
                    remove the entry."
                DEFVAL { valid }
                ::= { udpBcstServerEntry 2 }


            -- the UDP Broadcast Port table

            udpBcstPortTable OBJECT-TYPE
                SYNTAX SEQUENCE OF UdpBcstPortEntry
                ACCESS not-accessible
                STATUS mandatory
                DESCRIPTION
                    "Table of incoming UDP destination port numbers for 
                    which UDP broadcasts will be forwarded."
                ::= { xRouterUdp 2 }

            udpBcstPortEntry OBJECT-TYPE
                SYNTAX UdpBcstPortEntry
                ACCESS not-accessible
                STATUS mandatory
                DESCRIPTION
                    "A particular entry."
                INDEX { udpBcstPort }
                ::= { udpBcstPortTable 1 }

            UdpBcstPortEntry ::=
                SEQUENCE {
                    udpBcstPort
                        INTEGER,
                    udpBcstPortStatus
                        INTEGER
                }

            udpBcstPort OBJECT-TYPE
                SYNTAX INTEGER
                ACCESS read-only
                STATUS mandatory
                DESCRIPTION
                    "The incoming destination UDP port number."
                ::= { udpBcstPortEntry 1 }

            udpBcstPortStatus OBJECT-TYPE
                SYNTAX INTEGER { invalid(1), valid(2) }
                ACCESS read-write
                STATUS mandatory
                DESCRIPTION
                    "The status of broadcast forwarding for the port.  
                    Set to 'invalid' to remove the entry."
                DEFVAL { valid }
                ::= { udpBcstPortEntry 2 }


            -- Individual objects

            udpBcstRouting OBJECT-TYPE
                SYNTAX INTEGER { disabled(1), enabled(2) }
                ACCESS read-write
                STATUS mandatory
                DESCRIPTION
                    "The indication of whether this entity forwards UDP 
                    broadcasts."
                DEFVAL { disabled }
                ::= { xRouterUdp 3 }


            -- the Router Policy group

            -- Implementation of this group is mandatory for all iTouch
            -- systems that implement routing policy and do through
            -- routing

            -- the Router Policy group contains three subgroups:

            xImport OBJECT IDENTIFIER ::= { xRouterPolicy 1 }
            xExport OBJECT IDENTIFIER ::= { xRouterPolicy 2 }
            xFilter OBJECT IDENTIFIER ::= { xRouterPolicy 3 }

            -- the Import subgroup

            -- the EGP Import table

            impEgpRuleTable OBJECT-TYPE
                SYNTAX SEQUENCE OF ImpEgpRuleEntry
                ACCESS not-accessible
                STATUS mandatory
                DESCRIPTION
                    "The EGP import table."
                ::= { xImport 1 }

            impEgpRuleEntry OBJECT-TYPE
                SYNTAX ImpEgpRuleEntry
                ACCESS not-accessible
                STATUS mandatory
                DESCRIPTION
                    "An EGP import rule.  Each rule is keyed by the 
                    Autonomous System of the EGP neighbor and the IP 
                    network of the route learned from the  neighbor.  
                    The AS can be set to a wild card as can the IP 
                    network. When a route is learned from a neighbor, 
                    the most specific import rule is applied to the 
                    route.  The route is either accepted or discarded 
                    and its metrics are applied according to the rule.  
                    An exact match on the AS and IP network is the most 
                    exact rule.  An exact match on the AS and a wild 
                    card match on the IP network is the 2nd most exact 
                    rule. A wild card match on the AS and an exact match 
                    on the IP network is the 3rd most exact match.  
                    Finally, a total wild card match is the least exact 
                    rule."
                INDEX { impEgpRuleAs, impEgpRuleNetwork }
                ::= { impEgpRuleTable 1 }

            ImpEgpRuleEntry ::=
                SEQUENCE { 
                    impEgpRuleAs
                        INTEGER,
                    impEgpRuleNetwork
                        IpAddress,
                    impEgpRuleAction
                        INTEGER,
                    impEgpRulePreference
                        INTEGER,
                    impEgpRuleType
                        INTEGER,
                    impEgpRuleMetricAction
                        INTEGER,
                    impEgpRuleMetric
                        INTEGER,
                    impEgpRuleStatus
                        INTEGER
                }

            impEgpRuleAs OBJECT-TYPE
                SYNTAX INTEGER ( 0..65535 )
                ACCESS read-only
                STATUS mandatory
                DESCRIPTION
                    "The Autonomous System of the neighbor.  The value 
                    65535 is a wild card matching any AS number."
                ::= { impEgpRuleEntry 1 }

            impEgpRuleNetwork OBJECT-TYPE
                SYNTAX IpAddress
                ACCESS read-only
                STATUS mandatory
                DESCRIPTION
                    "The IP network learned from the neighbor.  The 
                    value 255.255.255.255 is a wild card matching any 
                    network."
                ::= { impEgpRuleEntry 2 }

            impEgpRuleAction OBJECT-TYPE
                SYNTAX INTEGER { discard(1), accept(2) }
                ACCESS read-write
                STATUS mandatory
                DESCRIPTION
                    "Control whether the route is learned or 
                    discarded."
                DEFVAL { accept }
                ::= { impEgpRuleEntry 3 }

            impEgpRulePreference OBJECT-TYPE
                SYNTAX INTEGER ( 1..255 )
                ACCESS read-write
                STATUS mandatory
                DESCRIPTION
                    "Preference to be stored with the route. The lower 
                    preference is preferred."
                DEFVAL { 2 }
                ::= { impEgpRuleEntry 4 }

            impEgpRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impEgpRuleEntry 5 }

            impEgpRuleMetricAction OBJECT-TYPE
                SYNTAX INTEGER { replace(1), increment(2),
                                 decrement(3) }
                ACCESS read-write
                STATUS mandatory
                DESCRIPTION
                    "How to apply the impEgpRuleMetric field to the 
                    metric learned with the route before storing it in 
                    the routing table."
                DEFVAL { increment }
                ::= { impEgpRuleEntry 6 }

            impEgpRuleMetric OBJECT-TYPE
                SYNTAX INTEGER (0..16777215)
                ACCESS read-write
                STATUS mandatory
                DESCRIPTION
                    "Metric value to be applied to the metric learned 
                    learned with the route before storing it in the 
                    routing table."
                DEFVAL { 0 }
                ::= { impEgpRuleEntry 7 }

            impEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impEgpRuleEntry 8 }

            -- the OSPF Import table

            impOspfRuleTable OBJECT-TYPE
                SYNTAX SEQUENCE OF ImpOspfRuleEntry
                ACCESS not-accessible
                STATUS mandatory
                DESCRIPTION
                    "The OSPF import table."
                ::= { xImport 2 }

            impOspfRuleEntry OBJECT-TYPE
                SYNTAX ImpOspfRuleEntry
                ACCESS not-accessible
                STATUS mandatory
                DESCRIPTION
                    "An OSPF import rule.  Each rule is keyed by the IP 
                    network of the route and the AS from which it was 
                    learned.  The Ip network and the AS can both be set 
                    to a wild card.  When an OSPF route is added to the 
                    routing table, the most specific import rule is 
                    applied to set the preference of the route.  An 
                    exact match on the Ip network and on the AS is the 
                    most exact rule.  An exact match on the IP network 
                    and a wild card match on the AS is the 2nd most 
                    exact rule.  A wild card match on both the  on the 
                    AS and IP network is the next and least exact 
                    rule."
                INDEX { impOspfRuleNetwork }
                ::= { impOspfRuleTable 1 }

            ImpOspfRuleEntry ::=
                SEQUENCE {
                    impOspfRuleNetwork
                        IpAddress,
                    impOspfRulePreference
                        INTEGER,
                    impOspfRuleStatus
                        INTEGER
                }

            impOspfRuleNetwork OBJECT-TYPE
                SYNTAX IpAddress
                ACCESS read-only
                STATUS mandatory
                DESCRIPTION
                    "The IP network of the route.  The value 
                    255.255.255.255 is a wild card matching any 
                    network."
                ::= { impOspfRuleEntry 1 }

            impOspfRulePreference OBJECT-TYPE
                SYNTAX INTEGER ( 1..255 )
                ACCESS read-write
                STATUS mandatory
                DESCRIPTION
                    "Preference to be stored with the route. The lower 
                    preference is preferred."
                DEFVAL { 8 }
                ::= { impOspfRuleEntry 2 }

            impOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impOspfRuleEntry 3 }

            -- the RIP Import table

            impRipRuleTable OBJECT-TYPE
                SYNTAX SEQUENCE OF ImpRipRuleEntry
                ACCESS not-accessible
                STATUS mandatory
                DESCRIPTION
                    "The RIP import table."
                ::= { xImport 3 }

            impRipRuleEntry OBJECT-TYPE
                SYNTAX ImpRipRuleEntry
                ACCESS not-accessible
                STATUS mandatory
                DESCRIPTION
                    "A RIP import rule.  Each rule is keyed by the 
                    interface and the IP network of the route learned 
                    from the neighbor.  The route is either accepted or 
                    discarded and its metrics are applied according to 
                    the rule.  An exact match on the IP network is the 
                    rule that will be applied.  If an exact match does 
                    not exist, the rule with the wild card IP network is 
                    used."
                INDEX { impRipRuleFromIf, impRipRuleNetwork }
                ::= { impRipRuleTable 1 }

            ImpRipRuleEntry ::=
                SEQUENCE {
                    impRipRuleFromIf
                        IpAddress,
                    impRipRuleNetwork
                        IpAddress,
                    impRipRuleAction
                        INTEGER,
                    impRipRulePreference
                        INTEGER,
                    impRipRuleType
                        INTEGER,
                    impRipRuleMetricAction
                        INTEGER,
                    impRipRuleMetric
                        INTEGER,
                    impRipRuleStatus
                        INTEGER
                }

            impRipRuleFromIf OBJECT-TYPE
                SYNTAX IpAddress
                ACCESS read-only
                STATUS mandatory
                DESCRIPTION
                    "The interface index of the interface where the rule 
                    applies, same as ifIndex."
                ::= { impRipRuleEntry 1 }

            impRipRuleNetwork OBJECT-TYPE
                SYNTAX IpAddress
                ACCESS read-only
                STATUS mandatory
                DESCRIPTION
                    "The IP network learned from the neighbor.  The 
                    value 255.255.255.255 is a wild card matching any 
                    network."
                ::= { impRipRuleEntry 2 }

            impRipRuleAction OBJECT-TYPE
                SYNTAX INTEGER { discard(1), accept(2) }
                ACCESS read-write
                STATUS mandatory
                DESCRIPTION
                    "Control whether the route is learned or 
                    discarded."
                DEFVAL { accept }
                ::= { impRipRuleEntry 3 }

            impRipRulePreference OBJECT-TYPE
                SYNTAX INTEGER ( 0..255 )
                ACCESS read-write
                STATUS mandatory
                DESCRIPTION
                    "Preference to be stored with the route. The lower 
                    preference are preferred."
                DEFVAL { 12 }
                ::= { impRipRuleEntry 4 }

            impRipRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impRipRuleEntry 5 }

            impRipRuleMetricAction OBJECT-TYPE
                SYNTAX INTEGER { replace(1), increment(2), decrement(3) }
                ACCESS read-write
                STATUS mandatory
                DESCRIPTION
                    "How to apply the impRipRuleMetric field to the 
                    metric learned with the route before storing it in 
                    the routing table."
                DEFVAL { increment }
                ::= { impRipRuleEntry 6 }

            impRipRuleMetric OBJECT-TYPE
                SYNTAX INTEGER (0..16777215)
                ACCESS read-write
                STATUS mandatory
                DESCRIPTION
                    "Metric value to be applied to the metric learned 
                    learned with the route before storing it in the 
                    routing table."
                DEFVAL { 0 }
                ::= { impRipRuleEntry 7 }

            impRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { impRipRuleEntry 8 }

            -- the ISIS Import table

            impIsisRuleTable OBJECT-TYPE
            	SYNTAX SEQUENCE OF ImpIsisRuleEntry
            	ACCESS not-accessible
            	STATUS mandatory
            	DESCRIPTION
            		"The Isis import table."
            	::= { xImport 4 }
            
            impIsisRuleEntry OBJECT-TYPE
            	SYNTAX ImpIsisRuleEntry
            	ACCESS not-accessible
            	STATUS mandatory
            	DESCRIPTION
            		"An Isis import rule.  Each rule is keyed by the IP
                    network of the route learned from the neighbor.  The
                    route is either accepted or discarded and its metrics
                    are applied according to the rule.  An exact match on the
                    IP network is the rule that will be applied.  If an exact
            		match does not exist, the rule with the wild card IP
                    network is used."
            	INDEX { impIsisRuleNetwork }
            	::= { impIsisRuleTable 1 }
            
            ImpIsisRuleEntry ::=
            	SEQUENCE {
            		impIsisRuleNetwork
            			IpAddress,
            		impIsisRuleAction
            			INTEGER,
            		impIsisRulePreference
            			INTEGER,
            		impIsisRuleType
            			INTEGER,
            		impIsisRuleMetricAction
            			INTEGER,
            		impIsisRuleMetric
            			INTEGER,
            		impIsisRuleStatus
            			INTEGER
            	}
            
            impIsisRuleNetwork OBJECT-TYPE
            	SYNTAX IpAddress
            	ACCESS read-only
            	STATUS mandatory
            	DESCRIPTION
            		"The IP network learned from the neighbor.  The value
                    255.255.255.255 is a wild card matching any network."
            	::= { impIsisRuleEntry 1 }
            
            impIsisRuleAction OBJECT-TYPE
            	SYNTAX INTEGER { discard(1), accept(2) }
            	ACCESS read-write
            	STATUS mandatory
            	DESCRIPTION
            		"Control whether the route is learned or discarded."
            	DEFVAL { accept }
            	::= { impIsisRuleEntry 2 }
            
            impIsisRulePreference OBJECT-TYPE
            	SYNTAX INTEGER ( 0..255 )
            	ACCESS read-write
            	STATUS mandatory
            	DESCRIPTION
            		"Preference to be stored with the route. The lower
                    preference are preferred."
            	DEFVAL { 6 }
            	::= { impIsisRuleEntry 3 }
            
            impIsisRuleType OBJECT-TYPE
            	SYNTAX INTEGER ( 1..2 )
            	ACCESS read-write
            	STATUS mandatory
            	DESCRIPTION
            		"Type to be stored with the route. The type is based on
                    the OSPF external type and used to help compare metrics.
                    Type 1 is preferred over type 2."
            	DEFVAL { 1 }
            	::= { impIsisRuleEntry 4 }
            
            impIsisRuleMetricAction OBJECT-TYPE
            	SYNTAX INTEGER { replace(1), increment(2), decrement(3) }
            	ACCESS read-write
            	STATUS mandatory
            	DESCRIPTION
            		"How to apply the impIsisRuleMetric field to the metric
                    learned with the route before storing it in the routing
                    table."
            	DEFVAL { increment }
            	::= { impIsisRuleEntry 5 }
            
            impIsisRuleMetric OBJECT-TYPE
            	SYNTAX INTEGER 
            	ACCESS read-write
            	STATUS mandatory
            	DESCRIPTION
            		"Metric value to be applied to the metric learned learned
                    with the route before storing it in the routing table."
            	DEFVAL { 0 }
            	::= { impIsisRuleEntry 6 }
            
            impIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { impIsisRuleEntry 7 }


            -- the Export subgroup

            expEgpToEgpRuleTable OBJECT-TYPE
                SYNTAX SEQUENCE OF ExpEgpToEgpRuleEntry
                ACCESS not-accessible
                STATUS mandatory
                DESCRIPTION
                    "The EGP to EGP export table."
                ::= { xExport 1 }

            expEgpToEgpRuleEntry OBJECT-TYPE
                SYNTAX ExpEgpToEgpRuleEntry
                ACCESS not-accessible
                STATUS mandatory
                DESCRIPTION
                    "An EGP to EGP export rule.  Each rule is keyed by 
                    the Autonomous  System of the EGP neighbor, the IP 
                    network of the EGP route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows: 

                            To As  IP Network     From AS  Rank

                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expEgpToEgpRuleToAs, expEgpToEgpRuleNetwork,
                        expEgpToEgpRuleFromAs }
                ::= { expEgpToEgpRuleTable 1 }

            ExpEgpToEgpRuleEntry ::=
                SEQUENCE {
                    expEgpToEgpRuleToAs
                        INTEGER,
                    expEgpToEgpRuleNetwork
                        IpAddress,
                    expEgpToEgpRuleFromAs
                        INTEGER,
                    expEgpToEgpRuleAction
                        INTEGER,
                    expEgpToEgpRuleMetricAction
                        INTEGER,
                    expEgpToEgpRuleMetric
                        INTEGER,
                    expEgpToEgpRuleStatus
                        INTEGER
                }

            expEgpToEgpRuleToAs OBJECT-TYPE
                SYNTAX INTEGER ( 0..65535 )
                ACCESS read-only
                STATUS mandatory
                DESCRIPTION
                    "The Autonomous System of the neighbor.  The value 
                    65535 is  a wild card matching any AS number."
                ::= { expEgpToEgpRuleEntry 1 }

            expEgpToEgpRuleNetwork OBJECT-TYPE
                SYNTAX IpAddress 
                ACCESS read-only
                STATUS mandatory
                DESCRIPTION
                    "The IP network of the route in the route table.  
                    The value 255.255.255.255 is a wild card matching 
                    any network."
                ::= { expEgpToEgpRuleEntry 2 }

            expEgpToEgpRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToEgpRuleEntry 3 }

            expEgpToEgpRuleAction OBJECT-TYPE
                SYNTAX INTEGER { hide(1), advertise(2) }
                ACCESS read-write
                STATUS mandatory
                DESCRIPTION
                    "Control whether the route is advertised or not."
                DEFVAL { advertise }
                ::= { expEgpToEgpRuleEntry 4 }

            expEgpToEgpRuleMetricAction OBJECT-TYPE
                SYNTAX INTEGER { replace(1), increment(2),
                                 decrement(3) }
                ACCESS read-write
                STATUS mandatory
                DESCRIPTION
                    "How to apply the expEgpToEgpRuleMetric field to the 
                    metric in the route table entry before the route is 
                    advertised."
                DEFVAL { increment }
                ::= { expEgpToEgpRuleEntry 5 }

            expEgpToEgpRuleMetric OBJECT-TYPE
                SYNTAX INTEGER (0..16777215)
                ACCESS read-write
                STATUS mandatory
                DESCRIPTION
                    "Metric value to be applied to the metric in the 
                    route table entry before the route is advertised."
                DEFVAL { 0 }
                ::= { expEgpToEgpRuleEntry 6 }

            expEgpToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToEgpRuleEntry 7 }

            -- ospf to egp

            expOspfToEgpRuleTable OBJECT-TYPE
                SYNTAX SEQUENCE OF ExpOspfToEgpRuleEntry
                ACCESS not-accessible
                STATUS mandatory
                DESCRIPTION
                    "The OSPF to EGP export table."
                ::= { xExport 2 }

            expOspfToEgpRuleEntry OBJECT-TYPE
                SYNTAX ExpOspfToEgpRuleEntry
                ACCESS not-accessible
                STATUS mandatory
                DESCRIPTION
                    "An OSPF to EGP export rule.  Each rule is keyed by 
                    the Autonomous  System of the EGP neighbor, the IP 
                    network of the OSPF route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows:

                            To As  IP Network     From AS  Rank

                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expOspfToEgpRuleToAs, expOspfToEgpRuleNetwork,
                        expOspfToEgpRuleFromAs }
                ::= { expOspfToEgpRuleTable 1 }

            ExpOspfToEgpRuleEntry ::=
                SEQUENCE {
                    expOspfToEgpRuleToAs
                        INTEGER,
                    expOspfToEgpRuleNetwork
                        IpAddress,
                    expOspfToEgpRuleFromAs
                        INTEGER,
                    expOspfToEgpRuleAction
                        INTEGER,
                    expOspfToEgpRuleMetricAction
                        INTEGER,
                    expOspfToEgpRuleMetric
                        INTEGER,
                    expOspfToEgpRuleStatus
                        INTEGER
                }

            expOspfToEgpRuleToAs OBJECT-TYPE
                SYNTAX INTEGER ( 0..65535 )
                ACCESS read-only
                STATUS mandatory
                DESCRIPTION
                    "The Autonomous System of the neighbor.  The value 
                    65535 is  a wild card matching any AS number."
                ::= { expOspfToEgpRuleEntry 1 }

            expOspfToEgpRuleNetwork OBJECT-TYPE
                SYNTAX IpAddress
                ACCESS read-only
                STATUS mandatory
                DESCRIPTION
                    "The IP network of the route in the route table.  
                    The value 255.255.255.255 is a wild card matching 
                    any network."
                ::= { expOspfToEgpRuleEntry 2 }

            expOspfToEgpRuleFromAs OBJECT-TYPE
                SYNTAX INTEGER ( 0..65535 )
                ACCESS read-only
                STATUS mandatory
                DESCRIPTION
                    "The Autonomous System of the route in the route 
                    table.  Local indicates that the route was not an 
                    external OSPF route.  The  value 65535 is a wild 
                    card matching any AS number, and the value 65534 is 
                    for routes within the local AS."
                ::= { expOspfToEgpRuleEntry 3 }

            expOspfToEgpRuleAction OBJECT-TYPE
                SYNTAX INTEGER { hide(1), advertise(2) }
                ACCESS read-write
                STATUS mandatory
                DESCRIPTION
                    "Control whether the route is advertised or not."
                DEFVAL { advertise }
                ::= { expOspfToEgpRuleEntry 4 }

            expOspfToEgpRuleMetricAction OBJECT-TYPE
                SYNTAX INTEGER { replace(1), increment(2),
                                 decrement(3) }
                ACCESS read-write
                STATUS mandatory
                DESCRIPTION
                    "How to apply the expOspfToEgpRuleMetric field to 
                    the metric in the route table entry before the route 
                    is advertised."
                DEFVAL { increment }
                ::= { expOspfToEgpRuleEntry 5 }

            expOspfToEgpRuleMetric OBJECT-TYPE
                SYNTAX INTEGER (0..16777215)
                ACCESS read-write
                STATUS mandatory
                DESCRIPTION
                    "Metric value to be applied to the metric in the 
                    route table entry before the route is advertised."
                DEFVAL { 0 }
                ::= { expOspfToEgpRuleEntry 6 }

            expOspfToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expOspfToEgpRuleEntry 7 }

            -- static to egp

            expStaticToEgpRuleTable OBJECT-TYPE
                SYNTAX SEQUENCE OF ExpStaticToEgpRuleEntry
                ACCESS not-accessible
                STATUS mandatory
                DESCRIPTION
                    "The Static to EGP export table."
                ::= { xExport 3 }

            expStaticToEgpRuleEntry OBJECT-TYPE
                SYNTAX ExpStaticToEgpRuleEntry
                ACCESS not-accessible
                STATUS mandatory
                DESCRIPTION
                    "An Static to EGP export rule.  Each rule is keyed 
                    by the Autonomous  System of the EGP neighbor and 
                    the IP network of the Static route in the  routing 
                    table.  The neighbor (to) AS can be set to a wild 
                    card as can the IP network.  The route is either 
                    accepted to be advertised to the  neighbor or 
                    discarded from being advertised, and its metric is 
                    applied  according to the rule.  The best match is 
                    as follows:

                            To As  IP Network  Rank

                            exact       exact   1st
                            exact   wild card   2nd
                        wild card       exact   3rd
                        wild card   wild card   4th
                    "
                INDEX { expStaticToEgpRuleToAs,
                        expStaticToEgpRuleNetwork }
                ::= { expStaticToEgpRuleTable 1 }

            ExpStaticToEgpRuleEntry ::=
                SEQUENCE {
                    expStaticToEgpRuleToAs
                        INTEGER,
                    expStaticToEgpRuleNetwork
                        IpAddress,
                    expStaticToEgpRuleAction
                        INTEGER,
                    expStaticToEgpRuleMetricAction
                        INTEGER,
                    expStaticToEgpRuleMetric
                        INTEGER,
                    expStaticToEgpRuleStatus
                        INTEGER
                }

            expStaticToEgpRuleToAs OBJECT-TYPE
                SYNTAX INTEGER ( 0..65535 )
                ACCESS read-only
                STATUS mandatory
                DESCRIPTION
                    "The Autonomous System of the neighbor.  The value 
                    65535 is  a wild card matching any AS number."
                ::= { expStaticToEgpRuleEntry 1 }

            expStaticToEgpRuleNetwork OBJECT-TYPE
                SYNTAX IpAddress
                ACCESS read-only
                STATUS mandatory
                DESCRIPTION
                    "The IP network of the route in the route table.  
                    The value 255.255.255.255 is a wild card matching 
                    any network."
                ::= { expStaticToEgpRuleEntry 2 }

            expStaticToEgpRuleAction OBJECT-TYPE
                SYNTAX INTEGER { hide(1), advertise(2) }
                ACCESS read-write
                STATUS mandatory
                DESCRIPTION
                    "Control whether the route is advertised or not."
                DEFVAL { advertise }
                ::= { expStaticToEgpRuleEntry 3 }

            expStaticToEgpRuleMetricAction OBJECT-TYPE
                SYNTAX INTEGER { replace(1), increment(2),
                                 decrement(3) }
                ACCESS read-write
                STATUS mandatory
                DESCRIPTION
                    "How to apply the expStaticToEgpRuleMetric field to 
                    the metric in the route table entry before the route 
                    is advertised."
                DEFVAL { increment }
                ::= { expStaticToEgpRuleEntry 4 }

            expStaticToEgpRuleMetric OBJECT-TYPE
                SYNTAX INTEGER (0..16777215)
                ACCESS read-write
                STATUS mandatory
                DESCRIPTION
                    "Metric value to be applied to the metric in the 
                    route table entry before the route is advertised."
                DEFVAL { 0 }
                ::= { expStaticToEgpRuleEntry 5 }

            expStaticToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expStaticToEgpRuleEntry 6 }

            -- egp to ospf

            expEgpToOspfRuleTable OBJECT-TYPE
                SYNTAX SEQUENCE OF ExpEgpToOspfRuleEntry
                ACCESS not-accessible
                STATUS mandatory
                DESCRIPTION
                    "The EGP to OSPF export table."
                ::= { xExport 4 }

            expEgpToOspfRuleEntry OBJECT-TYPE
                SYNTAX ExpEgpToOspfRuleEntry
                ACCESS not-accessible
                STATUS mandatory
                DESCRIPTION
                    "An EGP to OSPF export rule.  Each rule is keyed by 
                    the IP network  of the EGP route in the routing 
                    table, and the Autonomous System  from which the 
                    route was learned.  The Ip network can be set to a 
                    wild card as can the (from) AS.  The route is either 
                    accepted to be  advertised to the neighbor or 
                    discarded from being advertised, and its metric is 
                    applied according to the rule.  The best match is as  
                    follows:

                       IP Network     From AS  Rank

                            exact       exact   1st
                            exact   wild card   2nd
                        wild card       exact   3rd
                        wild card   wild card   4th
                    "
                INDEX { expEgpToOspfRuleNetwork, expEgpToOspfRuleFromAs }
                ::= { expEgpToOspfRuleTable 1 }

            ExpEgpToOspfRuleEntry ::=
                SEQUENCE {
                    expEgpToOspfRuleNetwork
                        IpAddress,
                    expEgpToOspfRuleFromAs
                        INTEGER,
                    expEgpToOspfRuleAction
                        INTEGER,
                    expEgpToOspfRuleStatus
                        INTEGER
                }

            expEgpToOspfRuleNetwork OBJECT-TYPE
                SYNTAX IpAddress
                ACCESS read-only
                STATUS mandatory
                DESCRIPTION
                    "The IP network of the route in the route table.  
                    The value 255.255.255.255 is a wild card matching 
                    any network."
                ::= { expEgpToOspfRuleEntry 1 }

            expEgpToOspfRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToOspfRuleEntry 2 }

            expEgpToOspfRuleAction OBJECT-TYPE
                SYNTAX INTEGER { hide(1), advertise(2) }
                ACCESS read-write
                STATUS mandatory
                DESCRIPTION
                    "Control whether the route is advertised or not."
                DEFVAL { advertise }
                ::= { expEgpToOspfRuleEntry 3 }

            expEgpToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToOspfRuleEntry 4 }

            -- rip to egp

            expRipToEgpRuleTable OBJECT-TYPE
                SYNTAX SEQUENCE OF ExpRipToEgpRuleEntry
                ACCESS not-accessible
                STATUS mandatory
                DESCRIPTION
                    "The Rip to EGP export table."
                ::= { xExport 5 }

            expRipToEgpRuleEntry OBJECT-TYPE
                SYNTAX ExpRipToEgpRuleEntry
                ACCESS not-accessible
                STATUS mandatory
                DESCRIPTION
                    "An Rip to EGP export rule.  Each rule is keyed by 
                    the Autonomous System of the EGP neighbor and the IP 
                    network of the Rip route in the routing table.  The 
                    neighbor (to) AS can be set to a wild card as can 
                    the IP network.  The route is either accepted to be 
                    advertised to the neighbor or discarded from being 
                    advertised, and its metric is applied according to 
                    the rule.  The best match is as follows:

                    To As       IP Network   Best Match Rank

                    exact       exact        1st
                    exact       wild card    2nd
                    wild card   exact        3rd
                    wild card   wild card    4th
                    "
                INDEX { expRipToEgpRuleToAs,
                        expRipToEgpRuleNetwork }
                ::= { expRipToEgpRuleTable 1 }

            ExpRipToEgpRuleEntry ::=
                SEQUENCE {
                    expRipToEgpRuleToAs
                        INTEGER,
                    expRipToEgpRuleNetwork
                        IpAddress,
                    expRipToEgpRuleAction
                        INTEGER,
                    expRipToEgpRuleMetricAction
                        INTEGER,
                    expRipToEgpRuleMetric
                        INTEGER,
                    expRipToEgpRuleStatus
                        INTEGER
                }

            expRipToEgpRuleToAs OBJECT-TYPE
                SYNTAX INTEGER ( 0..65535 )
                ACCESS read-only
                STATUS mandatory
                DESCRIPTION
                    "The Autonomous System of the neighbor.  The value 
                    65535 is a wild card matching any AS number."
                ::= { expRipToEgpRuleEntry 1 }

            expRipToEgpRuleNetwork OBJECT-TYPE
                SYNTAX IpAddress
                ACCESS read-only
                STATUS mandatory
                DESCRIPTION
                    "The IP network of the route in the route table.  
                    The value 255.255.255.255 is a wild card matching 
                    any network."
                ::= { expRipToEgpRuleEntry 2 }

            expRipToEgpRuleAction OBJECT-TYPE
                SYNTAX INTEGER { hide(1), advertise(2) }
                ACCESS read-write
                STATUS mandatory
                DESCRIPTION
                    "Control whether the route is advertised or not."
                DEFVAL { advertise }
                ::= { expRipToEgpRuleEntry 3 }

            expRipToEgpRuleMetricAction OBJECT-TYPE
                SYNTAX INTEGER { replace(1), increment(2), decrement(3) }
                ACCESS read-write
                STATUS mandatory
                DESCRIPTION
                    "How to apply the expRipToEgpRuleMetric field to the 
                    metric in the route table entry before the route is 
                    advertised."
                DEFVAL { increment }
                ::= { expRipToEgpRuleEntry 4 }

            expRipToEgpRuleMetric OBJECT-TYPE
                SYNTAX INTEGER (0..16777215)
                ACCESS read-write
                STATUS mandatory
                DESCRIPTION
                    "Metric value to be applied to the metric in the 
                    route table entry before the route is advertised."
                DEFVAL { 0 }
                ::= { expRipToEgpRuleEntry 5 }

            expRipToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToEgpRuleEntry 6 }

            -- rip to ospf

            expRipToOspfRuleTable OBJECT-TYPE
                SYNTAX SEQUENCE OF ExpRipToOspfRuleEntry
                ACCESS not-accessible
                STATUS mandatory
                DESCRIPTION
                    "The RIP to OSPF export table."
                ::= { xExport 6 }

            expRipToOspfRuleEntry OBJECT-TYPE
                SYNTAX ExpRipToOspfRuleEntry
                ACCESS not-accessible
                STATUS mandatory
                DESCRIPTION
                    "A RIP to OSPF export rule.  Each rule is keyed by 
                    the IP network of the RIP route in the routing 
                    table.  The IP network can be set to a wild card.  
                    The route is either accepted to be advertised to the 
                    neighbor or discarded from being advertised, and its 
                    metric is applied according to the rule.  The best 
                    match is as follows:

                    IP Network     Best Match Rank

                    exact          1st
                    wild card      2nd
                    "
                INDEX { expRipToOspfRuleNetwork }
                ::= { expRipToOspfRuleTable 1 }

            ExpRipToOspfRuleEntry ::=
                SEQUENCE {
                    expRipToOspfRuleNetwork
                        IpAddress,
                    expRipToOspfRuleAction
                        INTEGER,
                    expRipToOspfRuleStatus
                        INTEGER
                }

            expRipToOspfRuleNetwork OBJECT-TYPE
                SYNTAX IpAddress
                ACCESS read-only
                STATUS mandatory
                DESCRIPTION
                    "The IP network of the route in the route table.  
                    The value 255.255.255.255 is a wild card matching 
                    any network."
                ::= { expRipToOspfRuleEntry 1 }

            expRipToOspfRuleAction OBJECT-TYPE
                SYNTAX INTEGER { hide(1), advertise(2) }
                ACCESS read-write
                STATUS mandatory
                DESCRIPTION
                    "Control whether the route is advertised or not."
                DEFVAL { advertise }
                ::= { expRipToOspfRuleEntry 2 }

            expRipToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToOspfRuleEntry 3 }


            -- egp to rip

            expEgpToRipRuleTable OBJECT-TYPE
                SYNTAX SEQUENCE OF ExpEgpToRipRuleEntry
                ACCESS not-accessible
                STATUS mandatory
                DESCRIPTION
                    "The EGP to RIP export table."
                ::= { xExport 7 }

            expEgpToRipRuleEntry OBJECT-TYPE
                SYNTAX ExpEgpToRipRuleEntry
                ACCESS not-accessible
                STATUS mandatory
                DESCRIPTION
                    "An EGP to RIP export rule.  Each rule is keyed by 
                    the Autonomous System of the EGP neighbor, the IP 
                    network of the EGP route in the routing table, and 
                    the Autonomous System from which the route was 
                    learned.  The IP network can be set to a wild card 
                    as can the the from AS.  The route is either 
                    accepted to be advertised to the neighbor or 
                    discarded from being advertised, and its metric is 
                    applied according to the rule.  The best match is as 
                    follows:

                    IP Network   From AS     Best Match Rank

                    exact        exact       1st
                    exact        wild card   2nd
                    wild card    exact       3rd
                    wild card    wild card   4th
                    "
                INDEX { expEgpToRipRuleToIf, expEgpToRipRuleNetwork,
                        expEgpToRipRuleFromAs }
                ::= { expEgpToRipRuleTable 1 }

            ExpEgpToRipRuleEntry ::=
                SEQUENCE {
                    expEgpToRipRuleToIf
                        IpAddress,
                    expEgpToRipRuleNetwork
                        IpAddress,
                    expEgpToRipRuleFromAs
                        INTEGER,
                    expEgpToRipRuleAction
                        INTEGER,
                    expEgpToRipRuleMetricAction
                        INTEGER,
                    expEgpToRipRuleMetric
                        INTEGER,
                    expEgpToRipRuleStatus
                        INTEGER
                }

            expEgpToRipRuleToIf OBJECT-TYPE
                SYNTAX IpAddress 
                ACCESS read-only
                STATUS mandatory
                DESCRIPTION
                    "The IP address of the RIP interface to which the 
                    rule applies."
                ::= { expEgpToRipRuleEntry 1 }

            expEgpToRipRuleNetwork OBJECT-TYPE
                SYNTAX IpAddress 
                ACCESS read-only
                STATUS mandatory
                DESCRIPTION
                    "The IP network of the route in the route table.  
                    The value 255.255.255.255 is a wild card matching 
                    any network."
                ::= { expEgpToRipRuleEntry 2 }

            expEgpToRipRuleFromAs OBJECT-TYPE
                SYNTAX INTEGER ( 0..65535 )
                ACCESS read-only
                STATUS mandatory
                DESCRIPTION
                    "The Autonomous System of the route in the route 
                    table.  The value 65535 is a wild card matching any 
                    AS number."
                ::= { expEgpToRipRuleEntry 3 }

            expEgpToRipRuleAction OBJECT-TYPE
                SYNTAX INTEGER { hide(1), advertise(2) }
                ACCESS read-write
                STATUS mandatory
                DESCRIPTION
                    "Control whether the route is advertised or not."
                DEFVAL { advertise }
                ::= { expEgpToRipRuleEntry 4 }

            expEgpToRipRuleMetricAction OBJECT-TYPE
                SYNTAX INTEGER { replace(1), increment(2), decrement(3) }
                ACCESS read-write
                STATUS mandatory
                DESCRIPTION
                    "How to apply the expEgpToRipRuleMetric field to the 
                    metric in the route table entry before the route is 
                    advertised."
                DEFVAL { increment }
                ::= { expEgpToRipRuleEntry 5 }

            expEgpToRipRuleMetric OBJECT-TYPE
                SYNTAX INTEGER (0..16777215)
                ACCESS read-write
                STATUS mandatory
                DESCRIPTION
                    "Metric value to be applied to the metric in the 
                    route table entry before the route is advertised."
                DEFVAL { 0 }
                ::= { expEgpToRipRuleEntry 6 }

            expEgpToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expEgpToRipRuleEntry 7 }

            -- Ospf to rip

            expOspfToRipRuleTable OBJECT-TYPE
                SYNTAX SEQUENCE OF ExpOspfToRipRuleEntry
                ACCESS not-accessible
                STATUS mandatory
                DESCRIPTION
                    "The OSPF to RIP export table."
                ::= { xExport 8 }

            expOspfToRipRuleEntry OBJECT-TYPE
                SYNTAX ExpOspfToRipRuleEntry
                ACCESS not-accessible
                STATUS mandatory
                DESCRIPTION
                    "An Ospf to RIP export rule.  Each rule is keyed by 
                    the Autonomous System of the Ospf neighbor, the IP 
                    network of the Ospf route in the routing table, and 
                    the Autonomous System from which the route was 
                    learned.  The IP network can be set to a wild card 
                    as can the the from AS.  The route is either 
                    accepted to be advertised to the neighbor or 
                    discarded from being advertised, and its metric is 
                    applied according to the rule.  The best match is as 
                    follows:

                    IP Network   From AS     Best Match Rank

                    exact        exact       1st
                    exact        wild card   2nd
                    wild card    exact       3rd
                    wild card    wild card   4th
                    "
                INDEX { expOspfToRipRuleToIf, expOspfToRipRuleNetwork,
                        expOspfToRipRuleFromAs }
                ::= { expOspfToRipRuleTable 1 }

            ExpOspfToRipRuleEntry ::=
                SEQUENCE {
                    expOspfToRipRuleToIf
                        IpAddress,
                    expOspfToRipRuleNetwork
                        IpAddress,
                    expOspfToRipRuleFromAs
                        INTEGER,
                    expOspfToRipRuleAction
                        INTEGER,
                    expOspfToRipRuleMetricAction
                        INTEGER,
                    expOspfToRipRuleMetric
                        INTEGER,
                    expOspfToRipRuleStatus
                        INTEGER
                }

            expOspfToRipRuleToIf OBJECT-TYPE
                SYNTAX IpAddress
                ACCESS read-only
                STATUS mandatory
                DESCRIPTION
                    "The IP address of the RIP interface to which the 
                    rule applies."
                ::= { expOspfToRipRuleEntry 1 }

            expOspfToRipRuleNetwork OBJECT-TYPE
                SYNTAX IpAddress 
                ACCESS read-only
                STATUS mandatory
                DESCRIPTION
                    "The IP network of the route in the route table.  
                    The value 255.255.255.255 is a wild card matching 
                    any network."
                ::= { expOspfToRipRuleEntry 2 }

            expOspfToRipRuleFromAs OBJECT-TYPE
                SYNTAX INTEGER ( 0..65535 )
                ACCESS read-only
                STATUS mandatory
                DESCRIPTION
                    "The Autonomous System of the route in the route 
                    table.  The value 65535 is a wild card matching any 
                    AS number, and the value 65534 is for routes within 
                    the local AS."
                ::= { expOspfToRipRuleEntry 3 }

            expOspfToRipRuleAction OBJECT-TYPE
                SYNTAX INTEGER { hide(1), advertise(2) }
                ACCESS read-write
                STATUS mandatory
                DESCRIPTION
                    "Control whether the route is advertised or not."
                DEFVAL { advertise }
                ::= { expOspfToRipRuleEntry 4 }

            expOspfToRipRuleMetricAction OBJECT-TYPE
                SYNTAX INTEGER { replace(1), increment(2), decrement(3) }
                ACCESS read-write
                STATUS mandatory
                DESCRIPTION
                    "How to apply the expOspfToRipRuleMetric field to 
                    the metric in the route table entry before the route 
                    is advertised."
                DEFVAL { increment }
                ::= { expOspfToRipRuleEntry 5 }

            expOspfToRipRuleMetric OBJECT-TYPE
                SYNTAX INTEGER (0..16777215)
                ACCESS read-write
                STATUS mandatory
                DESCRIPTION
                    "Metric value to be applied to the metric in the 
                    route table entry before the route is advertised."
                DEFVAL { 0 }
                ::= { expOspfToRipRuleEntry 6 }

            expOspfToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values.  The 
                    same is true for the all wild cards where the AS is 
                    set to local"
                DEFVAL { valid }
                ::= { expOspfToRipRuleEntry 7 }

            -- rip to rip

            expRipToRipRuleTable OBJECT-TYPE
                SYNTAX SEQUENCE OF ExpRipToRipRuleEntry
                ACCESS not-accessible
                STATUS mandatory
                DESCRIPTION
                    "The Rip to Rip export table."
                ::= { xExport 9 }

            expRipToRipRuleEntry OBJECT-TYPE
                SYNTAX ExpRipToRipRuleEntry
                ACCESS not-accessible
                STATUS mandatory
                DESCRIPTION
                    "An Rip to Rip export rule.  Each rule is keyed by 
                    the IP network of the Rip route in the routing 
                    table.  The neighbor IP network can be set to a wild 
                    card.  The route is either accepted to be advertised 
                    to the neighbor or discarded from being advertised, 
                    and its metric is applied according to the rule.  
                    The best match is as follows:

                    IP Network   Best Match Rank

                    exact        1st
                    wild card    2nd
                    "
                INDEX { expRipToRipRuleToIf, expRipToRipRuleNetwork }
                ::= { expRipToRipRuleTable 1 }

            ExpRipToRipRuleEntry ::=
                SEQUENCE {
                    expRipToRipRuleToIf
                        IpAddress,
                    expRipToRipRuleNetwork
                        IpAddress,
                    expRipToRipRuleAction
                        INTEGER,
                    expRipToRipRuleMetricAction
                        INTEGER,
                    expRipToRipRuleMetric
                        INTEGER,
                    expRipToRipRuleStatus
                        INTEGER
                }

            expRipToRipRuleToIf OBJECT-TYPE
                SYNTAX IpAddress
                ACCESS read-only
                STATUS mandatory
                DESCRIPTION
                    "The IP address of the RIP interface to which the 
                    rule applies."
                ::= { expRipToRipRuleEntry 1 }

            expRipToRipRuleNetwork OBJECT-TYPE
                SYNTAX IpAddress
                ACCESS read-only
                STATUS mandatory
                DESCRIPTION
                    "The IP network of the route in the route table.  
                    The value 255.255.255.255 is a wild card matching 
                    any network."
                ::= { expRipToRipRuleEntry 2 }

            expRipToRipRuleAction OBJECT-TYPE
                SYNTAX INTEGER { hide(1), advertise(2) }
                ACCESS read-write
                STATUS mandatory
                DESCRIPTION
                    "Control whether the route is advertised or not."
                DEFVAL { advertise }
                ::= { expRipToRipRuleEntry 3 }

            expRipToRipRuleMetricAction OBJECT-TYPE
                SYNTAX INTEGER { replace(1), increment(2), decrement(3) }
                ACCESS read-write
                STATUS mandatory
                DESCRIPTION
                    "How to apply the expRipToRipRuleMetric field to the 
                    metric in the route table entry before the route is 
                    advertised."
                DEFVAL { increment }
                ::= { expRipToRipRuleEntry 4 }

            expRipToRipRuleMetric OBJECT-TYPE
                SYNTAX INTEGER (0..16777215)
                ACCESS read-write
                STATUS mandatory
                DESCRIPTION
                    "Metric value to be applied to the metric in the 
                    route table entry before the route is advertised."
                DEFVAL { 0 }
                ::= { expRipToRipRuleEntry 5 }

            expRipToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToRipRuleEntry 6 }

            -- static to rip

            expStaticToRipRuleTable OBJECT-TYPE
                SYNTAX SEQUENCE OF ExpStaticToRipRuleEntry
                ACCESS not-accessible
                STATUS mandatory
                DESCRIPTION
                    "The Static to Rip export table."
                ::= { xExport 10 }

            expStaticToRipRuleEntry OBJECT-TYPE
                SYNTAX ExpStaticToRipRuleEntry
                ACCESS not-accessible
                STATUS mandatory
                DESCRIPTION
                    "An Static to Rip export rule.  Each rule is keyed 
                    by the IP network of the Static route in the routing 
                    table.  The neighbor IP network can be set to a wild 
                    card.  The route is either accepted to be advertised 
                    to the neighbor or discarded from being advertised, 
                    and its metric is applied according to the rule.  
                    The best match is as follows:

                    IP Network   Best Match Rank

                    exact        1st
                    wild card    2nd
                    "
                INDEX { expStaticToRipRuleToIf,
                        expStaticToRipRuleNetwork }
                ::= { expStaticToRipRuleTable 1 }

            ExpStaticToRipRuleEntry ::=
                SEQUENCE {
                    expStaticToRipRuleToIf
                        IpAddress,
                    expStaticToRipRuleNetwork
                        IpAddress,
                    expStaticToRipRuleAction
                        INTEGER,
                    expStaticToRipRuleMetricAction
                        INTEGER,
                    expStaticToRipRuleMetric
                        INTEGER,
                    expStaticToRipRuleStatus
                        INTEGER
                }

            expStaticToRipRuleToIf OBJECT-TYPE
                SYNTAX IpAddress
                ACCESS read-only
                STATUS mandatory
                DESCRIPTION
                    "The IP address of the RIP interface to which the 
                    rule applies."
                ::= { expStaticToRipRuleEntry 1 }

            expStaticToRipRuleNetwork OBJECT-TYPE
                SYNTAX IpAddress
                ACCESS read-only
                STATUS mandatory
                DESCRIPTION
                    "The IP network of the route in the route table.  
                    The value 255.255.255.255 is a wild card matching 
                    any network."
                ::= { expStaticToRipRuleEntry 2 }

            expStaticToRipRuleAction OBJECT-TYPE
                SYNTAX INTEGER { hide(1), advertise(2) }
                ACCESS read-write
                STATUS mandatory
                DESCRIPTION
                    "Control whether the route is advertised or not."
                DEFVAL { advertise }
                ::= { expStaticToRipRuleEntry 3 }

            expStaticToRipRuleMetricAction OBJECT-TYPE
                SYNTAX INTEGER { replace(1), increment(2), decrement(3) }
                ACCESS read-write
                STATUS mandatory
                DESCRIPTION
                    "How to apply the expStaticToRipRuleMetric field to 
                    the metric in the route table entry before the route 
                    is advertised."
                DEFVAL { increment }
                ::= { expStaticToRipRuleEntry 4 }

            expStaticToRipRuleMetric OBJECT-TYPE
                SYNTAX INTEGER (0..16777215)
                ACCESS read-write
                STATUS mandatory
                DESCRIPTION
                    "Metric value to be applied to the metric in the 
                    route table entry before the route is advertised."
                DEFVAL { 0 }
                ::= { expStaticToRipRuleEntry 5 }

            expStaticToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expStaticToRipRuleEntry 6 }

            -- Isis to egp
            
            expIsisToEgpRuleTable OBJECT-TYPE
            	SYNTAX SEQUENCE OF ExpIsisToEgpRuleEntry
            	ACCESS not-accessible
            	STATUS mandatory
            	DESCRIPTION
            		"The Isis to EGP export table."
            	::= { xExport 11 }
            
            expIsisToEgpRuleEntry OBJECT-TYPE
            	SYNTAX ExpIsisToEgpRuleEntry
            	ACCESS not-accessible
            	STATUS mandatory
            	DESCRIPTION
            		"An Isis to EGP export rule.  Each rule is keyed by the Autonomous 
            		System of the EGP neighbor and the IP network of the Isis route in the 
            		routing table.  The neighbor (to) AS can be set to a wild card as can
            		the IP network.  The route is either accepted to be advertised to the 
            		neighbor or discarded from being advertised, and its metric is applied 
            		according to the rule.  The best match is as follows:
            
            				To As       IP Network      Best Match Rank
            
            				exact		exact			1st
            				exact		wild card		2nd
            				wild card	exact			3rd
            				wild card	wild card		4th
            
            		."
            	INDEX { expIsisToEgpRuleToAs, expIsisToEgpRuleNetwork }
            	::= { expIsisToEgpRuleTable 1 }
            
            ExpIsisToEgpRuleEntry ::=
            	SEQUENCE {
            		expIsisToEgpRuleToAs
            			INTEGER,
            		expIsisToEgpRuleNetwork
            			IpAddress,
            		expIsisToEgpRuleAction
            			INTEGER,
            		expIsisToEgpRuleMetricAction
            			INTEGER,
            		expIsisToEgpRuleMetric
            			INTEGER,
            		expIsisToEgpRuleStatus
            			INTEGER
            	}
            
            expIsisToEgpRuleToAs OBJECT-TYPE
            	SYNTAX INTEGER ( 0..65535 )
            	ACCESS read-only
            	STATUS mandatory
            	DESCRIPTION
            		"The Autonomous System of the neighbor.  The value 65535 is 
            		a wild card matching any AS number."
            	::= { expIsisToEgpRuleEntry 1 }
            
            expIsisToEgpRuleNetwork OBJECT-TYPE
            	SYNTAX IpAddress
            	ACCESS read-only
            	STATUS mandatory
            	DESCRIPTION
            		"The IP network of the route in the route table.  The value 
            		255.255.255.255	is a wild card matching any network."
            	::= { expIsisToEgpRuleEntry 2 }
            
            expIsisToEgpRuleAction OBJECT-TYPE
            	SYNTAX INTEGER { hide(1), advertise(2) }
            	ACCESS read-write
            	STATUS mandatory
            	DESCRIPTION
            		"Control whether the route is advertised or not."
            	DEFVAL { advertise }
            	::= { expIsisToEgpRuleEntry 3 }
            
            expIsisToEgpRuleMetricAction OBJECT-TYPE
            	SYNTAX INTEGER { replace(1), increment(2), decrement(3) }
            	ACCESS read-write
            	STATUS mandatory
            	DESCRIPTION
            		"How to apply the expIsisToEgpRuleMetric field to the metric in the route
            		table entry before the route is advertised."
            	DEFVAL { increment }
            	::= { expIsisToEgpRuleEntry 4 }
            
            expIsisToEgpRuleMetric OBJECT-TYPE
            	SYNTAX INTEGER 
            	ACCESS read-write
            	STATUS mandatory
            	DESCRIPTION
            		"Metric value to be applied to the metric in the route table entry
            		before the route is advertised."
            	DEFVAL { 0 }
            	::= { expIsisToEgpRuleEntry 5 }
            
            expIsisToEgpRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToEgpRuleEntry 6 }
            
            
            -- Isis to ospf
            
            expIsisToOspfRuleTable OBJECT-TYPE
            	SYNTAX SEQUENCE OF ExpIsisToOspfRuleEntry
            	ACCESS not-accessible
            	STATUS mandatory
            	DESCRIPTION
            		"The Isis to Ospf export table."
            	::= { xExport 12 }
            
            expIsisToOspfRuleEntry OBJECT-TYPE
            	SYNTAX ExpIsisToOspfRuleEntry
            	ACCESS not-accessible
            	STATUS mandatory
            	DESCRIPTION
            		"An Isis to Ospf export rule.  Each rule is keyed by the IP network of
            		the Isis route in the routing table.  The IP network can be set to a
            		wild card.  The route is either accepted to be advertised to the 
            		neighbor or discarded from being advertised, and its metric is applied 
            		according to the rule.  The best match is as follows:
            
            				IP Network      Best Match Rank
            
            				exact			1st
            				wild card		2nd
            
            		."
            	INDEX { expIsisToOspfRuleNetwork }
            	::= { expIsisToOspfRuleTable 1 }
            
            ExpIsisToOspfRuleEntry ::=
            	SEQUENCE {
            		expIsisToOspfRuleNetwork
            			IpAddress,
            		expIsisToOspfRuleAction
            			INTEGER,
            		expIsisToOspfRuleStatus
            			INTEGER
            	}
            
            expIsisToOspfRuleNetwork OBJECT-TYPE
            	SYNTAX IpAddress
            	ACCESS read-only
            	STATUS mandatory
            	DESCRIPTION
            		"The IP network of the route in the route table.  The value 
            		255.255.255.255	is a wild card matching any network."
            	::= { expIsisToOspfRuleEntry 1 }
            
            expIsisToOspfRuleAction OBJECT-TYPE
            	SYNTAX INTEGER { hide(1), advertise(2) }
            	ACCESS read-write
            	STATUS mandatory
            	DESCRIPTION
            		"Control whether the route is advertised or not."
            	DEFVAL { advertise }
            	::= { expIsisToOspfRuleEntry 2 }
            
            expIsisToOspfRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToOspfRuleEntry 3 }
            
            
            -- Isis to Rip
            
            expIsisToRipRuleTable OBJECT-TYPE
            	SYNTAX SEQUENCE OF ExpIsisToRipRuleEntry
            	ACCESS not-accessible
            	STATUS mandatory
            	DESCRIPTION
            		"The Isis to Rip export table."
            	::= { xExport 13 }
            
            expIsisToRipRuleEntry OBJECT-TYPE
            	SYNTAX ExpIsisToRipRuleEntry
            	ACCESS not-accessible
            	STATUS mandatory
            	DESCRIPTION
             		"An Isis to Rip export rule.  Each rule is keyed by the IP
                    network of the Isis route in the routing table.  The IP
                    network can be set to a	wild card.  The route is either
                    accepted to be advertised to the neighbor or discarded
                    from being advertised, and its metric is applied 
            		according to the rule.  The best match is as follows:
            
            				IP Network      Best Match Rank
            
            				exact			1st
            				wild card		2nd
            
            		."
            	INDEX { expIsisToRipRuleNetwork }
            	::= { expIsisToRipRuleTable 1 }
            
            ExpIsisToRipRuleEntry ::=
            	SEQUENCE {
                    expIsisToRipRuleToIf
                        IpAddress,
            		expIsisToRipRuleNetwork
            			IpAddress,
            		expIsisToRipRuleAction
            			INTEGER,
            		expIsisToRipRuleMetricAction
            			INTEGER,
            		expIsisToRipRuleMetric
            			INTEGER,
            		expIsisToRipRuleStatus
            			INTEGER
            	}
            
            expIsisToRipRuleToIf OBJECT-TYPE
                SYNTAX IpAddress
                ACCESS read-only
                STATUS mandatory
                DESCRIPTION
                    "The IP address of the RIP interface to which the 
                    rule applies."
                ::= { expIsisToRipRuleEntry 1 }

            expIsisToRipRuleNetwork OBJECT-TYPE
            	SYNTAX IpAddress
            	ACCESS read-only
            	STATUS mandatory
            	DESCRIPTION
            		"The IP network of the route in the route table.  The value 
            		255.255.255.255	is a wild card matching any network."
            	::= { expIsisToRipRuleEntry 2 }
            
            expIsisToRipRuleAction OBJECT-TYPE
            	SYNTAX INTEGER { hide(1), advertise(2) }
            	ACCESS read-write
            	STATUS mandatory
            	DESCRIPTION
            		"Control whether the route is advertised or not."
            	DEFVAL { advertise }
            	::= { expIsisToRipRuleEntry 3 }
            
            expIsisToRipRuleMetricAction OBJECT-TYPE
            	SYNTAX INTEGER { replace(1), increment(2), decrement(3) }
            	ACCESS read-write
            	STATUS mandatory
            	DESCRIPTION
            		"How to apply the expIsisToRipRuleMetric field to the metric in the route
            		table entry before the route is advertised."
            	DEFVAL { increment }
            	::= { expIsisToRipRuleEntry 4 }
            
            expIsisToRipRuleMetric OBJECT-TYPE
            	SYNTAX INTEGER 
            	ACCESS read-write
            	STATUS mandatory
            	DESCRIPTION
            		"Metric value to be applied to the metric in the route table entry
            		before the route is advertised."
            	DEFVAL { 0 }
            	::= { expIsisToRipRuleEntry 5 }
            
            expIsisToRipRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToRipRuleEntry 6 }
            
            
            -- egp to Isis
            
            expEgpToIsisRuleTable OBJECT-TYPE
            	SYNTAX SEQUENCE OF ExpEgpToIsisRuleEntry
            	ACCESS not-accessible
            	STATUS mandatory
            	DESCRIPTION
            		"The EGP to Isis export table."
            	::= { xExport 14 }
            
            expEgpToIsisRuleEntry OBJECT-TYPE
            	SYNTAX ExpEgpToIsisRuleEntry
            	ACCESS not-accessible
            	STATUS mandatory
            	DESCRIPTION
            		"An EGP to Isis export rule.  Each rule is keyed by the Autonomous 
            		System of the EGP neighbor, the IP network of the EGP route in the 
            		routing table, and the Autonomous System from which the route was
            		learned.  The IP network can be set to a wild card as can the
            		from AS.  The route is either accepted to be advertised to the 
            		neighbor or discarded from being advertised, and its metric is applied 
            		according to the rule.  The best match is as follows:
            
            				IP Network      From AS			Best Match Rank
            
            				exact			exact			1st
            				exact			wild card		2nd
            				wild card		exact			3rd
            				wild card		wild card		4th
            
            		."
            	INDEX { expEgpToIsisRuleNetwork, expEgpToIsisRuleFromAs }
            	::= { expEgpToIsisRuleTable 1 }
            
            ExpEgpToIsisRuleEntry ::=
            	SEQUENCE {
            		expEgpToIsisRuleNetwork
            			IpAddress,
            		expEgpToIsisRuleFromAs
            			INTEGER,
            		expEgpToIsisRuleAction
            			INTEGER,
            		expEgpToIsisRuleMetricType
            			INTEGER,
            		expEgpToIsisRuleDefaultMetricAction
            			INTEGER,
            		expEgpToIsisRuleDefaultMetric
            			INTEGER,
            		expEgpToIsisRuleDelayMetricAction
            			INTEGER,
            		expEgpToIsisRuleDelayMetric
            			INTEGER,
            		expEgpToIsisRuleErrorMetricAction
            			INTEGER,
            		expEgpToIsisRuleErrorMetric
            			INTEGER,
            		expEgpToIsisRuleExpenseMetricAction
            			INTEGER,
            		expEgpToIsisRuleExpenseMetric
            			INTEGER,
            		expEgpToIsisRuleStatus
            			INTEGER
            	}
            
            expEgpToIsisRuleNetwork OBJECT-TYPE
            	SYNTAX IpAddress 
            	ACCESS read-only
            	STATUS mandatory
            	DESCRIPTION
            		"The IP network of the route in the route table.  The value 
            		255.255.255.255	is a wild card matching any network."
            	::= { expEgpToIsisRuleEntry 1 }
            
            expEgpToIsisRuleFromAs OBJECT-TYPE
            	SYNTAX INTEGER ( 0..65535 )
            	ACCESS read-only
            	STATUS mandatory
            	DESCRIPTION
            		"The Autonomous System of the route in the route table.  The value 
            		65535 is a wild card matching any AS number."
            	::= { expEgpToIsisRuleEntry 2 }
            
            expEgpToIsisRuleAction OBJECT-TYPE
            	SYNTAX INTEGER { hide(1), advertise(2) }
            	ACCESS read-write
            	STATUS mandatory
            	DESCRIPTION
            		"Control whether the route is advertised or not."
            	DEFVAL { advertise }
            	::= { expEgpToIsisRuleEntry 3 }
            
            expEgpToIsisRuleMetricType OBJECT-TYPE
            	SYNTAX INTEGER { internal(1), external(2) }
            	ACCESS read-write
            	STATUS mandatory
            	DESCRIPTION
            		"Whether to advertise the metric as Internal or External."
            	DEFVAL { external }
            	::= { expEgpToIsisRuleEntry 4 }
            
            expEgpToIsisRuleDefaultMetricAction OBJECT-TYPE
            	SYNTAX INTEGER { replace(1), increment(2), decrement(3) }
            	ACCESS read-write
            	STATUS mandatory
            	DESCRIPTION
            		"How to apply the expEgpToIsisDefaultRuleMetric field to the metric in the route
            		table entry before the route is advertised."
            	DEFVAL { increment }
            	::= { expEgpToIsisRuleEntry 5 }
            
            expEgpToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expEgpToIsisRuleEntry 6 }
            
            expEgpToIsisRuleDelayMetricAction OBJECT-TYPE
            	SYNTAX INTEGER { replace(1), increment(2), decrement(3) }
            	ACCESS read-write
            	STATUS mandatory
            	DESCRIPTION
            		"How to apply the expEgpToIsisDelayRuleMetric field to the metric in the 
            		route table entry before the route is advertised."
            	DEFVAL { replace }
            	::= { expEgpToIsisRuleEntry 7 }
            
            expEgpToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expEgpToIsisRuleEntry 8 }
            
            expEgpToIsisRuleErrorMetricAction OBJECT-TYPE
            	SYNTAX INTEGER { replace(1), increment(2), decrement(3) }
            	ACCESS read-write
            	STATUS mandatory
            	DESCRIPTION
            		"How to apply the expEgpToIsisErrorRuleMetric field to the metric in the route
            		table entry before the route is advertised."
            	DEFVAL { replace }
            	::= { expEgpToIsisRuleEntry 9 }
            
            expEgpToIsisRuleErrorMetric OBJECT-TYPE
            	SYNTAX INTEGER 
            	ACCESS read-write
            	STATUS mandatory
            	DESCRIPTION
            		"Error metric value to be applied to the metric in the route table entry
            		before the route is advertised."
            	DEFVAL { 0 }
            	::= { expEgpToIsisRuleEntry 10 }
            
            expEgpToIsisRuleExpenseMetricAction OBJECT-TYPE
            	SYNTAX INTEGER { replace(1), increment(2), decrement(3) }
            	ACCESS read-write
            	STATUS mandatory
            	DESCRIPTION
            		"How to apply the expEgpToIsisExpenseRuleMetric field to the metric in the route
            		table entry before the route is advertised."
            	DEFVAL { replace }
            	::= { expEgpToIsisRuleEntry 11 }
            
            expEgpToIsisRuleExpenseMetric OBJECT-TYPE
            	SYNTAX INTEGER 
            	ACCESS read-write
            	STATUS mandatory
            	DESCRIPTION
            		"Expense metric value to be applied to the metric in the route table entry
            		before the route is advertised."
            	DEFVAL { 0 }
            	::= { expEgpToIsisRuleEntry 12 }
            
            expEgpToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expEgpToIsisRuleEntry 13 }
            
            
            -- Ospf to Isis
            
            expOspfToIsisRuleTable OBJECT-TYPE
            	SYNTAX SEQUENCE OF ExpOspfToIsisRuleEntry
            	ACCESS not-accessible
            	STATUS mandatory
            	DESCRIPTION
            		"The Ospf to Isis export table."
            	::= { xExport 15 }
            
            expOspfToIsisRuleEntry OBJECT-TYPE
            	SYNTAX ExpOspfToIsisRuleEntry
            	ACCESS not-accessible
            	STATUS mandatory
            	DESCRIPTION
            		"An Ospf to Isis export rule.  Each rule is keyed by the
                    Autonomous System of the Ospf neighbor, the IP network of
                    the Ospf route in the routing table, and the Autonomous
                    System from which the route was learned.  The IP network
                    can be set to a wild card as can the the from AS.  The
                    route is either accepted to be advertised to the neighbor
                    or discarded from being advertised, and its metric is
                    applied according to the rule.  The best match is as
                    follows:
            
            				IP Network      From AS			Best Match Rank
            
            				exact			exact			1st
            				exact			wild card		2nd
            				wild card		exact			3rd
            				wild card		wild card		4th
            
            		."
            	INDEX { expOspfToIsisRuleNetwork, expOspfToIsisRuleFromAs }
            	::= { expOspfToIsisRuleTable 1 }
            
            ExpOspfToIsisRuleEntry ::=
            	SEQUENCE {
            		expOspfToIsisRuleNetwork
            			IpAddress,
            		expOspfToIsisRuleFromAs
            			INTEGER,
            		expOspfToIsisRuleAction
            			INTEGER,
            		expOspfToIsisRuleMetricType
            			INTEGER,
            		expOspfToIsisRuleDefaultMetricAction
            			INTEGER,
            		expOspfToIsisRuleDefaultMetric
            			INTEGER,
            		expOspfToIsisRuleDelayMetricAction
            			INTEGER,
            		expOspfToIsisRuleDelayMetric
            			INTEGER,
            		expOspfToIsisRuleErrorMetricAction
            			INTEGER,
            		expOspfToIsisRuleErrorMetric
            			INTEGER,
            		expOspfToIsisRuleExpenseMetricAction
            			INTEGER,
            		expOspfToIsisRuleExpenseMetric
            			INTEGER,
            		expOspfToIsisRuleStatus
            			INTEGER
            	}
            
            expOspfToIsisRuleNetwork OBJECT-TYPE
            	SYNTAX IpAddress 
            	ACCESS read-only
            	STATUS mandatory
            	DESCRIPTION
            		"The IP network of the route in the route table.  The value
            		255.255.255.255	is a wild card matching any network."
            	::= { expOspfToIsisRuleEntry 1 }
            
            expOspfToIsisRuleFromAs OBJECT-TYPE
            	SYNTAX INTEGER ( 0..65535 )
            	ACCESS read-only
            	STATUS mandatory
            	DESCRIPTION
            		"The Autonomous System of the route in the route table.
                    The value 65535 is a wild card matching any AS number,
                    and the value 65534 is for routes within the local AS."
            	::= { expOspfToIsisRuleEntry 2 }
            
            expOspfToIsisRuleAction OBJECT-TYPE
            	SYNTAX INTEGER { hide(1), advertise(2) }
            	ACCESS read-write
            	STATUS mandatory
            	DESCRIPTION
            		"Control whether the route is advertised or not."
            	DEFVAL { advertise }
            	::= { expOspfToIsisRuleEntry 3 }
            
            expOspfToIsisRuleMetricType OBJECT-TYPE
            	SYNTAX INTEGER { internal(1), external(2) }
            	ACCESS read-write
            	STATUS mandatory
            	DESCRIPTION
            		"Whether to advertise the metric as Internal or External."
            	DEFVAL { external }
            	::= { expOspfToIsisRuleEntry 4 }
            
            expOspfToIsisRuleDefaultMetricAction OBJECT-TYPE
            	SYNTAX INTEGER { replace(1), increment(2), decrement(3) }
            	ACCESS read-write
            	STATUS mandatory
            	DESCRIPTION
            		"How to apply the expOspfToIsisDefaultRuleMetric field to
                    the metric in the route table entry before the route is
                    advertised."
            	DEFVAL { increment }
            	::= { expOspfToIsisRuleEntry 5 }
            
            expOspfToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expOspfToIsisRuleEntry 6 }
            
            expOspfToIsisRuleDelayMetricAction OBJECT-TYPE
            	SYNTAX INTEGER { replace(1), increment(2), decrement(3) }
            	ACCESS read-write
            	STATUS mandatory
            	DESCRIPTION
            		"How to apply the expOspfToIsisDelayRuleMetric field to the metric in the route
            		table entry before the route is advertised."
            	DEFVAL { replace }
            	::= { expOspfToIsisRuleEntry 7 }
            
            expOspfToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expOspfToIsisRuleEntry 8 }
            
            expOspfToIsisRuleErrorMetricAction OBJECT-TYPE
            	SYNTAX INTEGER { replace(1), increment(2), decrement(3) }
            	ACCESS read-write
            	STATUS mandatory
            	DESCRIPTION
            		"How to apply the expOspfToIsisErrorRuleMetric field to the metric in the route
            		table entry before the route is advertised."
            	DEFVAL { replace }
            	::= { expOspfToIsisRuleEntry 9 }
            
            expOspfToIsisRuleErrorMetric OBJECT-TYPE
            	SYNTAX INTEGER 
            	ACCESS read-write
            	STATUS mandatory
            	DESCRIPTION
            		"Error metric value to be applied to the metric in the route table entry
            		before the route is advertised."
            	DEFVAL { 0 }
            	::= { expOspfToIsisRuleEntry 10 }
            
            expOspfToIsisRuleExpenseMetricAction OBJECT-TYPE
            	SYNTAX INTEGER { replace(1), increment(2), decrement(3) }
            	ACCESS read-write
            	STATUS mandatory
            	DESCRIPTION
            		"How to apply the expOspfToIsisExpenseRuleMetric field to the metric in the route
            		table entry before the route is advertised."
            	DEFVAL { replace }
            	::= { expOspfToIsisRuleEntry 11 }
            
            expOspfToIsisRuleExpenseMetric OBJECT-TYPE
            	SYNTAX INTEGER 
            	ACCESS read-write
            	STATUS mandatory
            	DESCRIPTION
            		"Expense metric value to be applied to the metric in the route table entry
            		before the route is advertised."
            	DEFVAL { 0 }
            	::= { expOspfToIsisRuleEntry 12 }
            
            expOspfToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values.  The same is
            		true for the all wild cards where the AS is set to local"
            	DEFVAL { valid }
            	::= { expOspfToIsisRuleEntry 13 }
            
            
            -- Rip to Isis
            
            expRipToIsisRuleTable OBJECT-TYPE
            	SYNTAX SEQUENCE OF ExpRipToIsisRuleEntry
            	ACCESS not-accessible
            	STATUS mandatory
            	DESCRIPTION
            		"The Isis to Isis export table."
            	::= { xExport 16 }
            
            expRipToIsisRuleEntry OBJECT-TYPE
            	SYNTAX ExpRipToIsisRuleEntry
            	ACCESS not-accessible
            	STATUS mandatory
            	DESCRIPTION
            		"An Isis to Isis export rule.  Each rule is keyed by the
                    IP network of the Isis route in the routing table.  The
                    neighbor IP network can be set to a wild card.  The route
                    is either accepted to be advertised to the neighbor or
                    discarded from being advertised, and its metric is applied
                    according to the rule.  The best match is as follows:
            
            				IP Network      Best Match Rank
            
            				exact			1st
            				wild card		2nd
            
            		."
            	INDEX { expRipToIsisRuleNetwork }
            	::= { expRipToIsisRuleTable 1 }
            
            ExpRipToIsisRuleEntry ::=
            	SEQUENCE {
            		expRipToIsisRuleNetwork
            			IpAddress,
            		expRipToIsisRuleAction
            			INTEGER,
            		expRipToIsisRuleMetricType
            			INTEGER,
            		expRipToIsisRuleDefaultMetricAction
            			INTEGER,
            		expRipToIsisRuleDefaultMetric
            			INTEGER,
            		expRipToIsisRuleDelayMetricAction
            			INTEGER,
            		expRipToIsisRuleDelayMetric
            			INTEGER,
            		expRipToIsisRuleErrorMetricAction
            			INTEGER,
            		expRipToIsisRuleErrorMetric
            			INTEGER,
            		expRipToIsisRuleExpenseMetricAction
            			INTEGER,
            		expRipToIsisRuleExpenseMetric
            			INTEGER,
            		expRipToIsisRuleStatus
            			INTEGER
            	}
            
            expRipToIsisRuleNetwork OBJECT-TYPE
            	SYNTAX IpAddress
            	ACCESS read-only
            	STATUS mandatory
            	DESCRIPTION
            		"The IP network of the route in the route table.  The value 
            		255.255.255.255	is a wild card matching any network."
            	::= { expRipToIsisRuleEntry 1 }
            
            expRipToIsisRuleAction OBJECT-TYPE
            	SYNTAX INTEGER { hide(1), advertise(2) }
            	ACCESS read-write
            	STATUS mandatory
            	DESCRIPTION
            		"Control whether the route is advertised or not."
            	DEFVAL { advertise }
            	::= { expRipToIsisRuleEntry 2 }
            
            expRipToIsisRuleMetricType OBJECT-TYPE
            	SYNTAX INTEGER { internal(1), external(2) }
            	ACCESS read-write
            	STATUS mandatory
            	DESCRIPTION
            		"Whether to advertise the metric as Internal or External."
            	DEFVAL { external }
            	::= { expRipToIsisRuleEntry 3 }
            
            expRipToIsisRuleDefaultMetricAction OBJECT-TYPE
            	SYNTAX INTEGER { replace(1), increment(2), decrement(3) }
            	ACCESS read-write
            	STATUS mandatory
            	DESCRIPTION
            		"How to apply the expRipToIsisDefaultRuleMetric field to the metric in the route
            		table entry before the route is advertised."
            	DEFVAL { increment }
            	::= { expRipToIsisRuleEntry 4 }
            
            expRipToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expRipToIsisRuleEntry 5 }
            
            expRipToIsisRuleDelayMetricAction OBJECT-TYPE
            	SYNTAX INTEGER { replace(1), increment(2), decrement(3) }
            	ACCESS read-write
            	STATUS mandatory
            	DESCRIPTION
            		"How to apply the expRipToIsisDelayRuleMetric field to the metric in the route
            		table entry before the route is advertised."
            	DEFVAL { replace }
            	::= { expRipToIsisRuleEntry 6 }
            
            expRipToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expRipToIsisRuleEntry 7 }
            
            expRipToIsisRuleErrorMetricAction OBJECT-TYPE
            	SYNTAX INTEGER { replace(1), increment(2), decrement(3) }
            	ACCESS read-write
            	STATUS mandatory
            	DESCRIPTION
            		"How to apply the expRipToIsisErrorRuleMetric field to the metric in the route
            		table entry before the route is advertised."
            	DEFVAL { replace }
            	::= { expRipToIsisRuleEntry 8 }
            
            expRipToIsisRuleErrorMetric OBJECT-TYPE
            	SYNTAX INTEGER 
            	ACCESS read-write
            	STATUS mandatory
            	DESCRIPTION
            		"Error metric value to be applied to the metric in the
                    route table entry before the route is advertised."
            	DEFVAL { 0 }
            	::= { expRipToIsisRuleEntry 9 }
            
            expRipToIsisRuleExpenseMetricAction OBJECT-TYPE
            	SYNTAX INTEGER { replace(1), increment(2), decrement(3) }
            	ACCESS read-write
            	STATUS mandatory
            	DESCRIPTION
            		"How to apply the expRipToIsisExpenseRuleMetric field to
                    the metric in the route	table entry before the route is
                    advertised."
            	DEFVAL { replace }
            	::= { expRipToIsisRuleEntry 10 }
            
            expRipToIsisRuleExpenseMetric OBJECT-TYPE
            	SYNTAX INTEGER 
            	ACCESS read-write
            	STATUS mandatory
            	DESCRIPTION
            		"Expense metric value to be applied to the metric in the
                    route table entry before the route is advertised."
            	DEFVAL { 0 }
            	::= { expRipToIsisRuleEntry 11 }
            
            expRipToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expRipToIsisRuleEntry 12 }
            
            
            
            -- Static to Isis
            
            expStaticToIsisRuleTable OBJECT-TYPE
            	SYNTAX SEQUENCE OF ExpStaticToIsisRuleEntry
            	ACCESS not-accessible
            	STATUS mandatory
            	DESCRIPTION
            		"The Static to Isis export table."
            	::= { xExport 17 }
            
            expStaticToIsisRuleEntry OBJECT-TYPE
            	SYNTAX ExpStaticToIsisRuleEntry
            	ACCESS not-accessible
            	STATUS mandatory
            	DESCRIPTION
            		"An Static to Isis export rule.  Each rule is keyed by the
                    IP network of the Static route in the routing table.  The
                    neighbor IP network can be set to a wild card.  The route
                    is either accepted to be advertised to the neighbor or
                    discarded from being advertised, and its metric is applied
                    according to the rule.  The best match is as follows:
            
            				IP Network      Best Match Rank
            
            				exact			1st
            				wild card		2nd
            
            		."
            	INDEX { expStaticToIsisRuleNetwork }
            	::= { expStaticToIsisRuleTable 1 }
            
            ExpStaticToIsisRuleEntry ::=
            	SEQUENCE {
            		expStaticToIsisRuleNetwork
            			IpAddress,
            		expStaticToIsisRuleAction
            			INTEGER,
            		expStaticToIsisRuleMetricType
            			INTEGER,
            		expStaticToIsisRuleDefaultMetricAction
            			INTEGER,
            		expStaticToIsisRuleDefaultMetric
            			INTEGER,
            		expStaticToIsisRuleDelayMetricAction
            			INTEGER,
            		expStaticToIsisRuleDelayMetric
            			INTEGER,
            		expStaticToIsisRuleErrorMetricAction
            			INTEGER,
            		expStaticToIsisRuleErrorMetric
            			INTEGER,
            		expStaticToIsisRuleExpenseMetricAction
            			INTEGER,
            		expStaticToIsisRuleExpenseMetric
            			INTEGER,
            		expStaticToIsisRuleStatus
            			INTEGER
            	}
            
            expStaticToIsisRuleNetwork OBJECT-TYPE
            	SYNTAX IpAddress
            	ACCESS read-only
            	STATUS mandatory
            	DESCRIPTION
            		"The IP network of the route in the route table.  The value
            		255.255.255.255	is a wild card matching any network."
            	::= { expStaticToIsisRuleEntry 1 }
            
            expStaticToIsisRuleAction OBJECT-TYPE
            	SYNTAX INTEGER { hide(1), advertise(2) }
            	ACCESS read-write
            	STATUS mandatory
            	DESCRIPTION
            		"Control whether the route is advertised or not."
            	DEFVAL { advertise }
            	::= { expStaticToIsisRuleEntry 2 }
            
            expStaticToIsisRuleMetricType OBJECT-TYPE
            	SYNTAX INTEGER { internal(1), external(2) }
            	ACCESS read-write
            	STATUS mandatory
            	DESCRIPTION
            		"Whether to advertise the metric as Internal or External."
            	DEFVAL { external }
            	::= { expStaticToIsisRuleEntry 3 }
            
            expStaticToIsisRuleDefaultMetricAction OBJECT-TYPE
            	SYNTAX INTEGER { replace(1), increment(2), decrement(3) }
            	ACCESS read-write
            	STATUS mandatory
            	DESCRIPTION
            		"How to apply the expStaticToIsisDefaultRuleMetric field
                    to the metric in the route table entry before the route
                    is advertised."
            	DEFVAL { increment }
            	::= { expStaticToIsisRuleEntry 4 }
            
            expStaticToIsisRuleDefaultMetric OBJECT-TYPE
            	SYNTAX INTEGER 
            	ACCESS read-write
            	STATUS mandatory
            	DESCRIPTION
            		"Default metric value to be applied to the metric in the
                    route table entry before the route is advertised."
            	DEFVAL { 1 }
            	::= { expStaticToIsisRuleEntry 5 }
            
            expStaticToIsisRuleDelayMetricAction OBJECT-TYPE
            	SYNTAX INTEGER { replace(1), increment(2), decrement(3) }
            	ACCESS read-write
            	STATUS mandatory
            	DESCRIPTION
            		"How to apply the expStaticToIsisDelayRuleMetric field
                    to the metric in the route table entry before the route
                    is advertised."
            	DEFVAL { replace }
            	::= { expStaticToIsisRuleEntry 6 }
            
            expStaticToIsisRuleDelayMetric OBJECT-TYPE
            	SYNTAX INTEGER 
            	ACCESS read-write
            	STATUS mandatory
            	DESCRIPTION
            		"Delay metric value to be applied to the metric in the
                    route table entry before the route is advertised."
            	DEFVAL { 0 }
            	::= { expStaticToIsisRuleEntry 7 }
            
            expStaticToIsisRuleErrorMetricAction OBJECT-TYPE
            	SYNTAX INTEGER { replace(1), increment(2), decrement(3) }
            	ACCESS read-write
            	STATUS mandatory
            	DESCRIPTION
            		"How to apply the expStaticToIsisErrorRuleMetric field
                    to the metric in the route table entry before the route
                    is advertised."
            	DEFVAL { replace }
            	::= { expStaticToIsisRuleEntry 8 }
            
            expStaticToIsisRuleErrorMetric OBJECT-TYPE
            	SYNTAX INTEGER 
            	ACCESS read-write
            	STATUS mandatory
            	DESCRIPTION
            		"Error metric value to be applied to the metric in the
                    route table entry before the route is advertised."
            	DEFVAL { 0 }
            	::= { expStaticToIsisRuleEntry 9 }
            
            expStaticToIsisRuleExpenseMetricAction OBJECT-TYPE
            	SYNTAX INTEGER { replace(1), increment(2), decrement(3) }
            	ACCESS read-write
            	STATUS mandatory
            	DESCRIPTION
            		"How to apply the expStaticToIsisExpenseRuleMetric field
                    to the metric in the route table entry before the route
                    is advertised."
            	DEFVAL { replace }
            	::= { expStaticToIsisRuleEntry 10 }
            
            expStaticToIsisRuleExpenseMetric OBJECT-TYPE
            	SYNTAX INTEGER 
            	ACCESS read-write
            	STATUS mandatory
            	DESCRIPTION
            		"Expense metric value to be applied to the metric in the
                    route table entry before the route is advertised."
            	DEFVAL { 0 }
            	::= { expStaticToIsisRuleEntry 11 }
            
            expStaticToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expStaticToIsisRuleEntry 12 }


            -- the Filter subgroup

            -- Note: individual parameters follow table

            ipIfFilterTable OBJECT-TYPE
                SYNTAX SEQUENCE OF IpIfFilterEntry
                ACCESS not-accessible
                STATUS deprecated
                DESCRIPTION
                    "Table of filter entries."
                ::= { xFilter 1 }

            ipIfFilterEntry OBJECT-TYPE
                SYNTAX IpIfFilterEntry
                ACCESS not-accessible
                STATUS deprecated
                DESCRIPTION
                    "A particular entry."
                INDEX { ipIfFilterIndex, ipIfFilterProtocol,
                        ipIfFilterDstPort, ipIfFilterSrcPort,
                        ipIfFilterDstAddr, ipIfFilterDstMask,
                        ipIfFilterSrcAddr, ipIfFilterSrcMask }
                ::= { ipIfFilterTable 1 }

            IpIfFilterEntry ::=
                SEQUENCE {
                    ipIfFilterIndex
                        INTEGER,
                    ipIfFilterDstAddr
                        IpAddress,
                    ipIfFilterDstMask
                        IpAddress,
                    ipIfFilterSrcAddr
                        IpAddress,
                    ipIfFilterSrcMask
                         IpAddress,
                    ipIfFilterProtocol
                         INTEGER,
                    ipIfFilterDstPort
                         INTEGER,
                    ipIfFilterSrcPort
                         INTEGER,
                    ipIfFilterAction
                         INTEGER,
                    ipIfFilterStatus
                         INTEGER
                }

            ipIfFilterIndex OBJECT-TYPE
                SYNTAX INTEGER
                ACCESS read-only
                STATUS deprecated
                DESCRIPTION
                    "The interface index with which this entry is 
                    associated.  This value is the same as IfIndex."
                ::= { ipIfFilterEntry 1 }

            ipIfFilterDstAddr OBJECT-TYPE
                SYNTAX IpAddress
                ACCESS read-only
                STATUS deprecated
                DESCRIPTION
                    "The destination IP address to use in the filter 
                    match."
                ::= { ipIfFilterEntry 2 }

            ipIfFilterDstMask OBJECT-TYPE
                SYNTAX IpAddress
                ACCESS read-only
                STATUS deprecated
                DESCRIPTION
                    "The destination IP mask to use in the filter 
                    match."
                ::= { ipIfFilterEntry 3 }

            ipIfFilterSrcAddr OBJECT-TYPE
                SYNTAX IpAddress
                ACCESS read-only
                STATUS deprecated
                DESCRIPTION
                    "The source IP address to use in the filter match."
                ::= { ipIfFilterEntry 4 }

            ipIfFilterSrcMask OBJECT-TYPE
                SYNTAX IpAddress
                ACCESS read-only
                STATUS deprecated
                DESCRIPTION
                    "The source IP mask to use in the filter match."
                ::= { ipIfFilterEntry 5 }

            ipIfFilterProtocol OBJECT-TYPE
                SYNTAX INTEGER ( 0..256 )
                ACCESS read-only
                STATUS deprecated
                DESCRIPTION
                    "The protocol to use in the filter match.  The value 
                    256 indicates any protocol."
                ::= { ipIfFilterEntry 6 }

            ipIfFilterDstPort OBJECT-TYPE
                SYNTAX INTEGER ( 0..65536 )
                ACCESS read-only
                STATUS deprecated
                DESCRIPTION
                    "The destination port to use in the filter match.  
                    This field only applies to TCP and UDP protocol 
                    packets.  The value 65536 indicates any destination 
                    port."
                ::= { ipIfFilterEntry 7 }

            ipIfFilterSrcPort OBJECT-TYPE
                SYNTAX INTEGER ( 0..65536 )
                ACCESS read-only
                STATUS deprecated
                DESCRIPTION
                    "The source port to use in the filter match.  This 
                    field only applies to TCP and UDP protocol packets.  
                    The value 65536 indicates any source port."
                ::= { ipIfFilterEntry 8 }

            ipIfFilterAction OBJECT-TYPE
                SYNTAX INTEGER { discard(1), forward(2) }
                ACCESS read-write
                STATUS deprecated
                DESCRIPTION
                    "Control whether the packet for which this filter is 
                    the best match should be forwarded or discarded."
                DEFVAL { forward }
                ::= { ipIfFilterEntry 9 }

            ipIfFilterStatus OBJECT-TYPE
                SYNTAX INTEGER { invalid(1), valid(2) }
                ACCESS read-write
                STATUS deprecated
                DESCRIPTION
                    "The status of the filter entry.  Set to 'invalid' 
                    to remove the entry."
                DEFVAL { valid }
                ::= { ipIfFilterEntry 10 }

            -- individual parameters

            ipFilterState OBJECT-TYPE
                SYNTAX INTEGER { disabled(1), enabled(2) }
                ACCESS read-write
                STATUS mandatory
                DESCRIPTION
                    "The indication of whether this system does IP 
                    filtering."
                ::= { xFilter 2 }


            -- new filter table

            ipIfFilter2Table OBJECT-TYPE
                SYNTAX SEQUENCE OF IpIfFilter2Entry
                ACCESS not-accessible
                STATUS mandatory
                DESCRIPTION
                    "Table of filter entries."
                ::= { xFilter 3 }

            ipIfFilter2Entry OBJECT-TYPE
                SYNTAX IpIfFilter2Entry
                ACCESS not-accessible
                STATUS mandatory
                DESCRIPTION
                    "A particular entry."
                INDEX { ipIfFilter2Index, ipIfFilter2Protocol,
                        ipIfFilter2DstPortStart, ipIfFilter2DstPortEnd,
						ipIfFilter2TcpSyn,
                        ipIfFilter2SrcPortStart, ipIfFilter2SrcPortEnd,
                        ipIfFilter2DstMask, ipIfFilter2DstAddr,
                        ipIfFilter2SrcMask, ipIfFilter2SrcAddr }
                ::= { ipIfFilter2Table 1 }

            IpIfFilter2Entry ::=
                SEQUENCE {
                    ipIfFilter2Index
                        INTEGER,
                    ipIfFilter2DstAddr
                        IpAddress,
                    ipIfFilter2DstMask
                        IpAddress,
                    ipIfFilter2SrcAddr
                        IpAddress,
                    ipIfFilter2SrcMask
                         IpAddress,
                    ipIfFilter2Protocol
                         INTEGER,
                    ipIfFilter2DstPortStart
                         INTEGER,
                    ipIfFilter2SrcPortStart
                         INTEGER,
                    ipIfFilter2Action
                         INTEGER,
                    ipIfFilter2Status
                         INTEGER,
					ipIfFilter2DstPortEnd
						 INTEGER,
					ipIfFilter2SrcPortEnd
						 INTEGER,
					ipIfFilter2TcpSyn
						 INTEGER,
					ipIfFilter2ProtocolPriority
						 INTEGER
                }

            ipIfFilter2Index OBJECT-TYPE
                SYNTAX INTEGER
                ACCESS read-only
                STATUS mandatory
                DESCRIPTION
                    "The interface index with which this entry is 
                    associated.  This value is the same as IfIndex."
                ::= { ipIfFilter2Entry 1 }

            ipIfFilter2DstAddr OBJECT-TYPE
                SYNTAX IpAddress
                ACCESS read-only
                STATUS mandatory
                DESCRIPTION
                    "The destination IP address to use in the filter 
                    match."
                ::= { ipIfFilter2Entry 2 }

            ipIfFilter2DstMask OBJECT-TYPE
                SYNTAX IpAddress
                ACCESS read-only
                STATUS mandatory
                DESCRIPTION
                    "The destination IP mask to use in the filter 
                    match."
                ::= { ipIfFilter2Entry 3 }

            ipIfFilter2SrcAddr OBJECT-TYPE
                SYNTAX IpAddress
                ACCESS read-only
                STATUS mandatory
                DESCRIPTION
                    "The source IP address to use in the filter match."
                ::= { ipIfFilter2Entry 4 }

            ipIfFilter2SrcMask OBJECT-TYPE
                SYNTAX IpAddress
                ACCESS read-only
                STATUS mandatory
                DESCRIPTION
                    "The source IP mask to use in the filter match."
                ::= { ipIfFilter2Entry 5 }

            ipIfFilter2Protocol OBJECT-TYPE
                SYNTAX INTEGER ( 0..256 )
                ACCESS read-only
                STATUS mandatory
                DESCRIPTION
                    "The protocol to use in the filter match.  The value 
                    256 indicates any protocol."
                ::= { ipIfFilter2Entry 6 }

            ipIfFilter2DstPortStart OBJECT-TYPE
                SYNTAX INTEGER ( 0..65535 )
                ACCESS read-only
                STATUS mandatory
                DESCRIPTION
                    "The starting destination port in a range of 
					destination ports to use in the filter match.  
                    This field only applies to TCP and UDP protocol 
                    packets."
                ::= { ipIfFilter2Entry 7 }

            ipIfFilter2SrcPortStart OBJECT-TYPE
                SYNTAX INTEGER ( 0..65535 )
                ACCESS read-only
                STATUS mandatory
                DESCRIPTION
                    "The starting source port in a range of 
					source ports to use in the filter match.  
                    This field only applies to TCP and UDP protocol 
                    packets."
                ::= { ipIfFilter2Entry 8 }

            ipIfFilter2Action OBJECT-TYPE
                SYNTAX INTEGER { discard(1), forward(2) }
                ACCESS read-write
                STATUS mandatory
                DESCRIPTION
                    "Control whether the packet for which this filter is 
                    the best match should be forwarded or discarded."
                DEFVAL { forward }
                ::= { ipIfFilter2Entry 9 }

            ipIfFilter2Status OBJECT-TYPE
                SYNTAX INTEGER { invalid(1), valid(2) }
                ACCESS read-write
                STATUS mandatory
                DESCRIPTION
                    "The status of the filter entry.  Set to 'invalid' 
                    to remove the entry."
                DEFVAL { valid }
                ::= { ipIfFilter2Entry 10 }

            ipIfFilter2DstPortEnd OBJECT-TYPE
                SYNTAX INTEGER ( 0..65535 )
                ACCESS read-only
                STATUS mandatory
                DESCRIPTION
                    "The ending destination port in a range of 
					destination ports to use in the filter match.  
                    This field only applies to TCP and UDP protocol 
                    packets.  This filed must also be greater or
					equal to the ipIfFilter2DstPortStart field."
                ::= { ipIfFilter2Entry 11 }

            ipIfFilter2SrcPortEnd OBJECT-TYPE
                SYNTAX INTEGER ( 0..65535 )
                ACCESS read-only
                STATUS mandatory
                DESCRIPTION
                    "The starting source port in a range of 
					source ports to use in the filter match.  
                    This field only applies to TCP and UDP protocol 
                    packets.  This filed must also be greater or
					equal to the ipIfFilter2SrcPortStart field."
                ::= { ipIfFilter2Entry 12 }

            ipIfFilter2TcpSyn OBJECT-TYPE
                SYNTAX INTEGER { off(1), on(2), all(3) }
                ACCESS read-only
                STATUS mandatory
                DESCRIPTION
                    "The value of the TCP SYN and ACK bit to
					ues in the filter match.  This field only
					applies to TCP packets.  On indicates
					that the SYN bit is on and the ACK bit is 
					off.  Off is any other combination."
                ::= { ipIfFilter2Entry 13 }

            ipIfFilter2ProtocolPriority OBJECT-TYPE
                SYNTAX INTEGER { low(1), medium(3), high(5), none(256) }
                ACCESS read-write
                STATUS mandatory
                DESCRIPTION
                    "Control the priority at which the packet for which
					this filter is the best match should be placed on 
					the WAN output queue.  None indicates that the 
					sending interfaces protocol priority should be used." 
                DEFVAL { none }
                ::= { ipIfFilter2Entry 14 }

            -- the RIP group

            -- Implementation of this group is mandatory for all iTouch
            -- systems that implement RIP and route traffic through

            ripState OBJECT-TYPE
                SYNTAX INTEGER { disabled(1), enabled(2) }
                ACCESS read-write
                STATUS mandatory
                DESCRIPTION
                    "The indication of whether this system participates 
                    in RIP."
                DEFVAL { disabled }
                ::= { xRip 1 }

            ripStatus OBJECT-TYPE
                SYNTAX INTEGER { active(1), ripDisabled(2),
                                 ipDisabled(3), noNetworksEnabled(4),
                                 noMemory(5) }
                ACCESS read-only
                STATUS mandatory
                DESCRIPTION
                    "The status of the RIP software."
                ::= { xRip 2 }

            -- the RIP Network table

            ripNetTable OBJECT-TYPE
                SYNTAX SEQUENCE OF RipNetEntry
                ACCESS not-accessible
                STATUS mandatory
                DESCRIPTION
                    "Table of RIP entries."
                ::= { xRip 3 }

            ripNetEntry OBJECT-TYPE
                SYNTAX RipNetEntry
                ACCESS not-accessible
                STATUS mandatory
                DESCRIPTION
                    "A particular entry."
                INDEX { ripNetNet }
                ::= { ripNetTable 1 }

            RipNetEntry ::=
                SEQUENCE {
                    ripNetNet
                        IpAddress,
                    ripNetState
                        INTEGER,
                    ripNetRipsIn
                         Counter,
                    ripNetRipsOut
                         Counter,
                    ripNetAlgorithm
                        INTEGER
                }

            ripNetNet OBJECT-TYPE
                SYNTAX IpAddress
                ACCESS read-only
                STATUS mandatory
                DESCRIPTION
                    "The IP Network to which this entry applies."
                ::= { ripNetEntry 1 }

            ripNetState OBJECT-TYPE
                SYNTAX INTEGER { disabled(1), routerDiscovery(2),
                                 full(3) }
                ACCESS read-write
                STATUS mandatory
                DESCRIPTION
                    "This value controls the RIP protocol on this 
                    network."
                DEFVAL { full }
                ::= { ripNetEntry 2 }

            ripNetRipsIn OBJECT-TYPE
                SYNTAX Counter
                ACCESS read-only
                STATUS mandatory
                DESCRIPTION
                    "The number of RIP packets received from routers on 
                    this IP network."
                ::= { ripNetEntry 3 }

            ripNetRipsOut OBJECT-TYPE
                SYNTAX Counter
                ACCESS read-only
                STATUS mandatory
                DESCRIPTION
                    "The number of RIP packets sent to routers on this 
                    IP network."
                ::= { ripNetEntry 4 }

            ripNetAlgorithm OBJECT-TYPE
                SYNTAX INTEGER { poisonedReverse(1), splitHorizon(2) }
                ACCESS read-write
                STATUS mandatory
                DESCRIPTION
                    "This value controls the RIP algorithm on this 
                    network."
                ::= { ripNetEntry 5 }

            --  the lpd group

            --  Implementation of this group is mandatory for all iTouch 
            --  systems that implement lpd.

            --  The lpd Queue table

            lpdQueueTable OBJECT-TYPE
                SYNTAX SEQUENCE OF LpdQueueEntry
                ACCESS not-accessible
                STATUS mandatory
                DESCRIPTION
                    "A list of lpd queues on the server."
                ::= { xlpd 1 }

            lpdQueueEntry OBJECT-TYPE
                SYNTAX LpdQueueEntry
                ACCESS not-accessible
                STATUS mandatory
                DESCRIPTION
                    "Lpd parameter values plus counters for an 
                     individual lpd queue."
                INDEX { lpdQueueName }
                ::= { lpdQueueTable 1 }

            LpdQueueEntry ::=
                SEQUENCE {
                    lpdQueueStatus
                        INTEGER,
                    lpdQueueName
                        DisplayString,
                    lpdQueuePorts
                        OCTET STRING,
                    lpdQueueEnabled
                        INTEGER,
                    lpdQueueLfConversion
                        INTEGER,
                    lpdQueueTotalJobs
                        Gauge,
                    lpdQueueActiveJobs
                        Gauge,
                    lpdQueueWaitingJobs
                        Gauge,
                    lpdQueueProcessedJobs
                        Counter,
                    lpdQueueFormFeed
                        INTEGER,
                    lpdQueueBypass
                        INTEGER
                }

            lpdQueueStatus OBJECT-TYPE
                SYNTAX INTEGER { invalid(1), valid(2) }
                ACCESS read-write
                STATUS mandatory
                DESCRIPTION
                    "Status of this entry.  Setting the value to
                    'invalid' invalidates the entry, corresponding
                    directly to the CLEAR/PURGE SERVER LPD QUEUE 
                    command.  Setting the value to 'valid' validates
                    (creates) the entry, corresonding directly to 
                    the DEF/SET SERVER LPD QUEUE and lpd create 
                    commands."
                DEFVAL { valid }
                ::= { lpdQueueEntry 1 }

            lpdQueueName OBJECT-TYPE
                SYNTAX DisplayString (SIZE (1..16))
                ACCESS read-only
                STATUS mandatory
                DESCRIPTION
                    "Name of the LPD queue, case sensitive."
                ::= { lpdQueueEntry 2 }

            lpdQueuePorts OBJECT-TYPE
                SYNTAX OCTET STRING (SIZE (16))
                ACCESS read-write
                STATUS mandatory
                DESCRIPTION
                    "List of ports assigned to the queue.  An lpd queue 
                     can be associated with more than 1 port.  This 
                     object corresponds to the port-list in the
                     DEF/SET SERVER LPD QUEUE and lpc/create commands.
		     The OCTET STRING contains a bitmap, with one bit for
                     each port, and enough octets for all the ports on
                     the system.  Port numbers are as defined for
                     charPortIndex in the Character MIB [11].
                     Corresponding bit numbers start with 1 as the
                     high-order bit of the first octet. "
                ::= { lpdQueueEntry 3 }

            lpdQueueEnabled OBJECT-TYPE
                SYNTAX INTEGER { disabled(1), enabled(2) }
                ACCESS read-write
                STATUS mandatory
                DESCRIPTION
                    "Flag indicates if the queue is enabled.  A 'disabled'
                     queue will reject print requests from remote systems.
                     A 'enabled' queue accepts requests for printing."
		DEFVAL { disabled }
                ::= { lpdQueueEntry 4 }

            lpdQueueLfConversion OBJECT-TYPE
                SYNTAX INTEGER { lf(1), lfcr(2) }
                ACCESS read-write
                STATUS mandatory
                DESCRIPTION
                    "Flag indicates if the queue is converting linefeeds
                     to linefeeds, carriagereturns.  'lfcr' does the
                     converion, 'lf' does not."
		DEFVAL { lf }
                ::= { lpdQueueEntry 5 }

            lpdQueueTotalJobs OBJECT-TYPE
                SYNTAX Gauge
                ACCESS read-only
                STATUS mandatory
                DESCRIPTION
                    "The total number of jobs on the queue.  This number
                     should be equal to the number of active and waiting
                     jobs.  (lpdQueueActive + lpdQueueWaiting)"
                ::= { lpdQueueEntry 6 }

            lpdQueueActiveJobs OBJECT-TYPE
                SYNTAX Gauge
                ACCESS read-only
                STATUS mandatory
                DESCRIPTION
                    "The number of active jobs on the queue.  An active 
                     job is a job that has been assigned a port is in the
                     process of receiving data from a remote host and 
                     sending it out the port."
                ::= { lpdQueueEntry 7 }

            lpdQueueWaitingJobs OBJECT-TYPE
                SYNTAX Gauge
                ACCESS read-only
                STATUS mandatory
                DESCRIPTION
                    "The number of waiting jobs on the queue.  A waiting
                     job is a job that needs a port to send its data to.
                     This implies that the ports associated with this
                     queue are busy."
                ::= { lpdQueueEntry 8 }

            lpdQueueProcessedJobs OBJECT-TYPE
                SYNTAX Counter
                ACCESS read-only
                STATUS mandatory
                DESCRIPTION
                    "The total number of jobs processed by this queue
                     since server boot."
                ::= { lpdQueueEntry 9 }

            lpdQueueFormFeed OBJECT-TYPE
                SYNTAX INTEGER { formfeedafter(1), formfeedbefore(2),
                               formfeednone(3) }
                ACCESS read-write
                STATUS mandatory 
                DESCRIPTION
                     "A control to determine how we will send out a formfeed
                     when printing a lpd job. formfeedafter:  Send after job,
                     formfeedbefore: Send before job,
                     formfeednone: Send no formfeed."
                DEFVAL  { formfeedafter }
                ::= { lpdQueueEntry 10 }

            lpdQueueBypass OBJECT-TYPE 
                SYNTAX INTEGER { disabled(1), enabled(2) }
                ACCESS read-write
                STATUS mandatory
                DESCRIPTION
                     "Control for a queue to bypass a LPD port which has output
                      inhibited via flow control. Corresponds directly to the 
                      value labeled 'Bypass' in the SERVER LPD QUEUE display."
                DEFVAL { disabled }
                ::= { lpdQueueEntry 11 }
                

            -- lpd Job table

            lpdJobTable OBJECT-TYPE
                SYNTAX SEQUENCE OF LpdJobEntry
                ACCESS not-accessible
                STATUS mandatory
                DESCRIPTION
                    "A list of lpd jobs."
                ::= { xlpd 2 }

            lpdJobEntry OBJECT-TYPE
                SYNTAX LpdJobEntry
                ACCESS not-accessible
                STATUS mandatory
                DESCRIPTION
                    "A single lpd Job."
                INDEX { lpdQueueName, lpdJobNumber }
                ::= { lpdJobTable 1 }

            LpdJobEntry ::=
                SEQUENCE {
                    lpdJobStatus
                        INTEGER,
                    lpdJobNumber
                        INTEGER,
                    lpdJobAssignedPort
                        INTEGER,
                    lpdJobFileSize
                        INTEGER,
                    lpdJobHostName
                        DisplayString,
                    lpdJobFileName
                        DisplayString,
                    lpdJobState
                        INTEGER
                }

            lpdJobStatus OBJECT-TYPE
                SYNTAX INTEGER {invalid(1), valid(2)}
                ACCESS read-write
                STATUS mandatory
                DESCRIPTION
                    "Status of this entry.  Setting this object to
                     'invalid' will remove the job from the queue.  
                     Setting this object ot 'valid' has no effect since
                     the only way to create an lpd job is with the lpd
                     protocol."
                ::= { lpdJobEntry 1 }
        
            lpdJobNumber OBJECT-TYPE
                SYNTAX INTEGER (1..5000)
                ACCESS read-only
                STATUS mandatory
                DESCRIPTION
                    "The queue relative job number for this lpd job.  
                     Job numbers are assigned as jobs are accepted onto
                     the queue.  Job numbers are reset to 1 when they
                     reach a value greater than 1000 and the queue goes
                     empty."
                ::= { lpdJobEntry 2 }
        
            lpdJobAssignedPort OBJECT-TYPE
                SYNTAX INTEGER (0..256)
                ACCESS read-only
                STATUS mandatory
                DESCRIPTION
                    "The number of the port assigned to the lpd job."
                ::= { lpdJobEntry 3 }
        
            lpdJobFileSize OBJECT-TYPE
                SYNTAX INTEGER (0..2147483647)
                ACCESS read-only
                STATUS mandatory
                DESCRIPTION
                    "The size of the file being sent from the remote 
                     system."
                ::= { lpdJobEntry 4 }
        
            lpdJobHostName OBJECT-TYPE
                SYNTAX DisplayString (SIZE (1..34))
                ACCESS read-only
                STATUS mandatory
                DESCRIPTION
                    "The name of the host sending the job."
                ::= { lpdJobEntry 5 }
        
            lpdJobFileName OBJECT-TYPE
                SYNTAX DisplayString (SIZE (1..34))
                ACCESS read-only
                STATUS mandatory
                DESCRIPTION
                    "The name of the file being sent."
                ::= { lpdJobEntry 6 }

            lpdJobState OBJECT-TYPE
                SYNTAX INTEGER { initialized(1), waiting(2), 
                                 assigned(3), printingData(4),
                                 printingControl(5), aborted(6),
                                 completed(7), error(8),
                                 flushing(9) }
                ACCESS read-only
                STATUS mandatory
                DESCRIPTION
                    "The current state of the lpd job.  A typical job
                     transistions through the following states:
                     initialize->waiting->assigned->printingdata->
                     printingcontrol->completed."
                ::= { lpdJobEntry 7 }


            -- the SecurID group
            
            -- Implementation of this group is mandatory for all iTouch
            -- systems that implement a SecurID client
            
            securIDServerName0 OBJECT-TYPE
                SYNTAX DisplayString (SIZE (0..50))
                ACCESS read-write
                STATUS mandatory
                DESCRIPTION
                    "The Domain name of the first SecurID server to try 
                    when the system verifies a SecurID PASSCODE.  Corresponds 
                    directly to SERVER SECURID SERVER0 and the 
                    value labeled 'SecurID Server0:' in the 
                    SERVER SECURID display."
                ::= { xSecurID 1 }
            
            securIDServerName1 OBJECT-TYPE
                SYNTAX DisplayString (SIZE (0..50))
                ACCESS read-write
                STATUS mandatory
                DESCRIPTION
                    "The Domain name of the second SecurID server to try 
                    when the system verifies a SecurID PASSCODE.  Corresponds 
                    directly to SERVER SECURID SERVER1 and the 
                    value labeled 'SecurID Server1:' in the 
                    SERVER SECURID display."
                ::= { xSecurID 2 }
            
            securIDServerName2 OBJECT-TYPE
                SYNTAX DisplayString (SIZE (0..50))
                ACCESS read-write
                STATUS mandatory
                DESCRIPTION
                    "The Domain name of the third SecurID server to try 
                    when the system verifies a SecurID PASSCODE.  Corresponds 
                    directly to SERVER SECURID SERVER2 and the 
                    value labeled 'SecurID Server2:' in the 
                    SERVER SECURID display."
                ::= { xSecurID 3 }
            
            securIDServerName3 OBJECT-TYPE
                SYNTAX DisplayString (SIZE (0..50))
                ACCESS read-write
                STATUS mandatory
                DESCRIPTION
                    "The Domain name of the fourth SecurID server to try 
                    when the system verifies a SecurID PASSCODE.  Corresponds 
                    directly to SERVER SECURID SERVER3 and the 
                    value labeled 'SecurID Server3:' in the 
                    SERVER SECURID display."
                ::= { xSecurID 4 }
            
            securIDServerName4 OBJECT-TYPE
                SYNTAX DisplayString (SIZE (0..50))
                ACCESS read-write
                STATUS mandatory
                DESCRIPTION
                    "The Domain name of the fifth SecurID server to try 
                    when the system verifies a SecurID PASSCODE.  Corresponds 
                    directly to SERVER SECURID SERVER4 and the 
                    value labeled 'SecurID Server4:' in the 
                    SERVER SECURID display."
                ::= { xSecurID 5 }
            
            securIDMaxRetries OBJECT-TYPE
                SYNTAX INTEGER (1..10)
                ACCESS read-write
                STATUS mandatory
                DESCRIPTION
                    "The maximum number of times the server will 
                    try any single SecurID server to validate a
                    PASSCODE.  Corresponds directly to SERVER SECURID 
                    ACMMAXRETRIES and the value labeled 'SecurID 
                    ACMMAXRETRIES:' in the SERVER SECURID display."
                ::= { xSecurID 6 }
            
            securIDBaseTimeout OBJECT-TYPE
                SYNTAX INTEGER (1..10)
                ACCESS read-write
                STATUS mandatory
                DESCRIPTION
                    "The initial timeout value to be used between prompts
                    for a SecurID PASSCODE.
                    Corresponds directly to SERVER SECURID 
                    ACMBASETIMEOUT and the value labeled 'SecurID 
                    ACMBASETIMEOUT:' in the SERVER SECURID display."
                ::= { xSecurID 7 }
            
            securIDPort OBJECT-TYPE
                SYNTAX INTEGER (1..32767)
                ACCESS read-write
                STATUS mandatory
                DESCRIPTION
                    "The UDP port number to be used when communicating
                    with the SecurID servers. Corresponds directly to 
                    SERVER SECURID ACM_PORT and the value labeled 'SecurID 
                    ACM_PORT:' in the SERVER SECURID display."
                ::= { xSecurID 8 }
            
            securIDQueryLimit OBJECT-TYPE
                SYNTAX INTEGER (1..10)
                ACCESS read-write
                STATUS mandatory
                DESCRIPTION
                    "The maximum number of times a user will be queried 
                    for a SecurID PASSCODE before being logged out.
                    Corresponds directly to 
                    SERVER SECURID QUERY LIMIT and the value labeled 'SecurID 
                    Query Limit:' in the SERVER SECURID display."
                ::= { xSecurID 9 }
            
            securIDEncryptionMode OBJECT-TYPE
                SYNTAX INTEGER { sdiBlockCipher(1), des(2) }
                ACCESS read-write
                STATUS mandatory
                DESCRIPTION
                    "The type of encryption to use in SecurID validation.
                    Corresponds directly to the value labeled 'Encryption
                    Mode' in the SERVER SECURID display."
                ::= { xSecurID 10 }
            
            securIDInsecureLogins OBJECT-TYPE
                SYNTAX Counter
                ACCESS read-only
                STATUS mandatory
                DESCRIPTION
                    "The number of user logins on ports for which 
                    SecurID user verification is not enabled.  
                    Corresponds directly to the value labeled 'Logins 
                    without SecurID:' in the SERVER SECURID display."
                ::= { xSecurID 11 }
            
            securIDSecureLogins OBJECT-TYPE
                SYNTAX Counter
                ACCESS read-only
                STATUS mandatory
                DESCRIPTION
                    "The number of successful user logins on ports for 
                    which SecurID user verification is enabled.  
                    Corresponds directly to the value labeled 
                    'Successful Logins:' in the SERVER SECURID 
                    display."
                ::= { xSecurID 12 }
            
            securIDSecureLoginsFailed OBJECT-TYPE
                SYNTAX Counter
                ACCESS read-only
                STATUS mandatory
                DESCRIPTION
                    "The number of verification failures due to 
                    incorrect PASSCODE for attempted user logins 
                    on ports for which SecurID user verification is 
                    enabled.  Corresponds directly to the value labeled 
                    'Unsuccessful Logins:' in the SERVER SECURID 
                    display."
                ::= { xSecurID 13 }
            
            securIDServerAccess0 OBJECT-TYPE
                SYNTAX Counter
                ACCESS read-only
                STATUS mandatory
                DESCRIPTION
                    "The number of times the system successfully 
                    accessed the SecurID server0.  Corresponds 
                    directly to the value labeled 'Attempts to access:', 
                    'Server0', and 'Successful:' in the SERVER SECURID 
                    display."
                ::= { xSecurID 14 }
            
            securIDServerAccessFailed0 OBJECT-TYPE
                SYNTAX Counter
                ACCESS read-only
                STATUS mandatory
                DESCRIPTION
                    "The number of times the system unsuccessfully 
                    accessed the SecurID server0.  Corresponds 
                    directly to the value labeled 'Attempts to access:', 
                    'Server0', and 'UnSuccessful:' in the SERVER SECURID 
                    display."
                ::= { xSecurID 15 }
            
            securIDServerAccess1 OBJECT-TYPE
                SYNTAX Counter
                ACCESS read-only
                STATUS mandatory
                DESCRIPTION
                    "The number of times the system successfully 
                    accessed the SecurID server1.  Corresponds 
                    directly to the value labeled 'Attempts to access:', 
                    'Server1', and 'Successful:' in the SERVER SECURID 
                    display."
                ::= { xSecurID 16 }
            
            securIDServerAccessFailed1 OBJECT-TYPE
                SYNTAX Counter
                ACCESS read-only
                STATUS mandatory
                DESCRIPTION
                    "The number of times the system unsuccessfully 
                    accessed the SecurID server1.  Corresponds 
                    directly to the value labeled 'Attempts to access:', 
                    'Server1', and 'UnSuccessful:' in the SERVER SECURID 
                    display."
                ::= { xSecurID 17 }
            
            securIDServerAccess2 OBJECT-TYPE
                SYNTAX Counter
                ACCESS read-only
                STATUS mandatory
                DESCRIPTION
                    "The number of times the system successfully 
                    accessed the SecurID server2.  Corresponds 
                    directly to the value labeled 'Attempts to access:', 
                    'Server2', and 'Successful:' in the SERVER SECURID 
                    display."
                ::= { xSecurID 18 }
            
            securIDServerAccessFailed2 OBJECT-TYPE
                SYNTAX Counter
                ACCESS read-only
                STATUS mandatory
                DESCRIPTION
                    "The number of times the system unsuccessfully 
                    accessed the SecurID server2.  Corresponds 
                    directly to the value labeled 'Attempts to access:', 
                    'Server2', and 'UnSuccessful:' in the SERVER SECURID 
                    display."
                ::= { xSecurID 19 }
            
            securIDServerAccess3 OBJECT-TYPE
                SYNTAX Counter
                ACCESS read-only
                STATUS mandatory
                DESCRIPTION
                    "The number of times the system successfully 
                    accessed the SecurID server3.  Corresponds 
                    directly to the value labeled 'Attempts to access:', 
                    'Server3', and 'Successful:' in the SERVER SECURID 
                    display."
                ::= { xSecurID 20 }
            
            securIDServerAccessFailed3 OBJECT-TYPE
                SYNTAX Counter
                ACCESS read-only
                STATUS mandatory
                DESCRIPTION
                    "The number of times the system unsuccessfully 
                    accessed the SecurID server3.  Corresponds 
                    directly to the value labeled 'Attempts to access:', 
                    'Server3', and 'UnSuccessful:' in the SERVER SECURID 
                    display."
                ::= { xSecurID 21 }
            
            securIDServerAccess4 OBJECT-TYPE
                SYNTAX Counter
                ACCESS read-only
                STATUS mandatory
                DESCRIPTION
                    "The number of times the system successfully 
                    accessed the SecurID server4.  Corresponds 
                    directly to the value labeled 'Attempts to access:', 
                    'Server4', and 'Successful:' in the SERVER SECURID 
                    display."
                ::= { xSecurID 22 }
            
            securIDServerAccessFailed4 OBJECT-TYPE
                SYNTAX Counter
                ACCESS read-only
                STATUS mandatory
                DESCRIPTION
                    "The number of times the system unsuccessfully 
                    accessed the SecurID server4.  Corresponds 
                    directly to the value labeled 'Attempts to access:', 
                    'Server4', and 'UnSuccessful:' in the SERVER SECURID 
                    display."
                ::= { xSecurID 23 }
            
            securIDErrorPortIndex OBJECT-TYPE
                SYNTAX INTEGER (0..40)
                ACCESS read-only
                STATUS mandatory
                DESCRIPTION
                    "The index of the most recent port on which a SecurID 
                    access violation occurred.  Corresponds 
                    directly to the value labeled 'Last Unsuccessful
                    Login:' in the SERVER SECURID display."
                ::= { xSecurID 24 }
            
            securIDError OBJECT-TYPE
                SYNTAX INTEGER (0..40)
                ACCESS read-only
                STATUS mandatory
                DESCRIPTION
                    "The error number of the most recent SecurID-related
                    error.  Corresponds directly to the value labeled 
                    'Reason:' in the SERVER SECURID display.  See
                    iTouch documentation for a complete list of 
                    error numbers and their meaning."
                ::= { xSecurID 25 }
            
            securIDErrorUsername OBJECT-TYPE
                SYNTAX DisplayString (SIZE (0..17))
                ACCESS read-only
                STATUS mandatory
                DESCRIPTION
                    "The username associated with the most recent
                    SecurID-related error.  Corresponds directly to the value
                    labeled 'Username:' in the SERVER SECURID display."
                ::= { xSecurID 26 }
            
            
            -- the SecurID Port table
            
            securIDPortTable OBJECT-TYPE
                SYNTAX SEQUENCE OF SecurIDPortEntry
                ACCESS not-accessible
                STATUS mandatory
                DESCRIPTION
                    "A list of SecurID character port entries."
                ::= { xSecurID 27 }
            
            securIDPortEntry OBJECT-TYPE
                SYNTAX SecurIDPortEntry
                ACCESS not-accessible
                STATUS mandatory
                DESCRIPTION
                    "Parameter values for a SecurID port."
                INDEX { securIDPortIndex }
                ::= { securIDPortTable 1 }
            
            SecurIDPortEntry ::=
                SEQUENCE {
                    securIDPortIndex
                        INTEGER,
                    securIDPortStatus
                        INTEGER
                }
            
            securIDPortIndex OBJECT-TYPE
                SYNTAX INTEGER
                ACCESS read-only
                STATUS mandatory
                DESCRIPTION
                    "An index value that uniquely identifies a port 
                    could relate to SecurID.  The port identified by a 
                    particular value of this index is the same port as 
                    identified by charPortIndex in the Proposed Standard 
                    Internet Character MIB."
                ::= { securIDPortEntry 1 }
            
            securIDPortStatus OBJECT-TYPE
                SYNTAX INTEGER { disabled(1), enabled(2) }
                ACCESS read-write
                STATUS mandatory
                DESCRIPTION
                    "A control indicating the level of SecurID 
                    operation on the port.  Corresponds directly to PORT 
                    SECURID and the value 'SecurID' following the 
                    label 'Enabled Characteristics' in the PORT 
                    CHARACTERISTICS display."
                ::= { securIDPortEntry 2 }


-- the SSH Port Table

sshPortTable OBJECT-TYPE
   SYNTAX SEQUENCE OF SshPortEntry
   ACCESS not-accessible
   STATUS mandatory
   DESCRIPTION
      "A list of SSH port entries"
   ::= { xSsh 1 }

sshPortEntry OBJECT-TYPE
   SYNTAX SshPortEntry
   ACCESS not-accessible
   STATUS mandatory
   DESCRIPTION
      "Parameter values for an SSH port."
   INDEX { sshPortIndex }
   ::= { sshPortTable 1 }

SshPortEntry ::=
   SEQUENCE {
      sshPortIndex
         INTEGER,
      sshPortIncomingTcpPort
         INTEGER,
      sshPortNewlineFiltering
         INTEGER,
      sshPortNewline
         INTEGER,
      sshPortTransmitBufferedTime
         INTEGER,
      sshPortRemoteProtocol
         INTEGER
   }

sshPortIndex  OBJECT-TYPE
   SYNTAX INTEGER
   ACCESS read-only
   STATUS mandatory
   DESCRIPTION
      "An index value that uniquely identifies an SSH port. The port 
       identified by a particular value of this index is the same port as 
       identified by charPortIndex in the proposed standard Internet 
       Character MIB."
   ::= { sshPortEntry 1 }                

sshPortIncomingTcpPort  OBJECT-TYPE
   SYNTAX INTEGER (1..32767)
   ACCESS read-write
   STATUS mandatory
   DESCRIPTION
      "Specifies the TCP port number used to identify the port when a SSH
       connection request arrives at the server. The default for a physical
       port is 2022 + 100 * port's physical port number. The default is 22
       for virtual ports. Corresponds directly to the value labeled 'Remote 
       Port:' in the PORT SSH CHARACTERISTICS display."
   ::= { sshPortEntry 2 }                

sshPortNewlineFiltering  OBJECT-TYPE
   SYNTAX INTEGER { none(1), crToCrLf(2), crToCrNull(3), crLfToCr(4),
                    crLfToCrNull(5), crNullToCr(6), crNullToCrLf(7) }
   ACCESS read-write
   STATUS mandatory
   DESCRIPTION
      "Translation to apply to newline sequences (CR/NULL or CR/LF) received
       from the network during a SSH session, before sending the newline to 
       the character port. The value indicates which input sequence is 
       converted to which output sequence and sent to the 
       character port, with 'none' meaning no translation.
       Corresponds directly to the value labeled 'Newline Filtering:'
       in the PORT SSH CHARACTERISTICS display."
   DEFVAL { none }
   ::= { sshPortEntry 3 }                

sshPortNewline  OBJECT-TYPE
   SYNTAX INTEGER { none(1), crToCrLf(2), crToCrNull(3), crLfToCr(4),
                    crLfToCrNull(5), crNullToCr(6), crNullToCrLf(7) }
   ACCESS read-write
   STATUS mandatory
   DESCRIPTION
      "Translation to apply to newline (carriage return) received from the 
       character port during an SSH session, before sending the newline to the
       remote partner. Corresponds directly to the value labeled 'Newline:' 
       in the PORT SSH CHARACTERISTICS display."
   DEFVAL { none }       
   ::= { sshPortEntry 4 }                

sshPortTransmitBufferedTime  OBJECT-TYPE
   SYNTAX INTEGER (30..1500)
   ACCESS read-write
   STATUS mandatory
   DESCRIPTION
      "Number of milliseconds to wait before transmitting data received from 
       a character port during an interactive SSH session. 
       Corresponds directly to the value labeled 'Transmit Buffered Time:' in
       the PORT SSH CHARACTERISTICS display."
   DEFVAL { 80 } 
   ::= { sshPortEntry 5 }                

sshPortRemoteProtocol  OBJECT-TYPE
   SYNTAX INTEGER { ssh(1), telnet(2), both(3) }
   ACCESS read-write
   STATUS mandatory
   DESCRIPTION
      "Indicates which remote protocols will be accepted at this port.
       Corresponds indirectly to the presence of 'Telnet' or 'SSH' under the 
       label 'Enabled Characteristics:' in the PORT SSH CHARACTERISTICS 
       display. If both protocols are accepted at the port, the choice of 
       protocol is determined by which features are enabled on the server with
       SSH taking precedence over Telnet."
   DEFVAL { both }
   ::= { sshPortEntry 6 }                



sshCipherMask  OBJECT-TYPE
   SYNTAX OCTET STRING (SIZE (2)) 
   ACCESS read-write 
   STATUS mandatory
   DESCRIPTION
      "This is a list of the encryption methods supported.
       The OCTET STRING contains a bitmap, with one bit for each cipher type.
       Corresponding bit numbers start with 0 as the low-order bit of the
       second octet. The following bit positions are defined:  
       none(0), des(2), tripleDes(3), and blowfish(6). Corresponds directly to
       the value labeled 'SSH Cipher Enabled:' in the SERVER SSH 
       CHARACTERISTICS display."
   ::= { xSsh 2 }                

sshAuthenticationTimeout  OBJECT-TYPE
   SYNTAX INTEGER (1..120)
   ACCESS read-write
   STATUS mandatory
   DESCRIPTION
      "The timeout in minutes before disconnecting if no successful 
       authentication of SSH parties has been made. Corresponds directly to 
       the value labeled 'Authentication Timeout:' in the SERVER SSH 
       CHARACTERISTICS display."
   DEFVAL { 5 }
   ::= { xSsh 3 }                

sshHostKeyLength  OBJECT-TYPE
   SYNTAX INTEGER (512..2048)
   ACCESS read-write
   STATUS mandatory
   DESCRIPTION
      "The bit length of the SSH host encryption key. When modified, the 
      desired change does not occur until the next system initialization.
      Corresponds directly to the value labeled 'Host Key Length:' in the 
      SERVER SSH CHARACTERISTICS display."
   DEFVAL { 1024 }
   ::= { xSsh 4 }                

sshHostKeyGenerate  OBJECT-TYPE
   SYNTAX INTEGER { ready(1), generate(2), update(3) }
   ACCESS read-write
   STATUS mandatory
   DESCRIPTION
      "For a set-request with a value of generate or update, a new host key
       will be generated in the background. When modified with generate, the
       desired change does not occur until the next system initialization
       whereas when modified with update the change goes into effect upon
       completion of the new key.   

       In response to a get-request or a get-next-request the agent will
       respond ready except when a host key is being created in which case 
       the agent responds generate."
   ::= { xSsh 5 }                
  
sshServerKeyLength  OBJECT-TYPE
   SYNTAX INTEGER (512..2048)
   ACCESS read-write
   STATUS mandatory
   DESCRIPTION
      "The bit length of the SSH server encryption key. The difference between
       the server and host key lengths should be greater than 128 bits.
      Corresponds directly to the value labeled 'Server Key Length:' in the 
      SERVER SSH CHARACTERISTICS display."
   DEFVAL { 768 }
   ::= { xSsh 6 }                

sshServerKeyTtl  OBJECT-TYPE
   SYNTAX INTEGER (30..1440)
   ACCESS read-write
   STATUS mandatory
   DESCRIPTION
      "The time in minutes that the server key remains valid. After this time
       the server key is automatically re-generated. Corresponds directly to
       the value labeled 'Server Key Timeout:' in the SERVER SSH 
       CHARACTERISTICS display."
   DEFVAL { 60 }
   ::= { xSsh 7 }                

   sshServerMaxBufferSize OBJECT-TYPE
	SYNTAX INTEGER (4096..262144)
	ACCESS read-write
	STATUS mandatory
	DESCRIPTION
	    "The size of the four buffers used by SSH for input and
	     output. These buffers are used for data coming from the 
             console, going to the network, coming from the network and
	     going to the console."
	DEFVAL { 4096 }
	::= { xSsh 8 }

END
