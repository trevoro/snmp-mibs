-- *********************************************************************
-- CISCO-RSCN-MIB.my: Registered State Change Notificaton (RSCN) Mib
--
-- September 2002, H K Vivek
--
-- Copyright (c) 2002 by cisco Systems, Inc.
-- All rights reserved.
-- 
-- *********************************************************************
 
CISCO-RSCN-MIB DEFINITIONS ::= BEGIN

IMPORTS
        MODULE-IDENTITY,OBJECT-TYPE,
        NOTIFICATION-TYPE,
        Counter32,Integer32                FROM    SNMPv2-SMI
        MODULE-COMPLIANCE, OBJECT-GROUP,
        NOTIFICATION-GROUP                 FROM    SNMPv2-CONF
        TruthValue                         FROM    SNMPv2-TC
        ciscoMgmt                          FROM    CISCO-SMI
        FcAddressId                        FROM    CISCO-ST-TC
        vsanIndex                          FROM    CISCO-VSAN-MIB
        FcGs3RejectReasonCode              FROM    CISCO-NS-MIB;
          

ciscoRscnMIB  MODULE-IDENTITY
        LAST-UPDATED "200209200000Z"
        ORGANIZATION "Cisco Systems Inc."
        CONTACT-INFO 
                "     Cisco Systems
                      Customer Service
                Postal: 170 W Tasman Drive
                      San Jose, CA  95134
                      USA
                Tel: +1 800 553 -NETS
                E-mail: cs-san@cisco.com"
        DESCRIPTION
                "The MIB module for the management of the Fibre
                 Channel's Registered State Change Notification 
                 (RSCN) functionality, which is specified by
                 FC-FLA and FC-FS."
        REVISION "200209200000Z"
        DESCRIPTION
                "Initial version of this MIB module."
        ::= { ciscoMgmt 292 }


ciscoRscnMIBObjects OBJECT IDENTIFIER ::= { ciscoRscnMIB 1 }
rscnMIBConformance  OBJECT IDENTIFIER ::= { ciscoRscnMIB 2 }
rscnConfiguration   OBJECT IDENTIFIER ::= { ciscoRscnMIBObjects 1 }
rscnStats           OBJECT IDENTIFIER ::= { ciscoRscnMIBObjects 2 }
rscnInformation     OBJECT IDENTIFIER ::= { ciscoRscnMIBObjects 3 }
rscnNotification    OBJECT IDENTIFIER ::= { ciscoRscnMIBObjects 4 }
rscnNotifications   OBJECT IDENTIFIER ::= { rscnNotification 0 }

-- State Change Registration Table


rscnScrNumber OBJECT-TYPE
        SYNTAX         Integer32 (0..2147483647)
        MAX-ACCESS     read-only
        STATUS         current
        DESCRIPTION
                "The number of Nx_Ports currently registered
                 to receive RSCNs."
        ::= { rscnConfiguration 1 }

rscnScrTable  OBJECT-TYPE
        SYNTAX         SEQUENCE OF RscnScrEntry
        MAX-ACCESS     not-accessible
        STATUS         current
        DESCRIPTION
                "A table of Nx_Ports that have registered to
                 receive RSCNs on all VSANs configured on the 
                 local switch."
        ::= { rscnConfiguration 2 }

rscnScrEntry  OBJECT-TYPE
        SYNTAX        RscnScrEntry
        MAX-ACCESS    not-accessible
        STATUS        current
        DESCRIPTION
                "An entry (conceptual row) containing information
                 about one Nx_Port which has registered to receive
                 RSCNs on the VSAN indicated by vsanIndex."
        INDEX { vsanIndex, rscnScrFcId }
        ::= { rscnScrTable 1 }

RscnScrEntry ::= SEQUENCE {
        rscnScrFcId             FcAddressId,
        rscnScrRegType          INTEGER
}

rscnScrFcId  OBJECT-TYPE
        SYNTAX        FcAddressId
        MAX-ACCESS    not-accessible
        STATUS        current
        DESCRIPTION
                "The Fibre Channel Identifier (FC-ID) of the
                 subscribing Nx_Port."
        ::= { rscnScrEntry 1 }

rscnScrRegType  OBJECT-TYPE
        SYNTAX        INTEGER {
                       fromFabricCtrlr(1), -- RSCNs by Fab Controller
                       fromNxPort(2), -- RSCNs by Nx_Ports
                       fromBoth(3) -- RSCNs by both of the above
                      }
        MAX-ACCESS    read-only
        STATUS        current
        DESCRIPTION
                "This object indicates the type of registration
                 desired by the subscriber.

                 'fromFabricCtrlr' indicates RSCNs generated by the 
                 Fabric Controller.

                 'fromNxPort' indicates RSCNs generated by 
                 Nx_Ports.

                 'fromBoth' indicates RSCNs generated by Fabric
                 Controller and Nx_Ports."
        ::= { rscnScrEntry 2 }


-- Statistics

rscnScrTotalRejects OBJECT-TYPE
        SYNTAX         Counter32
        MAX-ACCESS     read-only
        STATUS         current
        DESCRIPTION
                "The total number of SCRs rejected
                 across all VSANs by the local switch."
        ::= { rscnStats 1 }

rscnRscnReqTotalRejects OBJECT-TYPE
        SYNTAX         Counter32
        MAX-ACCESS     read-only
        STATUS         current
        DESCRIPTION
                "The total number of RSCN requests rejected
                 across all VSANs by the local switch."
        ::= { rscnStats 2 }

rscnSwRscnReqTotalRejects OBJECT-TYPE
        SYNTAX         Counter32
        MAX-ACCESS     read-only
        STATUS         current
        DESCRIPTION
                "The total number of SW_RSCN requests rejected
                 across all VSANs by the local switch."
        ::= { rscnStats 3 }

rscnStatsTable  OBJECT-TYPE
        SYNTAX         SEQUENCE OF RscnStatsEntry
        MAX-ACCESS     not-accessible
        STATUS         current
        DESCRIPTION
                "The statistics related to the RSCN module. The
                 statistics are maintained per VSAN."
        ::= { rscnStats 4 }

rscnStatsEntry  OBJECT-TYPE
        SYNTAX        RscnStatsEntry
        MAX-ACCESS    not-accessible
        STATUS        current
        DESCRIPTION
                "An entry (conceptual row) in this table."
        INDEX { vsanIndex }
        ::= { rscnStatsTable 1 }

RscnStatsEntry ::= SEQUENCE {
        rscnRxScrs                      Counter32,
        rscnRxRscns                     Counter32,
        rscnTxRscns                     Counter32,
        rscnRxSwRscns                   Counter32,
        rscnTxSwRscns                   Counter32,
        rscnScrRej                      Counter32,
        rscnRscnReqRej                  Counter32,
        rscnSwRscnReqRej                Counter32
}

rscnRxScrs  OBJECT-TYPE
        SYNTAX         Counter32
        MAX-ACCESS     read-only
        STATUS         current
        DESCRIPTION
                "The number of SCRs received from Nx_Ports
                 on this VSAN."
        ::= { rscnStatsEntry 1 }


rscnRxRscns  OBJECT-TYPE
        SYNTAX         Counter32
        MAX-ACCESS     read-only
        STATUS         current
        DESCRIPTION
                "The number of RSCNs from Nx_Ports received on
                 this VSAN."
        ::= { rscnStatsEntry 2 }

rscnTxRscns  OBJECT-TYPE
        SYNTAX         Counter32
        MAX-ACCESS     read-only
        STATUS         current
        DESCRIPTION
                "The total number of RSCNs transmitted on this 
                 VSAN."
        ::= { rscnStatsEntry 3 }


rscnRxSwRscns  OBJECT-TYPE
        SYNTAX         Counter32
        MAX-ACCESS     read-only
        STATUS         current
        DESCRIPTION
                "The number of Inter-Switch Registered State
                 Change Notifications (SW_RSCN) received on this
                 VSAN from other switches."
        ::= { rscnStatsEntry 4 }

rscnTxSwRscns  OBJECT-TYPE
        SYNTAX         Counter32
        MAX-ACCESS     read-only
        STATUS         current
        DESCRIPTION
                "The number of Inter-Switch Registered State
                 Change Notifications (SW_RSCN) transmitted
                 on this VSAN to other switches."
        ::= { rscnStatsEntry 5 }


rscnScrRej  OBJECT-TYPE
        SYNTAX         Counter32
        MAX-ACCESS     read-only
        STATUS         current
        DESCRIPTION
                "The number of SCR rejected on this VSAN."
        ::= { rscnStatsEntry 6 }

rscnRscnReqRej OBJECT-TYPE
        SYNTAX         Counter32
        MAX-ACCESS     read-only
        STATUS         current
        DESCRIPTION
                "The number of RSCN requests rejected on this VSAN."
        ::= { rscnStatsEntry 7 }

rscnSwRscnReqRej  OBJECT-TYPE
        SYNTAX         Counter32
        MAX-ACCESS     read-only
        STATUS         current
        DESCRIPTION
                "The number of SW_RSCN requests rejected on this VSAN."
        ::= { rscnStatsEntry 8 }


-- Notification Information

rscnIlsRejReasonCode OBJECT-TYPE
        SYNTAX         FcGs3RejectReasonCode
        MAX-ACCESS     read-only
        STATUS         current
        DESCRIPTION
                "The reason code corresponding to an ILS
                 request rejection. This object contains the 
                 reason code corresponding to the most recent 
                 SCR or RSCN  request rejection by the RSCN 
                 module."
        ::= { rscnInformation 1 }

rscnElsRejReasonCode OBJECT-TYPE
        SYNTAX         FcGs3RejectReasonCode
        MAX-ACCESS     read-only
        STATUS         current
        DESCRIPTION
                "The reason code corresponding to an ELS
                 request rejection. This object contains the
                 reason code corresponding the most recent
                 SW_RSCN request rejection by the RSCN module."
        ::= { rscnInformation 2 }

-- Notification control objects
                                        
rscnIlsRejectReqNotifyEnable OBJECT-TYPE
        SYNTAX        TruthValue
        MAX-ACCESS    read-write
        STATUS        current
        DESCRIPTION
               "This object specifies if the RSCN module should
               generate 'rscnIlsRejectReqNotify' notifications.
                
               If value of this object is 'true', then the 
               notification is generated when a SW_RSCN request 
               is rejected. 

               If it is 'false', the notification is not generated."
        DEFVAL { false }
        ::= { rscnConfiguration 3 }

rscnElsRejectReqNotifyEnable OBJECT-TYPE
        SYNTAX        TruthValue
        MAX-ACCESS    read-write
        STATUS        current
        DESCRIPTION
               "This object specifies if the RSCN module should
               generate 'rscnElsRejectReqNotify' notifications.
                
               If value of this object is 'true', then the 
               notification is generated when a SCR or RSCN request 
               is rejected. 

               If it is 'false', the notification is not generated."
        DEFVAL { false }
        ::= { rscnConfiguration 4 }


rscnNotifyFcId OBJECT-TYPE
        SYNTAX        FcAddressId
        MAX-ACCESS    accessible-for-notify
        STATUS        current
        DESCRIPTION
                "The FC-ID of an Nx_Port. 
                 This object is to be used in the notifications:
                 rscnElsRejectReqNotify and rscnIlsRejectReqNotify.
                 This object is defined since the rscnScrFcId
                 object in the rscnScrTable is not-accessible."
        ::= { rscnConfiguration 5 }

-- Notifications

rscnElsRejectReqNotify NOTIFICATION-TYPE
        OBJECTS {rscnElsRejReasonCode, rscnNotifyFcId}
        STATUS  current
        DESCRIPTION
                "This notification is generated by the RSCN module 
                 on this switch whenever it rejects a SCR or RSCN 
                 request.

                 The RSCN module  should update the 
                 rscnElsRejReasonCode object with the corresponding 
                 reason code before sending the notification.

                 The rscnScrFcId object indicates the FC-ID of the 
                 sender of the request that was rejected."
        ::= { rscnNotifications 1 }

rscnIlsRejectReqNotify NOTIFICATION-TYPE
        OBJECTS {rscnIlsRejReasonCode, rscnNotifyFcId}
        STATUS  current
        DESCRIPTION
                "This notification is generated by the RSCN module 
                 on this switch whenever it rejects a SW_RSCN 
                 request.

                 The RSCN module  should update the 
                 rscnIlsRejReasonCode object with the corresponding 
                 reason code before sending the notification.

                 The rscnScrFcId object contains the FC-ID of the
                 sender of the request that was rejected."
        ::= { rscnNotifications 2 }



-- Conformance
rscnMIBCompliances OBJECT IDENTIFIER ::= { rscnMIBConformance 1 }
rscnMIBGroups      OBJECT IDENTIFIER ::= { rscnMIBConformance 2 }

rscnMIBCompliance MODULE-COMPLIANCE
        STATUS    current
        DESCRIPTION
                "The compliance statement for entities which 
                 implement RSCN feature."
        MODULE MANDATORY-GROUPS {rscnConfigGroup,
                                 rscnStatsGroup,
                                 rscnNotifyControlGroup,
                                 rscnNotifyGroup}   
        
        ::= { rscnMIBCompliances 1 }


-- Units of conformance

rscnConfigGroup         OBJECT-GROUP
        OBJECTS {rscnScrNumber,
                 rscnScrRegType,
                 rscnNotifyFcId}
        STATUS  current
        DESCRIPTION
                "A collection of objects for configuring
                 and displaying SCR entries."
        ::= { rscnMIBGroups 1 }

rscnStatsGroup         OBJECT-GROUP
        OBJECTS {rscnScrTotalRejects,
                 rscnRscnReqTotalRejects,
                 rscnSwRscnReqTotalRejects,
                 rscnRxScrs,
                 rscnRxRscns,
                 rscnTxRscns,
                 rscnRxSwRscns,
                 rscnTxSwRscns,
                 rscnScrRej,
                 rscnRscnReqRej,
                 rscnSwRscnReqRej}
        STATUS  current
        DESCRIPTION
                "A collection of objects for displaying 
                 RSCN statistics."
        ::= { rscnMIBGroups 2 }

rscnNotifyControlGroup         OBJECT-GROUP
        OBJECTS {rscnIlsRejReasonCode,
                 rscnElsRejReasonCode,
                 rscnIlsRejectReqNotifyEnable,
                 rscnElsRejectReqNotifyEnable}
        STATUS  current
        DESCRIPTION
                "A collection of notification control and
                 notification information objects."
        ::= { rscnMIBGroups 3 }

rscnNotifyGroup         NOTIFICATION-GROUP
        NOTIFICATIONS {rscnIlsRejectReqNotify,
                       rscnElsRejectReqNotify}
        STATUS        current
        DESCRIPTION
                "A collection of notifications for monitoring
                 ILS and ELS request rejection by the RSCN
                 module."
        ::= { rscnMIBGroups 4 }


END
