-- SNARLSNMP-MIB.txt
-- MIB generated by Stephan Wenzel
-- Saturday, December 14, 2002 at 16:00 GMT +01:00
--

	SNARLSNMP-MIB DEFINITIONS ::= BEGIN

		IMPORTS 
	TRAP-TYPE FROM RFC-1215
			enterprises, TimeTicks, Opaque, Integer32, 
			OBJECT-TYPE, MODULE-IDENTITY, NOTIFICATION-TYPE			
				FROM SNMPv2-SMI			
			DisplayString, TEXTUAL-CONVENTION			
				FROM SNMPv2-TC;
	
	
	      snarlsnmp MODULE-IDENTITY
			LAST-UPDATED "200212141400Z"
			ORGANIZATION
				"SnarlSNMP Dynamic Web Application Monitor Developers Group"
			CONTACT-INFO
				"http://snarl-snmp.org"
			DESCRIPTION
				"SnarlSNMP is an application to monitor dynamic web pages"
			::= { enterprises 15553 }
		
	
--
-- Textual conventions
--
	
		TruthValue ::= TEXTUAL-CONVENTION
			STATUS current
			DESCRIPTION
				"True is a boolean one and false is a bolean zero"
			SYNTAX INTEGER
				{
				false(0),
				true(1)
				}
			
		Comparative ::= TEXTUAL-CONVENTION
			STATUS current
			DESCRIPTION
				"True is a boolean one and false is a bolean zero"
			SYNTAX INTEGER
				{
				smaller(-1),
				equal(0),
				bigger(1)
				}

	      AgeComparative ::= TEXTUAL-CONVENTION
			STATUS current
			DESCRIPTION
				"True is a boolean one and false is a bolean zero"
			SYNTAX INTEGER
				{
				smaller(-1),
				equal(0),
				bigger(1)
				}

		Float ::= TEXTUAL-CONVENTION
			STATUS current
			DESCRIPTION
				"A single precision floating-point number.  The semantics
				and encoding are identical for type 'single' defined in
				IEEE Standard for Binary Floating-Point,
				ANSI/IEEE Std 754-1985.
				The value is restricted to the BER serialization of
				the following ASN.1 type:
				    FLOATTYPE ::= [120] IMPLICIT FloatType
				(note: the value 120 is the sum of '30'h and '48'h)
				The BER serialization of the length for values of
				this type must use the definite length, short
				encoding form.
				
				For example, the BER serialization of value 123
				of type FLOATTYPE is '9f780442f60000'h.  (The tag
				is '9f78'h; the length is '04'h; and the value is
				'42f60000'h.) The BER serialization of value
				'9f780442f60000'h of data type Opaque is
				'44079f780442f60000'h. (The tag is '44'h; the length
				is '07'h; and the value is '9f780442f60000'h."
			SYNTAX Opaque (SIZE (7))
			
	
--
-- Node definitions
--
	
		snarl OBJECT IDENTIFIER ::= { snarlsnmp 1 }
		
		snarlGlobalInfo OBJECT IDENTIFIER ::= { snarl 1 }
		
		snarlTotalTaskCount OBJECT-TYPE
			SYNTAX Integer32
			MAX-ACCESS read-only
			STATUS current
			DESCRIPTION
				"The total number of configured tasks within snarl"
			::= { snarlGlobalInfo 1 }
-- The total number of assigned tasks.
		
		snarlTotalTransfers OBJECT-TYPE
			SYNTAX Integer32
			MAX-ACCESS read-only
			STATUS current
			DESCRIPTION
				"The total number of transfers done."
			::= { snarlGlobalInfo 2 }
		
		snarlTotalTransferVolume OBJECT-TYPE
			SYNTAX Integer32
			MAX-ACCESS read-only
			STATUS current
			DESCRIPTION
				"The total transfer volume in number of bytes."
			::= { snarlGlobalInfo 3 }
		
		siteTable OBJECT-TYPE
			SYNTAX SEQUENCE OF SiteEntry
			MAX-ACCESS not-accessible
			STATUS current
			DESCRIPTION
				"The table of monitored URLs."
			::= { snarl 2 }
		
		siteEntry OBJECT-TYPE
			SYNTAX SiteEntry
			MAX-ACCESS not-accessible
			STATUS current
			DESCRIPTION
				"The data table of one monitored URL."
			INDEX { siteIndex }
			::= { siteTable 1 }
		
		SiteEntry ::=
			SEQUENCE { 
				siteIndex
					Integer32,
				siteName
					DisplayString,
				siteID
					DisplayString,
				siteInterval
					Integer32,
				siteURL
					DisplayString,
				siteDynamicURLRegexPattern
					DisplayString,
				siteDynmaicURLRegexCompilation
					DisplayString,
				siteDynmaicURLRegexError
					DisplayString,
				siteDynamicURL
					DisplayString,
				siteGetDynamicURLFrom
					DisplayString,
				siteProxy
					DisplayString,
				siteMultiFormData
					DisplayString,
				siteFormData
					DisplayString,
				siteEffectiveURL
					DisplayString,
				siteURLHTTPCode
					Integer32,
				sitePerformanceDNS
					Integer32,
				sitePerformanceConnect
					Integer32,
				sitePerformanceFirstByte
					Integer32,
				sitePerformanceTotal
					Integer32,
				sitePerformanceTotalWarningThreshold
					Integer32,
				sitePerformanceTotalCriticalThreshold
					Integer32,
				siteRegexPattern
					DisplayString,
				siteRegexCompilation
					DisplayString,
				siteRegexPatternMatchFlag
					TruthValue,
				siteRegexPatternAlertOnMatch
					TruthValue,
				siteContentMatchSize
					Integer32,
				siteContentActualSize
					Integer32,
				siteContentSizeMatchFlag
					INTEGER,
				siteContentSizeAlertOnMatch
					TruthValue,
				siteURLContentPattern
					DisplayString,
				siteURLContentPatternMatchFlag
					TruthValue,
				siteURLContentPatternAlertOnMatch
					TruthValue,
				siteURLContentPatternProxy
					DisplayString,
				siteURLContentPatternHTTPCode
					Integer32,
				siteURLSize
					DisplayString,
				siteURLSizeMatchFlag
					TruthValue,
				siteURLSizeAlertOnMatch
					TruthValue,
				siteURLSizeProxy
					DisplayString,
				siteURLSizeHTTPCode
					Integer32,
				siteFetchRegex
					DisplayString,
				siteFetchRegexCompilationError
					DisplayString,
				siteFetchRegexMatchingError
					DisplayString,
				siteFetchRegexSubResult0
					DisplayString,
				siteFetchRegexSubResult1
					DisplayString,
				siteFetchRegexSubResult2
					DisplayString,
				siteFetchRegexSubResult3
					DisplayString,
				siteFetchRegexSubResult4
					DisplayString,
				siteFetchRegexSubResult5
					DisplayString,
				siteFetchRegexSubResult6
					DisplayString,
				siteFetchRegexSubResult7
					DisplayString,
				siteAppendRegexResultFrom
					DisplayString,
				siteAppendRegexResultFromIndex
					Integer32,
				siteNumericalRegexSubMatch
					Integer32,
				siteNumericalPattern
					DisplayString,
				siteNumericalAlertOn
					AgeComparative,
				siteFileTime
					Integer32,
				siteDateAgeRegexConstruct
					DisplayString,
				siteDateAgePattern
					DisplayString,
				siteDateAgeAlertOn
					AgeComparative,
				siteTaskSuspendStart
					DisplayString,
				siteTaskSuspendEnd
					DisplayString,
				siteStatusNormal
					TruthValue,
				siteStatusWarning
					TruthValue,
				siteStatusCritical
					TruthValue,
				siteGroupStatusNormal
					TruthValue,
				siteGroupStatusWarning
					TruthValue,
				siteGroupStatusCritical
					TruthValue,
				siteReliability
					Integer32,
				siteMTBWarnings
					TimeTicks,
				siteMTTRWarnings
					TimeTicks,
				siteAccumulatedWarnings
					Integer32,
				siteMTBCriticals
					TimeTicks,
				siteMTTRCriticals
					TimeTicks,
				siteAccumulatedCriticals
					Integer32,
				siteGroupReliability
					Integer32,
				siteGroupMTBWarnings
					TimeTicks,
				siteGroupMTTRWarnings
					TimeTicks,
				siteGroupAccumulatedWarnings
					Integer32,
				siteGroupMTBCriticals
					TimeTicks,
				siteGroupMTTRCriticals
					TimeTicks,
				siteGroupAccumulatedCriticals
					Integer32,
				siteLastRunRelativeTime
					TimeTicks,
				siteLastRunAbsTimeString
					DisplayString,
				siteNextRunRelativeTime
					TimeTicks,
				siteNextRunAbsTimeString
					DisplayString,
				siteFirstRun
					DisplayString,
				siteTotalTransfers
					Integer32,
				siteTotalTransferVolume
					Integer32
			 }

		siteIndex OBJECT-TYPE
			SYNTAX Integer32 (1..65535)
			MAX-ACCESS read-only
			STATUS current
			DESCRIPTION
				"The index number for this task."
			::= { siteEntry 1 }
		
		siteName OBJECT-TYPE
			SYNTAX DisplayString
			MAX-ACCESS read-only
			STATUS current
			DESCRIPTION
				"The group name of the site directive this task belongs to."
			::= { siteEntry 2 }
		
		siteID OBJECT-TYPE
			SYNTAX DisplayString
			MAX-ACCESS read-only
			STATUS current
			DESCRIPTION
				"The URL ID of this task."
			::= { siteEntry 3 }
		
		siteInterval OBJECT-TYPE
			SYNTAX Integer32
			MAX-ACCESS read-only
			STATUS current
			DESCRIPTION
				"The interval between two consecutive checks in seconds."
			::= { siteEntry 4 }
		
		siteURL OBJECT-TYPE
			SYNTAX DisplayString
			MAX-ACCESS read-only
			STATUS current
			DESCRIPTION
				"The URL in full notation."
			::= { siteEntry 5 }
		
		siteDynamicURLRegexPattern OBJECT-TYPE
			SYNTAX DisplayString
			MAX-ACCESS read-only
			STATUS current
			DESCRIPTION
				"The regular expression pattern to be applied when searching for a URL in a downloaded document."
			::= { siteEntry 6 }
		
		siteDynmaicURLRegexCompilation OBJECT-TYPE
			SYNTAX DisplayString
			MAX-ACCESS read-only
			STATUS current
			DESCRIPTION
				"The result of the regular expression compilation."
			::= { siteEntry 7 }
		
		siteDynmaicURLRegexError OBJECT-TYPE
			SYNTAX DisplayString
			MAX-ACCESS read-only
			STATUS current
			DESCRIPTION
				"The error code of the regular expression match"
			::= { siteEntry 8 }
		
		siteDynamicURL OBJECT-TYPE
			SYNTAX DisplayString
			MAX-ACCESS read-only
			STATUS current
			DESCRIPTION
				"The dynamic URL that was fetched from another document for this task."
			::= { siteEntry 9 }
		
		siteGetDynamicURLFrom OBJECT-TYPE
			SYNTAX DisplayString
			MAX-ACCESS read-only
			STATUS current
			DESCRIPTION
				"The task Id from which to fetch the dynamic URL."
			::= { siteEntry 10 }
		
		siteProxy OBJECT-TYPE
			SYNTAX DisplayString
			MAX-ACCESS read-only
			STATUS current
			DESCRIPTION
				"The access method of the URL - direct (empty) or via proxy."
			::= { siteEntry 11 }
		
		siteMultiFormData OBJECT-TYPE
			SYNTAX DisplayString
			MAX-ACCESS read-only
			STATUS current
			DESCRIPTION
				"The multi form data for a http POST oeration."
			::= { siteEntry 12 }
		
		siteFormData OBJECT-TYPE
			SYNTAX DisplayString
			MAX-ACCESS read-only
			STATUS current
			DESCRIPTION
				"The effective multi form data for a http POST oeration,
				containing dynamically appended data."
			::= { siteEntry 13 }
		
		siteEffectiveURL OBJECT-TYPE
			SYNTAX DisplayString
			MAX-ACCESS read-only
			STATUS current
			DESCRIPTION
				"The effective URL, it my differ from siteURL
				by following http redirects or by fetching dynamic URL's."
			::= { siteEntry 14 }
		
		siteURLHTTPCode OBJECT-TYPE
			SYNTAX Integer32
			MAX-ACCESS read-only
			STATUS current
			DESCRIPTION
				"The result code of the last http operation with the main URL of this task."
			::= { siteEntry 15 }
		
		sitePerformanceDNS OBJECT-TYPE
			SYNTAX Integer32
			MAX-ACCESS read-only
			STATUS current
			DESCRIPTION
				"The cumulative elapsed time for the DNS lookup in milliseconds.
				This time is the sum of all DNS lookup times when following http redirects."
			::= { siteEntry 16 }
		
		sitePerformanceConnect OBJECT-TYPE
			SYNTAX Integer32
			MAX-ACCESS read-only
			STATUS current
			DESCRIPTION
				"The cumulative elapsed time until the connection was established.
				This time is the sum of all connection times when following http redirects."
			::= { siteEntry 17 }
		
		sitePerformanceFirstByte OBJECT-TYPE
			SYNTAX Integer32
			MAX-ACCESS read-only
			STATUS current
			DESCRIPTION
				"The time elapsed until the first byte was received in milliseconds.
				This time is the sum of all elapsed first byte reception times when following http redirects."
			::= { siteEntry 18 }
		
		sitePerformanceTotal OBJECT-TYPE
			SYNTAX Integer32
			MAX-ACCESS read-only
			STATUS current
			DESCRIPTION
				"The total time elapsed until the transaction is over.
				This time is absolute for the last transaction only."
			::= { siteEntry 19 }
		
		sitePerformanceTotalWarningThreshold OBJECT-TYPE
			SYNTAX Integer32
			MAX-ACCESS read-only
			STATUS current
			DESCRIPTION
				"The threshold in ms for when a WARNING trap will be sent."
			::= { siteEntry 20 }
		
		sitePerformanceTotalCriticalThreshold OBJECT-TYPE
			SYNTAX Integer32
			MAX-ACCESS read-only
			STATUS current
			DESCRIPTION
				"The threshold in ms for when a CRITICAL trap will be sent."
			::= { siteEntry 21 }
		
		siteRegexPattern OBJECT-TYPE
			SYNTAX DisplayString
			MAX-ACCESS read-only
			STATUS current
			DESCRIPTION
				"The regular expression for a pattern match on the contents of the URL."
			::= { siteEntry 22 }
		
		siteRegexCompilation OBJECT-TYPE
			SYNTAX DisplayString
			MAX-ACCESS read-only
			STATUS current
			DESCRIPTION
				"The result of the regular expression compilation for the URL content match regular expression."
			::= { siteEntry 23 }
		
		siteRegexPatternMatchFlag OBJECT-TYPE
			SYNTAX TruthValue
			MAX-ACCESS read-only
			STATUS current
			DESCRIPTION
				"Flag 0 (false) means no match, 1 (true) means match."
			::= { siteEntry 24 }
		
		siteRegexPatternAlertOnMatch OBJECT-TYPE
			SYNTAX TruthValue
			MAX-ACCESS read-only
			STATUS current
			DESCRIPTION
				"If true  a trap will be sent if URL content matches regular expression.
				If false a trap will be sent if URL content does not match regular expression."
			::= { siteEntry 25 }
		
		siteContentMatchSize OBJECT-TYPE
			SYNTAX Integer32
			MAX-ACCESS read-only
			STATUS current
			DESCRIPTION
				"The static size of the URL to be matched."
			::= { siteEntry 26 }
		
		siteContentActualSize OBJECT-TYPE
			SYNTAX Integer32
			MAX-ACCESS read-only
			STATUS current
			DESCRIPTION
				"The actual size of the downloaded URL."
			::= { siteEntry 27 }
		
		siteContentSizeMatchFlag OBJECT-TYPE
			SYNTAX Comparative
			MAX-ACCESS read-only
			STATUS current
			DESCRIPTION
				"Flag 0 (smaller) means URL content size is smaller than siteContentMatchSize,
				 Flag 1 (equal)   means URL content size is of same siteContentMatchSize,
				 Flag 2 (bigger)  means URL content size is bigger than siteContentMatchSize.
				"
			::= { siteEntry 28 }
		
		siteContentSizeAlertOnMatch OBJECT-TYPE
			SYNTAX TruthValue
			MAX-ACCESS read-only
			STATUS current
			DESCRIPTION
				"If true  a trap will be sent if URL content size matches.
				If false a trap will be sent if URL content size does not match."
			::= { siteEntry 29 }
		
		siteURLContentPattern OBJECT-TYPE
			SYNTAX DisplayString
			MAX-ACCESS read-only
			STATUS current
			DESCRIPTION
				"The URL of the contents to be matched against the contents of this URL."
			::= { siteEntry 30 }
		
		siteURLContentPatternMatchFlag OBJECT-TYPE
			SYNTAX TruthValue
			MAX-ACCESS read-only
			STATUS current
			DESCRIPTION
				"Flag 0 (false) means no match,
				Flag 1 (true)  means contents matches."
			::= { siteEntry 31 }
		
		siteURLContentPatternAlertOnMatch OBJECT-TYPE
			SYNTAX TruthValue
			MAX-ACCESS read-only
			STATUS current
			DESCRIPTION
				"If true  a trap will be sent if both URL contents match.
				If false a trap will be sent if both URL contents do not match."
			::= { siteEntry 32 }
		
		siteURLContentPatternProxy OBJECT-TYPE
			SYNTAX DisplayString
			MAX-ACCESS read-only
			STATUS current
			DESCRIPTION
				"The proxy for URL of siteURLContentPattern."
			::= { siteEntry 33 }
		
		siteURLContentPatternHTTPCode OBJECT-TYPE
			SYNTAX Integer32
			MAX-ACCESS read-only
			STATUS current
			DESCRIPTION
				"The result code of the last http operation with the siteURLContentPattern URL of this task."
			::= { siteEntry 34 }
		
		siteURLSize OBJECT-TYPE
			SYNTAX DisplayString
			MAX-ACCESS read-only
			STATUS current
			DESCRIPTION
				"The URL which content size in number of bytes needs to be matched against the content size in number of bytes of this URL."
			::= { siteEntry 35 }
		
		siteURLSizeMatchFlag OBJECT-TYPE
			SYNTAX TruthValue
			MAX-ACCESS read-only
			STATUS current
			DESCRIPTION
				"Flag 0 (false) means contents size of URL matches the size in number of bytes of this URL.
				Flag 1 (true)  means contents size of URL does not match the content size in number of bytes of this URL,
				"
			::= { siteEntry 36 }
		
		siteURLSizeAlertOnMatch OBJECT-TYPE
			SYNTAX TruthValue
			MAX-ACCESS read-only
			STATUS current
			DESCRIPTION
				"Flag 1 (true)  means a trap will be sent if both URL content sizes in number of bytes match.
				Flag 0 (false) means a trap will be sent if both URL content sizes in number of bytes do not match."
			::= { siteEntry 37 }
		
		siteURLSizeProxy OBJECT-TYPE
			SYNTAX DisplayString
			MAX-ACCESS read-only
			STATUS current
			DESCRIPTION
				"The proxy for URL of siteURLSize."
			::= { siteEntry 38 }
		
		siteURLSizeHTTPCode OBJECT-TYPE
			SYNTAX Integer32
			MAX-ACCESS read-only
			STATUS current
			DESCRIPTION
				"he result code of the last http operation with the siteURLSize URL of this task."
			::= { siteEntry 39 }
		
		siteFetchRegex OBJECT-TYPE
			SYNTAX DisplayString
			MAX-ACCESS read-only
			STATUS current
			DESCRIPTION
				"The regular expression to be matched against the content of this URL.
				The regular expression match result is kept in siteFetchRegexSubResult 0 - 3 for subpatterns."
			::= { siteEntry 40 }
		
		siteFetchRegexCompilationError OBJECT-TYPE
			SYNTAX DisplayString
			MAX-ACCESS read-only
			STATUS current
			DESCRIPTION
				"The result of the regular expression compilation for the siteFetchRegex regular expression."
			::= { siteEntry 41 }
		
		siteFetchRegexMatchingError OBJECT-TYPE
			SYNTAX DisplayString
			MAX-ACCESS read-only
			STATUS current
			DESCRIPTION
				"The error message for the regular expression match for the siteFetchRegex regular expression."
			::= { siteEntry 42 }
		
		siteFetchRegexSubResult0 OBJECT-TYPE
			SYNTAX DisplayString
			MAX-ACCESS read-only
			STATUS current
			DESCRIPTION
				"The siteFetchRegex sub pattern 0."
			::= { siteEntry 43 }
		
		siteFetchRegexSubResult1 OBJECT-TYPE
			SYNTAX DisplayString
			MAX-ACCESS read-only
			STATUS current
			DESCRIPTION
				"The siteFetchRegex sub pattern 1."
			::= { siteEntry 44 }
		
		siteFetchRegexSubResult2 OBJECT-TYPE
			SYNTAX DisplayString
			MAX-ACCESS read-only
			STATUS current
			DESCRIPTION
				"The siteFetchRegex sub pattern 2."
			::= { siteEntry 45 }
		
		siteFetchRegexSubResult3 OBJECT-TYPE
			SYNTAX DisplayString
			MAX-ACCESS read-only
			STATUS current
			DESCRIPTION
				"The siteFetchRegex sub pattern 3."
			::= { siteEntry 46 }
		
		siteFetchRegexSubResult4 OBJECT-TYPE
			SYNTAX DisplayString
			MAX-ACCESS read-only
			STATUS current
			DESCRIPTION
				"The siteFetchRegex sub pattern 4."
			::= { siteEntry 47 }
		
		siteFetchRegexSubResult5 OBJECT-TYPE
			SYNTAX DisplayString
			MAX-ACCESS read-only
			STATUS current
			DESCRIPTION
				"The siteFetchRegex sub pattern 5."
			::= { siteEntry 48 }
		
		siteFetchRegexSubResult6 OBJECT-TYPE
			SYNTAX DisplayString
			MAX-ACCESS read-only
			STATUS current
			DESCRIPTION
				"The siteFetchRegex sub pattern 6."
			::= { siteEntry 49 }
		
		siteFetchRegexSubResult7 OBJECT-TYPE
			SYNTAX DisplayString
			MAX-ACCESS read-only
			STATUS current
			DESCRIPTION
				"The siteFetchRegex sub pattern 7."
			::= { siteEntry 50 }
		
		siteAppendRegexResultFrom OBJECT-TYPE
			SYNTAX DisplayString
			MAX-ACCESS read-only
			STATUS current
			DESCRIPTION
				"The ID of the URL within this group from that a regular expression match result should be appended to the main URL of this task."
			::= { siteEntry 51 }
		
		siteAppendRegexResultFromIndex OBJECT-TYPE
			SYNTAX Integer32
			MAX-ACCESS read-only
			STATUS current
			DESCRIPTION
				"The index 0 - 7 for the regular expression sub pattern result
				that should be appended to the main URL of this task."
			::= { siteEntry 52 }
		
		siteNumericalRegexSubMatch OBJECT-TYPE
			SYNTAX Integer32
			MAX-ACCESS read-only
			STATUS current
			DESCRIPTION
				"The index number of the regular expression match result from
				the FetchRegex directive to be used in this numerical match."
			::= { siteEntry 53 }
		
		siteNumericalPattern OBJECT-TYPE
			SYNTAX DisplayString
			MAX-ACCESS read-only
			STATUS current
			DESCRIPTION
				"The number in string form to compare with the siteNumericalRegexSubMatch."
			::= { siteEntry 54 }
		
		siteNumericalAlertOn OBJECT-TYPE
			SYNTAX Comparative
			MAX-ACCESS read-only
			STATUS current
			DESCRIPTION
				"The action code for alerting smaller, equal or bigger."
			::= { siteEntry 55 }
		
		siteFileTime OBJECT-TYPE
			SYNTAX Integer32
			MAX-ACCESS read-only
			STATUS current
			DESCRIPTION
				"The time this downloaded file time was created.
				(if supported by respective protocol)."
			::= { siteEntry 56 }
		
		siteDateAgeRegexConstruct OBJECT-TYPE
			SYNTAX DisplayString
			MAX-ACCESS read-only
			STATUS current
			DESCRIPTION
				"The string constructed from static text and the submatches from FetchRegex.
				(Example: $2/$1/$3)"
			::= { siteEntry 57 }
		
		siteDateAgePattern OBJECT-TYPE
			SYNTAX DisplayString
			MAX-ACCESS read-only
			STATUS current
			DESCRIPTION
				"The amount of time in string form to compare with the sitedateAgeRegexCandidate."
			::= { siteEntry 58 }
		
		siteDateAgeAlertOn OBJECT-TYPE
			SYNTAX AgeComparative
			MAX-ACCESS read-only
			STATUS current
			DESCRIPTION
				"The action code for alerting younger, equal or older"
			::= { siteEntry 59 }
		
		siteTaskSuspendStart OBJECT-TYPE
			SYNTAX DisplayString
			MAX-ACCESS read-only
			STATUS current
			DESCRIPTION
				"Next time this task will be suspended."
			::= { siteEntry 60 }
		
		siteTaskSuspendEnd OBJECT-TYPE
			SYNTAX DisplayString
			MAX-ACCESS read-only
			STATUS current
			DESCRIPTION
				"Next time this task will be reactivated vom suspension."
			::= { siteEntry 61 }
		
		siteStatusNormal OBJECT-TYPE
			SYNTAX TruthValue
			MAX-ACCESS read-only
			STATUS current
			DESCRIPTION
				"True if this task is currently at status NORMAL false if at other status."
			::= { siteEntry 62 }
		
		siteStatusWarning OBJECT-TYPE
			SYNTAX TruthValue
			MAX-ACCESS read-only
			STATUS current
			DESCRIPTION
				"True if this task is currently at status WARNING or CRITICAL false if at other status."
			::= { siteEntry 63 }
		
		siteStatusCritical OBJECT-TYPE
			SYNTAX TruthValue
			MAX-ACCESS read-only
			STATUS current
			DESCRIPTION
				"True if this task is currently at status CRITICAL false if at other status."
			::= { siteEntry 64 }
		
		siteGroupStatusNormal OBJECT-TYPE
			SYNTAX TruthValue
			MAX-ACCESS read-only
			STATUS current
			DESCRIPTION
				"True if the group this task belongs to is currently at status
				NORMAL false if at other status."
			::= { siteEntry 65 }
		
		siteGroupStatusWarning OBJECT-TYPE
			SYNTAX TruthValue
			MAX-ACCESS read-only
			STATUS current
			DESCRIPTION
				"True if the group this task belongs to is currently at status
				WARNING or CRITICAL false if at other status."
			::= { siteEntry 66 }
		
		siteGroupStatusCritical OBJECT-TYPE
			SYNTAX TruthValue
			MAX-ACCESS read-write
			STATUS current
			DESCRIPTION
				"True if the group this task belongs to is currently at status
				CRITICAL false if at other status."
			::= { siteEntry 67 }
		
		siteReliability OBJECT-TYPE
			SYNTAX Integer32
			MAX-ACCESS read-only
			STATUS current
			DESCRIPTION
				"The reliability measure for this task measured in 
				(accumulated time at status WARNING + accumulated time at status CRITICAL)
				divided by (accumulated running time of this task) * 10000."
			::= { siteEntry 68 }
		
		siteMTBWarnings OBJECT-TYPE
			SYNTAX TimeTicks
			MAX-ACCESS read-only
			STATUS current
			DESCRIPTION
				"The mean time between status WARNING measure for this task measured in 
				(accumulated time between status WARNING)
				divided by (accumulated different WARNINGs - 1)."
			::= { siteEntry 69 }
		
		siteMTTRWarnings OBJECT-TYPE
			SYNTAX TimeTicks
			MAX-ACCESS read-only
			STATUS current
			DESCRIPTION
				"The mean time to repair WARNINGs measure for this task measured in 
				(accumulated time of status WARNING)
				divided by (accumulated different WARNINGs)."
			::= { siteEntry 70 }
		
		siteAccumulatedWarnings OBJECT-TYPE
			SYNTAX Integer32
			MAX-ACCESS read-only
			STATUS current
			DESCRIPTION
				"The number of accumulated different WARNINGs this task generated. "
			::= { siteEntry 71 }
		
		siteMTBCriticals OBJECT-TYPE
			SYNTAX TimeTicks
			MAX-ACCESS read-only
			STATUS current
			DESCRIPTION
				"The mean time between status CRITICAL measure for this task measured in 
				(accumulated time between status CRITICAL)
				divided by (accumulated different CRITICALs - 1)"
			::= { siteEntry 72 }
		
		siteMTTRCriticals OBJECT-TYPE
			SYNTAX TimeTicks
			MAX-ACCESS read-only
			STATUS current
			DESCRIPTION
				"The mean time to repair CRITICALs measure for this task measured in 
				(accumulated time of status CRITICAL)
				divided by (accumulated different CRITICALs)"
			::= { siteEntry 73 }
		
		siteAccumulatedCriticals OBJECT-TYPE
			SYNTAX Integer32
			MAX-ACCESS read-write
			STATUS current
			DESCRIPTION
				"The number of accumulated different CRITICALs this task generated. "
			::= { siteEntry 74 }
		
		siteGroupReliability OBJECT-TYPE
			SYNTAX Integer32
			MAX-ACCESS read-only
			STATUS current
			DESCRIPTION
				"The reliability measure for this group measured in 
				(accumulated time at status WARNING + accumulated time at status CRITICAL)
				divided by (accumulated running time of this group) * 10000"
			::= { siteEntry 75 }
		
		siteGroupMTBWarnings OBJECT-TYPE
			SYNTAX TimeTicks
			MAX-ACCESS read-only
			STATUS current
			DESCRIPTION
				"The mean time between status WARNING measure for this group measured in 
				(accumulated time between status WARNING)
				divided by (accumulated different WARNINGs - 1)"
			::= { siteEntry 76 }
		
		siteGroupMTTRWarnings OBJECT-TYPE
			SYNTAX TimeTicks
			MAX-ACCESS read-only
			STATUS current
			DESCRIPTION
				"The mean time to repair WARNINGs measure for this group measured in 
				(accumulated time of status WARNING)
				divided by (accumulated different WARNINGs)"
			::= { siteEntry 77 }
		
		siteGroupAccumulatedWarnings OBJECT-TYPE
			SYNTAX Integer32
			MAX-ACCESS read-only
			STATUS current
			DESCRIPTION
				"The number of accumulated different WARNINGs this group generated. "
			::= { siteEntry 78 }
		
		siteGroupMTBCriticals OBJECT-TYPE
			SYNTAX TimeTicks
			MAX-ACCESS read-only
			STATUS current
			DESCRIPTION
				"The mean time between status CRITICAL measure for this group measured in 
				(accumulated time between status CRITICAL)
				divided by (accumulated different CRITICALs)"
			::= { siteEntry 79 }
		
		siteGroupMTTRCriticals OBJECT-TYPE
			SYNTAX TimeTicks
			MAX-ACCESS read-only
			STATUS current
			DESCRIPTION
				"The mean time to repair CRITICALs measure for this group measured in 
				(accumulated time of status CRITICAL)
				divided by (accumulated different CRITICALs)"
			::= { siteEntry 80 }
		
		siteGroupAccumulatedCriticals OBJECT-TYPE
			SYNTAX Integer32
			MAX-ACCESS read-only
			STATUS current
			DESCRIPTION
				"The number of accumulated different CRITICALs this group generated. "
			::= { siteEntry 81 }
		
		siteLastRunRelativeTime OBJECT-TYPE
			SYNTAX TimeTicks
			MAX-ACCESS read-only
			STATUS current
			DESCRIPTION
				"The last time this task actively conducted tests in timeticks ago."
			::= { siteEntry 82 }
		
		siteLastRunAbsTimeString OBJECT-TYPE
			SYNTAX DisplayString
			MAX-ACCESS read-only
			STATUS current
			DESCRIPTION
				"The last absolute time this task actively conducted tests in string form."
			::= { siteEntry 83 }
		
		siteNextRunRelativeTime OBJECT-TYPE
			SYNTAX TimeTicks
			MAX-ACCESS read-only
			STATUS current
			DESCRIPTION
				"The next time this task will actively conduct tests in timeticks to go."
			::= { siteEntry 84 }
		
		siteNextRunAbsTimeString OBJECT-TYPE
			SYNTAX DisplayString
			MAX-ACCESS read-only
			STATUS current
			DESCRIPTION
				"The next absolute time this task will actively conduct tests in string form."
			::= { siteEntry 85 }
		
		siteFirstRun OBJECT-TYPE
			SYNTAX DisplayString
			MAX-ACCESS read-only
			STATUS current
			DESCRIPTION
				"The time epoch of this task. This is the time when this task started."
			::= { siteEntry 86 }
		
		siteTotalTransfers OBJECT-TYPE
			SYNTAX Integer32
			MAX-ACCESS read-only
			STATUS current
			DESCRIPTION
				"The total number of transfers for this task."
			::= { siteEntry 87 }
		
		siteTotalTransferVolume OBJECT-TYPE
			SYNTAX Integer32
			MAX-ACCESS read-only
			STATUS current
			DESCRIPTION
				"The total transfer volume for this task mod (2 to power of 32)."
			::= { siteEntry 88 }
--
-- definitions
--

		groupStatus OBJECT-TYPE
			SYNTAX Integer32
			MAX-ACCESS not-accessible
			STATUS current
			DESCRIPTION
				"The group status in variable bound to a trap."
			::= { snarl 100 }

		proxyStatus OBJECT-TYPE
			SYNTAX Integer32
			MAX-ACCESS not-accessible
			STATUS current
			DESCRIPTION
				"The proxy status in variable bound to a trap."
			::= { snarl 101 }

		siteStatus OBJECT-TYPE
			SYNTAX Integer32
			MAX-ACCESS not-accessible
			STATUS current
			DESCRIPTION
				"The site status in variable bound to a trap."
			::= { snarl 102 }

		subTaskID OBJECT-TYPE
			SYNTAX INTEGER
			{
			 general(1),
			 performance(2),
			 httpCode(3),
			 matchRegex(4),
			 matchSize(5),
			 urlSizeMatch(6),
			 urlContentMatch(7),
			 numericalMatch(8),
			 dateAgeMatch(9),
			 suspension(10),
			 warmStart(11),
			 coldStart(12),
                         heartBeat(13),
                         syncRequest(14)
			}
			MAX-ACCESS not-accessible
			STATUS current
			DESCRIPTION
				"The subTaskID in variable bound to a trap."
			::= { snarl 103 }

		eventTime OBJECT-TYPE
			SYNTAX Integer32
			MAX-ACCESS not-accessible
			STATUS current
			DESCRIPTION
				"The unix time in variable bound to a trap."
			::= { snarl 104 }
		

	    siteTrapMessage OBJECT-TYPE
			SYNTAX DisplayString
			MAX-ACCESS not-accessible
			STATUS current
			DESCRIPTION
				"The status message of the trap."
			::= { snarl 105 }
		

--
-- Trap definitions
--
	
		snarlsnmpInfo TRAP-TYPE
			ENTERPRISE snarlsnmp
			VARIABLES { siteIndex, subTaskID, siteTrapMessage, groupStatus, siteName, siteID, siteProxy, eventTime, siteStatus, proxyStatus }
			DESCRIPTION
				"An snarlsnmpInfo trap signifies that the sending
				protocol entity has undergone minor run changes
				that usually require no special attention. The
				information given in this trap are mainly for
				logging purposes"
			::=  1
			
		snarlsnmpNormal TRAP-TYPE
			ENTERPRISE snarlsnmp
			VARIABLES { siteIndex, subTaskID, siteTrapMessage, groupStatus, siteName, siteID, siteProxy, eventTime, siteStatus, proxyStatus }
			DESCRIPTION
				"An snarlsnmpNormal trap signifies that the sending
				protocol entity is working properly"
			::=  2
			
		snarlsnmpWarning TRAP-TYPE
			ENTERPRISE snarlsnmp
			VARIABLES { siteIndex, subTaskID, siteTrapMessage, groupStatus, siteName, siteID, siteProxy, eventTime, siteStatus, proxyStatus }
			DESCRIPTION
				"An snarlsnmpWarning trap signifies that the sending
				protocol entity is impaired and requires attention"
			::=  3
			
		snarlsnmpCritical TRAP-TYPE
			ENTERPRISE snarlsnmp
			VARIABLES { siteIndex, subTaskID, siteTrapMessage, groupStatus, siteName, siteID, siteProxy, eventTime, siteStatus, proxyStatus }
			DESCRIPTION
				"An snarlsnmpCritical trap signifies that the sending
				protocol entity is having major problems and need
				immediate attention"
			::=  4
			
		snarlsnmpSuspended TRAP-TYPE
			ENTERPRISE snarlsnmp
			VARIABLES { siteIndex, subTaskID, siteTrapMessage, groupStatus, siteName, siteID, siteProxy, eventTime, siteStatus, proxyStatus }
			DESCRIPTION
				"An snarlsnmpSuspended signfies that the sending task is about to be suspended"
			::=  5
			
		snarlsnmpResumed TRAP-TYPE
			ENTERPRISE snarlsnmp
			VARIABLES { siteIndex, subTaskID, siteTrapMessage, groupStatus, siteName, siteID, siteProxy, eventTime, siteStatus, proxyStatus }
			DESCRIPTION
				"An snarlsnmpResumed trap signfies that the sending task is about to resume from suspension"
			::=  6
			
		snarlsnmpGenericInfo TRAP-TYPE
			ENTERPRISE snarlsnmp
			VARIABLES { siteIndex, subTaskID, siteTrapMessage, groupStatus, siteName, siteID, siteProxy, eventTime, siteStatus, proxyStatus }
			DESCRIPTION
				"An snarlsnmpGenericInfo trap signifies that the sending
				protocol entity sends logging information"
			::=  7
			
		snarlsnmpStateUnknown TRAP-TYPE
			ENTERPRISE snarlsnmp
			VARIABLES { siteIndex, subTaskID, siteTrapMessage, groupStatus, siteName, siteID, siteProxy, eventTime, siteStatus, proxyStatus }
			DESCRIPTION
				"An snarlsnmpStateUnknown trap signifies that the sending
				protocol entity is undefined state"
			::=  8	
	END

--
-- SNARLSNMP-MIB.txt
--
