-- *****************************************************************************
-- Unisphere-Data-Autoconfigure-CONF
--
-- SNMP Agent Capabilities definitions for the Auto-Configuration MIB.
--
-- Copyright (c) 2001 Unisphere Networks, Inc.  All rights reserved.
-- *****************************************************************************

Unisphere-Data-Autoconfigure-CONF DEFINITIONS ::= BEGIN

IMPORTS
    MODULE-IDENTITY
        FROM SNMPv2-SMI
    AGENT-CAPABILITIES
        FROM SNMPv2-CONF
    usDataAgents
        FROM Unisphere-Data-Agents
    usdAutoConfGroup
        FROM Unisphere-Data-AUTOCONFIGURE-MIB;

usdAutoConfAgent MODULE-IDENTITY
    LAST-UPDATED "200103272008Z"  -- 27-Mar-01 03:08 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Auto-Configuration component
        of the SNMP agent in the Unisphere Routing Switch family of products."
    -- Revision History
    REVISION    "200103272008Z"  -- 27-Mar-01 03:08 PM EST  - RX 3.2
    DESCRIPTION
        "The initial release of this management information module."
    ::= { usDataAgents 44 }

usdAutoConfAgentV1 AGENT-CAPABILITIES
    PRODUCT-RELEASE
        "Version 1 of the Auto-Configuration component of the Unisphere Routing
        Switch SNMP agent.  This version of the Auto-Configuration component is
        supported in the Unisphere RX 3.0 and subsequent system releases."
    STATUS      current
    DESCRIPTION
        "The MIB supported by the SNMP agent for auto-configuration capabilities
        in the Unisphere Routing Switch."

    SUPPORTS        Unisphere-Data-AUTOCONFIGURE-MIB
        INCLUDES  { usdAutoConfGroup }

    ::= { usdAutoConfAgent 1 }

END
