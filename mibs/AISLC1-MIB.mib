AISLC1-MIB DEFINITIONS ::=  BEGIN

-- Applied Innovation Series 1 Protocol Termination MIB definitions
-- @(#) ai $Revision:   1.11  $ $Date:   15 Jan 1999 12:08:58  $

IMPORTS
    DisplayString
        FROM RFC1213-MIB

    MODULE-IDENTITY, OBJECT-TYPE, Counter32, Gauge32,
    enterprises
        FROM SNMPv2-SMI;


-- group object IDs

aii             OBJECT IDENTIFIER ::= { enterprises 539 }
aiSystemOID     OBJECT IDENTIFIER ::= { aii 2 }

aiSLC1  MODULE-IDENTITY
    LAST-UPDATED "980803164411Z"
    ORGANIZATION "Applied Innovation Incorporated"
    CONTACT-INFO
        "        Engineering MIB Administrator

        Postal:  Applied Innovation Inc.
                 5800 Innovation Drive
                 Dublin, OH 43016-3271

           Tel:  614/798-2000
           Fax:  614/798-1770
        E-mail:  snmp@aiinet.com"
    DESCRIPTION  " The MIB Module for Series One Smart Line Cards
                 (SLC)."
    ::= { aii 11 }

-- System group for Series One Smart Line Cards

aiSLC1System    OBJECT IDENTIFIER ::= { aiSLC1 1 }


-- sysObjectIDs

ai192           OBJECT IDENTIFIER ::= { aiSystemOID 192 }
ai192Ver7       OBJECT IDENTIFIER ::= { ai192 7 }
ai192Ver70      OBJECT IDENTIFIER ::= { ai192Ver7 0 }
ai192Ver708     OBJECT IDENTIFIER ::= { ai192Ver70 8 }
ai192Ver709     OBJECT IDENTIFIER ::= { ai192Ver70 9 }
ai192Ver71      OBJECT IDENTIFIER ::= { ai192Ver7 1 }
ai192Ver710     OBJECT IDENTIFIER ::= { ai192Ver71 0 }
ai192Ver711     OBJECT IDENTIFIER ::= { ai192Ver71 1 }
ai192Ver72      OBJECT IDENTIFIER ::= { ai192Ver7 2 }
ai192Ver720     OBJECT IDENTIFIER ::= { ai192Ver72 0 }
ai192Ver77      OBJECT IDENTIFIER ::= { ai192Ver7 7 }

ai196           OBJECT IDENTIFIER ::= { aiSystemOID 196 }
ai196Ver7       OBJECT IDENTIFIER ::= { ai196 7 }
ai196Ver70      OBJECT IDENTIFIER ::= { ai196Ver7 0 }
ai196Ver708     OBJECT IDENTIFIER ::= { ai196Ver70 8 }
ai196Ver709     OBJECT IDENTIFIER ::= { ai196Ver70 9 }
ai196Ver71      OBJECT IDENTIFIER ::= { ai196Ver7 1 }
ai196Ver710     OBJECT IDENTIFIER ::= { ai196Ver71 0 }
ai196Ver711     OBJECT IDENTIFIER ::= { ai196Ver71 1 }
ai196Ver72      OBJECT IDENTIFIER ::= { ai196Ver7 2 }
ai196Ver720     OBJECT IDENTIFIER ::= { ai196Ver72 0 }
ai196Ver77      OBJECT IDENTIFIER ::= { ai196Ver7 7 }


-- System Group

-- Implementation of this group is mandatory for all Applied Innovation
-- Series 1 Cards (SLC's) that support SNMP management

    aislc1AdminLogsEnabled OBJECT-TYPE
        SYNTAX     INTEGER {
                         on(1),
                         off(2)
                        }
        MAX-ACCESS read-write
        STATUS current
        DESCRIPTION
            "Determines whether the SLC sends log messages to the console
            port of the AISwitch."
       DEFVAL { on }
        ::= { aiSLC1System 1 }

    aislc1AdminTrapsEnabled OBJECT-TYPE
        SYNTAX     INTEGER {
                         on(1),
                         off(2)
                        }
        MAX-ACCESS read-write
        STATUS current
        DESCRIPTION
            "Determines whether the SLC sends SNMP Trap PDUs.  If the
            active CLC in the AISwitch chassis with the SLC is not
            SNMP capable, this object cannot be set to the value on(1)."
       DEFVAL { on }
        ::= { aiSLC1System 2 }

    aislc1AdminTrapTimer OBJECT-TYPE
        SYNTAX INTEGER(0..'ffff'h)
        MAX-ACCESS read-write
        STATUS current
        DESCRIPTION
            "After a trap is generated, a timer is started.  If the
            event that generated the trap occurs while the timer is
            running, no trap will be generated for the event.  The
            value of this object is the duration of the timer in
            seconds."
        DEFVAL { 300 }
        ::= { aiSLC1System 3 }

    aislc1OperLastMsgText OBJECT-TYPE
        SYNTAX     DisplayString (SIZE (0..245))
        MAX-ACCESS read-only
        STATUS current
        DESCRIPTION
            "Contains the message text of the last log message that
            was sent by the SLC (or would have been sent, if log
            message transmission is disabled."
        ::= { aiSLC1System 4 }

    aislc1OperLastMsgNum OBJECT-TYPE
        SYNTAX INTEGER(0..'ffff'h)
        MAX-ACCESS read-only
        STATUS current
        DESCRIPTION
            "Contains the message number of the last log message that
            was sent by the SLC (or would have been sent, if log
            message transmission is disabled."
        ::= { aiSLC1System 5 }

    aislc1OperCrashCode OBJECT-TYPE
        SYNTAX INTEGER{
                        crashbus('01'h),
                        crashvector('09'h),
                        crashx25('a0'h),
                        crashstack('a2'h),
                        crashmain('a3'h),
                        crashchecksum('a4'h),
                        crashinit('a5'h),
                        crashreboot('a6'h),
                        crashtimer('a7'h),
                        crashstopped('a8'h),
                        crashbadzero('a9'h),
                        crashmemfail('aa'h),
                        crashrxfifo('ab'h),
                        crashscc('ac'h)
                        }
        MAX-ACCESS read-only
        STATUS current
        DESCRIPTION
            "Contains a crash cause code. This object is for use as
            a varbind in TRAP PDUs only."
        ::= { aiSLC1System 6 }

    aislc1OperNumEventsSinceLastTrap OBJECT-TYPE
        SYNTAX INTEGER(0..'ffff'h)
        MAX-ACCESS read-only
        STATUS current
        DESCRIPTION
            "The number of times this trap was discarded because the
            aislcAdminTrapTimer had not yet expired since the last
            time the event which generated the trap occured. This
            object is for use as a varbind in TRAP PDUs only."
        ::= { aiSLC1System 7 }

    aislc1StatAIBfrsInUse OBJECT-TYPE
        SYNTAX     INTEGER(0..'ffff'h)
        MAX-ACCESS read-only
        STATUS     current
        DESCRIPTION
            "The number of AI buffers currently in use."
        ::= { aiSLC1System 8 }

    aislc1StatAIBfrsTotal OBJECT-TYPE
        SYNTAX     INTEGER(0..'ffff'h)
        MAX-ACCESS read-only
        STATUS     current
        DESCRIPTION
            "The total number of AI buffers." 
        ::= { aiSLC1System 9 }

    aislc1StatActiveVCs OBJECT-TYPE
        SYNTAX     INTEGER(0.. 'ffff'h)
        MAX-ACCESS read-only
        STATUS     current
        DESCRIPTION
            "The number of Virtual Connections currently in some
            state other than Idle."
        ::= { aiSLC1System 10 }

    aislc1StatTotalVCs OBJECT-TYPE
        SYNTAX     INTEGER(0..'ffff'h)
        MAX-ACCESS read-only
        STATUS     current
        DESCRIPTION
            "The total number of Virtual Connection structures
            allocated on the SLC."
        ::= { aiSLC1System 11 }

    aislc1StatMinLoopsPerSecond OBJECT-TYPE
        SYNTAX     Gauge32
        MAX-ACCESS read-only
        STATUS     current
        DESCRIPTION
            "The minimum number of iterations per second of the SLC's
            main polling loop during the sample period."
        ::= { aiSLC1System 12 }

    aislc1StatAvgLoopsPerSecond OBJECT-TYPE
        SYNTAX     Gauge32
        MAX-ACCESS read-only
        STATUS     current
        DESCRIPTION
            "The average number of iterations per second of the SLC's
            main polling loop during the sample period."
        ::= { aiSLC1System 13 }

    aislc1StatCurLoopsPerSecond OBJECT-TYPE
        SYNTAX     Gauge32
        MAX-ACCESS read-only
        STATUS     current
        DESCRIPTION
            "The number of iterations of the SLC's main polling loop
            during the past second."
        ::= { aiSLC1System 14 }

    aislc1StatFErrFifoInIsr OBJECT-TYPE
        SYNTAX     Counter32
        MAX-ACCESS read-only
        STATUS     current
        DESCRIPTION
            "Number of RxFIFO half-full ISR interrupts which occurred.
            This is not always an error, but may be indicative of a
            heavy load on the X.25 software."
        ::= { aiSLC1System 15 }

    aislc1StatErrFifoInFull OBJECT-TYPE
        SYNTAX     Counter32
        MAX-ACCESS read-only
        STATUS     current
        DESCRIPTION
            "Number of times the input FIFO was detected as full.
            This means that data has probably been lost, due to the
            inability of the X.25 software to keep pace with the
            RxFIFO."
        ::= { aiSLC1System 16 }

    aislc1StatErrFifoInPort OBJECT-TYPE
        SYNTAX     Counter32
        MAX-ACCESS read-only
        STATUS     current
        DESCRIPTION
            "Number of times a bad port number has been received through
            the FIFO.  This is probably indicative of a hardware failure,
            or perhaps a software problem in the CLC code."
        ::= { aiSLC1System 17 }

    aislc1StatErrFifoInLost OBJECT-TYPE
        SYNTAX     Counter32
        MAX-ACCESS read-only
        STATUS     current
        DESCRIPTION
            "Number of characters received from the FIFO which were
            discarded because of lack of space."
        ::= { aiSLC1System 18 }

    aislc1StatErrFifoOutFull OBJECT-TYPE
        SYNTAX     Counter32
        MAX-ACCESS read-only
        STATUS     current
        DESCRIPTION
            "Number of times the output FIFO was detected as full.
            This may be an indication of a hardware fault, or a
            breakdown in communications between the X.25 software and
            CLC regarding the status of a connection(i.e., if the CLC
            breaks a connection while the X.25 software is still using
            it, a TxFIFO full will definitely result)."
        ::= { aiSLC1System 19 }

    aislc1StatErrWinInCode OBJECT-TYPE
        SYNTAX     Counter32
        MAX-ACCESS read-only
        STATUS     current
        DESCRIPTION
            "Number of bad transaction codes received from the CLC
            via the window(i.e., the transaction code is out of
            range of the expected values)."
        ::= { aiSLC1System 20 }

    aislc1StatErrWinInPort OBJECT-TYPE
        SYNTAX     Counter32
        MAX-ACCESS read-only
        STATUS     current
        DESCRIPTION
            "Number of bad port numbers received from the CLC via
            the window(i.e., the relative port number is out of range
            of the expected values)."
        ::= { aiSLC1System 21 }

    aislc1StatErrWinInConn OBJECT-TYPE
        SYNTAX     Counter32
        MAX-ACCESS read-only
        STATUS     current
        DESCRIPTION
            "Number of bad connection transactions from the CLC via
            the window."
        ::= { aiSLC1System 22 }
    
    aislc1StatErrWinInDisc OBJECT-TYPE
        SYNTAX     Counter32
        MAX-ACCESS read-only
        STATUS     current
        DESCRIPTION
            "Number of bad disconnection transactions from the CLC
            via the window.  Note that this counter will probably be
            incremented if calls are disconnected following a link
            outage, it is not necessarily indicative of a serious
            problem."
        ::= { aiSLC1System 23 }

    aislc1StatErrWinInAck OBJECT-TYPE
        SYNTAX     Counter32
        MAX-ACCESS read-only
        STATUS     current
        DESCRIPTION
            "Number of unexpected connection ACK's from the CLC via
            the window."
        ::= { aiSLC1System 24 }

    aislc1StatErrWinInNak OBJECT-TYPE
        SYNTAX     Counter32
        MAX-ACCESS read-only
        STATUS     current
        DESCRIPTION
            "Number of unexpected connection NAK's from the CLC via
            the window."
        ::= { aiSLC1System 25 }

    aislc1StatErrWinOutLost OBJECT-TYPE
        SYNTAX     Counter32
        MAX-ACCESS read-only
        STATUS     current
        DESCRIPTION
            "Number of output window transactions which were lost
            due to buffer failures."
        ::= { aiSLC1System 26 }

    aislc1StatAIBfrsMax OBJECT-TYPE
        SYNTAX     INTEGER(0..'ffff'h)
        MAX-ACCESS read-only
        STATUS     current
        DESCRIPTION
            "The maximum number of AI buffers that have been used."
        ::= { aiSLC1System 27 }

END
