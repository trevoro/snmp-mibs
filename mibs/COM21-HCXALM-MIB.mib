--
--  Copyright 1996, Com21 Inc.  All Rights Reserved.
--

COM21-HCXALM-MIB DEFINITIONS ::= BEGIN
        IMPORTS MODULE-IDENTITY, OBJECT-TYPE, NOTIFICATION-TYPE, Integer32
        FROM SNMPv2-SMI
		  DisplayString, MacAddress FROM SNMPv2-TC
        com21, com21Hcx
        FROM COM21-HCX-MIB;

        com21HcxAlm MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"
 
                DESCRIPTION
                        "This is the Com21 ComController Alarm Management 
			   MIB module. COM21 Part# 005-0025-00"
                ::= { com21Hcx 11 }

        com21HcxCurrAlmGroup            OBJECT IDENTIFIER ::= {com21Hcx 15}
        com21HcxEventLogGroup           OBJECT IDENTIFIER ::= {com21Hcx 16}
        com21HcxAlmSeverityGroup        OBJECT IDENTIFIER ::= {com21Hcx 17} 

        EpochTime        ::= INTEGER (0..2147483647) 
        AlarmSeverity    ::= INTEGER { clear(1), warning(2), minor(3),
                                       major(4), critical(5) }
 
        -- -- -- -- -- -- -- -- -- -- -- -- -- -- -- -- -- -- -- -- -- -- -- --
        -- -- -- -- -- -- -- -- -- -- -- -- -- -- -- -- -- -- -- -- -- -- -- --
        --
        -- COM21 ComController Enterprise MIB
        --
        -- This MIB contains SNMP Groups and Attributes definitions for COM21
        -- specific management.
        -- Also supported by the ComController shall be the MIB II for the 
	-- SNMP interface and the MIB II Interfaces Group for both the 
	-- ComController and ComPort Ethernet interfaces.
        -- This Enterprise MIB contains many elements of the ATM UNI 2.1 ILMI
        -- MIB. This full MIB is not presently supported by the COM21 equipment
        -- as there are no external UNI interfaces. When this changes then the
        -- full MIB should be supported and the related Enterprise MIB entries
        -- removed.
        --
        -- The com21HcxAlm MIB contains the following groups :
        --
        --   com21HcxCurrAlmGroup       - this group hold all current alarms in
        --                                the ComController. Note NOT the 
	--				  ComPort.
        --
        --   com21HcxEventLogGroup      - this group holds a log of the last
        --                                x alarms (including clears). x is
        --                                defined by the hcxEventLogSize
        --                                attribute in the com21HcxControlGroup
        --
        --   com21HcxAlmSeverityGroup   - this group allows for a user to
        --                                define the severity associated with
        --                                an trap type.
        --
        -- -- -- -- -- -- -- -- -- -- -- -- -- -- -- -- -- -- -- -- -- -- -- --
        -- -- -- -- -- -- -- -- -- -- -- -- -- -- -- -- -- -- -- -- -- -- -- --
 

        -- -- -- -- -- -- -- -- -- -- -- -- -- -- -- -- -- -- -- -- -- -- -- --
        -- -- -- -- -- -- -- -- -- -- -- -- -- -- -- -- -- -- -- -- -- -- -- --
        --
        -- com21HcxCurrAlmGroup
        --
        -- defines a list of current alarms in the ComController system. 
	-- The number of alarms in the current alarm list is specified in the
	-- com21HcxAlmOverGroup attribute hcxNoCurrAlarms.
        --
        -- -- -- -- -- -- -- -- -- -- -- -- -- -- -- -- -- -- -- -- -- -- -- --
        -- -- -- -- -- -- -- -- -- -- -- -- -- -- -- -- -- -- -- -- -- -- -- --
 
        com21HcxCurrAlmTable OBJECT-TYPE
                SYNTAX  SEQUENCE OF HcxAlarmEntry
                MAX-ACCESS  not-accessible
                STATUS  current
                DESCRIPTION   
                        "table of current alarms."
                ::= { com21HcxCurrAlmGroup 1 }  

        com21HcxAlmEntry OBJECT-TYPE
		SYNTAX HcxAlarmEntry
                MAX-ACCESS  not-accessible
                STATUS  current
                DESCRIPTION "."
                INDEX {hcxAlmTrapId, hcxAlmShelfId, hcxAlmSlotId, hcxAlmPortId}
                ::= { com21HcxCurrAlmTable 1 }

        HcxAlarmEntry ::= SEQUENCE {
		hcxAlmTrapId	    Integer32,
		hcxAlmSeverity	    AlarmSeverity,
		hcxAlmTime	    EpochTime,
		hcxAlmShelfId	    INTEGER,
		hcxAlmSlotId	    Integer32,
		hcxAlmPortId	    INTEGER,
		hcxAlmMacAddr	    MacAddress,
		hcxAlmDataAValid    INTEGER,
		hcxAlmDataA         Integer32,
		hcxAlmDataBValid    INTEGER,
		hcxAlmDataB         Integer32,
		hcxAlmStrDataValid  INTEGER,
		hcxAlmStrData       DisplayString }

        hcxAlmTrapId OBJECT-TYPE
                SYNTAX Integer32
                MAX-ACCESS read-only
                STATUS current
                DESCRIPTION "
                        contains the trap id associated with the alarm."
                ::= { com21HcxAlmEntry 1 }

        hcxAlmSeverity OBJECT-TYPE
                SYNTAX AlarmSeverity
                MAX-ACCESS read-only
                STATUS current
                DESCRIPTION "
                        contains alarm severity."
                ::= { com21HcxAlmEntry 2 }

        hcxAlmTime OBJECT-TYPE
                SYNTAX EpochTime
                MAX-ACCESS read-only
                STATUS current
                DESCRIPTION "
                        contains time (in the form of Epoch) that alarm
			occured."
                ::= { com21HcxAlmEntry 3 }

        hcxAlmShelfId OBJECT-TYPE
                SYNTAX INTEGER (1..2)
                MAX-ACCESS read-only
                STATUS current
                DESCRIPTION "
                        contains the shelf id associated with the alarm."
                ::= { com21HcxAlmEntry 4 }

        hcxAlmSlotId OBJECT-TYPE
                SYNTAX Integer32
                MAX-ACCESS read-only
                STATUS current
                DESCRIPTION "
                        contains the slot id associated with the alarm."
                ::= { com21HcxAlmEntry 5 }

        hcxAlmPortId OBJECT-TYPE
                SYNTAX INTEGER (0..4)
                MAX-ACCESS read-only
                STATUS current
                DESCRIPTION "
                        contains any port id associated with the alarm. If
			there is no associated port number then this attribute
			will be 0."
                ::= { com21HcxAlmEntry 6 }

        hcxAlmMacAddr OBJECT-TYPE
                SYNTAX MacAddress
                MAX-ACCESS read-only
                STATUS current
                DESCRIPTION "
                        contains any MAC address (i.e. ComPort MAC Address)
			associated with the alarm. If there is no associated 
			MAC address then this attribute will be 0."
                ::= { com21HcxAlmEntry 7 }

	hcxAlmDataAValid OBJECT-TYPE
		SYNTAX INTEGER { true (1), false (2) }
                MAX-ACCESS read-only
                STATUS current
                DESCRIPTION "
                        this attribute indicates if the hcxAlmDataA
			attribute is valid for this alarm."
                ::= { com21HcxAlmEntry 8 }

        hcxAlmDataA OBJECT-TYPE
                SYNTAX Integer32
                MAX-ACCESS read-only
                STATUS current
                DESCRIPTION "
                        contains a single integer for data related to the
			alarm. i.e. for storing a threshold value associated
			with a threshold alarm. The application reading
                        this value must have explicit knowledge of the 
			trap id inorder to interpret this attribute."
                ::= { com21HcxAlmEntry 9 }

        hcxAlmDataBValid OBJECT-TYPE
                SYNTAX INTEGER { true (1), false (2) } 
                MAX-ACCESS read-only 
                STATUS current
                DESCRIPTION " 
                        this attribute indicates if the hcxAlmDataB
                        attribute is valid for this alarm."   
                ::= { com21HcxAlmEntry 10 } 
 
        hcxAlmDataB OBJECT-TYPE
                SYNTAX Integer32
                MAX-ACCESS read-only
                STATUS current
                DESCRIPTION "
                        contains a second integer field for data related to 
			the alarm. The application reading this value must 
			have explicit knowledge of the trap id in order to 
			interpret this attribute."
                ::= { com21HcxAlmEntry 11 }

        hcxAlmStrDataValid OBJECT-TYPE
                SYNTAX INTEGER { true (1), false (2) } 
                MAX-ACCESS read-only 
                STATUS current
                DESCRIPTION " 
                        this attribute indicates if the hcxAlmStrData
                        attribute is valid for this alarm."   
                ::= { com21HcxAlmEntry 12 } 
 
        hcxAlmStrData OBJECT-TYPE
                SYNTAX DisplayString (SIZE (16))
                MAX-ACCESS read-only
                STATUS current
                DESCRIPTION "
                        contains a display string for information related to 
			the alarm. It maybe for storing a descriptive
			string or other text information."
                ::= { com21HcxAlmEntry 13 }



        -- -- -- -- -- -- -- -- -- -- -- -- -- -- -- -- -- -- -- -- -- -- -- --
        -- -- -- -- -- -- -- -- -- -- -- -- -- -- -- -- -- -- -- -- -- -- -- --
        --
        -- com21HcxEventLogGroup
        --
        -- defines a ComController alarm log. The number of alarms in the log 
	-- can be specified via the com21HcxAlmOverGroup attribute 
	-- hcxEventLogSize.
        --
        -- -- -- -- -- -- -- -- -- -- -- -- -- -- -- -- -- -- -- -- -- -- -- --
        -- -- -- -- -- -- -- -- -- -- -- -- -- -- -- -- -- -- -- -- -- -- -- --
 
        com21HcxEventLogTable OBJECT-TYPE
                SYNTAX  SEQUENCE OF HcxEventLogEntry
                MAX-ACCESS  not-accessible
                STATUS  current
                DESCRIPTION   
                        "table of alarm log."
                ::= { com21HcxEventLogGroup 1 }  

        com21HcxEventLogEntry OBJECT-TYPE
                SYNTAX HcxEventLogEntry
                MAX-ACCESS  not-accessible
                STATUS  current
                DESCRIPTION "."
                INDEX { hcxEventLogId }
                ::= { com21HcxEventLogTable 1 }

        HcxEventLogEntry ::= SEQUENCE {
                hcxEventLogId          Integer32,
                hcxEventLogSeverity    AlarmSeverity,
                hcxEventLogTime        EpochTime,
                hcxEventLogShelfId     INTEGER,
                hcxEventLogSlotId      Integer32,
                hcxEventLogPortId      INTEGER,
                hcxEventLogMacAddr     MacAddress,
                hcxEventLogTrapId      Integer32,
		hcxEventLogDataAValid  INTEGER,
		hcxEventLogDataA       Integer32,
		hcxEventLogDataBValid  INTEGER, 
                hcxEventLogDataB       Integer32,
		hcxEventStrDataValid   INTEGER,
        	hcxEventStrData        DisplayString }
 
        hcxEventLogId OBJECT-TYPE
                SYNTAX Integer32
                MAX-ACCESS read-only
                STATUS current
                DESCRIPTION "
                        contains alarm id. This is a simple sequential
                        number starting at 1."
                ::= { com21HcxEventLogEntry 1 }
 
        hcxEventLogSeverity OBJECT-TYPE
                SYNTAX AlarmSeverity
                MAX-ACCESS read-only
                STATUS current
                DESCRIPTION "
                        contains alarm severity."
                ::= { com21HcxEventLogEntry 2 }
 
        hcxEventLogTime OBJECT-TYPE
                SYNTAX EpochTime
                MAX-ACCESS read-only
                STATUS current
                DESCRIPTION "
                        contains time (in the form of Epoch) that alarm
                        occured."
                ::= { com21HcxEventLogEntry 3 }
 
        hcxEventLogShelfId OBJECT-TYPE
                SYNTAX INTEGER (1..2)
                MAX-ACCESS read-only
                STATUS current
                DESCRIPTION "
                        contains the shelf id associated with the alarm."
                ::= { com21HcxEventLogEntry 4 }
 
        hcxEventLogSlotId OBJECT-TYPE
                SYNTAX Integer32
                MAX-ACCESS read-only
                STATUS current
                DESCRIPTION "
                        contains the slot id associated with the alarm."
                ::= { com21HcxEventLogEntry 5 }
 
        hcxEventLogPortId OBJECT-TYPE
                SYNTAX INTEGER (0..4)
                MAX-ACCESS read-only
                STATUS current
                DESCRIPTION "
                        contains any port id associated with the alarm. If
                        there is no associated port number then this attribute
                        will be 0."
                ::= { com21HcxEventLogEntry 6 }
 
        hcxEventLogMacAddr OBJECT-TYPE
                SYNTAX MacAddress
                MAX-ACCESS read-only
                STATUS current
                DESCRIPTION "
                        contains any MAC Address associated with the alarm. If
                        there is no associated MAC Address then this attribute
                        will be 0."
                ::= { com21HcxEventLogEntry 7 }

        hcxEventLogTrapId OBJECT-TYPE
                SYNTAX Integer32
                MAX-ACCESS read-only
                STATUS current
                DESCRIPTION "
                        contains the trap id associated with the alarm."
                ::= { com21HcxEventLogEntry 8 }

        hcxEventLogDataAValid OBJECT-TYPE
                SYNTAX INTEGER { true (1), false (2) }
                MAX-ACCESS read-only
                STATUS current
                DESCRIPTION "
                        this attribute indicates if the hcxEventLogDataA
                        attribute is valid for this alarm."
                ::= { com21HcxEventLogEntry 9 }
 
        hcxEventLogDataA OBJECT-TYPE
                SYNTAX Integer32
                MAX-ACCESS read-only
                STATUS current
                DESCRIPTION "
                        contains a single integer for data related to the
                        alarm. i.e. for storing a threshold value associated
                        with a threshold alarm. The application reading
                        this value must have explicit knowledge of the
                        trap id inorder to interpret this attribute."
                ::= { com21HcxEventLogEntry 10 }
 
        hcxEventLogDataBValid OBJECT-TYPE
                SYNTAX INTEGER { true (1), false (2) }
                MAX-ACCESS read-only 
                STATUS current
                DESCRIPTION " 
                        this attribute indicates if the hcxEventLogDataB
                        attribute is valid for this alarm."
                ::= { com21HcxEventLogEntry 11 }
 
        hcxEventLogDataB OBJECT-TYPE
                SYNTAX Integer32
                MAX-ACCESS read-only
                STATUS current
                DESCRIPTION "
                        contains a second integer field for data related to
                        the alarm. The application reading this value must
                        have explicit knowledge of the trap id in order to
                        interpret this attribute."
                ::= { com21HcxEventLogEntry 12 }
 
        hcxEventStrDataValid OBJECT-TYPE
                SYNTAX INTEGER { true (1), false (2) }
                MAX-ACCESS read-only 
                STATUS current
                DESCRIPTION " 
                        this attribute indicates if the hcxEventStrData
                        attribute is valid for this alarm."
                ::= { com21HcxEventLogEntry 13 }
 
        hcxEventStrData OBJECT-TYPE
                SYNTAX DisplayString (SIZE (16))
                MAX-ACCESS read-only
                STATUS current
                DESCRIPTION "
                        contains a display string for information related to
                        the alarm. It maybe for storing a descriptive
                        string or other text information."
                ::= { com21HcxEventLogEntry 14 } 


        -- -- -- -- -- -- -- -- -- -- -- -- -- -- -- -- -- -- -- -- -- -- -- --
        -- -- -- -- -- -- -- -- -- -- -- -- -- -- -- -- -- -- -- -- -- -- -- --
        --
        -- com21HcxAlmSeverityGroup
        --
        -- defines a table used to set the severity of any trap supported
	-- by the ComController. Note that (at least initially) ComPort alarm 
	-- severity is not supported. This list shall contain all traps 
	-- supported by the ComController. The list shall be initialized 
	-- with the default severities specified in each trap definition.
        --
        -- -- -- -- -- -- -- -- -- -- -- -- -- -- -- -- -- -- -- -- -- -- -- --
        -- -- -- -- -- -- -- -- -- -- -- -- -- -- -- -- -- -- -- -- -- -- -- --

        com21HcxAlmSeverityTable OBJECT-TYPE
                SYNTAX  SEQUENCE OF HcxAlmSeverityEntry
                MAX-ACCESS  not-accessible
                STATUS  current
                DESCRIPTION
                        "table of alarm severities."
                ::= { com21HcxAlmSeverityGroup 1 }

        com21HcxAlmSeverityEntry OBJECT-TYPE
                SYNTAX HcxAlmSeverityEntry
                MAX-ACCESS  not-accessible
                STATUS  current
                DESCRIPTION "."
                INDEX { hcxAlmSevTrapId }
                ::= { com21HcxAlmSeverityTable 1 }

        HcxAlmSeverityEntry ::= SEQUENCE {
                hcxAlmSevTrapId    Integer32,
                hcxSetAlmSeverity  AlarmSeverity }

        hcxAlmSevTrapId OBJECT-TYPE
                SYNTAX Integer32
                MAX-ACCESS read-only
                STATUS current
                DESCRIPTION "
                        contains the trap id."
                ::= { com21HcxAlmSeverityEntry 1 }
 
        hcxSetAlmSeverity OBJECT-TYPE
                SYNTAX AlarmSeverity
                MAX-ACCESS read-write
                STATUS current
                DESCRIPTION "
                        contains alarm severity. See trap description for 
			defaults."
                ::= { com21HcxAlmSeverityEntry 2 } 


END
