Wellfleet-TCP-MIB DEFINITIONS ::= BEGIN

-- Created by mdl2asn version 3.1
-- Creation date: Wed Aug 30 16:49:12 EDT 1995


    IMPORTS

      IpAddress, Counter, Gauge
        FROM RFC1155-SMI
      OBJECT-TYPE
        FROM RFC-1212
      wfTcpGroup
        FROM Wellfleet-COMMON-MIB;


    wfTcp		OBJECT IDENTIFIER ::= { wfTcpGroup 1 }

    wfTcpDelete OBJECT-TYPE
        SYNTAX	INTEGER {
    		    created(1),
    		    deleted(2)
    		}
        ACCESS	read-write
        STATUS	mandatory
        DESCRIPTION
                "Create/Delete parameter. Default is created.
                Users perform a set operation on this
                object in order to create/delete TCP."
        DEFVAL	{ created }
        ::= { wfTcp 1 }

    wfTcpDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable TCP."
        DEFVAL	{ enabled }
        ::= { wfTcp 2 }

    wfTcpState OBJECT-TYPE
        SYNTAX	INTEGER {
    		    up(1),
    		    down(2),
    		    init(3),
    		    notpresent(4)
    		}
        ACCESS	read-only
        STATUS	mandatory
        DESCRIPTION
                "The current state of the entire TCP."
        DEFVAL	{ notpresent }
        ::= { wfTcp 3 }

    wfTcpRtoAlgorithm OBJECT-TYPE
        SYNTAX	INTEGER {
    		    other(1),
    		    constant(2),
    		    rsre(3),
    		    vanj(4)
    		}
        ACCESS	read-only
        STATUS	mandatory
        DESCRIPTION
                "The algorithm used to determine the timeout value
                used for retransmitting unacknowledged octets."
        DEFVAL	{ vanj }
        ::= { wfTcp 4 }

    wfTcpRtoMin OBJECT-TYPE
        SYNTAX	INTEGER(100..15000)
        ACCESS	read-write
        STATUS	mandatory
        DESCRIPTION
                "The minimum value permitted by a TCP
                implementation for the retransmission timeout,
                measured in milliseconds.  More refined semantics
                for objects of this type depend upon the algorithm
                used to determine the retransmission timeout.  In
                particular, when the timeout algorithm is rsre(3),
                an object of this type has the semantics of the
                LBOUND quantity described in RFC 793."
        DEFVAL	{ 250 }
        ::= { wfTcp 5 }

    wfTcpRtoMax OBJECT-TYPE
        SYNTAX	INTEGER(15000..240000)
        ACCESS	read-write
        STATUS	mandatory
        DESCRIPTION
                "The maximum value permitted by a TCP
                implementation for the retransmission timeout,
                measured in milliseconds.  More refined semantics
                for objects of this type depend upon the algorithm
                used to determine the retransmission timeout.  In
                particular, when the timeout algorithm is rsre(3),
                an object of this type has the semantics of the
                UBOUND quantity described in RFC 793."
        DEFVAL	{ 240000 }
        ::= { wfTcp 6 }

    wfTcpMaxConn OBJECT-TYPE
        SYNTAX	INTEGER
        ACCESS	read-only
        STATUS	mandatory
        DESCRIPTION
                "The limit on the total number of TCP connections
                the entity can support.  In entities where the
                maximum number of connections is dynamic, this
                object should contain the value -1."
        ::= { wfTcp 7 }

    wfTcpActiveOpens OBJECT-TYPE
        SYNTAX	Counter
        ACCESS	read-only
        STATUS	mandatory
        DESCRIPTION
                "The number of times TCP connections have made a
                direct transition to the SYN-SENT state from the
                CLOSED state."
        ::= { wfTcp 8 }

    wfTcpPassiveOpens OBJECT-TYPE
        SYNTAX	Counter
        ACCESS	read-only
        STATUS	mandatory
        DESCRIPTION
                "The number of times TCP connections have made a
                direct transition to the SYN-RCVD state from the
                LISTEN state."
        ::= { wfTcp 9 }

    wfTcpAttemptFails OBJECT-TYPE
        SYNTAX	Counter
        ACCESS	read-only
        STATUS	mandatory
        DESCRIPTION
                "The number of times TCP connections have made a
                direct transition to the CLOSED state from either
                the SYN-SENT state or the SYN-RCVD state, plus the
                number of times TCP connections have made a direct
                transition to the LISTEN state from the SYN-RCVD
                state."
        ::= { wfTcp 10 }

    wfTcpEstabResets OBJECT-TYPE
        SYNTAX	Gauge
        ACCESS	read-only
        STATUS	mandatory
        DESCRIPTION
                "The number of times TCP connections have made a
                direct transition to the CLOSED state from either
                the ESTABLISHED state or the CLOSE-WAIT state."
        ::= { wfTcp 11 }

    wfTcpCurrEstab OBJECT-TYPE
        SYNTAX	Gauge
        ACCESS	read-only
        STATUS	mandatory
        DESCRIPTION
                "The number of TCP connections for which the
                current state is either ESTABLISHED or CLOSE-
                WAIT."
        ::= { wfTcp 12 }

    wfTcpInSegs OBJECT-TYPE
        SYNTAX	Counter
        ACCESS	read-only
        STATUS	mandatory
        DESCRIPTION
                "The total number of segments received, including
                those received in error.  This count includes
                segments received on currently established
                connections."
        ::= { wfTcp 13 }

    wfTcpOutSegs OBJECT-TYPE
        SYNTAX	Counter
        ACCESS	read-only
        STATUS	mandatory
        DESCRIPTION
                "The total number of segments sent, including
                those on current connections but excluding those
                containing only retransmitted octets."
        ::= { wfTcp 14 }

    wfTcpRetransSegs OBJECT-TYPE
        SYNTAX	Counter
        ACCESS	read-only
        STATUS	mandatory
        DESCRIPTION
                "The total number of segments retransmitted - that
                is, the number of TCP segments transmitted
                containing one or more previously transmitted
                octets."
        ::= { wfTcp 15 }

    wfTcpInErrs OBJECT-TYPE
        SYNTAX	Counter
        ACCESS	read-only
        STATUS	mandatory
        DESCRIPTION
                "The total number of segments received in error
                (e.g., bad TCP checksums)."
        ::= { wfTcp 16 }

    wfTcpOutRsts OBJECT-TYPE
        SYNTAX	Counter
        ACCESS	read-only
        STATUS	mandatory
        DESCRIPTION
                "The number of TCP segments sent containing the
                RST flag."
        ::= { wfTcp 17 }

    wfTcpMaxWindow OBJECT-TYPE
        SYNTAX	INTEGER(512..65535)
        ACCESS	read-write
        STATUS	mandatory
        DESCRIPTION
                "The maximum transmit and receive window size TCP will allow
                for each connection measured in octets."
        DEFVAL	{ 4096 }
        ::= { wfTcp 18 }

    wfTcpConnTable OBJECT-TYPE
        SYNTAX	SEQUENCE OF WfTcpConnEntry
        ACCESS	not-accessible
        STATUS	mandatory
        DESCRIPTION
                "The TCP connection table contains information about this
                entity's existing TCP connections."
        ::= { wfTcpGroup 2 }

    wfTcpConnEntry OBJECT-TYPE
        SYNTAX	WfTcpConnEntry
        ACCESS	not-accessible
        STATUS	mandatory
        DESCRIPTION
                "A TCP Connection"
        INDEX	{ wfTcpConnLocalAddress,
    		  wfTcpConnLocalPort,
    		  wfTcpConnRemAddress,
    		  wfTcpConnRemPort }
        ::= { wfTcpConnTable 1 }

    WfTcpConnEntry ::= SEQUENCE {
    	    wfTcpConnDelete
    		INTEGER,
    	    wfTcpConnState
    		INTEGER,
    	    wfTcpConnLocalAddress
    		IpAddress,
    	    wfTcpConnLocalPort
    		INTEGER,
    	    wfTcpConnRemAddress
    		IpAddress,
    	    wfTcpConnRemPort
    		INTEGER,
            wfTcpConnKeepAliveInterval
                INTEGER,
            wfTcpConnKeepAliveRto
                INTEGER,
            wfTcpConnKeepAliveCount
                Counter,
            wfTcpConnMd5Errors
                Counter
        }

    wfTcpConnDelete OBJECT-TYPE
        SYNTAX	INTEGER {
    		    created(1),
    		    deleted(2)
    		}
        ACCESS	read-write
        STATUS	mandatory
        DESCRIPTION
                "The Delete connection attribute. Users set this attribute
                to a value of TCP_CONN_STATE_DELETE to delete a TCP connection.
                This is the only value that can be written. The instance should
                never get created by a user writing to this attribute."
        DEFVAL	{ created }
        ::= { wfTcpConnEntry 1 }

    wfTcpConnState OBJECT-TYPE
        SYNTAX	INTEGER {
    		    closed(1),
    		    listen(2),
    		    synsent(3),
    		    synreceived(4),
    		    established(5),
    		    finwait1(6),
    		    finwait2(7),
    		    closewait(8),
    		    lastack(9),
    		    closing(10),
    		    timewait(11),
    		    deletetcb(12)
    		}
        ACCESS	read-only
        STATUS	mandatory
        DESCRIPTION
                "The state of this TCP connection.

                 The only value which may be set by a management
                 station is deleteTCB(12).  Accordingly, it is
                 appropriate for an agent to return a `badValue'
                 response if a management station attempts to set
                 this object to any other value.

                 If a management station sets this object to the
                 value deleteTCB(12), then this has the effect of
                 deleting the TCB (as defined in RFC 793) of the
                 corresponding connection on the managed node,
                 resulting in immediate termination of the
                 connection.

                 As an implementation-specific option, a RST
                 segment may be sent from the managed node to the
                 other TCP endpoint (note however that RST segments
                 are not sent reliably)."
        DEFVAL	{ closed }
        ::= { wfTcpConnEntry 2 }

    wfTcpConnLocalAddress OBJECT-TYPE
        SYNTAX	IpAddress
        ACCESS	read-only
        STATUS	mandatory
        DESCRIPTION
                "The local IP address for this TCP connection. In
                the case of a connection in the listen state which
                is willing to accept connections for any IP
                interface associated with the node, the value
                0.0.0.0 is used."
        ::= { wfTcpConnEntry 3 }

    wfTcpConnLocalPort OBJECT-TYPE
        SYNTAX	INTEGER(1..65535)
        ACCESS	read-only
        STATUS	mandatory
        DESCRIPTION
                "The local port number for this TCP connection"
        ::= { wfTcpConnEntry 4 }

    wfTcpConnRemAddress OBJECT-TYPE
        SYNTAX	IpAddress
        ACCESS	read-only
        STATUS	mandatory
        DESCRIPTION
                "The remote IP address for this TCP connection."
        ::= { wfTcpConnEntry 5 }

    wfTcpConnRemPort OBJECT-TYPE
        SYNTAX	INTEGER(1..65535)
        ACCESS	read-only
        STATUS	mandatory
        DESCRIPTION
                "The remote port number for this TCP connection."
        ::= { wfTcpConnEntry 6 }

    wfTcpConnKeepAliveInterval OBJECT-TYPE
        SYNTAX        INTEGER(0..86400)
        ACCESS        read-only
        STATUS        mandatory
        DESCRIPTION
                "The Interval(seconds) during which no packet has been 
                 received on a session.  A PROBE packet is sent to elicit 
                 an ACK.  Value passed by application in tcp_open or tcp_accept."
        ::= { wfTcpConnEntry 7 }

    wfTcpConnKeepAliveRto OBJECT-TYPE
        SYNTAX        INTEGER(0..86400)
        ACCESS        read-only
        STATUS        mandatory
        DESCRIPTION
                "Keep Alive Retransmit timer (seconds) after which a PROBE 
                 packet is sent again if no response has been received. 
                 Value passed by application in tcp_open or tcp_accept."
        ::= { wfTcpConnEntry 8 }

    wfTcpConnKeepAliveCount OBJECT-TYPE
        SYNTAX        Counter
        ACCESS        read-only
        STATUS        mandatory
        DESCRIPTION
                "The current number of consecutive Keep-Alive PROBES sent."
        ::= { wfTcpConnEntry 9 }

    wfTcpConnMd5Errors OBJECT-TYPE
        SYNTAX        Counter
        ACCESS        read-only
        STATUS        mandatory
        DESCRIPTION
                "A count of the number of TCP packets dropped \
                 due to MD5 authentication errors"
        ::= { wfTcpConnEntry 10 }

    END  -- Wellfleet-TCP-MIB
