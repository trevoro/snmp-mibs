FNC-COMMON-SMI DEFINITIONS ::= BEGIN

IMPORTS
    MODULE-IDENTITY, enterprises
        FROM SNMPv2-SMI;

fnc MODULE-IDENTITY
    LAST-UPDATED "200401281500Z" -- Jan. 28, 2004
    ORGANIZATION
        "Fujitsu Network Communications"
    CONTACT-INFO 
        "Fujitsu Technical Assistance Center (FTAC),        
         1-800-USE-FTAC (1-800-873-3822)"
    DESCRIPTION 
        "This MIB module contains all of the base level headers
         used for control of the FNC enterprises MIB tree.
         It should contain both object definitions for specific
         groups and references to other objects that are contained
         in other MIB modules.

         The main utility of this MIB module is to collect the
         MIB tree of the base objects in the fnc branch."
    REVISION      "200401281500Z"
    DESCRIPTION
            "Removed conflicting NETSMART OID definitions."
    REVISION      "200310061500Z"
    DESCRIPTION
            "Added FNC common MIB revision history."
    REVISION      "200308121500Z"
    DESCRIPTION
            "Initial revision proposed by FW7500 and FW4020 snmp team."
    ::= { enterprises 3861 }

--=====================================================================--
-- Base Level Objects                                                  --
--=====================================================================--
--
-- NOTE TO USERS:
--   This MIB module will contain mostly comments.  It is a utility used
--   to list the base headers in the MIB where they can not be contained
--   in a MIB module.  If the objects are contained in a MIB module,
--   they should still be added to this MIB in the form of comments along
--   with a pointer to the MIB which contains the definition.
-- 
fncTraps OBJECT IDENTIFIER               ::= { fnc 0 }


fastlane OBJECT IDENTIFIER               ::= { fnc 1 }


-- flash150 OBJECT IDENTIFIER            ::= { flash 1 }
--      OBSOLETE

-- flash600 OBJECT IDENTIFIER            ::= { flash 2 }
--      OBSOLETE

flash OBJECT IDENTIFIER                  ::= { fnc 2 }

    flashBase OBJECT IDENTIFIER            ::= { flash 1 }

    stm OBJECT IDENTIFIER                  ::= { flashBase 7 }

      sonet OBJECT IDENTIFIER              ::= { stm 1 }


flashwave OBJECT IDENTIFIER              ::= { fnc 3 }

    fwCommon OBJECT IDENTIFIER               ::= { flashwave 1 }

    fw4100 OBJECT IDENTIFIER                 ::= { flashwave 4100 }

    fw4300 OBJECT IDENTIFIER                 ::= { flashwave 4300 }

    fw4500 OBJECT IDENTIFIER                 ::= { flashwave 4500 }

    fw7500 OBJECT IDENTIFIER                 ::= { flashwave 7500 }

    fw4020 OBJECT IDENTIFIER                 ::= { flashwave 4020 }


-- nexion OBJECT IDENTIFIER                 ::= { fnc 4 }


netsmart OBJECT IDENTIFIER               ::= { fnc 4 }




--=====================================================================--
-- Compliance and Conformance information                              --
--=====================================================================--
-- None needed unless leaf nodes actually defined.

END
