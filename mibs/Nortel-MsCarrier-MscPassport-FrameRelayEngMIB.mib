Nortel-MsCarrier-MscPassport-FrameRelayEngMIB
DEFINITIONS ::= BEGIN



IMPORTS

      OBJECT-TYPE
   FROM RFC-1212

      mscPassportMIBs
   FROM Nortel-MsCarrier-MscPassport-UsefulDefinitionsMIB

      DisplayString,
      StorageType,
      RowStatus,
      Gauge32,
      Unsigned32
   FROM Nortel-MsCarrier-MscPassport-StandardTextualConventionsMIB

      NonReplicated
   FROM Nortel-MsCarrier-MscPassport-TextualConventionsMIB

      mscLpEng,
      mscLpIndex,
      mscLpEngIndex
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FrameRelayEng Enterprise MIB."

frameRelayEngMIB OBJECT IDENTIFIER ::= { mscPassportMIBs 73 }










-- 
-- Lp Eng FrameRelaySystem
-- This component holds engineering parameters and statistics used by 
-- Frame Relay on this LP.

mscLpEngFrs OBJECT IDENTIFIER ::= { mscLpEng 3 }



mscLpEngFrsRowStatusTable OBJECT-TYPE
   SYNTAX     SEQUENCE OF MscLpEngFrsRowStatusEntry
   ACCESS     not-accessible
   STATUS     mandatory
   DESCRIPTION
     "This entry controls the addition and deletion of 
      mscLpEngFrs components."
::= { mscLpEngFrs 1 }

mscLpEngFrsRowStatusEntry OBJECT-TYPE
   SYNTAX     MscLpEngFrsRowStatusEntry
   ACCESS     not-accessible
   STATUS     mandatory
   DESCRIPTION
     "A single entry in the table represents a single 
      mscLpEngFrs component."
   INDEX {
      mscLpIndex,
      mscLpEngIndex,
      mscLpEngFrsIndex }
::= { mscLpEngFrsRowStatusTable 1 }

MscLpEngFrsRowStatusEntry ::= SEQUENCE {
   mscLpEngFrsRowStatus
      RowStatus,
   mscLpEngFrsComponentName
      DisplayString,
   mscLpEngFrsStorageType
      StorageType,
   mscLpEngFrsIndex
      NonReplicated }

mscLpEngFrsRowStatus OBJECT-TYPE
   SYNTAX     RowStatus 
   ACCESS     read-write
   STATUS     mandatory
   DESCRIPTION
     "This variable is used as the basis for SNMP naming of
      mscLpEngFrs components.
      These components can be added and deleted."
::= { mscLpEngFrsRowStatusEntry 1 }

mscLpEngFrsComponentName OBJECT-TYPE
   SYNTAX     DisplayString 
   ACCESS     read-only
   STATUS     mandatory
   DESCRIPTION
     "This variable provides the component's string name for
      use with the ASCII Console Interface"
::= { mscLpEngFrsRowStatusEntry 2 }

mscLpEngFrsStorageType OBJECT-TYPE
   SYNTAX     StorageType 
   ACCESS     read-only
   STATUS     mandatory
   DESCRIPTION
     "This variable represents the storage type value for the
      mscLpEngFrs tables."
::= { mscLpEngFrsRowStatusEntry 4 }

mscLpEngFrsIndex OBJECT-TYPE
   SYNTAX     NonReplicated 
   ACCESS     not-accessible
   STATUS     mandatory
   DESCRIPTION
     "This variable represents the index for the mscLpEngFrs tables."
::= { mscLpEngFrsRowStatusEntry 10 }

mscLpEngFrsOperTable OBJECT-TYPE
   SYNTAX     SEQUENCE OF MscLpEngFrsOperEntry
   ACCESS     not-accessible
   STATUS     mandatory
   DESCRIPTION
     "This group contains the Frame Relay default or current engineering 
      parameters and statistics for this LP."
::= { mscLpEngFrs 10 }

mscLpEngFrsOperEntry OBJECT-TYPE
   SYNTAX     MscLpEngFrsOperEntry
   ACCESS     not-accessible
   STATUS     mandatory
   DESCRIPTION
     "An entry in the mscLpEngFrsOperTable."
   INDEX {
      mscLpIndex,
      mscLpEngIndex,
      mscLpEngFrsIndex }
::= { mscLpEngFrsOperTable 1 }

MscLpEngFrsOperEntry ::= SEQUENCE {
   mscLpEngFrsMaxCalls
      Unsigned32,
   mscLpEngFrsHeadroomCalls
      Unsigned32,
   mscLpEngFrsCurrentCalls
      Gauge32,
   mscLpEngFrsCallsRefused
      Unsigned32 }

mscLpEngFrsMaxCalls OBJECT-TYPE
   SYNTAX     Unsigned32 (0..1000000)
   ACCESS     read-only
   STATUS     mandatory
   DESCRIPTION
     "This attribute indicates the maximum number of Frame Relay (FR) 
      calls of any type (PVC, SPVC, or SVC) which can be 
      simultaneously 'current' on the LP. Note that 'current' doesn't 
      necessarily mean that the call is in data transfer. It minimally means 
      that such a call can subsequently generate accounting records. 
      When the value of currentCalls reaches the value of maxCalls for 
      FR on this LP, subsequent call attempts are rejected by the FR 
      service."
   DEFVAL     { 1000000 }
::= { mscLpEngFrsOperEntry 1 }

mscLpEngFrsHeadroomCalls OBJECT-TYPE
   SYNTAX     Unsigned32 (0..1000000)
   ACCESS     read-only
   STATUS     mandatory
   DESCRIPTION
     "This attribute indicates a number which allows a network engineer 
      to do some statistical multiplexing for admitting calls when certain 
      overload conditions are reached. For setting this, refer to the 
      Engineering Guidelines. It depends on conditions such as the 
      expected sustained SVC call setup/clear rates and how conservative 
      one wants to be in certain 'error' conditions where many calls are 
      cleared simultaneously."
   DEFVAL     { 1000000 }
::= { mscLpEngFrsOperEntry 2 }

mscLpEngFrsCurrentCalls OBJECT-TYPE
   SYNTAX     Gauge32 (0..4294967295)
   ACCESS     read-only
   STATUS     mandatory
   DESCRIPTION
     "This attribute counts the total number of Frame Relay calls (initially 
      just FrUni and FrNni) which are 'current'. Note that 'current' 
      doesn't necessarily mean that the call is in data transfer. It 
      minimally means that such a call can subsequently generate 
      accounting records."
::= { mscLpEngFrsOperEntry 3 }

mscLpEngFrsCallsRefused OBJECT-TYPE
   SYNTAX     Unsigned32 (0..4294967295)
   ACCESS     read-only
   STATUS     mandatory
   DESCRIPTION
     "This attribute counts the total number of call connections (including 
      calls from the link as well as calls from the subnet) that have been 
      refused because currentCalls has reached the limits, as specified by 
      the engineering formulas for Frs on this LP."
::= { mscLpEngFrsOperEntry 4 }


-- 
-- Lp Eng Frs Override
-- This component holds provisionable engineering parameters used 
-- by Frame Relay on this LP.

mscLpEngFrsOv OBJECT IDENTIFIER ::= { mscLpEngFrs 2 }



mscLpEngFrsOvRowStatusTable OBJECT-TYPE
   SYNTAX     SEQUENCE OF MscLpEngFrsOvRowStatusEntry
   ACCESS     not-accessible
   STATUS     mandatory
   DESCRIPTION
     "This entry controls the addition and deletion of 
      mscLpEngFrsOv components."
::= { mscLpEngFrsOv 1 }

mscLpEngFrsOvRowStatusEntry OBJECT-TYPE
   SYNTAX     MscLpEngFrsOvRowStatusEntry
   ACCESS     not-accessible
   STATUS     mandatory
   DESCRIPTION
     "A single entry in the table represents a single 
      mscLpEngFrsOv component."
   INDEX {
      mscLpIndex,
      mscLpEngIndex,
      mscLpEngFrsIndex,
      mscLpEngFrsOvIndex }
::= { mscLpEngFrsOvRowStatusTable 1 }

MscLpEngFrsOvRowStatusEntry ::= SEQUENCE {
   mscLpEngFrsOvRowStatus
      RowStatus,
   mscLpEngFrsOvComponentName
      DisplayString,
   mscLpEngFrsOvStorageType
      StorageType,
   mscLpEngFrsOvIndex
      NonReplicated }

mscLpEngFrsOvRowStatus OBJECT-TYPE
   SYNTAX     RowStatus 
   ACCESS     read-write
   STATUS     mandatory
   DESCRIPTION
     "This variable is used as the basis for SNMP naming of
      mscLpEngFrsOv components.
      These components can be added and deleted."
::= { mscLpEngFrsOvRowStatusEntry 1 }

mscLpEngFrsOvComponentName OBJECT-TYPE
   SYNTAX     DisplayString 
   ACCESS     read-only
   STATUS     mandatory
   DESCRIPTION
     "This variable provides the component's string name for
      use with the ASCII Console Interface"
::= { mscLpEngFrsOvRowStatusEntry 2 }

mscLpEngFrsOvStorageType OBJECT-TYPE
   SYNTAX     StorageType 
   ACCESS     read-only
   STATUS     mandatory
   DESCRIPTION
     "This variable represents the storage type value for the
      mscLpEngFrsOv tables."
::= { mscLpEngFrsOvRowStatusEntry 4 }

mscLpEngFrsOvIndex OBJECT-TYPE
   SYNTAX     NonReplicated 
   ACCESS     not-accessible
   STATUS     mandatory
   DESCRIPTION
     "This variable represents the index for the mscLpEngFrsOv tables."
::= { mscLpEngFrsOvRowStatusEntry 10 }

mscLpEngFrsOvProvTable OBJECT-TYPE
   SYNTAX     SEQUENCE OF MscLpEngFrsOvProvEntry
   ACCESS     not-accessible
   STATUS     mandatory
   DESCRIPTION
     "This group contains the Frame Relay provisionable engineering 
      parameters for this LP.
      DESCRIPTION"
::= { mscLpEngFrsOv 10 }

mscLpEngFrsOvProvEntry OBJECT-TYPE
   SYNTAX     MscLpEngFrsOvProvEntry
   ACCESS     not-accessible
   STATUS     mandatory
   DESCRIPTION
     "An entry in the mscLpEngFrsOvProvTable."
   INDEX {
      mscLpIndex,
      mscLpEngIndex,
      mscLpEngFrsIndex,
      mscLpEngFrsOvIndex }
::= { mscLpEngFrsOvProvTable 1 }

MscLpEngFrsOvProvEntry ::= SEQUENCE {
   mscLpEngFrsOvMaxCalls
      Unsigned32,
   mscLpEngFrsOvHeadroomCalls
      Unsigned32 }

mscLpEngFrsOvMaxCalls OBJECT-TYPE
   SYNTAX     Unsigned32 (0..1000000)
   ACCESS     read-write
   STATUS     mandatory
   DESCRIPTION
     "This attribute specifies the maximum number of Frame Relay calls 
      of any type (PVC, SPVC, or SVC) which can be simultaneously 
      'current' on this LP. Note that 'current' doesn't necessarily mean 
      that the call is in data transfer. It minimally means that such a call 
      can subsequently generate accounting records. When the value of 
      currentCalls reaches the value of maxCalls for FR on this LP, 
      subsequent call attempts are rejected by the FR services."
   DEFVAL     { 1000000 }
::= { mscLpEngFrsOvProvEntry 1 }

mscLpEngFrsOvHeadroomCalls OBJECT-TYPE
   SYNTAX     Unsigned32 (0..1000000)
   ACCESS     read-write
   STATUS     mandatory
   DESCRIPTION
     "This attribute specifies a number which allows a network engineer 
      to do some statistical multiplexing for admitting calls when certain 
      overload conditions are reached. For setting this, refer to the 
      Engineering Guidelines. It depends on conditions such as the 
      expected sustained SVC call setup/clear rates and how conservative 
      one wants to be in certain 'error' conditions where many calls are 
      cleared simultaneously."
   DEFVAL     { 1000000 }
::= { mscLpEngFrsOvProvEntry 2 }




-- 
-- Version and Compliance statements
-- 



-- Object-Group Statement:
-- A list of all current accessible leaf objects.

-- OBJECTS { mscLpEngFrsRowStatus,
--           mscLpEngFrsOvRowStatus,
--           mscLpEngFrsMaxCalls,
--           mscLpEngFrsOvMaxCalls,
--           mscLpEngFrsOvStorageType,
--           mscLpEngFrsCallsRefused,
--           mscLpEngFrsComponentName,
--           mscLpEngFrsOvComponentName,
--           mscLpEngFrsHeadroomCalls,
--           mscLpEngFrsOvHeadroomCalls,
--           mscLpEngFrsCurrentCalls,
--           mscLpEngFrsStorageType }
-- STATUS  mandatory
-- DESCRIPTION
--   "A list of all current accessible leaf objects."

frameRelayEngGroup OBJECT IDENTIFIER ::= { frameRelayEngMIB 1 }
frameRelayEngGroupCA OBJECT IDENTIFIER ::= { frameRelayEngGroup 1 }
frameRelayEngGroupCA02 OBJECT IDENTIFIER ::= { frameRelayEngGroupCA 3 }
frameRelayEngGroupCA02A OBJECT IDENTIFIER ::= { frameRelayEngGroupCA02 2 }



-- Agent-Capabilities Statement:

-- PRODUCT-RELEASE "MscPassport Release 1.2 FrameRelayEng."
-- STATUS          mandatory
-- DESCRIPTION     "Carrier Passport FrameRelayEng MIB: MIB Version CA02A,
--                  Software Version CA02S9C."
-- SUPPORTS        Nortel-MsCarrier-MscPassport-FrameRelayEngMIB
--    INCLUDES     { frameRelayEngGroupCA02A }

frameRelayEngCapabilities OBJECT IDENTIFIER ::= { frameRelayEngMIB 3 }
frameRelayEngCapabilitiesCA OBJECT IDENTIFIER ::= { frameRelayEngCapabilities 1 }
frameRelayEngCapabilitiesCA02 OBJECT IDENTIFIER ::= { frameRelayEngCapabilitiesCA 3 }
frameRelayEngCapabilitiesCA02A OBJECT IDENTIFIER ::= { frameRelayEngCapabilitiesCA02 2 }





END
