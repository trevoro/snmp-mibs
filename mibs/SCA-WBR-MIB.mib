SCA-WBR-MIB DEFINITIONS ::= BEGIN

-- Copyright (C) 1997 Intel Corporation. All rights reserved.
--
-- WAN Bridging MIB, 02-05-1997
--
-- This mib is a proprietary extension to the RFC 1493 Bridge MIB.
--
-- Change History:
-- 97-05-02 Initial version
-- 97-04-06 Spelling errors, descriptions & enums corrected
-- 97-04-10 added counters for Total
--

IMPORTS
        Counter, TimeTicks      FROM RFC1155-SMI
        scanet                  FROM SCANET-MIB
        OBJECT-TYPE             FROM RFC-1212;

wbr                     OBJECT IDENTIFIER ::= { scanet 49 }
wbrBase                 OBJECT IDENTIFIER ::= { wbr 1 }
wbrStp                  OBJECT IDENTIFIER ::= { wbr 2 }
wbrTp                   OBJECT IDENTIFIER ::= { wbr 3 }

wbrBaseLastConfigTime OBJECT-TYPE
    SYNTAX TimeTicks
    ACCESS read-only
    STATUS mandatory
    DESCRIPTION "Time of last change in bridge configuration"
    ::= { wbrBase 1 }

wbrBaseBridging OBJECT-TYPE
    SYNTAX INTEGER { disabled(1), enabled(2) }
    ACCESS read-only
    STATUS mandatory
    DESCRIPTION "Is Bridging (except of IP/IPX) enabled - 'Enabled' or 'Disabled'"
    ::= { wbrBase 2 }

wbrBaseBridgingIP OBJECT-TYPE
    SYNTAX INTEGER { disabled(1), enabled(2) }
    ACCESS read-only
    STATUS mandatory
    DESCRIPTION "Is Bridging of IP traffic Enabled - 'Enabled' or 'Disabled'"
    ::= { wbrBase 3 }

wbrBaseBridgingIPX OBJECT-TYPE
    SYNTAX INTEGER { disabled(1), enabled(2) }
    ACCESS read-only
    STATUS mandatory
    DESCRIPTION "Is Bridging of IPX traffic Enabled - 'Enabled' or 'Disabled'"
    ::= { wbrBase 4 }

wbrStpBridgeAgeingTime OBJECT-TYPE
    SYNTAX INTEGER
    ACCESS read-only
    STATUS mandatory
    DESCRIPTION "The Ageing Time configured for this Bridge"
    ::= { wbrStp 1 }

wbrStpBridgeIsRoot OBJECT-TYPE
    SYNTAX INTEGER { no(1), yes(2) }
    ACCESS read-only
    STATUS mandatory
    DESCRIPTION "Is this Bridge the Root Bridge - 'Yes' or 'No'"
    ::= { wbrStp 2 }

wbrStpRxBPDUs OBJECT-TYPE
    SYNTAX Counter
    ACCESS read-only
    STATUS mandatory
    DESCRIPTION "Total number of BPDUs packets received"
    ::= { wbrStp 3 }

wbrStpTxBPDUs OBJECT-TYPE
    SYNTAX Counter
    ACCESS read-only
    STATUS mandatory
    DESCRIPTION "Total number of BPDUs packets transmitted"
    ::= { wbrStp 4 }

wbrStpTxBPDUsFailed OBJECT-TYPE
    SYNTAX Counter
    ACCESS read-only
    STATUS mandatory
    DESCRIPTION "Total number of BPDUs packets unsuccessfully transmitted"
    ::= { wbrStp 5 }

wbrStpRxSpoofBPDUs OBJECT-TYPE
    SYNTAX Counter
    ACCESS read-only
    STATUS mandatory
    DESCRIPTION "Total number of BPDUs packets spoofed instead of received"
    ::= { wbrStp 6 }

wbrStpTxSpoofBPDUs OBJECT-TYPE
    SYNTAX Counter
    ACCESS read-only
    STATUS mandatory
    DESCRIPTION "Total number of BPDUs packets spoofed instead of transmitted"
    ::= { wbrStp 7 }

wbrStpTxSpoofFailed OBJECT-TYPE
    SYNTAX Counter
    ACCESS read-only
    STATUS mandatory
    DESCRIPTION "Total number of spoofing protocol packets unsuccessfully
                 transmitted"
    ::= { wbrStp 8 }

wbrStpTxSpoofData OBJECT-TYPE
    SYNTAX Counter
    ACCESS read-only
    STATUS mandatory
    DESCRIPTION "Total number of packets spoofed instead of transmitted"
    ::= { wbrStp 9 }

wbrStpTable OBJECT-TYPE
    SYNTAX SEQUENCE OF WbrStpEntry
    ACCESS not-accessible
    STATUS mandatory
    DESCRIPTION "A table that contains port-specific information
                 for the Spanning Tree Protocol."
    ::= { wbrStp 10 }

wbrStpEntry OBJECT-TYPE
    SYNTAX WbrStpEntry
    ACCESS not-accessible
    STATUS mandatory
    DESCRIPTION ""
    INDEX { wbrStpIfIndex }
    ::= { wbrStpTable 1 }

WbrStpEntry ::= SEQUENCE {
                        wbrStpIfIndex
                           INTEGER,
                        wbrStpRxProtocolBytes
                           Counter,
                        wbrStpTxProtocolBytes
                           Counter,
                        wbrStpRxBPDUs
                           Counter,
                        wbrStpTxBPDUs
                           Counter,
                        wbrStpTxBPDUsFailed
                           Counter,
                        wbrStpRxSpoofBPDUs
                           Counter,
                        wbrStpTxSpoofBPDUs
                           Counter,
                        wbrStpTxSpoofFailed
                           Counter,
                        wbrStpTxSpoofData
                           Counter,
                        wbrStpSPTStatus
                           OCTET STRING,
                        wbrStpConfigBPDUPending
                           INTEGER,
                        wbrStpTopologyChangeAck
                           INTEGER,
                        wbrStpConfigBPDUAgeActive
                           INTEGER,
                        wbrStpConfigBPDUAge
                           INTEGER,
                        wbrStpBPDUSpoofing
                           OCTET STRING,
                        wbrStpNonBPDUSpoofing
                           OCTET STRING,
                        wbrStpSpoofing
                           INTEGER
                        }

wbrStpIfIndex OBJECT-TYPE
    SYNTAX INTEGER
    ACCESS read-only
    STATUS mandatory
    DESCRIPTION "Link Index"
    ::= { wbrStpEntry 1 }

wbrStpRxProtocolBytes OBJECT-TYPE
    SYNTAX Counter
    ACCESS read-only
    STATUS mandatory
    DESCRIPTION "BPDUs bytes received"
    ::= { wbrStpEntry 2 }

wbrStpTxProtocolBytes OBJECT-TYPE
    SYNTAX Counter
    ACCESS read-only
    STATUS mandatory
    DESCRIPTION "BPDU bytes transmitted"
    ::= { wbrStpEntry 3 }

wbrStpRxBPDUs OBJECT-TYPE
    SYNTAX Counter
    ACCESS read-only
    STATUS mandatory
    DESCRIPTION "Number of BPDUs packets received"
    ::= { wbrStpEntry 4 }

wbrStpTxBPDUs OBJECT-TYPE
    SYNTAX Counter
    ACCESS read-only
    STATUS mandatory
    DESCRIPTION "Number of BPDUs packets transmitted"
    ::= { wbrStpEntry 5 }

wbrStpTxBPDUsFailed OBJECT-TYPE
    SYNTAX Counter
    ACCESS read-only
    STATUS mandatory
    DESCRIPTION "Number of BPDUs packets unsuccessfully transmitted
                 from the link"
    ::= { wbrStpEntry 6 }

wbrStpRxSpoofBPDUs OBJECT-TYPE
    SYNTAX Counter
    ACCESS read-only
    STATUS mandatory
    DESCRIPTION "Number of BPDUs packets spoofed instead of received on link"
    ::= { wbrStpEntry 7 }

wbrStpTxSpoofBPDUs OBJECT-TYPE
    SYNTAX Counter
    ACCESS read-only
    STATUS mandatory
    DESCRIPTION "Number of BPDUs packets spoofed instead of transmitted on link"
    ::= { wbrStpEntry 8 }

wbrStpTxSpoofFailed OBJECT-TYPE
    SYNTAX Counter
    ACCESS read-only
    STATUS mandatory
    DESCRIPTION "Number of spoofing protocol packets unsuccessfully
                 transmitted from the link"
    ::= { wbrStpEntry 9 }

wbrStpTxSpoofData OBJECT-TYPE
    SYNTAX Counter
    ACCESS read-only
    STATUS mandatory
    DESCRIPTION "Number of packets spoofed instead of transmitted on link"
    ::= { wbrStpEntry 10 }

wbrStpSPTStatus OBJECT-TYPE
    SYNTAX OCTET STRING (SIZE(30))
    ACCESS read-only
    STATUS mandatory
    DESCRIPTION "Status for Spanning Tree Link"
    ::= { wbrStpEntry 11 }

wbrStpConfigBPDUPending OBJECT-TYPE
    SYNTAX INTEGER { no(1), yes(2) }
    ACCESS read-only
    STATUS mandatory
    DESCRIPTION "Whether a Configuration BPDU packet is to
                 be forwarded to the Bridges on the Designated
                 ports (via Configuration BPDUs) - 'Yes' or 'No'"
    ::= { wbrStpEntry 12 }

wbrStpTopologyChangeAck OBJECT-TYPE
    SYNTAX INTEGER { no(1), yes(2) }
    ACCESS read-only
    STATUS mandatory
    DESCRIPTION "Determines if the configuration change is
                 to be forwarded to the Bridges on the Designated
                 Ports (via Configuration BPDUs) - 'Yes' or 'No'"
    ::= { wbrStpEntry 13 }

wbrStpConfigBPDUAgeActive OBJECT-TYPE
    SYNTAX INTEGER { no(1), yes(2) }
    ACCESS read-only
    STATUS mandatory
    DESCRIPTION "Whether ConfigBPDUAge is active/valid for
                 monitoring. If not active then ConfigBPDUAge is undefined
                 i.e. 'Not Active'"
    ::= { wbrStpEntry 14 }

wbrStpConfigBPDUAge OBJECT-TYPE
    SYNTAX INTEGER
    ACCESS read-only
    STATUS mandatory
    DESCRIPTION "The age of the information within the last
                 Configuration BPDU packet received from the
                 Designated Bridge"
    ::= { wbrStpEntry 15 }

wbrStpBPDUSpoofing OBJECT-TYPE
    SYNTAX OCTET STRING (SIZE(14))
    ACCESS read-only
    STATUS mandatory
    DESCRIPTION "Whether Configuration BPDU packets are
                 spoofed - 'Yes' or 'Not Active'"
    ::= { wbrStpEntry 16 }

wbrStpNonBPDUSpoofing OBJECT-TYPE
    SYNTAX OCTET STRING (SIZE(14))
    ACCESS read-only
    STATUS mandatory
    DESCRIPTION "Whether Non-BPDU packets are spoofed -
                  'Yes' or 'Not Active'"
    ::= { wbrStpEntry 17 }

wbrStpSpoofing OBJECT-TYPE
    SYNTAX INTEGER { disabled(1), enabled(2) }
    ACCESS read-only
    STATUS mandatory
    DESCRIPTION "If Spoofing is enabled in Setup"
    ::= { wbrStpEntry 18 }

wbrTpRxPackets OBJECT-TYPE
    SYNTAX Counter
    ACCESS read-only
    STATUS mandatory
    DESCRIPTION "Total number of bridged packets
                 (non BPDU packets) received"
    ::= { wbrTp 1 }

wbrTpTxPackets OBJECT-TYPE
    SYNTAX Counter
    ACCESS read-only
    STATUS mandatory
    DESCRIPTION "Total number of bridged packets
                 (non BPDU packets) transmitted"
    ::= { wbrTp 2 }

wbrTpTxFailed OBJECT-TYPE
    SYNTAX Counter
    ACCESS read-only
    STATUS mandatory
    DESCRIPTION "Total number of packets that the
                 router failed to transmit"
    ::= { wbrTp 3 }

wbrTpRxRejUnknown OBJECT-TYPE
    SYNTAX Counter
    ACCESS read-only
    STATUS mandatory
    DESCRIPTION "Total number of unknown Unicast packets
                 received which were discarded due to exceeding
                 the maximum number of unknown Unicast packets
                 (5 within 5 seconds for the entire Bridge)"
    ::= { wbrTp 4 }

wbrTpRxRejTotal OBJECT-TYPE
    SYNTAX Counter
    ACCESS read-only
    STATUS mandatory
    DESCRIPTION "Total number of valid frames received
                 which were rejected (i.e., filtered)
                 by the Forwarding Process"
    ::= { wbrTp 5 }

wbrTpRxInvalid OBJECT-TYPE
    SYNTAX Counter
    ACCESS read-only
    STATUS mandatory
    DESCRIPTION "Total number of erroneous packets received"
    ::= { wbrTp 6 }

wbrTpRejUnicast OBJECT-TYPE
    SYNTAX Counter
    ACCESS read-only
    STATUS mandatory
    DESCRIPTION "Total number of packets received
                 which were rejected by the Unicast Destination
                 Forwarding Table"
    ::= { wbrTp 7 }

wbrTpRejDefaultUnicast OBJECT-TYPE
    SYNTAX Counter
    ACCESS read-only
    STATUS mandatory
    DESCRIPTION "Total number of packets received
                 which were rejected by the Default Action of the
                 Unicast Destination Forwarding Table"
    ::= { wbrTp 8 }

wbrTpRejMulticast OBJECT-TYPE
    SYNTAX Counter
    ACCESS read-only
    STATUS mandatory
    DESCRIPTION "Total number of packets received
                 which were rejected by the Multicast Destination
                 Forwarding Table"
    ::= { wbrTp 9 }

wbrTpRejDefaultMulticast OBJECT-TYPE
    SYNTAX Counter
    ACCESS read-only
    STATUS mandatory
    DESCRIPTION "Total number of packets received
                 which were rejected by the Default Action of
                 the Multicast Destination Forwarding Table"
    ::= { wbrTp 10 }

wbrTpRejSource OBJECT-TYPE
    SYNTAX Counter
    ACCESS read-only
    STATUS mandatory
    DESCRIPTION "Total number of packets received
                 which were rejected by the Source Forwarding Table"
    ::= { wbrTp 11 }

wbrTpRejDefaultSource OBJECT-TYPE
    SYNTAX Counter
    ACCESS read-only
    STATUS mandatory
    DESCRIPTION "Total number of packets received
                 which were rejected by the Default Action of the
                 Source Forwarding Table"
    ::= { wbrTp 12 }

wbrTpRejType OBJECT-TYPE
    SYNTAX Counter
    ACCESS read-only
    STATUS mandatory
    DESCRIPTION "Total number of packets received
                 which were rejected by the Type Forwarding Table"
    ::= { wbrTp 13 }

wbrTpRejDefaultType OBJECT-TYPE
    SYNTAX Counter
    ACCESS read-only
    STATUS mandatory
    DESCRIPTION "Total number of packets received
                 which were rejected by the Default Action of the
                 Type Forwarding Table"
    ::= { wbrTp 14 }

wbrTpTable OBJECT-TYPE
    SYNTAX SEQUENCE OF WbrTpEntry
    ACCESS not-accessible
    STATUS mandatory
    DESCRIPTION "A table that contains information about every
                 port that is associated with this transparent
                 bridge."
    ::= { wbrTp 15 }

wbrTpEntry OBJECT-TYPE
    SYNTAX WbrTpEntry
    ACCESS not-accessible
    STATUS mandatory
    DESCRIPTION ""
    INDEX { wbrTpIfIndex }
    ::= { wbrTpTable 1 }

WbrTpEntry ::= SEQUENCE {
                        wbrTpIfIndex
                           INTEGER,
                        wbrTpRxOtherBytes
                           Counter,
                        wbrTpTxOtherBytes
                           Counter,
                        wbrTpRxRejectedBytes
                           Counter,
                        wbrTpTxRejectedBytes
                           Counter,
                        wbrTpRxRejUnknown
                           Counter,
                        wbrTpRxInvalid
                           Counter,
                        wbrTpTxFailed
                           Counter,
                        wbrTpRxRejUnicast
                           Counter,
                        wbrTpRxRejMulticast
                           Counter,
                        wbrTpRxRejSource
                           Counter,
                        wbrTpRxRejType
                           Counter,
                        wbrTpRxRejDefaultUnicast
                           Counter,
                        wbrTpRxRejDefaultMulticast
                           Counter,
                        wbrTpRxRejDefaultSource
                           Counter,
                        wbrTpRxRejDefaultType
                           Counter
                        }

wbrTpIfIndex OBJECT-TYPE
    SYNTAX INTEGER
    ACCESS read-only
    STATUS mandatory
    DESCRIPTION "Link Index"
    ::= { wbrTpEntry 1 }

wbrTpRxOtherBytes OBJECT-TYPE
    SYNTAX Counter
    ACCESS read-only
    STATUS mandatory
    DESCRIPTION "Non-BPDU bytes received"
    ::= { wbrTpEntry 2 }

wbrTpTxOtherBytes OBJECT-TYPE
    SYNTAX Counter
    ACCESS read-only
    STATUS mandatory
    DESCRIPTION "Non-BPDU bytes transmitted"
    ::= { wbrTpEntry 3 }

wbrTpRxRejectedBytes OBJECT-TYPE
    SYNTAX Counter
    ACCESS read-only
    STATUS mandatory
    DESCRIPTION "Number of non-BPDU bytes received on this
                 link which were rejected"
    ::= { wbrTpEntry 4 }

wbrTpTxRejectedBytes OBJECT-TYPE
    SYNTAX Counter
    ACCESS read-only
    STATUS mandatory
    DESCRIPTION "Number of non-BPDU bytes to be transmitted
                 on this link which were rejected"
    ::= { wbrTpEntry 5 }

wbrTpRxRejUnknown OBJECT-TYPE
    SYNTAX Counter
    ACCESS read-only
    STATUS mandatory
    DESCRIPTION "Number of unknown Unicast packets received
                 on the link which were discarded due to exceeding
                 the maximum number of unknown Unicast packets
                 (5 within 5 seconds for the entire Bridge)"
    ::= { wbrTpEntry 6 }

wbrTpRxInvalid OBJECT-TYPE
    SYNTAX Counter
    ACCESS read-only
    STATUS mandatory
    DESCRIPTION "Number of erroneous packets received"
    ::= { wbrTpEntry 7 }

wbrTpTxFailed OBJECT-TYPE
    SYNTAX Counter
    ACCESS read-only
    STATUS mandatory
    DESCRIPTION "Number of non-BPDU packets unsuccessfully
                 transmitted from the link"
    ::= { wbrTpEntry 8 }

wbrTpRxRejUnicast OBJECT-TYPE
    SYNTAX Counter
    ACCESS read-only
    STATUS mandatory
    DESCRIPTION "Number of packets received on this link
                 which were rejected by the Unicast Destination
                 Forwarding Table"
    ::= { wbrTpEntry 9 }

wbrTpRxRejMulticast OBJECT-TYPE
    SYNTAX Counter
    ACCESS read-only
    STATUS mandatory
    DESCRIPTION "Number of packets received on this link
                 which were rejected by the Multicast Destination
                 Forwarding Table"
    ::= { wbrTpEntry 10 }

wbrTpRxRejSource OBJECT-TYPE
    SYNTAX Counter
    ACCESS read-only
    STATUS mandatory
    DESCRIPTION "Number of packets received on this link which
                 were rejected by the Source Forwarding Table"
    ::= { wbrTpEntry 11 }

wbrTpRxRejType OBJECT-TYPE
    SYNTAX Counter
    ACCESS read-only
    STATUS mandatory
    DESCRIPTION "Number of packets received on this link which
                 were rejected by the Type Forwarding Table"
    ::= { wbrTpEntry 12 }

wbrTpRxRejDefaultUnicast OBJECT-TYPE
    SYNTAX Counter
    ACCESS read-only
    STATUS mandatory
    DESCRIPTION "Number of packets received on this link
                 which were rejected by the Default Action of the
                 Unicast Destination Forwarding Table"
    ::= { wbrTpEntry 13 }

wbrTpRxRejDefaultMulticast OBJECT-TYPE
    SYNTAX Counter
    ACCESS read-only
    STATUS mandatory
    DESCRIPTION "Number of packets received on this link
                 which were rejected by the Default Action of
                 the Multicast Destination Forwarding Table"
    ::= { wbrTpEntry 14 }

wbrTpRxRejDefaultSource OBJECT-TYPE
    SYNTAX Counter
    ACCESS read-only
    STATUS mandatory
    DESCRIPTION "Number of packets received on this link
                 which were rejected by the Default Action of the
                 Source Forwarding Table"
    ::= { wbrTpEntry 15 }

wbrTpRxRejDefaultType OBJECT-TYPE
    SYNTAX Counter
    ACCESS read-only
    STATUS mandatory
    DESCRIPTION "Number of packets received on this link
                 which were rejected by the Default Action of the
                 Type Forwarding Table"
    ::= { wbrTpEntry 16 }

END
