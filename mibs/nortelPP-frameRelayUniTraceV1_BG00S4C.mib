Nortel-Magellan-Passport-FrameRelayUniTraceMIB
DEFINITIONS ::= BEGIN



IMPORTS

      OBJECT-TYPE
   FROM RFC-1212

      passportMIBs
   FROM Nortel-Magellan-Passport-UsefulDefinitionsMIB

      RowPointer,
      DisplayString,
      StorageType,
      RowStatus,
      Unsigned32
   FROM Nortel-Magellan-Passport-StandardTextualConventionsMIB

      AsciiString,
      NonReplicated
   FROM Nortel-Magellan-Passport-TextualConventionsMIB

      frUniIndex,
      frUni
   FROM Nortel-Magellan-Passport-FrameRelayUniMIB;




-- LAST-UPDATED   "9706300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayUniTrace Enterprise MIB."

frameRelayUniTraceMIB OBJECT IDENTIFIER ::= { passportMIBs 105 }










-- FrUni/n Trace
-- FrNni/n Trace
-- The Trace component of the Frame Relay service determines if the 
-- trace capability is allowed on this interface. If it is not provisioned, 
-- then a trace session cannot be started on this service.

frUniTrace OBJECT IDENTIFIER ::= { frUni 7 }



frUniTraceRowStatusTable OBJECT-TYPE
   SYNTAX     SEQUENCE OF FrUniTraceRowStatusEntry
   ACCESS     not-accessible
   STATUS     mandatory
   DESCRIPTION
     "This entry controls the addition and deletion of 
      frUniTrace components."
::= { frUniTrace 1 }

frUniTraceRowStatusEntry OBJECT-TYPE
   SYNTAX     FrUniTraceRowStatusEntry
   ACCESS     not-accessible
   STATUS     mandatory
   DESCRIPTION
     "A single entry in the table represents a single 
      frUniTrace component."
   INDEX {
      frUniIndex,
      frUniTraceIndex }
::= { frUniTraceRowStatusTable 1 }

FrUniTraceRowStatusEntry ::= SEQUENCE {
   frUniTraceRowStatus
      RowStatus,
   frUniTraceComponentName
      DisplayString,
   frUniTraceStorageType
      StorageType,
   frUniTraceIndex
      NonReplicated }

frUniTraceRowStatus OBJECT-TYPE
   SYNTAX     RowStatus 
   ACCESS     read-write
   STATUS     mandatory
   DESCRIPTION
     "This variable is used as the basis for SNMP naming of
      frUniTrace components.
      These components can be added and deleted."
::= { frUniTraceRowStatusEntry 1 }

frUniTraceComponentName OBJECT-TYPE
   SYNTAX     DisplayString 
   ACCESS     read-only
   STATUS     mandatory
   DESCRIPTION
     "This variable provides the component's string name for
      use with the ASCII Console Interface"
::= { frUniTraceRowStatusEntry 2 }

frUniTraceStorageType OBJECT-TYPE
   SYNTAX     StorageType 
   ACCESS     read-only
   STATUS     mandatory
   DESCRIPTION
     "This variable represents the storage type value for the
      frUniTrace tables."
::= { frUniTraceRowStatusEntry 4 }

frUniTraceIndex OBJECT-TYPE
   SYNTAX     NonReplicated 
   ACCESS     not-accessible
   STATUS     mandatory
   DESCRIPTION
     "This variable represents the index for the frUniTrace tables."
::= { frUniTraceRowStatusEntry 10 }

frUniTraceOperationalTable OBJECT-TYPE
   SYNTAX     SEQUENCE OF FrUniTraceOperationalEntry
   ACCESS     not-accessible
   STATUS     mandatory
   DESCRIPTION
     "This group provides the operational attributes for the Trace 
      component."
::= { frUniTrace 10 }

frUniTraceOperationalEntry OBJECT-TYPE
   SYNTAX     FrUniTraceOperationalEntry
   ACCESS     not-accessible
   STATUS     mandatory
   DESCRIPTION
     "An entry in the frUniTraceOperationalTable."
   INDEX {
      frUniIndex,
      frUniTraceIndex }
::= { frUniTraceOperationalTable 1 }

FrUniTraceOperationalEntry ::= SEQUENCE {
   frUniTraceReceiverName
      AsciiString,
   frUniTraceDuration
      Unsigned32,
   frUniTraceQueueLimit
      Unsigned32,
   frUniTraceSession
      RowPointer }

frUniTraceReceiverName OBJECT-TYPE
   SYNTAX     AsciiString (SIZE (0..8))
   ACCESS     read-write
   STATUS     mandatory
   DESCRIPTION
     "This attribute should be set to the name of the desired trace receiver 
      before starting a trace session. All available trace receivers are listed 
      under the Trace Rcvr/<string> component. This attribute cannot be 
      set while a trace is active."
::= { frUniTraceOperationalEntry 2 }

frUniTraceDuration OBJECT-TYPE
   SYNTAX     Unsigned32 (0..9999)
   ACCESS     read-write
   STATUS     mandatory
   DESCRIPTION
     "This attribute specifies the duration, in minutes, of a trace session. 
      A value of 0 indicates unlimited duration in which case a trace 
      session remains active until a stop command is issued. The default 
      duration is 60 minutes. This attribute cannot be set while a trace is 
      active."
   DEFVAL     { 60 }
::= { frUniTraceOperationalEntry 3 }

frUniTraceQueueLimit OBJECT-TYPE
   SYNTAX     Unsigned32 (1..100)
   ACCESS     read-write
   STATUS     mandatory
   DESCRIPTION
     "This attribute specifies the total number of bytes of traced data 
      which may be queued for transmission to the trace receiver. When 
      this limit is exceeded, incoming traced frames are discarded. This 
      attribute can be set while a trace is active and takes effect 
      immediately."
   DEFVAL     { 20 }
::= { frUniTraceOperationalEntry 4 }

frUniTraceSession OBJECT-TYPE
   SYNTAX     RowPointer 
   ACCESS     read-only
   STATUS     mandatory
   DESCRIPTION
     "This attribute is set automatically. It identifies the Trace Session 
      component which is forwarding the trace data. This attribute is 
      empty unless a trace is active."
::= { frUniTraceOperationalEntry 5 }


-- FrUni/n Trace Filter 
-- FrNni/n Trace Filter
-- The Filter component defines the type of traced data that is sent to 
-- the receiver. The Filter component provides default values for all its 
-- attributes which are sufficient to start a trace session. Nonetheless, if 
-- needed, these attributes may be changed before or during a trace 
-- session.

frUniTraceFilter OBJECT IDENTIFIER ::= { frUniTrace 2 }



frUniTraceFilterRowStatusTable OBJECT-TYPE
   SYNTAX     SEQUENCE OF FrUniTraceFilterRowStatusEntry
   ACCESS     not-accessible
   STATUS     mandatory
   DESCRIPTION
     "This entry controls the addition and deletion of 
      frUniTraceFilter components."
::= { frUniTraceFilter 1 }

frUniTraceFilterRowStatusEntry OBJECT-TYPE
   SYNTAX     FrUniTraceFilterRowStatusEntry
   ACCESS     not-accessible
   STATUS     mandatory
   DESCRIPTION
     "A single entry in the table represents a single 
      frUniTraceFilter component."
   INDEX {
      frUniIndex,
      frUniTraceIndex,
      frUniTraceFilterIndex }
::= { frUniTraceFilterRowStatusTable 1 }

FrUniTraceFilterRowStatusEntry ::= SEQUENCE {
   frUniTraceFilterRowStatus
      RowStatus,
   frUniTraceFilterComponentName
      DisplayString,
   frUniTraceFilterStorageType
      StorageType,
   frUniTraceFilterIndex
      NonReplicated }

frUniTraceFilterRowStatus OBJECT-TYPE
   SYNTAX     RowStatus 
   ACCESS     read-only
   STATUS     mandatory
   DESCRIPTION
     "This variable is used as the basis for SNMP naming of
      frUniTraceFilter components.
      These components cannot be added nor deleted."
::= { frUniTraceFilterRowStatusEntry 1 }

frUniTraceFilterComponentName OBJECT-TYPE
   SYNTAX     DisplayString 
   ACCESS     read-only
   STATUS     mandatory
   DESCRIPTION
     "This variable provides the component's string name for
      use with the ASCII Console Interface"
::= { frUniTraceFilterRowStatusEntry 2 }

frUniTraceFilterStorageType OBJECT-TYPE
   SYNTAX     StorageType 
   ACCESS     read-only
   STATUS     mandatory
   DESCRIPTION
     "This variable represents the storage type value for the
      frUniTraceFilter tables."
::= { frUniTraceFilterRowStatusEntry 4 }

frUniTraceFilterIndex OBJECT-TYPE
   SYNTAX     NonReplicated 
   ACCESS     not-accessible
   STATUS     mandatory
   DESCRIPTION
     "This variable represents the index for the frUniTraceFilter tables."
::= { frUniTraceFilterRowStatusEntry 10 }

frUniTraceFilterOperationalTable OBJECT-TYPE
   SYNTAX     SEQUENCE OF FrUniTraceFilterOperationalEntry
   ACCESS     not-accessible
   STATUS     mandatory
   DESCRIPTION
     "This group provides the operational attributes for the Frame Relay 
      Trace Filter component."
::= { frUniTraceFilter 10 }

frUniTraceFilterOperationalEntry OBJECT-TYPE
   SYNTAX     FrUniTraceFilterOperationalEntry
   ACCESS     not-accessible
   STATUS     mandatory
   DESCRIPTION
     "An entry in the frUniTraceFilterOperationalTable."
   INDEX {
      frUniIndex,
      frUniTraceIndex,
      frUniTraceFilterIndex }
::= { frUniTraceFilterOperationalTable 1 }

FrUniTraceFilterOperationalEntry ::= SEQUENCE {
   frUniTraceFilterTraceType
      OCTET STRING,
   frUniTraceFilterTracedDlci
      Unsigned32,
   frUniTraceFilterDirection
      OCTET STRING,
   frUniTraceFilterTracedLength
      Unsigned32 }

frUniTraceFilterTraceType OBJECT-TYPE
   SYNTAX     OCTET STRING (SIZE (1))
   ACCESS     read-write
   STATUS     mandatory
   DESCRIPTION
     "This attribute specifies the level of filtering required for this trace 
      session. A value of lmi indicates that Lmi frames are traced. A 
      value of dlci indicates that frames from the Dlci specified by the 
      tracedDlci attribute are traced. A value of badFrames indicates that 
      bad received frames (overruns, CRC errors, aborts) are traced. The 
      default is to trace all frames. This attribute can be set while a trace 
      is active and takes effect immediately.

      Description of bits:
      lmi(0)
      dlci(1)
      badFrames(2)"
   DEFVAL     { 'e0'H }
::= { frUniTraceFilterOperationalEntry 1 }

frUniTraceFilterTracedDlci OBJECT-TYPE
   SYNTAX     Unsigned32 (0..1007)
   ACCESS     read-write
   STATUS     mandatory
   DESCRIPTION
     "This attribute specifies a particular Dlci to trace. A value of zero 
      specifies that all Dlcis are to be traced. This attribute can be set 
      while a trace is active and takes effect immediately."
   DEFVAL     { 0 }
::= { frUniTraceFilterOperationalEntry 2 }

frUniTraceFilterDirection OBJECT-TYPE
   SYNTAX     OCTET STRING (SIZE (1))
   ACCESS     read-write
   STATUS     mandatory
   DESCRIPTION
     "This attribute specifies the direction of the data to be traced as 
      viewed by the service. The values can be egress, and/or ingress. An 
      egress value indicates frames outbound from the service. An 
      ingress value indicates frames inbound to the service. This attribute 
      can be set while a trace is active and takes effect immediately.

      Description of bits:
      egress(0)
      ingress(1)"
   DEFVAL     { 'c0'H }
::= { frUniTraceFilterOperationalEntry 3 }

frUniTraceFilterTracedLength OBJECT-TYPE
   SYNTAX     Unsigned32 (1..2000)
   ACCESS     read-write
   STATUS     mandatory
   DESCRIPTION
     "This attribute specifies the maximum number of bytes to trace per 
      frame starting from the byte following the frame flag. If the frame 
      length is longer than the value specified by this attribute, then the 
      traced frame is truncated. This attribute can be set while a trace is 
      active and takes effect immediately."
   DEFVAL     { 2000 }
::= { frUniTraceFilterOperationalEntry 4 }




-- 
-- Version and Compliance statements
-- 



-- Object-Group Statement:
-- A list of all current accessible leaf objects.

-- OBJECTS { frUniTraceStorageType,
--           frUniTraceRowStatus,
--           frUniTraceDuration,
--           frUniTraceFilterTracedDlci,
--           frUniTraceFilterComponentName,
--           frUniTraceQueueLimit,
--           frUniTraceSession,
--           frUniTraceFilterRowStatus,
--           frUniTraceFilterDirection,
--           frUniTraceReceiverName,
--           frUniTraceFilterTracedLength,
--           frUniTraceFilterTraceType,
--           frUniTraceFilterStorageType,
--           frUniTraceComponentName }
-- STATUS  mandatory
-- DESCRIPTION
--   "A list of all current accessible leaf objects."

frameRelayUniTraceGroup OBJECT IDENTIFIER ::= { frameRelayUniTraceMIB 1 }
frameRelayUniTraceGroupBD OBJECT IDENTIFIER ::= { frameRelayUniTraceGroup 4 }
frameRelayUniTraceGroupBD01 OBJECT IDENTIFIER ::= { frameRelayUniTraceGroupBD 2 }
frameRelayUniTraceGroupBD01A OBJECT IDENTIFIER ::= { frameRelayUniTraceGroupBD01 2 }



-- Agent-Capabilities Statement:

-- PRODUCT-RELEASE "Passport Release 7.0 FrameRelayUniTrace."
-- STATUS          mandatory
-- DESCRIPTION     "FrameRelayUniTrace MIB: MIB Version BD01A,
--                  Software Version BG00S4C."
-- SUPPORTS        Nortel-Magellan-Passport-FrameRelayUniTraceMIB
--    INCLUDES     { frameRelayUniTraceGroupBD01A }

frameRelayUniTraceCapabilities OBJECT IDENTIFIER ::= { frameRelayUniTraceMIB 3 }
frameRelayUniTraceCapabilitiesBD OBJECT IDENTIFIER ::= { frameRelayUniTraceCapabilities 4 }
frameRelayUniTraceCapabilitiesBD01 OBJECT IDENTIFIER ::= { frameRelayUniTraceCapabilitiesBD 2 }
frameRelayUniTraceCapabilitiesBD01A OBJECT IDENTIFIER ::= { frameRelayUniTraceCapabilitiesBD01 2 }





END
