-- COPYRIGHT NOTICE
-- Copyright (c) Alteon Networks, Inc. 1996, 1997 
-- All rights reserved
-- 
-- 
-- HISTORY
-- $Log: altswitch.mib $
-- Revision ts_8_16_rekha/6 2000/10/09 20:33:54 rekha
-- 	Fixed 4817: Added MIB objects to e/d forwarding directed broadcasts.
-- 
-- Revision ts_8_16_rekha/4 2000/10/09 18:03:26 rekha
-- 	Fixed 4878: Show backup server id as 'none' instead of 0.
-- 
-- Revision ts_8_16_rekha/2 2000/10/07 01:35:11 rekha
-- 	Fixed 4805: Added mib object to show enabled software features.
-- 
-- Revision ts80_16_smiao/2 2000/09/29 18:36:36 smiao
-- 	Fixed 4933. Changed inapproriate Counter type for some statistics
-- 	data to Gauge type.
-- 
-- Revision genie_rekha/6 2000/04/07 21:04:29 rekha
-- 	Modified Radius group for consistency.
-- 
-- Revision genie_rekha/4 2000/03/29 00:37:09 rekha
-- 	Fixed 3025: Implemented radius secret in WebUI and MIB
-- 
-- Revision genie_rekha/2 2000/03/23 17:34:05 rekha
-- 	Fixed 2960 : Added proxy enable/disable to WEBUI and MIB
-- 
-- Revision test_smiao/82 2000/03/17 01:05:41 smiao
-- 	Fixed 2889. Added filter FWLB hashing in webUI and MIBs.
-- 
-- Revision test_smiao/80 2000/03/16 22:27:53 smiao
-- 	Implemented MAC SAC substitution for real server in webUI and MIBs.
-- 
-- Revision latest_mlin/85 2000/03/15 19:21:17 mlin
-- 	Fixed 2363.  Obsoleted 64 bit SLB stats.
-- 
-- Revision wnLatest_wtnelson/4 2000/02/26 13:51:26 wtnelson
-- 	Bug 2808 - Corrected the index of vrrpInfoVirtRtrTableEntry by 
-- 	changing it from slbRealServerInfoIndex to vrrpInfoVirtRtrIndex.
-- 	This Gets rid of an extra column when displaying the
-- 	vrrpInfoVirtRtrTable.
-- 
-- Revision test_smiao/78 2000/02/23 00:54:51 smiao
-- 	Code cleanup for BWM SNMP.
-- 
-- Revision latest_mlin/81 2000/02/17 22:52:12 mlin
-- 	Fixed bug 1816. Forgot to mention bug number.
-- 
-- Revision latest_mlin/80 2000/02/17 22:25:14 mlin
-- 	Added object to support deletion of a virtual service.
-- 
-- Revision test_smiao/75 2000/02/14 22:31:51 smiao
-- 	Implemented SMTP configuations in SNMP and webUI.
-- 
-- Revision test_smiao/73 2000/02/11 19:49:30 smiao
-- 	Added BWM contract for trunkgroup in webUI and SNMP.
-- 
-- Revision latest_mlin/78 2000/02/09 20:55:01 mlin
-- 	Fixed 2478.  Forget to specify bug ID from previous.
-- 
-- Revision latest_mlin/77 2000/02/09 20:48:12 mlin
-- 	Added vrrpNewCfgIfDelete object to delete a virtual router interface.
-- 
-- Revision test_smiao/71 2000/02/07 23:45:22 smiao
-- 	Changed the limit configurations in SNMP and webUI.
-- 
-- Revision test_smiao/70 2000/02/07 17:27:45 smiao
-- 	merged
-- 
-- Revision latest_mlin/75 2000/02/06 01:20:39 mlin
-- 	Added MIB support to filter non-IP/ARP/RARP frames per port
-- 
-- Revision latest_mlin/73 2000/02/06 00:01:50 mlin
-- 	Added VLAN range (1..4094) in ipCurCfgIntfVlan, ipNewCfgIntfVlan.
-- 
-- Revision latest_mlin/70 2000/02/04 19:06:38 mlin
-- 	Added VRRP failover virtual router group support.
-- 
-- Revision latest_mlin/68 2000/02/02 00:44:21 mlin
-- 	Added mgmt support for IP TOS filtering.
-- 
-- Revision latest_mlin/66 2000/02/01 00:17:33 mlin
-- 	Added port configurations to support failover.
-- 
-- Revision latest_mlin/64 2000/01/31 02:14:39 mlin
-- 	Added enable/disable hotstandby processing.
-- 
-- Revision latest_mlin/62 2000/01/31 00:52:09 mlin
-- 	Added IP interface in static route to support 4 sub-net fire wall 
-- 	load balancing.
-- 
-- Revision latest_mlin/61 2000/01/30 22:26:12 mlin
-- 	Added direct server return and script health check support.
-- 
-- Revision latest_mlin/59 2000/01/30 00:13:07 mlin
-- 	Added VMA configuration support and minor cleanup.
-- 
-- Revision latest_mlin/57 2000/01/28 22:32:39 mlin
-- 	Added tcpStatHalfOpens stats support.
-- 
-- Revision ge_sandbox_dlin/28 2000/01/28 01:15:46 dlin
-- 	Rearrange the entry number for flt table
-- 
-- Revision test_smiao/68 2000/01/27 22:13:42 smiao
-- 	Extended VIP classification to virtual services in webUI and SNMP.
-- 
-- Revision test_smiao/67 2000/01/27 22:12:56 smiao
-- 	Added policy enforcement in webUI and SNMP.
-- 
-- Revision ge_sandbox_dlin/24 2000/01/27 07:44:37 dlin
-- 	Change ICMP objects to a single object.
-- 
-- Revision ge_sandbox_dlin/23 2000/01/27 07:34:10 dlin
-- 	Keep ICMP filter simple by making it a single object
-- 
-- Revision new_ge_latest_bshao/28 2000/01/27 03:04:09 bshao
-- 	Added SNMP support for new URL SLB menu system
-- 
-- Revision test_smiao/65 2000/01/25 20:13:08 smiao
-- 	Added precedence, TOS overwrite, history save and VLAN contract for BWM in SNMP.
-- 
-- Revision ge_latest_tolin/5 2000/01/24 22:52:05 tolin
-- 	Added SNMP support for ACL IP options
-- 
-- Revision latest_mlin/55 2000/01/24 17:19:43 mlin
-- 	merged
-- 
-- Revision latest_mlin/54 2000/01/24 17:15:56 mlin
-- 	merged
-- 
-- Revision latest_mlin/53 2000/01/24 17:15:26 mlin
-- 	Added range (1..120) for ripCurCfgUpdatePeriod.
-- 
-- Revision test_smiao/63 2000/01/24 01:37:11 smiao
-- 	Implemented BWM general configuration in webUI and SNMP.
-- 
-- Revision test_smiao/62 2000/01/24 01:18:00 smiao
-- 	merged
-- 
-- Revision ge_sandbox_dlin/20 2000/01/23 04:18:27 dlin
-- 	Replace allow/deny with enable/disable for ACL
-- 
-- Revision test_smiao/58 2000/01/20 20:15:50 smiao
-- 	Added port based and filter based BW Contracts in webUI and SNMP.
-- 
-- Revision ge_latest_jpao/9 2000/01/19 19:28:31 jpao
-- 	support secret to 32 bytes
-- 
-- Revision test_smiao/56 2000/01/18 19:56:57 smiao
-- 	Added TOS in and out of profile for policy config.
-- 
-- Revision latest_mlin/51 2000/01/16 00:57:47 mlin
-- 	Removed codes for supporting obsoleted L4 failover.
-- 
-- Revision test_smiao/53 2000/01/13 22:31:50 smiao
-- 	Implemented Bandwidth Management in SNMP and webUI.
-- 
-- Revision latest_mlin/47 2000/01/12 01:05:22 mlin
-- 	Added DisplayString size definition for host name of a virtual service.
-- 
-- Revision ge_sandbox_dlin/18 2000/01/06 02:05:04 dlin
-- 	Add SNMP support for TCP/ICMP ACL
-- 	As a side note, the way to config TCP/ICMP ACL filtering 
-- 	using SNMP right now is not very efficient.  A better way
-- 	propose by Michael is much better.  Instead of using a 
-- 	single object for each TCP flag or a object for 
-- 	each ICMP type, use two objects for TCP and another two 
-- 	objects for ICMP, one is the flag and other beings the mask.
-- 	For now, this should be sufficient, it will be clean up later
-- 	if ones should implement it in two objects instead of multiply
-- 	objects.
-- 
-- Revision ge_sandbox_dlin/17 2000/01/05 18:47:45 dlin
-- 	merged
-- 
-- Revision latest_mlin/45 2000/01/05 16:22:30 mlin
-- 	merged
-- 
-- Revision latest_mlin/44 2000/01/03 17:13:30 mlin
-- 	Defined range for GroupHealthCheckUrl, GroupRealThreshold.
-- 
-- Revision latest_mlin/43 1999/12/28 17:23:26 mlin
-- 	merged
-- 
-- Revision latest_mlin/42 1999/12/28 17:22:12 mlin
-- 	Added proper integer range for various objects in SLB group and more 
-- 	consistency.
-- 
-- Revision new_ge_latest_bshao/26 2000/01/05 01:04:03 bshao
-- 	Added code to support exclusionary string matching
-- 
-- Revision mysbx_dtai/18 1999/12/27 19:35:14 dtai
-- 	expanded RADIUS max timeout value from 3 secs to 10 secs for SecurID feature
-- 
-- Revision latest_mlin/40 1999/12/23 01:45:59 mlin
-- 	Modified in consistency for vrrp group.
-- 
-- Revision latest_mlin/39 1999/12/23 00:19:41 mlin
-- 	merged
-- 
-- Revision new_ge_latest_bshao/24 1999/12/22 02:30:06 bshao
-- 	Added URL based WCR stats
-- 
-- Revision new_ge_latest_bshao/22 1999/12/21 20:49:10 bshao
-- 	Added WEBUI and SNMP support for no-cache header
-- 
-- Revision latest_mlin/37 1999/12/17 00:13:17 mlin
-- 	Fix type error.
-- 
-- Revision latest_mlin/35 1999/12/17 00:00:22 mlin
-- 	Minor change for object name consistency.
-- 
-- Revision latest_mlin/33 1999/12/16 01:52:20 mlin
-- 	Removed range definition of filter table index (1..64).
-- 
-- Revision new_ge_latest_bshao/20 1999/12/06 22:33:53 bshao
-- 	Display URL info by V-server instead of V-service
-- 
-- Revision mysbx_dtai/16 1999/12/03 18:50:53 dtai
-- 	+renaming GPP, Static, and all related OIDs
-- 
-- Revision ge_sandbox_dlin/14 1999/11/27 03:35:49 dlin
-- 	Add the object ftpStats and there are two
-- 	items can be retrieve from this object, the
-- 	ftpSlbStatTotal and ftpNatStatTotal.  
-- 
-- Revision ge_sandbox_dlin/12 1999/11/24 07:47:14 dlin
-- 	Change the object name from passive to parsing
-- 
-- Revision new_ge_latest_bshao/18 1999/11/23 23:19:49 bshao
-- 	Added Web UI & SNMP support for URL SLB URL hashing
-- 
-- Revision test_smiao/46 1999/11/12 18:01:27 smiao
-- 	Made consitency in enable/disbale MIB defining.
-- 
-- Revision mysbx_dtai/14 1999/11/09 22:35:22 dtai
-- 	removed Vip3 to Vip8 per 6.1 final requirement
-- 
-- Revision test_smiao/44 1999/11/05 18:27:08 smiao
-- 	Implemented geographic awareness in gslb and ARP health checks in gateway.
-- 
-- Revision mysbx_dtai/12 1999/11/05 00:25:26 dtai
-- 	fixed object access mode to R/W for gslbNewCfgStaticSourceIp
-- 
-- Revision mysbx_dtai/10 1999/11/04 19:44:35 dtai
-- 	moved gpp parameter to GPP menu
-- 
-- Revision test_smiao/40 1999/11/04 01:54:39 smiao
-- 	Implemented Synch Configurations for SNMP and webUI.
-- 
-- Revision new_ge_latest_bshao/14 1999/11/03 03:22:42 bshao
-- 	Allow customize error message for URL SLB
-- 
-- Revision new_ge_latest_bshao/12 1999/11/01 17:45:31 bshao
-- 	fixed nightly build error
-- 
-- Revision new_ge_latest_bshao/10 1999/11/01 02:20:15 bshao
-- 	Added WEBUI and SNMP support for HTTP Header LB
-- 
-- Revision mysbx_dtai/6 1999/10/30 02:08:15 dtai
-- 	add SNMP code for GPP and Static table
-- 
-- Revision ge_latest_jpao/2 1999/10/23 00:13:10 jpao
-- 	add Radius mibs
-- 
-- Revision ge_sandbox_dlin/8 1999/10/19 08:50:56 dlin
-- 	Add initial support for ftp nat.
-- 
-- Revision test_smiao/38 1999/10/19 00:27:50 smiao
-- 	Added feature to allow users configure syslog facility (local0 - local7) in MIBs.
-- 
-- Revision new_ge_latest_bshao/8 1999/10/12 00:35:41 bshao
-- 	fixed bug 2362
-- 
-- Revision test_smiao/36 1999/09/22 17:42:32 smiao
-- 	Added MAC address filtering to SNMP.
-- 
-- Revision test_smiao/34 1999/09/20 22:01:19 smiao
-- 	Added synch peer server configuraions to SNMP.
-- 
-- Revision latest_mlin/31 1999/09/19 22:13:30 mlin
-- 	When adding new objects, always keep backward compatibility in mind, do NOT change object tree numbering.  Understood this MIB has been grown too big and out of control and this has been addressed in genie.
-- 
-- Revision test_smiao/22 1999/09/16 23:29:35 smiao
-- 	merged
-- 
-- Revision test_smiao/21 1999/09/16 22:57:43 smiao
-- 	Added backup server group to SNMP and webUI.
-- 
-- Revision new_ge_latest_bshao/6 1999/09/16 22:36:25 bshao
-- 	Added SNMP support for URL hashing
-- 
-- Revision test_smiao/19 1999/09/15 20:01:33 smiao
-- 	Added graceful server failure for SNMP and webUI.
-- 
-- Revision test_smiao/16 1999/09/15 01:34:06 smiao
-- 	Added stateless UDP LB, 2nd syslog host, server failure syslog threshold for Tigon.
-- 
-- Revision test_smiao/13 1999/09/10 17:39:29 smiao
-- 	Added slbStatPortMaintFilteredDeniedFrames for Tigon SNMP and webUI.
-- 
-- Revision test_smiao/11 1999/09/10 00:36:09 smiao
-- 	Implemented STEM memory statistics, packet statistics for Tigon.
-- 
-- Revision test_smiao/9 1999/09/08 23:34:47 smiao
-- 	Added tcpCurConn Statistic to SNMP.
-- 
-- Revision latest_mlin/29 1999/09/03 20:09:47 mlin
-- 	2231, Added MIB objects of retrieving higher/lower 32 bit values for 64 bit stats - slbStatPortRealServerHCOctets, slbStatRServerHCOctets, slbStatGroupHCOctets, slbStatVServerHCOctets as requested by UUNET.
-- 
-- Revision latest_mlin/27 1999/09/03 19:51:46 mlin
-- 	merged
-- 
-- Revision test_smiao/7 1999/09/03 18:47:44 smiao
-- 	Added GSLB min conns and hostname redirect and persistent mask.
-- 
-- Revision new_ge_latest_bshao/4 1999/08/24 02:01:07 bshao
-- 	Added code for real server to handle non-cookie requests
-- 
-- Revision new_ge_latest_bshao/2 1999/08/16 16:49:22 bshao
-- 	Added in snmp support for cookie LB
-- 
-- Revision latest_mlin/25 1999/07/11 01:44:03 mlin
-- 	Added MIB support for URL Redir/SLB in release 6.0.
-- 
-- Revision new_ge_latest_sunil/11 1999/07/03 06:48:52 sunil
-- 	Make STICKY values consistent
-- 
-- Revision new_ge_latest_sunil/9 1999/07/02 04:33:03 sunil
-- 	Changed pbind clientip/sessid/none back to pbind enabled/disabled/sessid, fixed webui/snmp being out of sync with cli - defects 2102,2105,2107,2108
-- 
-- Revision latest_mlin/23 1999/06/22 05:55:25 mlin
-- 	Fix 2058. Changed 'Dslb' and 'distributedSLB' to 'Gslb', 'globalSLB'.
-- 
-- Revision new_ge_latest_sunil/7 1999/06/14 19:11:59 sunil
-- 	added SSLH health check support to Web & SNMP
-- 
-- Revision latest_mlin/21 1999/06/10 17:02:36 mlin
-- 	Fix 2058.  DSLB is now renamed as GSLB.
-- 
-- Revision new_ge_latest_sunil/5 1999/06/07 03:49:53 sunil
-- 	modified meaning of PBind for SSL
-- 
-- Revision latest_mlin/19 1999/06/01 16:50:59 mlin
-- 	Fixed 2056 - Clarify re-arp object name.
-- 
-- Revision latest_mlin/17 1999/05/21 23:46:19 mlin
-- 	Added MIB support for VRRP trackings.
-- 
-- Revision ge_taylor/4 1999/05/16 21:14:57 taylor
-- 	Removed virtual server VRRP configuration item
-- 
-- Revision latest_mlin/15 1999/05/02 00:17:41 mlin
-- 	Added MIB support for URL Redir/SLB.
-- 
-- Revision ge_taylor/2 1999/04/29 19:19:46 taylor
-- 	Changed fragment mode to direct access mode
-- 
-- Revision latest_mlin/12 1999/04/20 01:06:11 mlin
-- 	Added VRRP support for virtual server config.
-- 
-- Revision latest_mlin/8 1999/04/16 21:06:58 mlin
-- 	Fixed 1942 - WDT when mibwalk VRRP mibs.
-- 
-- Revision latest_mlin/6 1999/04/10 04:27:18 mlin
-- 	First cut of VRRP MIB support.
-- 
-- Revision latest_mlin/4 1999/04/02 01:26:11 mlin
-- 	Added MIB support for 5.2 features.
-- 
-- Revision latest_mlin/2 1999/03/04 23:06:57 mlin
-- 	Added MIB support for 5.1 features.
-- 
-- Revision 1.1.2.27  1999/02/07  00:46:25  mlin
-- 	Changed object names for DNS configuration.
-- 	[1999/02/07  00:45:05  mlin]
--
-- Revision 1.1.2.26  1999/02/05  00:36:12  mlin
-- 	MIB cleanup.  Changed some objects with more consistent and proper names.
-- 	[1999/02/05  00:23:03  mlin]
-- 
-- Revision 1.1.2.25  1998/10/30  22:30:41  mlin
-- 	Added oper command in MIB to clear per port ABT table.
-- 	[1998/10/30  22:30:11  mlin]
-- 
-- Revision 1.1.2.24  1998/10/28  18:19:24  mlin
-- 	Initial checkin for supporting HP.  Pending on HP's response to fine tune weight mapping algorithm.
-- 	[1998/10/28  01:21:59  mlin]
-- 
-- Revision 1.1.2.23  1998/10/23  17:14:14  mlin
-- 	Added enable/disable client proxy control to fix filter defeciency.
-- 	[1998/10/23  16:20:43  mlin]
-- 
-- 	1550 2ndary fix.  Added control of supply route updates from standby switch.
-- 	[1998/10/23  15:49:10  mlin]
-- 
-- Revision 1.1.2.22  1998/10/13  21:20:27  mlin
-- 	Fixed alteon enterprise traps.
-- 	[1998/10/13  21:20:06  mlin]
-- 
-- Revision 1.1.2.21  1998/10/09  23:38:35  mlin
-- 	1527.  Added DNS stats to MIB and WEB-UI.
-- 	[1998/10/09  23:37:54  mlin]
-- 
-- Revision 1.1.2.20  1998/10/03  01:24:43  mlin
-- 	Added port name on MIB/WEB-UI.
-- 	[1998/10/03  01:24:02  mlin]
-- 
-- Revision 1.1.2.19  1998/09/30  14:48:19  mlin
-- 	Added invert field for filter entry configuration.
-- 	[1998/09/30  00:30:25  mlin]
-- 
-- Revision 1.1.2.18  1998/09/29  14:49:09  mlin
-- 	1468, Added wport to MIB only.  Don't allow users to configure wport on WEB-UI.
-- 	[1998/09/29  14:48:49  mlin]
-- 
-- Revision 1.1.2.17  1998/09/22  21:53:12  mlin
-- 	Increased real server weight granularity to 1..48.
-- 	[1998/09/22  21:52:49  mlin]
-- 
-- Revision 1.1.2.16  1998/09/03  15:35:11  mlin
-- 	Added 4 default gateways API/MIB/WEB-UI support.
-- 	[1998/09/03  15:34:25  mlin]
-- 
-- Revision 1.1.2.15  1998/09/02  15:54:07  mlin
-- 	Added Dname, Hname for virtual server configuration.
-- 	[1998/09/02  15:53:34  mlin]
-- 
-- Revision 1.1.2.14  1998/09/01  18:52:09  mlin
-- 	Added more health check options.
-- 	[1998/09/01  18:51:36  mlin]
-- 
-- Revision 1.1.2.13  1998/08/28  06:10:48  mlin
-- 	Added API and MIB support for DSLB.
-- 	[1998/08/28  06:10:23  mlin]
-- 
-- Revision 1.1.2.12  1998/08/27  21:04:16  mlin
-- 	Added local/remote real server configuration.
-- 	[1998/08/27  21:03:39  mlin]
-- 
-- Revision 1.1.2.11  1998/08/27  06:24:35  mlin
-- 	Added hash selection for server group metric.
-- 	[1998/08/27  06:24:04  mlin]
-- 
-- Revision 1.1.2.10  1998/08/27  05:56:20  mlin
-- 	Added NAT, cache support for filtering.
-- 	[1998/08/27  05:53:11  mlin]
-- 
-- Revision 1.1.2.9  1998/07/22  22:26:34  mlin
-- 	Added filter port table support.
-- 	[1998/07/22  22:26:10  mlin]
-- 
-- Revision 1.1.2.8  1998/07/19  06:00:32  mlin
-- 	Added API/MIB support of filtering table.
-- 	[1998/07/19  05:58:10  mlin]
-- 
-- Revision 1.1.2.7  1998/07/17  19:58:59  taylor
-- 	Allow absense of default rule
-- 	[1998/07/17  19:54:21  taylor]
-- 
-- Revision 1.1.2.6  1998/07/02  18:59:10  mlin
-- 	Fixed bug reported by SUN regarding real server group server bit map.  This fixed also the bit map for vlan and trunkgroup port list.
-- 	[1998/07/02  18:58:41  mlin]
-- 
-- Revision 1.1.2.5  1998/06/30  18:48:52  taylor
-- 	webui: Added routing and arp stats
-- 	[1998/06/30  18:48:09  taylor]
-- 
-- Revision 1.1.2.4  1998/06/27  20:00:23  taylor
-- 	SLB: added management network and mask
-- 	[1998/06/27  19:59:37  taylor]
-- 
-- Revision 1.1.2.3  1998/06/21  08:22:58  mlin
-- 	Fixed 1225.  Added Flag field.  This is also added to altswitch.mib.
-- 	[1998/06/21  08:22:35  mlin]
-- 
-- Revision 1.1.2.2  1998/06/18  23:51:36  taylor
-- 	Update to 4.0 changes
-- 	[1998/06/18  23:50:59  taylor]
-- 
-- Revision 1.1.2.1  1998/06/12  17:23:46  kyung
-- 	moved ag_* into /src/lib/agent
-- 	[1998/06/12  17:21:01  kyung]
-- 
-- Revision 1.1.2.21  1998/06/09  22:24:21  mlin
-- 	Fixed 1066.  Using table index instead of destination IP as index of static route table.
-- 	[1998/06/09  22:23:45  mlin]
-- 
-- Revision 1.1.2.20  1998/06/04  00:03:02  mlin
-- 	Fixed 1104,1107,1109.  Changed not to use destination IP as table index.
-- 	[1998/06/04  00:02:39  mlin]
-- 
-- Revision 1.1.2.19  1998/05/30  00:49:44  taylor
-- 	Merged with changes from 1.1.2.18
-- 	[1998/05/30  00:48:50  taylor]
-- 
-- 	Merged WCR with filtering
-- 	[1998/05/30  00:44:28  taylor]
-- 
-- Revision 1.1.2.18  1998/05/29  23:41:38  cghatge
-- 	Added poison reverse to the RIP configuration. Fixes DEFECT 1073.
-- 	[1998/05/29  23:37:43  cghatge]
-- 
-- Revision 1.1.2.17  1998/05/29  06:14:18  mlin
-- 	Fixed 1085-add Metric field, changed next-hop router -> Gateway, Source->Tag for consistency.
-- 	[1998/05/29  06:13:53  mlin]
-- 
-- Revision 1.1.2.16  1998/05/28  23:08:23  taylor
-- 	Added redirection to IP filtering: phase 1
-- 	[1998/05/28  23:06:37  taylor]
-- 
-- Revision 1.1.2.15  1998/05/21  17:50:04  cghatge
-- 	Fixed DEFECT1042.
-- 
-- 	Changed the MIB variable names from Sticky to PBind.
-- 	[1998/05/21  17:48:29  cghatge]
-- 
-- Revision 1.1.2.14  1998/05/20  22:59:00  cghatge
-- 	Fixed DEFECT 975.
-- 
-- 	Reversed the definitions of 'overflow' and 'non-overflow'.
-- 	[1998/05/20  22:56:19  cghatge]
-- 
-- Revision 1.1.2.13  1998/05/20  19:07:59  cghatge
-- 	Merged with changes from 1.1.2.12
-- 	[1998/05/20  19:07:50  cghatge]
-- 
-- 	Fixed DEFECT000000954.
-- 
-- 	Removed two objects that are no longer needed -
-- 	agPortCurCfgNic and agPortNewCfgNic.
-- 	[1998/05/20  19:00:05  cghatge]
-- 
-- Revision 1.1.2.12  1998/05/20  19:03:38  mlin
-- 	updated with more meaningful description for slbCurCfgGroupHealthCheckUrl
-- 	[1998/05/20  19:03:20  mlin]
-- 
-- Revision 1.1.2.11  1998/05/18  02:07:49  cghatge
-- 	Merged with changes from 1.1.2.10
-- 	[1998/05/18  02:07:39  cghatge]
-- 
-- 	Added the Arp Info and Route Info groups.
-- 	[1998/05/18  02:04:09  cghatge]
-- 
-- Revision 1.1.2.10  1998/05/16  22:55:23  mlin
-- 	Added management support of URL health check.
-- 	[1998/05/16  22:54:51  mlin]
-- 
-- Revision 1.1.2.9  1998/05/15  17:42:41  mlin
-- 	Added backupServ/overflowSrv stats - bug 974.
-- 	[1998/05/15  17:41:31  mlin]
-- 
-- Revision 1.1.2.8  1998/05/14  20:19:31  mlin
-- 	Replaced with more meaningful object name/description of ipRouteInfoTable.
-- 	[1998/05/14  20:18:09  mlin]
-- 
-- Revision 1.1.2.7  1998/05/13  02:15:11  cghatge
-- 	Added the agStaticRouteInfoTable group.
-- 	[1998/05/13  01:43:08  cghatge]
-- 
-- Revision 1.1.2.6  1998/05/02  03:34:32  cghatge
-- 	Added objects for SLB global control.
-- 	[1998/05/02  03:33:50  cghatge]
-- 
-- Revision 1.1.2.5  1998/05/02  01:32:36  cghatge
-- 	Added the proxy IP address for each interface in the SLB port Tables.
-- 	[1998/05/02  01:26:59  cghatge]
-- 
-- Revision 1.1.2.4  1998/04/30  17:36:06  cghatge
-- 	Merged with changes from 1.1.2.3
-- 	[1998/04/30  17:35:51  cghatge]
-- 
-- 	Added objects for deleteing the servers in the real server and virtual server
-- 	groups.
-- 	[1998/04/30  17:02:02  cghatge]
-- 
-- Revision 1.1.2.3  1998/04/30  17:04:48  cghatge
-- 	Added objects for deleteing the servers in the real server and virtual server
-- 	groups.
-- 	[1998/04/30  17:02:02  cghatge]
-- 
-- Revision 1.1.2.2  1998/04/27  22:25:48  mlin
-- 	Code cleanup: merged #define from ag_vlans.h to ag_vlans.c, removed unnecessary #include.
-- 	[1998/04/27  22:25:15  mlin]
-- 
-- Revision 1.1.2.1  1998/04/24  22:41:09  wayne
-- 	Moved here from ./alt-ts/lib to flatten directory structure
-- 	[1998/04/24  22:15:53  wayne]
-- 
-- Revision 1.1.2.11  1998/04/20  23:24:38  mlin
-- 	some MIB and code cleanup of SLB group.
-- 	[1998/04/20  23:24:12  mlin]
-- 
-- Revision 1.1.2.10  1998/04/20  18:19:36  mlin
-- 	Converted slbFailOver objects into table.
-- 	[1998/04/20  18:19:04  mlin]
-- 
-- Revision 1.1.2.9  1998/04/18  06:45:24  mlin
-- 	Added stats group support.
-- 	[1998/04/18  06:33:15  mlin]
-- 
-- Revision 1.1.2.8  1998/04/17  01:44:25  cghatge
-- 	Made some modifications to the SLB Group Tables and some misc stuff.
-- 	[1998/04/17  01:12:40  cghatge]
-- 
-- Revision 1.1.2.7  1998/04/16  00:13:19  cghatge
-- 	Modified the trunkgroup part of the Alteon Private MIB.
-- 	[1998/04/15  23:57:47  cghatge]
-- 
-- Revision 1.1.2.6  1998/04/15  17:37:15  cghatge
-- 	Merged with changes from 1.1.2.5
-- 	[1998/04/15  17:36:44  cghatge]
-- 
-- 	Added cache redirection and ip routing and SLB Group.
-- 	[1998/04/15  00:23:08  cghatge]
-- 
-- Revision 1.1.2.5  1998/04/14  01:57:56  kyung
-- 	added hardware agent group
-- 	[1998/04/14  01:57:40  kyung]
-- 
-- Revision 1.1.2.4  1998/04/13  17:15:20  mlin
-- 	Added information group support.  agPortActualTable is now agPortInfotable and moved to information group.
-- 	[1998/04/13  17:14:16  mlin]
-- 
-- Revision 1.1.2.3  1998/04/08  20:53:47  mlin
-- 	Added vlan group support
-- 	[1998/04/08  19:56:41  mlin]
-- 
-- Revision 1.1.2.2  1998/04/06  22:03:38  mlin
-- 	added port mirroring group support
-- 	[1998/04/06  22:03:06  mlin]
-- 
-- Revision 1.1.2.1  1998/04/05  02:47:41  mlin
-- 	Changed to support agAgent group defined in altswitch.mib.
-- 	[1998/04/05  02:19:03  mlin]
-- 
-- $EndLog$
-- 
-- Version 1.0.1
-- Date: 04/04/98
--

ALTEON-PRIVATE-MIBS DEFINITIONS ::= BEGIN

IMPORTS
	enterprises, mgmt, NetworkAddress, IpAddress, Counter, Gauge,
		TimeTicks 
		FROM RFC1155-SMI
	OBJECT-TYPE
		FROM RFC-1212
	PhysAddress, DisplayString
		FROM RFC1213-MIB
        Counter64
		FROM SNMPv2-SMI;


alteon       OBJECT IDENTIFIER ::= { enterprises 1872 }
 
-- groups in alteon
 
registration OBJECT IDENTIFIER ::= { alteon 1 }
 
private-mibs OBJECT IDENTIFIER ::= { alteon 2 }
 


-- textual conventions

-- groups in private-mibs

switch            OBJECT IDENTIFIER ::= { private-mibs 1 }

hardware          OBJECT IDENTIFIER ::= { switch 1 }
agent             OBJECT IDENTIFIER ::= { switch 2 }
iprouting	  OBJECT IDENTIFIER ::= { switch 3 }
vlans             OBJECT IDENTIFIER ::= { switch 4 }
serverloadbalance OBJECT IDENTIFIER ::= { switch 5 }
portmirroring     OBJECT IDENTIFIER ::= { switch 6 }
trunkgroup        OBJECT IDENTIFIER ::= { switch 7 }
stats		  OBJECT IDENTIFIER ::= { switch 8 }
information	  OBJECT IDENTIFIER ::= { switch 9 }
filtering  	  OBJECT IDENTIFIER ::= { switch 10 }
globalSLB         OBJECT IDENTIFIER ::= { switch 11 }
dynamicSLB        OBJECT IDENTIFIER ::= { switch 12 }
altswitchTraps    OBJECT IDENTIFIER ::= { switch 13 }
operCmds          OBJECT IDENTIFIER ::= { switch 14 }
vrrp              OBJECT IDENTIFIER ::= { switch 15 }
radius            OBJECT IDENTIFIER ::= { switch 16 }
bwm               OBJECT IDENTIFIER ::= { switch 17 }

agGeneral         OBJECT IDENTIFIER ::= { agent 1 }
agGeneralConfig   OBJECT IDENTIFIER ::= { agent 2 }
agPortConfig      OBJECT IDENTIFIER ::= { agent 3 }

slbfailover	  OBJECT IDENTIFIER ::= { serverloadbalance 16 } -- obsoleted
slbUrl            OBJECT IDENTIFIER ::= { serverloadbalance 27 }

slbUrlRedir       OBJECT IDENTIFIER ::= { slbUrl 1 }
slbUrlBalance     OBJECT IDENTIFIER ::= { slbUrl 2 }

gslbGeneral       OBJECT IDENTIFIER ::= { globalSLB 1 }
gslbDNS           OBJECT IDENTIFIER ::= { globalSLB 2 }
gslbSites         OBJECT IDENTIFIER ::= { globalSLB 3 }
gslbLookup        OBJECT IDENTIFIER ::= { globalSLB 4 }


ripStats  	  OBJECT IDENTIFIER ::= { stats  1 }
slbStats  	  OBJECT IDENTIFIER ::= { stats  2 }
arpStats  	  OBJECT IDENTIFIER ::= { stats  3 }
routeStats  	  OBJECT IDENTIFIER ::= { stats  4 }
dnsStats  	  OBJECT IDENTIFIER ::= { stats  5 }
filterStats  	  OBJECT IDENTIFIER ::= { stats  6 }
gslbStats  	  OBJECT IDENTIFIER ::= { stats  7 }
gslbMaintStats    OBJECT IDENTIFIER ::= { stats  8 }
vrrpStats         OBJECT IDENTIFIER ::= { stats  9 }
urlStats          OBJECT IDENTIFIER ::= { stats  10 }
tcpStats	  OBJECT IDENTIFIER ::= { stats  11 }
memStats	  OBJECT IDENTIFIER ::= { stats  12 }
pktStats	  OBJECT IDENTIFIER ::= { stats  13 }
ftpStats          OBJECT IDENTIFIER ::= { stats  14 }
bwmStats          OBJECT IDENTIFIER ::= { stats  15 }


port-info	  OBJECT IDENTIFIER ::= { information 1 }
slb-info	  OBJECT IDENTIFIER ::= { information 2 }
ip-info	  	  OBJECT IDENTIFIER ::= { information 3 }
vrrp-info         OBJECT IDENTIFIER ::= { information 4 }


-- There are two configuration blocks for Alteon switches.
-- The "current_config" reflects the configuration parameters that the
-- switch is operating on and it is read-only.  The objects with "CurCfg"
-- in the name are reflect to this configuration block.
--
-- The "new_config" accepts user configurations on set.  The objects with
-- "NewCfg" in the name are reflect to this configuration block.
--
-- The newly set configurations will not take effect until a "apply"
-- command has been issued (See agApplyConfiguration object defined in
-- ALTEON-PRIVATE-MIBS).
--
-- The newly set configurations will not be saved through next restarting
-- of the switch unless a "save" command has been issued (See
-- agSaveConfiguration object defined in ALTEON-PRIVATE-MIBS).


-- MIB Objects

-- Hardware Information

hwPartNumber OBJECT-TYPE
        SYNTAX  DisplayString (SIZE(0..16))
        ACCESS  read-only
        STATUS  mandatory
        DESCRIPTION
                "The hardware part number of the Alteon Switch." 
        ::= { hardware 1 }

hwRevision OBJECT-TYPE
	SYNTAX	DisplayString (SIZE(0..16))
	ACCESS	read-only
	STATUS	mandatory
	DESCRIPTION
		"The hardware revision.  If the revision is not
		 available, a zero length string should be returned."
	::= { hardware 2 }

hwPowerSupplyStatus OBJECT-TYPE
        SYNTAX  INTEGER {
                ok(1),
                bad(2)
                }
        ACCESS  read-only
        STATUS  mandatory
        DESCRIPTION
		"The status of the internal power supply."
        ::= { hardware 3 }

hwRedundantPSPresent OBJECT-TYPE 
        SYNTAX  INTEGER { 
                notPresent(3),  
                present(4) 

                } 
        ACCESS  read-only
        STATUS  mandatory 
        DESCRIPTION 
                "Existence of redundant power supply." 
        ::= { hardware 4 } 

hwRedundantPSStatus OBJECT-TYPE 
        SYNTAX  INTEGER { 
                ok(1), 
                bad(2),
                notPresent(3)  
                } 
        ACCESS  read-only
        STATUS  mandatory 
        DESCRIPTION 
                "The status of the redundant power supply." 
        ::= { hardware 5 }

hwSensor1Temp OBJECT-TYPE
        SYNTAX  INTEGER 
        ACCESS  read-only
        STATUS  mandatory
        DESCRIPTION
                "The temperature in degrees Celcius of the sensor number 1."
        ::= { hardware 6 }

hwSensor2Temp OBJECT-TYPE 
        SYNTAX  INTEGER 
        ACCESS  read-only 
        STATUS  mandatory
        DESCRIPTION
                "The temperature in degrees Celcius of the sensor number 2."
        ::= { hardware 7 } 

hwSensor3Temp OBJECT-TYPE 
        SYNTAX  INTEGER 
        ACCESS  read-only 
        STATUS  mandatory
        DESCRIPTION
                "The temperature in degrees Celcius of the sensor number 3."
        ::= { hardware 8 } 

hwSensor4Temp OBJECT-TYPE 
        SYNTAX  INTEGER 
        ACCESS  read-only 
        STATUS  mandatory
        DESCRIPTION
                "The temperature in degrees Celcius of the sensor number 4."
        ::= { hardware 9 } 


-- Agent Group
 
-- Agent General Group
-- This group of objects take effect on the 'SET' request.
-- There is no need to 'apply' or 'save'.
 
agSaveConfiguration OBJECT-TYPE
        SYNTAX  INTEGER {
                ok(1),
                saveActive(2),
                notSaveActive(3)
                }
        ACCESS  read-write
        STATUS  mandatory
        DESCRIPTION
                "This is an action object to write current configuration
                 to nonvolatile storage.

                 When issued with the saveActive, the active configuration
                 in flash is saved to backup in flash and then the new
                 configuration is saved to the active configuration in flash.

                 When issued with notSaveActive, the active configuration
                 is NOT saved to the flash and the active configuration is
                 overwritten with the new configuration.

                 ok(1) is returned always when read."
        ::= { agGeneral 1 }

agApplyConfiguration OBJECT-TYPE
        SYNTAX  INTEGER {
                other(1),
                apply(2)
                }
        ACCESS  read-write
        STATUS  mandatory
        DESCRIPTION
                "This is an action object to apply the changes made to
                 configuration of the switch. By setting the value to
                 apply(2), all the changes made since the last apply
                 are written to the new_config block.

                 other(1) is returned when this object ie read. "
        ::= { agGeneral 2 }

agApplyPending OBJECT-TYPE
        SYNTAX  INTEGER {
                other(1),
                applyNeeded(2),
                noApplyNeeded(3)
                }
        ACCESS  read-only
        STATUS  mandatory
        DESCRIPTION
                "This object, when read, gives the user information
                 whether an apply action is needed and that the configuration
                 has been chaged by the user actions. The user then can
                 apply the changes by setting proper value to the object
                 agApplyConfiguration described above."
        ::= { agGeneral 3 }

agReset OBJECT-TYPE
        SYNTAX  INTEGER {
                other(1),
                coldReset(2),
                warmReset(3)
                }
        ACCESS  read-write
        STATUS  mandatory
        DESCRIPTION
                "This is an action object to reboot the agent.
                 other(1) is returned always when read.

                 The following values are writable:
                   coldReset(2)...
                   warmReset(3)..."
        ::= { agGeneral 4 }

agConfigForNxtReset OBJECT-TYPE
        SYNTAX  INTEGER {
                other(1),
                active(2),
                backup(3),
                default(4)
                }
        ACCESS  read-write
        STATUS  mandatory
        DESCRIPTION
                "The configuration information to be loaded from at
                 next reset.
                   other(1)...unknown configuration (read-only)

                 The following values are writable:
                   active(2)...active configuration block
                   backup(3)...backup configuration block
                   default(4)..default configuration block"
        ::= { agGeneral 5 }

agImageForNxtReset OBJECT-TYPE
        SYNTAX  INTEGER {
                other(1),
                image1(2),
                image2(3)
                }
        ACCESS  read-write
	STATUS	mandatory
        DESCRIPTION
                "The software image to be booted from at next reset.
                   other(1)...unknown image (read-only)

                 The following values are writable:
                   image1(2)...image 1
                   image2(3)...image 2"
        ::= { agGeneral 6 }

agSoftwareVersion OBJECT-TYPE
        SYNTAX  DisplayString (SIZE(0..16))
        ACCESS  read-only
        STATUS  mandatory
        DESCRIPTION
                "The version of the software image that is currently
                 running on the system in the form of
                 'major.minor.bugfix'.  A zero length string
                 is returned if version is not available."
        ::= { agGeneral 7 }

agBootVer OBJECT-TYPE
        SYNTAX  DisplayString (SIZE(0..16))
        ACCESS  read-only
        STATUS  mandatory
        DESCRIPTION
                "The version of the boot code in the form of
                 'major.minor.bugfix'.  A zero length string
                 is returned if version is not available."
        ::= { agGeneral 8 }

agImage1Ver OBJECT-TYPE
        SYNTAX  DisplayString (SIZE(0..128))
        ACCESS  read-only
        STATUS  mandatory
        DESCRIPTION
                "The version of the software image stored in
                 image 1 storage in the form of
                 'major.minor.bugfix'.  A zero length string
                 is returned if version is not available or
                 there is no valid software image."
        ::= { agGeneral 9 }

agImage2Ver OBJECT-TYPE
        SYNTAX  DisplayString (SIZE(0..128))
        ACCESS  read-only
        STATUS  mandatory
        DESCRIPTION
                "The version of the software image stored in
                 image 2 storage in the form of
                 'major.minor.bugfix'.  A zero length string
                 is returned if version is not available or
                 there is no valid software image."
        ::= { agGeneral 10 }

agRtcDate OBJECT-TYPE
        SYNTAX  DisplayString (SIZE(0..16))
        ACCESS  read-write
        STATUS  mandatory
        DESCRIPTION
                "The date on the real time clock in the form
                 of 'mm/dd/yy'.  A zero length string is
                 returned if date is not available."
        ::= { agGeneral 11 }

agRtcTime OBJECT-TYPE
        SYNTAX  DisplayString (SIZE(0..16))
        ACCESS  read-write
        STATUS  mandatory
        DESCRIPTION
                "The time on the real time clock in the form
                 of 'hh:mm:ss'.  A zero length string is
                 returned if date is not available."
        ::= { agGeneral 12 }

agTftpServerIpAddr OBJECT-TYPE
        SYNTAX  IpAddress
        ACCESS  read-write
        STATUS  mandatory
        DESCRIPTION
                "The TFTP server IP address."
        ::= { agGeneral 13 }

agTftpImageFileName OBJECT-TYPE
        SYNTAX  DisplayString (SIZE(0..128))
        ACCESS  read-write
        STATUS  mandatory
        DESCRIPTION
                "The image file name to be downloaded."
        ::= { agGeneral 14 }

agTftpImage OBJECT-TYPE
        SYNTAX  INTEGER {
                other(1),
                image1(2),
                image2(3)
                }
        ACCESS  read-write
        STATUS  mandatory
        DESCRIPTION
                "Whether the image file should be loaded in image1 or image2
                 in flash."
        ::= { agGeneral 15 }

agTftpDownload OBJECT-TYPE
        SYNTAX  INTEGER {
                other(1),
                download(2)
                }
        ACCESS  read-write
        STATUS  mandatory
        DESCRIPTION
                "This is an action object to cause to download software
                 image according to the setup of agTftpServerIpAddr,
                 agTftpImageFileName, agTftpImage when download(2) is
                 issued.
                 other(1) is returned always when read."
        ::= { agGeneral 16 }

agLastSetErrorReason   OBJECT-TYPE
        SYNTAX  DisplayString (SIZE(0..256))
        ACCESS  read-only
        STATUS  mandatory
        DESCRIPTION
                "The error reason of the last SET failure."
        ::= { agGeneral 17 }

agTftpServer OBJECT-TYPE
        SYNTAX  DisplayString (SIZE(0..64))
        ACCESS  read-write
        STATUS  mandatory
        DESCRIPTION
                "The TFTP server IP address or domain name."
        ::= { agGeneral 18 }

agTftpCfgFileName OBJECT-TYPE
        SYNTAX  DisplayString (SIZE(0..128))
        ACCESS  read-write
        STATUS  mandatory
        DESCRIPTION
                "The configuration file name."
        ::= { agGeneral 19 }

agTftpDumpFileName OBJECT-TYPE
        SYNTAX  DisplayString (SIZE(0..128))
        ACCESS  read-write
        STATUS  mandatory
        DESCRIPTION
                "The file name for core dump."
        ::= { agGeneral 20 }

agTftpAction OBJECT-TYPE
        SYNTAX  INTEGER {
                other(1),
                img-get(2),
                cfg-get(3),
                cfg-put(4),
                dump-put(5)
                }
        ACCESS  read-write
        STATUS  mandatory
        DESCRIPTION
                "This is an action object to perform various TFTP Get or Put 
		 functions.  The TFTP sever is specified in agTftpServer
		 object.
		 img-get(2) - Download switch image from a specified image
                              file (agTftpImageFileName) on the TFTP server to
		              the destinated storage (agTftpImage).
		 cfg-get(3) - Download switch configuration from a specified
                              file (agTftpCfgFileName) on the TFTP server.
		 cfg-put(4) - Upload switch configuration to a specified
                              file (agTftpCfgFileName) on the TFTP server.
		 dump-put(5)- Download switch core dump to a specified
                               file (agTftpDumpFileName) on the TFTP server.

                 other(1) is returned always when read."
        ::= { agGeneral 21 }

agTftpLastActionStatus OBJECT-TYPE
        SYNTAX  DisplayString (SIZE(0..128))
        ACCESS  read-only
        STATUS  mandatory
        DESCRIPTION
                "The recorded status of the previous TFTP activity."
        ::= { agGeneral 22 }

agEnabledSwFeatures OBJECT-TYPE
    SYNTAX  DisplayString
    ACCESS  read-only
    STATUS  mandatory
    DESCRIPTION
        "The software features that are enabled on the switch."
    ::= { agGeneral 25 }

-- Agent General Configuration Group

agNewCfgSyslogHost OBJECT-TYPE
        SYNTAX  IpAddress
        ACCESS  read-write
        STATUS  mandatory
        DESCRIPTION
                "The syslog host IP address, in the new_configuration block."
        ::= { agGeneralConfig 1 }

agCurCfgSyslogHost OBJECT-TYPE
        SYNTAX  IpAddress
        ACCESS  read-only
        STATUS  mandatory
        DESCRIPTION
                "The syslog host IP address, as currently configured in
                 the current_configuration block."
        ::= { agGeneralConfig 2 }

agNewCfgBootp OBJECT-TYPE
        SYNTAX  INTEGER {
                other(1),
                enabled(2),
                disabled(3)
                }
        ACCESS  read-write
        STATUS  mandatory
        DESCRIPTION
                "Enable or disable the use of BootP, in the new_configuration
                 block."
        ::= { agGeneralConfig 3 }

agCurCfgBootp OBJECT-TYPE
        SYNTAX  INTEGER {
                other(1),
                enabled(2),
                disabled(3)
                }
        ACCESS  read-only
        STATUS  mandatory
        DESCRIPTION
                "Enable or disable the use of BootP, as currently
                 configured in the current_configuration block."
        ::= { agGeneralConfig 4 }

agNewCfgSpanningTree OBJECT-TYPE
        SYNTAX  INTEGER {
                other(1),
                on(2),
                off(3)
                }
        ACCESS  read-write
        STATUS  mandatory
        DESCRIPTION
                "Turn On or Off Spanning Tree Protocol for the switch,
                 in the new_configuration block."
        ::= { agGeneralConfig 5 }

agCurCfgSpanningTree OBJECT-TYPE
        SYNTAX  INTEGER {
                other(1),
                on(2),
                off(3)
                }
        ACCESS  read-only
        STATUS  mandatory
        DESCRIPTION
                "The state of Spanning Tree Protocol for the switch, as
                 currently configured in the current_configuration block."
        ::= { agGeneralConfig 6 }


-- Trap host table

agTrapHostTableMaxEnt OBJECT-TYPE
        SYNTAX  INTEGER
        ACCESS  read-only
        STATUS  mandatory
        DESCRIPTION
                "The maximum number of rows in the trap host table."
        ::= { agGeneralConfig 7 }


agCurCfgTrapHostTable OBJECT-TYPE
        SYNTAX  SEQUENCE OF AgCurCfgTrapHostEntry
        ACCESS  not-accessible
        STATUS  mandatory
        DESCRIPTION
                "The table of trap hosts which to send SNMP traps in
                 the current_configuration block."
        ::= { agGeneralConfig 8 }

agCurCfgTrapHostEntry OBJECT-TYPE
        SYNTAX  AgCurCfgTrapHostEntry
        ACCESS  not-accessible
        STATUS  mandatory
        DESCRIPTION
                "A row in the trap host table in the current_configuration
                 block."
        INDEX   { agCurCfgTrapHostIndx }
        ::= { agCurCfgTrapHostTable 1 }

AgCurCfgTrapHostEntry ::= SEQUENCE {
        agCurCfgTrapHostIndx            INTEGER,
        agCurCfgTrapHostIpAddr          IpAddress,
        agCurCfgTrapHostCommString      DisplayString
        }

agCurCfgTrapHostIndx OBJECT-TYPE
        SYNTAX  INTEGER  (1..255)
        ACCESS  read-only
        STATUS  mandatory
        DESCRIPTION
                "The index of the row in trap host table."
        ::= { agCurCfgTrapHostEntry 1 }

agCurCfgTrapHostIpAddr OBJECT-TYPE
        SYNTAX  IpAddress
        ACCESS  read-only
        STATUS  mandatory
        DESCRIPTION
                "The IP address of a trap host."
        ::= { agCurCfgTrapHostEntry 2 }

agCurCfgTrapHostCommString OBJECT-TYPE
        SYNTAX  DisplayString (SIZE (0..32))
        ACCESS  read-only
        STATUS  mandatory
        DESCRIPTION
                "The SNMP community string to use with the
                 trap host"
        ::= { agCurCfgTrapHostEntry 3 }


agNewCfgTrapHostTable OBJECT-TYPE
        SYNTAX  SEQUENCE OF AgNewCfgTrapHostEntry
        ACCESS  not-accessible
        STATUS  mandatory
        DESCRIPTION
                "The table of trap hosts which to send SNMP traps in the
                 new_configuration block."
        ::= { agGeneralConfig 9 }

agNewCfgTrapHostEntry OBJECT-TYPE
        SYNTAX  AgNewCfgTrapHostEntry
        ACCESS  not-accessible
        STATUS  mandatory
        DESCRIPTION
                "A row in the trap host table in the new_configuration block."
        INDEX   { agNewCfgTrapHostIndx }
        ::= { agNewCfgTrapHostTable 1 }

AgNewCfgTrapHostEntry ::= SEQUENCE {
        agNewCfgTrapHostIndx            INTEGER,
        agNewCfgTrapHostIpAddr          IpAddress,
        agNewCfgTrapHostCommString      DisplayString
        }

agNewCfgTrapHostIndx OBJECT-TYPE
        SYNTAX  INTEGER  (1..255)
        ACCESS  read-only
        STATUS  mandatory
        DESCRIPTION
                "The index of the row in trap host table."
        ::= { agNewCfgTrapHostEntry 1 }

agNewCfgTrapHostIpAddr OBJECT-TYPE
        SYNTAX  IpAddress
        ACCESS  read-write
        STATUS  mandatory
        DESCRIPTION
                "The IP address of a trap host."
        ::= { agNewCfgTrapHostEntry 2 }

agNewCfgTrapHostCommString OBJECT-TYPE
        SYNTAX  DisplayString (SIZE (0..32))
        ACCESS  read-write
        STATUS  mandatory
        DESCRIPTION
                "The SNMP community string to use with the
                 trap host"
        ::= { agNewCfgTrapHostEntry 3 }

agCurCfgHttpServerPort OBJECT-TYPE
        SYNTAX  INTEGER {
                other(1),
                on(2),
                off(3)
                }
        ACCESS  read-only
        STATUS  mandatory
        DESCRIPTION
                "The TCP port number that the HTTP server is listening to 
                 in the new_configuration block."
        ::= { agGeneralConfig 10 }

agNewCfgHttpServerPort OBJECT-TYPE
        SYNTAX  INTEGER 
        ACCESS  read-write
        STATUS  mandatory
        DESCRIPTION
                "The TCP port number that the HTTP server is listening to 
                 in the new_configuration block."
        ::= { agGeneralConfig 11 }

agCurCfgLoginBanner OBJECT-TYPE
        SYNTAX  DisplayString (SIZE(0..79))
        ACCESS  read-only
        STATUS  mandatory
        DESCRIPTION
                "The user defined login banner."
        ::= { agGeneralConfig 12 }

agNewCfgLoginBanner OBJECT-TYPE
        SYNTAX  DisplayString (SIZE(0..79))
        ACCESS  read-write
        STATUS  mandatory
        DESCRIPTION
                "The user defined login banner."
        ::= { agGeneralConfig 13 }

agNewCfgSyslog2Host OBJECT-TYPE
        SYNTAX  IpAddress
        ACCESS  read-write
        STATUS  mandatory
        DESCRIPTION
                "The second syslog host IP address, in the new_configuration block."
        ::= { agGeneralConfig 14 }

agCurCfgSyslog2Host OBJECT-TYPE
        SYNTAX  IpAddress
        ACCESS  read-only
        STATUS  mandatory
        DESCRIPTION
                "The second syslog host IP address, as currently configured in
                 the current_configuration block."
        ::= { agGeneralConfig 15 }

agCurCfgSyslogFac   OBJECT-TYPE
        SYNTAX  INTEGER  {
	    local0(1),
	    local1(2),
	    local2(3),
	    local3(4),
	    local4(5),
	    local5(6),
	    local6(7),
	    local7(8)
	}
        ACCESS  read-only
        STATUS  mandatory
        DESCRIPTION
                "The facility of syslog host in the current_configuration block."
        ::= { agGeneralConfig 16 }

agNewCfgSyslogFac   OBJECT-TYPE
        SYNTAX  INTEGER  {
	    local0(1), 
	    local1(2),
	    local2(3),
	    local3(4),
	    local4(5),
	    local5(6),
            local6(7),
	    local7(8)
	}
        ACCESS  read-write
        STATUS  mandatory
        DESCRIPTION
                "The facility of syslog host in the new_configuration block."
        ::= { agGeneralConfig 17 }

agCurCfgSyslog2Fac   OBJECT-TYPE
        SYNTAX  INTEGER  {
	    local0(1),
	    local1(2),
	    local2(3),
	    local3(4),
	    local4(5),
	    local5(6),
	    local6(7),
	    local7(8)
	}
        ACCESS  read-only
        STATUS  mandatory
        DESCRIPTION
                "The facility of syslog2 host in the current_configuration block."
        ::= { agGeneralConfig 18 }

agNewCfgSyslog2Fac   OBJECT-TYPE
        SYNTAX  INTEGER  {
	    local0(1), 
	    local1(2),
	    local2(3),
	    local3(4),
	    local4(5),
	    local5(6),
            local6(7),
	    local7(8)
	}
        ACCESS  read-write
        STATUS  mandatory
        DESCRIPTION
                "The facility of syslogs host in the new_configuration block."
        ::= { agGeneralConfig 19 }

agCurCfgSmtpHost OBJECT-TYPE
        SYNTAX  DisplayString (SIZE(0..127))
        ACCESS  read-only
        STATUS  mandatory
        DESCRIPTION
                "The user defined SMTP host."
        ::= { agGeneralConfig 20}

agNewCfgSmtpHost OBJECT-TYPE
        SYNTAX  DisplayString (SIZE(0..127))
        ACCESS  read-write
        STATUS  mandatory
        DESCRIPTION
                "The user defined SMTP host."
        ::= { agGeneralConfig 21 }

-- Agent Port Table

agPortTableMaxEnt OBJECT-TYPE
        SYNTAX  INTEGER
        ACCESS  read-only
        STATUS  mandatory
        DESCRIPTION
                "The maximum number of rows in the port configuration
                 host table."
        ::= { agPortConfig 1 }

agPortCurCfgTable OBJECT-TYPE
        SYNTAX  SEQUENCE OF AgPortCurCfgTableEntry
        ACCESS  not-accessible
        STATUS  mandatory
        DESCRIPTION
                "The table of port configuration in the current_configuration
                 block."
        ::= { agPortConfig 2 }

agPortCurCfgTableEntry OBJECT-TYPE
        SYNTAX  AgPortCurCfgTableEntry
        ACCESS  not-accessible
        STATUS  mandatory
        DESCRIPTION
                "A row in the port configuration table in the
                 current_configuration block."
        INDEX   { agPortCurCfgIndx }
        ::= { agPortCurCfgTable 1 }

AgPortCurCfgTableEntry ::= SEQUENCE {
        agPortCurCfgIndx           INTEGER,
        agPortCurCfgPrefLink       INTEGER,
        agPortCurCfgBackLink       INTEGER,
        agPortCurCfgState          INTEGER,
        agPortCurCfgVlanTag        INTEGER,
        agPortCurCfgStp            INTEGER,
        agPortCurCfgRmon           INTEGER,
        agPortCurCfgPVID           INTEGER,
        agPortCurCfgFastEthAutoNeg INTEGER,
        agPortCurCfgFastEthSpeed   INTEGER,
        agPortCurCfgFastEthMode    INTEGER,
        agPortCurCfgFastEthFctl    INTEGER,
        agPortCurCfgGigEthAutoNeg  INTEGER,
        agPortCurCfgGigEthFctl     INTEGER,
        agPortCurCfgPortName       DisplayString,
	agPortCurCfgBwmContract	   INTEGER,
	agPortCurCfgDiscardNonIPs  INTEGER
        }

agPortCurCfgIndx OBJECT-TYPE
        SYNTAX  INTEGER  (1..255)
        ACCESS  read-only
        STATUS  mandatory
        DESCRIPTION
                "The index of the row in port configurations table."
        ::= { agPortCurCfgTableEntry 1 }

agPortCurCfgPrefLink OBJECT-TYPE
        SYNTAX  INTEGER {
                other(1),
                fast-ethernet(2),
                gigabit-ethernet(3)
                }
        ACCESS  read-only
        STATUS  mandatory
        DESCRIPTION
                "This is the preferred link."
        ::= { agPortCurCfgTableEntry 2 }

agPortCurCfgBackLink OBJECT-TYPE
        SYNTAX  INTEGER {
                other(1),
                fast-ethernet(2),
                gigabit-ethernet(3),
                none(4)
                }
        ACCESS  read-only
        STATUS  mandatory
        DESCRIPTION
                "This is the backup link."
        ::= { agPortCurCfgTableEntry 3 }

agPortCurCfgState OBJECT-TYPE
        SYNTAX  INTEGER {
                other(1),
                enabled(2),
                disabled(3)
		}
        ACCESS  read-only
        STATUS  mandatory
        DESCRIPTION
                "This is the state of the port."
        ::= { agPortCurCfgTableEntry 4 }

agPortCurCfgVlanTag OBJECT-TYPE
        SYNTAX  INTEGER {
                other(1),
                tagged(2),
                untagged(3)
                }
        ACCESS  read-only
        STATUS  mandatory
        DESCRIPTION
                "This is VLAN tag state of the port"
        ::= { agPortCurCfgTableEntry 5 }

agPortCurCfgStp OBJECT-TYPE
        SYNTAX  INTEGER {
                other(1),
                on(2),
                off(3)
                }
        ACCESS  read-only
        STATUS  mandatory
        DESCRIPTION
                "This object is used to turn Spanning Tree on or off for the
                 port."
        ::= { agPortCurCfgTableEntry 6 }

agPortCurCfgRmon OBJECT-TYPE
        SYNTAX  INTEGER {
                other(1),
                on(2),
                off(3)
                }
        ACCESS  read-only
        STATUS  mandatory
        DESCRIPTION
                "This object is used to turn RMON on or off on the port."
        ::= { agPortCurCfgTableEntry 7 }

agPortCurCfgPVID OBJECT-TYPE
        SYNTAX  INTEGER
        ACCESS  read-only
        STATUS  mandatory
        DESCRIPTION
                "The default VLAN ID for the port."
        ::= { agPortCurCfgTableEntry 8 }

agPortCurCfgFastEthAutoNeg OBJECT-TYPE
        SYNTAX  INTEGER {
                other(1),
                on(2),
                off(3)
                }
        ACCESS  read-only
        STATUS  mandatory
        DESCRIPTION
                "This object is used to turn the autonegotiation on or off
                 for fast Ethernet connection."
        ::= { agPortCurCfgTableEntry 9 }

agPortCurCfgFastEthSpeed OBJECT-TYPE
        SYNTAX  INTEGER {
                other(1),
                mbs10(2),
                mbs100(3),
                mbs10or100(4)
                }
        ACCESS  read-only
        STATUS  mandatory
        DESCRIPTION
                "This object is used to select port speed for fast Ethernet
                 connection."
        ::= { agPortCurCfgTableEntry 10 }

agPortCurCfgFastEthMode OBJECT-TYPE
        SYNTAX  INTEGER {
                other(1),
                full-duplex(2),
                half-duplex(3),
                full-or-half-duplex(4)
                }
        ACCESS  read-only
        STATUS  mandatory
        DESCRIPTION
                "This object is used to select port mode for fast Ethernet
                 connection."
        ::= { agPortCurCfgTableEntry 11 }

agPortCurCfgFastEthFctl OBJECT-TYPE
        SYNTAX  INTEGER {
                other(1),
                transmit(2),
                receive(3),
                both(4),
                none(5)
                }
        ACCESS  read-only
        STATUS  mandatory
        DESCRIPTION
                "This object is used to select port flow control for fast
                 Ethernet connection."
        ::= { agPortCurCfgTableEntry 12 }

agPortCurCfgGigEthAutoNeg OBJECT-TYPE
        SYNTAX  INTEGER {
                other(1),
                on(2),
                off(3)
                }
        ACCESS  read-only
        STATUS  mandatory
        DESCRIPTION
                "This object is used to turn the autonegotiation on or off
                 for gigabit Ethernet connection."
        ::= { agPortCurCfgTableEntry 13 }

agPortCurCfgGigEthFctl OBJECT-TYPE
        SYNTAX  INTEGER {
                other(1),
                transmit(2),
                receive(3),
                both(4),
                none(5)
                }
        ACCESS  read-only
        STATUS  mandatory
        DESCRIPTION
                "This object is used to select port flow control for
                 gigabit Ethernet connection."
        ::= { agPortCurCfgTableEntry 14 }

agPortCurCfgPortName	OBJECT-TYPE
	SYNTAX	DisplayString (SIZE(0..64))
	ACCESS	read-only
	STATUS	mandatory
	DESCRIPTION
		"The switch port name."
	::= { agPortCurCfgTableEntry 15 }

agPortCurCfgBwmContract OBJECT-TYPE
	SYNTAX	INTEGER 
	ACCESS	read-only
	STATUS	mandatory
	DESCRIPTION
		"The switch port Bandwidth Management contract number."
	::= { agPortCurCfgTableEntry 16 }

agPortCurCfgDiscardNonIPs OBJECT-TYPE
        SYNTAX  INTEGER {
                other(1),
                enabled(2),
                disabled(3)
                }
	ACCESS	read-only
	STATUS	mandatory
	DESCRIPTION
		"Enable or disable to discard all non-IP traffic on the 
                 switch port."
	::= { agPortCurCfgTableEntry 17 }


agPortNewCfgTable OBJECT-TYPE
        SYNTAX  SEQUENCE OF AgPortNewCfgTableEntry
        ACCESS  not-accessible
        STATUS  mandatory
        DESCRIPTION
                "The table of port configuration in the new_configuration
                 block."
        ::= { agPortConfig 3 }

agPortNewCfgTableEntry OBJECT-TYPE
        SYNTAX  AgPortNewCfgTableEntry
        ACCESS  not-accessible
        STATUS  mandatory
        DESCRIPTION
                "A row in the port configuration table in the
                 new_configuration block."
        INDEX   { agPortNewCfgIndx }
        ::= { agPortNewCfgTable 1 }

AgPortNewCfgTableEntry ::= SEQUENCE {
        agPortNewCfgIndx           INTEGER,
        agPortNewCfgPrefLink       INTEGER,
        agPortNewCfgBackLink       INTEGER,
        agPortNewCfgState          INTEGER,
        agPortNewCfgVlanTag        INTEGER,
        agPortNewCfgStp            INTEGER,
        agPortNewCfgRmon           INTEGER,
        agPortNewCfgPVID           INTEGER,
        agPortNewCfgFastEthAutoNeg INTEGER,
        agPortNewCfgFastEthSpeed   INTEGER,
        agPortNewCfgFastEthMode    INTEGER,
        agPortNewCfgFastEthFctl    INTEGER,
        agPortNewCfgGigEthAutoNeg  INTEGER,
        agPortNewCfgGigEthFctl     INTEGER,
        agPortNewCfgPortName       DisplayString,
	agPortNewCfgBwmContract	   INTEGER,
	agPortNewCfgDiscardNonIPs  INTEGER
        }

agPortNewCfgIndx OBJECT-TYPE
        SYNTAX  INTEGER  (1..255)
        ACCESS  read-only
        STATUS  mandatory
        DESCRIPTION
                "The index of the row in port configurations table."
        ::= { agPortNewCfgTableEntry 1 }

agPortNewCfgPrefLink OBJECT-TYPE
        SYNTAX  INTEGER {
                other(1),
                fast-ethernet(2),
                gigabit-ethernet(3)
                }
        ACCESS  read-write
        STATUS  mandatory
        DESCRIPTION
                "This is the preferred link."
        ::= { agPortNewCfgTableEntry 2 }

agPortNewCfgBackLink OBJECT-TYPE
        SYNTAX  INTEGER {
                other(1),
                fast-ethernet(2),
                gigabit-ethernet(3)
                }
        ACCESS  read-write
        STATUS  mandatory
        DESCRIPTION
                "This is the backup link."
        ::= { agPortNewCfgTableEntry 3 }


agPortNewCfgState OBJECT-TYPE
        SYNTAX  INTEGER {
                other(1),
                enabled(2),
                disabled(3)
                }
        ACCESS  read-write
        STATUS  mandatory
        DESCRIPTION
                "This is the state of the port."
        ::= { agPortNewCfgTableEntry 4 }

agPortNewCfgVlanTag OBJECT-TYPE
        SYNTAX  INTEGER {
                other(1),
                tagged(2),
                untagged(3)
                }
        ACCESS  read-write
        STATUS  mandatory
        DESCRIPTION
                "This is VLAN tag state of the port"
        ::= { agPortNewCfgTableEntry 5 }

agPortNewCfgStp OBJECT-TYPE
        SYNTAX  INTEGER {
                other(1),
                on(2),
                off(3)
                }
        ACCESS  read-write
        STATUS  mandatory
        DESCRIPTION
                "This object is used to turn Spanning Tree on or off for the
                 port."
        ::= { agPortNewCfgTableEntry 6 }

agPortNewCfgRmon OBJECT-TYPE
        SYNTAX  INTEGER {
                other(1),
                on(2),
                off(3)
                }
        ACCESS  read-write
        STATUS  mandatory
        DESCRIPTION
                "This object is used to turn RMON on or off on the port."
        ::= { agPortNewCfgTableEntry 7 }

agPortNewCfgPVID OBJECT-TYPE
        SYNTAX  INTEGER
        ACCESS  read-write
        STATUS  mandatory
        DESCRIPTION
                "The default VLAN ID for the port."
        ::= { agPortNewCfgTableEntry 8 }

agPortNewCfgFastEthAutoNeg OBJECT-TYPE
        SYNTAX  INTEGER {
                other(1),
                on(2),
                off(3)
                }
        ACCESS  read-write
        STATUS  mandatory
        DESCRIPTION
                "This object is used to turn the autonegotiation on or off
                 for fast Ethernet connection."
        ::= { agPortNewCfgTableEntry 9 }

agPortNewCfgFastEthSpeed OBJECT-TYPE
        SYNTAX  INTEGER {
                other(1),
                mbs10(2),
                mbs100(3),
                mbs10or100(4)
                }
        ACCESS  read-write
        STATUS  mandatory
        DESCRIPTION
                "This object is used to select port speed for fast Ethernet
                 connection."
        ::= { agPortNewCfgTableEntry 10 }
 
agPortNewCfgFastEthMode OBJECT-TYPE
        SYNTAX  INTEGER {
                other(1),
                full-duplex(2),
                half-duplex(3),
                full-or-half-duplex(4)
                }
        ACCESS  read-write
        STATUS  mandatory
        DESCRIPTION
                "This object is used to select port mode for fast Ethernet
                 connection."
        ::= { agPortNewCfgTableEntry 11 }

agPortNewCfgFastEthFctl OBJECT-TYPE
        SYNTAX  INTEGER {
                other(1),
                transmit(2),
                receive(3),
                both(4),
                none(5)
                }
        ACCESS  read-write
        STATUS  mandatory
        DESCRIPTION
                "This object is used to select port flow control for fast
                 Ethernet connection."
        ::= { agPortNewCfgTableEntry 12 }

agPortNewCfgGigEthAutoNeg OBJECT-TYPE
        SYNTAX  INTEGER {
                other(1),
                on(2),
                off(3)
                }
        ACCESS  read-write
        STATUS  mandatory
        DESCRIPTION
                "This object is used to turn the autonegotiation on or off
                 for gigabit Ethernet connection."
        ::= { agPortNewCfgTableEntry 13 }

agPortNewCfgGigEthFctl OBJECT-TYPE
        SYNTAX  INTEGER {
                other(1),
                transmit(2),
                receive(3),
                both(4),
                none(5)
                }
        ACCESS  read-write
        STATUS  mandatory
        DESCRIPTION
                "This object is used to select port flow control for
                 gigabit Ethernet connection."
        ::= { agPortNewCfgTableEntry 14 }

agPortNewCfgPortName	OBJECT-TYPE
	SYNTAX	DisplayString (SIZE(0..64))
	ACCESS	read-write
	STATUS	mandatory
	DESCRIPTION
		"The switch port name."
	::= { agPortNewCfgTableEntry 15 }

agPortNewCfgBwmContract OBJECT-TYPE
	SYNTAX	INTEGER
	ACCESS	read-write
	STATUS	mandatory
	DESCRIPTION
		"The switch port Bandwidth Management contract number."
	::= { agPortNewCfgTableEntry 16 }

agPortNewCfgDiscardNonIPs OBJECT-TYPE
        SYNTAX  INTEGER {
                other(1),
                enabled(2),
                disabled(3)
                }
	ACCESS	read-write
	STATUS	mandatory
	DESCRIPTION
		"Enable or disable to discard all non-IP traffic on the 
                 switch port."
	::= { agPortNewCfgTableEntry 17 }


-- Agent Ip Configuration

ipInterfaceTableMax OBJECT-TYPE
        SYNTAX  INTEGER
        ACCESS  read-only
        STATUS  mandatory
        DESCRIPTION
                "The maximum number of rows in the Ip interface
                 table."
        ::= { iprouting 1 }

ipCurCfgIntfTable OBJECT-TYPE
        SYNTAX  SEQUENCE OF IpCurCfgIntfEntry
        ACCESS  not-accessible
        STATUS  mandatory
        DESCRIPTION
                "The table of IP interface configuration."
        ::= { iprouting 2 }

ipCurCfgIntfEntry OBJECT-TYPE
        SYNTAX  IpCurCfgIntfEntry
        ACCESS  not-accessible
        STATUS  mandatory
        DESCRIPTION
                "A row in the Ip interface table"
        INDEX   { ipCurCfgIntfIndex }
        ::= { ipCurCfgIntfTable 1 }
 
IpCurCfgIntfEntry ::= SEQUENCE {
        ipCurCfgIntfIndex         INTEGER,
        ipCurCfgIntfAddr          IpAddress,
        ipCurCfgIntfMask          IpAddress,
        ipCurCfgIntfBroadcast     IpAddress,
        ipCurCfgIntfVlan          INTEGER,
        ipCurCfgIntfState         INTEGER
        }
 
ipCurCfgIntfIndex OBJECT-TYPE
        SYNTAX  INTEGER  (1..64)
        ACCESS  read-only
        STATUS  mandatory
        DESCRIPTION
		"The interface number for which the IP information
		 is related."
	::= { ipCurCfgIntfEntry 1}

ipCurCfgIntfAddr OBJECT-TYPE
      SYNTAX  IpAddress
      ACCESS  read-only
      STATUS  mandatory
      DESCRIPTION
              "The IP address of the interface."
      ::= { ipCurCfgIntfEntry 2 }

ipCurCfgIntfMask OBJECT-TYPE
      SYNTAX  IpAddress
      ACCESS  read-only
      STATUS  mandatory  
      DESCRIPTION
              "The subnet mask of the interface."
      ::= { ipCurCfgIntfEntry 3 }

ipCurCfgIntfBroadcast OBJECT-TYPE
      SYNTAX  IpAddress
      ACCESS  read-only
      STATUS  mandatory  
      DESCRIPTION
              "The broadcast address of the interface."
      ::= { ipCurCfgIntfEntry 4 }

ipCurCfgIntfVlan OBJECT-TYPE
      SYNTAX  INTEGER (1..4094)
      ACCESS  read-only
      STATUS  mandatory  
      DESCRIPTION
              "The VLAN associated with the interface."
      ::= { ipCurCfgIntfEntry 5 }

ipCurCfgIntfState OBJECT-TYPE
      SYNTAX  INTEGER { 
			other(1),
			enabled(2),
			disabled(3)
	      }
      ACCESS  read-only
      STATUS  mandatory  
      DESCRIPTION
              "The state of the interface."
      ::= { ipCurCfgIntfEntry 6 }


ipNewCfgIntfTable OBJECT-TYPE
        SYNTAX  SEQUENCE OF IpNewCfgIntfEntry
        ACCESS  not-accessible
        STATUS  mandatory
        DESCRIPTION
                "The table of interface configuration in the New 
		 Configuration Block."
        ::= { iprouting 3 }

ipNewCfgIntfEntry OBJECT-TYPE
        SYNTAX  IpNewCfgIntfEntry
        ACCESS  not-accessible
        STATUS  mandatory
        DESCRIPTION
                "A row in the Ip interface table"
        INDEX   { ipNewCfgIntfIndex }
        ::= { ipNewCfgIntfTable 1 }
 
IpNewCfgIntfEntry ::= SEQUENCE {
        ipNewCfgIntfIndex         INTEGER,
        ipNewCfgIntfAddr          IpAddress,
        ipNewCfgIntfMask          IpAddress,
        ipNewCfgIntfBroadcast     IpAddress,
        ipNewCfgIntfVlan          INTEGER,
        ipNewCfgIntfState         INTEGER,
        ipNewCfgIntfDelete	 INTEGER
        }
 
ipNewCfgIntfIndex OBJECT-TYPE
        SYNTAX  INTEGER  (1..64)
        ACCESS  read-only
        STATUS  mandatory
        DESCRIPTION
		"The interface number for which the IP information
		 is related."
	::= { ipNewCfgIntfEntry 1 }

ipNewCfgIntfAddr OBJECT-TYPE
      SYNTAX  IpAddress
      ACCESS  read-write
      STATUS  mandatory
      DESCRIPTION
              "The IP address of the interface."
      ::= { ipNewCfgIntfEntry 2 }

ipNewCfgIntfMask OBJECT-TYPE
      SYNTAX  IpAddress
      ACCESS  read-write
      STATUS  mandatory  
      DESCRIPTION
              "The subnet mask of the interface."
      ::= { ipNewCfgIntfEntry 3 }

ipNewCfgIntfBroadcast OBJECT-TYPE
      SYNTAX  IpAddress
      ACCESS  read-write
      STATUS  mandatory  
      DESCRIPTION
              "The broadcast address of the interface."
      ::= { ipNewCfgIntfEntry 4 }

ipNewCfgIntfVlan OBJECT-TYPE
      SYNTAX  INTEGER (1..4094)
      ACCESS  read-write
      STATUS  mandatory  
      DESCRIPTION
              "The VLAN associated with the interface."
      ::= { ipNewCfgIntfEntry 5 }

ipNewCfgIntfState OBJECT-TYPE
      SYNTAX  INTEGER { 
		other(1),
		enabled(2),
		disabled(3)
		}
      ACCESS  read-write
      STATUS  mandatory  
      DESCRIPTION
              "The state of the interface."
      ::= { ipNewCfgIntfEntry 6 }

ipNewCfgIntfDelete OBJECT-TYPE
      SYNTAX  INTEGER { 
		other(1),
                delete(2)
		}
      ACCESS  read-write
      STATUS  mandatory
      DESCRIPTION
              "When set to the value of 2 (delete), the entire row
	       is deleted. When read, other(1) is returned. Setting the value
	       to anything other than 2(delete) has no effect on the state
	       of the row."
      ::= { ipNewCfgIntfEntry 7 }


-- Ip Gateway Tables 

ipGatewayTableMax OBJECT-TYPE
        SYNTAX  INTEGER
        ACCESS  read-only
        STATUS  mandatory
        DESCRIPTION
                "The maximum number of rows in the IP gateway 
                 table."
        ::= { iprouting 4 }

ipCurCfgGwTable OBJECT-TYPE
        SYNTAX  SEQUENCE OF IpCurCfgGwEntry
        ACCESS  not-accessible
        STATUS  mandatory
        DESCRIPTION
                "The table of gateway configuration in the Current
		 configuration Block."
        ::= { iprouting 5 }

ipCurCfgGwEntry OBJECT-TYPE
        SYNTAX  IpCurCfgGwEntry
        ACCESS  not-accessible
        STATUS  mandatory
        DESCRIPTION
                "A row in the Ip gateway table"
        INDEX   { ipCurCfgGwIndex }
        ::= { ipCurCfgGwTable 1 }

IpCurCfgGwEntry ::= SEQUENCE {
        ipCurCfgGwIndex         INTEGER,
        ipCurCfgGwAddr          IpAddress,
        ipCurCfgGwInterval      INTEGER,
        ipCurCfgGwRetry         INTEGER,
        ipCurCfgGwState         INTEGER,
        ipCurCfgGwArp           INTEGER
        }

ipCurCfgGwIndex OBJECT-TYPE
        SYNTAX  INTEGER  (1..4)
        ACCESS  read-only
        STATUS  mandatory
        DESCRIPTION
                "The gateway number for which the information 
        	 is related."
        ::= { ipCurCfgGwEntry 1}

ipCurCfgGwAddr OBJECT-TYPE
      SYNTAX  IpAddress
      ACCESS  read-only
      STATUS  mandatory
      DESCRIPTION
              "The IP address of the default gateway."
      ::= { ipCurCfgGwEntry 2 }

ipCurCfgGwInterval OBJECT-TYPE 
      SYNTAX  INTEGER (1..60)
      ACCESS  read-only 
      STATUS  mandatory 
      DESCRIPTION 
              "The interval between ping attempts." 
      ::= { ipCurCfgGwEntry 3 }

ipCurCfgGwRetry OBJECT-TYPE
      SYNTAX  INTEGER (1..120)   
      ACCESS  read-only
      STATUS  mandatory
      DESCRIPTION
              "The number of failed attempts to declare the default gateway
	       DOWN."
      ::= { ipCurCfgGwEntry 4 }

ipCurCfgGwState OBJECT-TYPE
      SYNTAX  INTEGER {
		other(1),
                enabled(2),
                disabled(3)
		}  
      ACCESS  read-only
      STATUS  mandatory
      DESCRIPTION
              "The state of the default gateway."
      ::= { ipCurCfgGwEntry 5 }

ipCurCfgGwArp OBJECT-TYPE
      SYNTAX  INTEGER {
                other(1),
                enabled(2),
                disabled(3)
                } 
      ACCESS  read-only
      STATUS  mandatory
      DESCRIPTION
              "The state of ARP only health checks."
      ::= { ipCurCfgGwEntry 6 }


ipNewCfgGwTable OBJECT-TYPE
        SYNTAX  SEQUENCE OF IpNewCfgGwEntry
        ACCESS  not-accessible
        STATUS  mandatory
        DESCRIPTION
                "The table of default gateway configuration in the
		 New Configuration Block."
        ::= { iprouting 6 }

ipNewCfgGwEntry OBJECT-TYPE
        SYNTAX  IpNewCfgGwEntry
        ACCESS  not-accessible
        STATUS  mandatory
        DESCRIPTION
                "A row in the Ip default gateway table"
        INDEX   { ipNewCfgGwIndex }
        ::= { ipNewCfgGwTable 1 }

IpNewCfgGwEntry ::= SEQUENCE {
        ipNewCfgGwIndex         INTEGER,
        ipNewCfgGwAddr          IpAddress,
        ipNewCfgGwInterval      INTEGER,
        ipNewCfgGwRetry         INTEGER,
        ipNewCfgGwState         INTEGER,
	ipNewCfgGwDelete	INTEGER,
        ipNewCfgGwArp           INTEGER
        }

ipNewCfgGwIndex OBJECT-TYPE
        SYNTAX  INTEGER  (1..4)
        ACCESS  read-only
        STATUS  mandatory
        DESCRIPTION
                "The gateway number for which the information 
        	 is related."
        ::= { ipNewCfgGwEntry 1}

ipNewCfgGwAddr OBJECT-TYPE
      SYNTAX  IpAddress
      ACCESS  read-write
      STATUS  mandatory
      DESCRIPTION
              "The IP address of the default gateway."
      ::= { ipNewCfgGwEntry 2 }

ipNewCfgGwInterval OBJECT-TYPE 
      SYNTAX  INTEGER (1..60)
      ACCESS  read-write 
      STATUS  mandatory 
      DESCRIPTION 
              "The interval in seconds between ping attempts." 
      ::= { ipNewCfgGwEntry 3 }

ipNewCfgGwRetry OBJECT-TYPE
      SYNTAX  INTEGER (1..120)   
      ACCESS  read-write
      STATUS  mandatory
      DESCRIPTION
              "The number of failed attempts to declare the default gateway
	       DOWN."
      ::= { ipNewCfgGwEntry 4 }

ipNewCfgGwState OBJECT-TYPE
      SYNTAX  INTEGER {
		other(1),
                enabled(2),
                disabled(3)
		}
      ACCESS  read-write
      STATUS  mandatory
      DESCRIPTION
              "The state of the default gateway."
      ::= { ipNewCfgGwEntry 5 }

ipNewCfgGwDelete OBJECT-TYPE
      SYNTAX  INTEGER {
		other(1),
                delete(2)
		}
      ACCESS  read-write
      STATUS  mandatory
      DESCRIPTION
              "When set to the value of 2 (delete), the entire row
               is deleted. When read, other is returned. Setting the value
               to anything other than 2(delete) has no effect on the state
               of the row."
      ::= { ipNewCfgGwEntry 6 }

ipNewCfgGwArp OBJECT-TYPE
      SYNTAX  INTEGER {
                other(1),
                enabled(2),
                disabled(3)
                }
      ACCESS  read-write
      STATUS  mandatory
      DESCRIPTION
              "The state of the ARP only health checks."
      ::= { ipNewCfgGwEntry 7 }

ipCurCfgStaticRouteTable OBJECT-TYPE
        SYNTAX  SEQUENCE OF IpCurCfgStaticRouteEntry
        ACCESS  not-accessible
        STATUS  mandatory
        DESCRIPTION
                "The table of static routes in the current configuration
		 block."
        ::= { iprouting 7 }

ipCurCfgStaticRouteEntry OBJECT-TYPE
        SYNTAX  IpCurCfgStaticRouteEntry
        ACCESS  not-accessible
        STATUS  mandatory
        DESCRIPTION
                "A row in the static IP route table"
        INDEX   { ipCurCfgStaticRouteIndx }
        ::= { ipCurCfgStaticRouteTable 1 }

IpCurCfgStaticRouteEntry ::= SEQUENCE {
        ipCurCfgStaticRouteIndx         INTEGER,
        ipCurCfgStaticRouteDestIp       IpAddress,
        ipCurCfgStaticRouteMask         IpAddress,
        ipCurCfgStaticRouteGateway      IpAddress,
        ipCurCfgStaticRouteInterface    INTEGER
        }

ipCurCfgStaticRouteIndx OBJECT-TYPE
        SYNTAX  INTEGER (1..64)
        ACCESS  read-only
        STATUS  mandatory
        DESCRIPTION
                "The index of the static routing table."
        ::= { ipCurCfgStaticRouteEntry 1}

ipCurCfgStaticRouteDestIp OBJECT-TYPE
        SYNTAX  IpAddress
        ACCESS  read-only
        STATUS  mandatory
        DESCRIPTION
                "The destination IP address of this route."
        ::= { ipCurCfgStaticRouteEntry 2}

ipCurCfgStaticRouteMask OBJECT-TYPE 
        SYNTAX  IpAddress
        ACCESS  read-only 
        STATUS  mandatory 
        DESCRIPTION 
                "The destination IP address of this route."
        ::= { ipCurCfgStaticRouteEntry 3}

ipCurCfgStaticRouteGateway OBJECT-TYPE 
        SYNTAX  IpAddress
        ACCESS  read-only 
        STATUS  mandatory 
        DESCRIPTION 
                "The destination IP address of this route."
        ::= { ipCurCfgStaticRouteEntry 4}

ipCurCfgStaticRouteInterface OBJECT-TYPE 
        SYNTAX  INTEGER
        ACCESS  read-only 
        STATUS  mandatory 
        DESCRIPTION 
                "The IP interface of this route.  The IP address of
		 the specified interface shall be use as source IP when 
		 performs routing."
        ::= { ipCurCfgStaticRouteEntry 5}


ipNewCfgStaticRouteTable OBJECT-TYPE
        SYNTAX  SEQUENCE OF IpNewCfgStaticRouteEntry
        ACCESS  not-accessible
        STATUS  mandatory
        DESCRIPTION
                "The table of static routes in the new configuration block."
        ::= { iprouting 8 }

ipNewCfgStaticRouteEntry OBJECT-TYPE
        SYNTAX  IpNewCfgStaticRouteEntry
        ACCESS  not-accessible
        STATUS  mandatory
        DESCRIPTION
                "A row in the static IP route table"
        INDEX   { ipNewCfgStaticRouteIndx }
        ::= { ipNewCfgStaticRouteTable 1 }

IpNewCfgStaticRouteEntry ::= SEQUENCE {
        ipNewCfgStaticRouteIndx         INTEGER,
        ipNewCfgStaticRouteDestIp       IpAddress,
        ipNewCfgStaticRouteMask         IpAddress,
        ipNewCfgStaticRouteGateway      IpAddress,
	ipNewCfgStaticRouteAction       INTEGER,
        ipNewCfgStaticRouteInterface    INTEGER
        }

ipNewCfgStaticRouteIndx OBJECT-TYPE
        SYNTAX  INTEGER (1..64)
        ACCESS  read-only
        STATUS  mandatory
        DESCRIPTION
                "The index of the static routing table."
        ::= { ipNewCfgStaticRouteEntry 1}

ipNewCfgStaticRouteDestIp OBJECT-TYPE
        SYNTAX  IpAddress
        ACCESS  read-write
        STATUS  mandatory
        DESCRIPTION
                "The destination IP address of this route."
        ::= { ipNewCfgStaticRouteEntry 2}

ipNewCfgStaticRouteMask OBJECT-TYPE 
        SYNTAX  IpAddress
        ACCESS  read-write 
        STATUS  mandatory 
        DESCRIPTION 
                "The subnet mask of this route."
        ::= { ipNewCfgStaticRouteEntry 3}

ipNewCfgStaticRouteGateway OBJECT-TYPE 
        SYNTAX  IpAddress
        ACCESS  read-write 
        STATUS  mandatory 
        DESCRIPTION 
                "The IP address of the gateway for this route."
        ::= { ipNewCfgStaticRouteEntry 4}

ipNewCfgStaticRouteAction OBJECT-TYPE
      SYNTAX  INTEGER {
              other(1),
              delete(2)
              }  
      ACCESS  read-write
      STATUS  mandatory
      DESCRIPTION
              "When set to the value of 2 (delete), the entire row
               is deleted. When read, other is returned. Setting the value
               to anything other than 2(delete) has no effect on the state
               of the row."
      ::= { ipNewCfgStaticRouteEntry 5 }

ipNewCfgStaticRouteInterface OBJECT-TYPE 
        SYNTAX  INTEGER
        ACCESS  read-write 
        STATUS  mandatory 
        DESCRIPTION 
                "The IP interface of this route.  The IP address of
		 the specified interface shall be use as source IP when 
		 performs routing."
        ::= { ipNewCfgStaticRouteEntry 6 }


-- Forwarding group 

ipForward         OBJECT IDENTIFIER ::= { iprouting 9 }

ripConfig	    OBJECT IDENTIFIER ::= { ipForward 1 }

ripCurCfgSupply OBJECT-TYPE
      SYNTAX  INTEGER {
		other(1),
		enabled(2),	
		disabled(3)
		}
      ACCESS  read-only
      STATUS  mandatory
      DESCRIPTION
              "Enable or disable supplying route updates."
      ::= { ripConfig 1 }

ripNewCfgSupply OBJECT-TYPE
      SYNTAX  INTEGER {
		other(1),
                enabled(2),
                disabled(3)
		}
      ACCESS  read-write
      STATUS  mandatory
      DESCRIPTION
              "Enable or disable supplying route updates."
      ::= { ripConfig 2 }


ripCurCfgListen OBJECT-TYPE 
      SYNTAX  INTEGER {
		other(1),
                enabled(2),      
                disabled(3) 
		}
      ACCESS  read-only 
      STATUS  mandatory  
      DESCRIPTION 
              "Enable or disable listening to route updates." 
      ::= { ripConfig 3 }

ripNewCfgListen OBJECT-TYPE
      SYNTAX  INTEGER {
		other(1),
                enabled(2),
                disabled(3)
		}
      ACCESS  read-write
      STATUS  mandatory
      DESCRIPTION
              "Enable or disable listening to route updates."
      ::= { ripConfig 4 }

ripCurCfgDefListen OBJECT-TYPE 
      SYNTAX  INTEGER {
		other(1),
                enabled(2),      
                disabled(3) 
		}
      ACCESS  read-only 
      STATUS  mandatory  
      DESCRIPTION 
              "Enable or disable listening to default routes." 
      ::= { ripConfig 5 }

ripNewCfgDefListen OBJECT-TYPE
      SYNTAX  INTEGER {
		other(1),
                enabled(2),
                disabled(3)
		}
      ACCESS  read-write
      STATUS  mandatory
      DESCRIPTION
              "Enable or disable listening to default routes."
      ::= { ripConfig 6 }

ripCurCfgStaticSupply OBJECT-TYPE 
      SYNTAX  INTEGER {
		other(1),
                enabled(2),      
                disabled(3) 
		}
      ACCESS  read-only 
      STATUS  mandatory  
      DESCRIPTION 
              "Enable or disable supplying static route updates." 
      ::= { ripConfig 7 }

ripNewCfgStaticSupply OBJECT-TYPE
      SYNTAX  INTEGER {
		other(1),
                enabled(2),
                disabled(3)
		}
      ACCESS  read-write
      STATUS  mandatory
      DESCRIPTION
              "Enable or disable supplying static route updates."
      ::= { ripConfig 8 }

ripCurCfgUpdatePeriod OBJECT-TYPE
      SYNTAX  INTEGER  (1..120)
      ACCESS  read-only
      STATUS  mandatory
      DESCRIPTION
              "Update Period in seconds."
      ::= { ripConfig 9 }

ripNewCfgUpdatePeriod OBJECT-TYPE
      SYNTAX  INTEGER (1..120)
      ACCESS  read-write
      STATUS  mandatory
      DESCRIPTION
              "Update period in seconds."
      ::= { ripConfig 10 }

ripCurCfgState OBJECT-TYPE
      SYNTAX  INTEGER {
		other(1),
                on(2),
                off(3)
		}
      ACCESS  read-only
      STATUS  mandatory
      DESCRIPTION
              "RIP global state."
      ::= { ripConfig 11 }

ripNewCfgState OBJECT-TYPE
      SYNTAX  INTEGER {
		other(1),
                on(2),
                off(3)
		}
      ACCESS  read-write
      STATUS  mandatory
      DESCRIPTION
              "Globally turn RIP on or off."
      ::= { ripConfig 12 }

ripCurCfgPoisonReverse OBJECT-TYPE
      SYNTAX  INTEGER {
		other(1),
                enabled(2),
                disabled(3)
		}
      ACCESS  read-only
      STATUS  mandatory
      DESCRIPTION
              "RIP poison reverse."
      ::= { ripConfig 13 }
 
ripNewCfgPoisonReverse OBJECT-TYPE
      SYNTAX  INTEGER {
		other(1),
                enabled(2),
                disabled(3)
		}
      ACCESS  read-write
      STATUS  mandatory
      DESCRIPTION
              "RIP poison reverse."
      ::= { ripConfig 14 }


-- Table to turn on/off forwarding per port

ipFwdCurCfgPortTable OBJECT-TYPE
        SYNTAX  SEQUENCE OF IpFwdCurCfgPortEntry
        ACCESS  not-accessible
        STATUS  mandatory
        DESCRIPTION
                "The table of ports and their forwarding states"
        ::= { ipForward 2 }

ipFwdCurCfgPortEntry OBJECT-TYPE
        SYNTAX  IpFwdCurCfgPortEntry
        ACCESS  not-accessible
        STATUS  mandatory
        DESCRIPTION
                "A row in the ipFwdCurCfgPortTable "
        INDEX   { ipFwdCurCfgPortIndex }
        ::= { ipFwdCurCfgPortTable 1 }

IpFwdCurCfgPortEntry ::= SEQUENCE {
        ipFwdCurCfgPortIndex	INTEGER,
        ipFwdCurCfgPortState	INTEGER
        }

ipFwdCurCfgPortIndex OBJECT-TYPE
        SYNTAX  INTEGER
        ACCESS  read-only
        STATUS  mandatory
        DESCRIPTION
                "The port number for which the forwarding state 
	         information pertains."
        ::= { ipFwdCurCfgPortEntry 1 }
 
ipFwdCurCfgPortState OBJECT-TYPE
        SYNTAX  INTEGER {
			   other(1),
			   enabled(2),
		   	   disabled(3)
                        }
        ACCESS  read-only
        STATUS  mandatory
        DESCRIPTION
                "The forwarding state of the port."
        ::= { ipFwdCurCfgPortEntry 2 }


ipFwdNewCfgPortTable OBJECT-TYPE
        SYNTAX  SEQUENCE OF IpFwdNewCfgPortEntry
        ACCESS  not-accessible
        STATUS  mandatory
        DESCRIPTION
                "The table of ports and their forwarding states"
        ::= { ipForward 3 }
 
ipFwdNewCfgPortEntry OBJECT-TYPE
        SYNTAX  IpFwdNewCfgPortEntry
        ACCESS  not-accessible
        STATUS  mandatory
        DESCRIPTION
                "A row in the ipFwdNewCfgPortTable "
        INDEX   { ipFwdNewCfgPortIndex }
        ::= { ipFwdNewCfgPortTable 1 }
 
IpFwdNewCfgPortEntry ::= SEQUENCE {
        ipFwdNewCfgPortIndex           INTEGER,
        ipFwdNewCfgPortState           INTEGER
        }
 
ipFwdNewCfgPortIndex OBJECT-TYPE
        SYNTAX  INTEGER
        ACCESS  read-only
        STATUS  mandatory
        DESCRIPTION
                "The port number for which the forwarding state
                 information pertains."
        ::= { ipFwdNewCfgPortEntry 1 }
 
ipFwdNewCfgPortState OBJECT-TYPE
        SYNTAX  INTEGER {
		other(1),
                enabled(2),
                disabled(3)
                }
        ACCESS  read-write  
        STATUS  mandatory
        DESCRIPTION
                "The forwarding state of the port."
        ::= { ipFwdNewCfgPortEntry 2 }

ipFwdCurCfgLocalSubnet OBJECT-TYPE
       SYNTAX  IpAddress
       ACCESS  read-only
       STATUS  mandatory
       DESCRIPTION
              "The current local IP subnet."
       ::= { ipForward 4 }

ipFwdNewCfgLocalSubnet OBJECT-TYPE 
       SYNTAX  IpAddress 
       ACCESS  read-write 
       STATUS  mandatory
       DESCRIPTION 
              "The new local IP subnet." 
       ::= { ipForward 5 }

ipFwdCurCfgLocalMask OBJECT-TYPE 
       SYNTAX  IpAddress 
       ACCESS  read-only 
       STATUS  mandatory
       DESCRIPTION 
              "The current local IP subnet mask." 
       ::= { ipForward 6 } 
 
ipFwdNewCfgLocalMask OBJECT-TYPE  
       SYNTAX  IpAddress  
       ACCESS  read-write  
       STATUS  mandatory
       DESCRIPTION  
              "The new local IP subnet mask."  
       ::= { ipForward 7 }

ipFwdCurCfgState OBJECT-TYPE
      SYNTAX  INTEGER {
		other(1),
                on(2),
                off(3)
		}
      ACCESS  read-only
      STATUS  mandatory
      DESCRIPTION
              "IP forwarding global state."
      ::= { ipForward 8 }

ipFwdNewCfgState OBJECT-TYPE
      SYNTAX  INTEGER { 
		other(1), 
                on(2),
                off(3) 
		}
      ACCESS  read-write
      STATUS  mandatory  
      DESCRIPTION 
              "IP forwarding global state." 
      ::= { ipForward 9 }

ipFwdCurCfgDirectedBcast OBJECT-TYPE
    SYNTAX INTEGER {
        enabled(2),
        disabled(3)
	}
    ACCESS read-only
    STATUS mandatory
    DESCRIPTION
        "Enable or disable forwarding directed broadcasts."
    ::= { ipForward 10 }

ipFwdNewCfgDirectedBcast OBJECT-TYPE
    SYNTAX INTEGER {
        enabled(2),
        disabled(3)
	}
    ACCESS read-write
    STATUS mandatory
    DESCRIPTION
        "Enable or disable forwarding directed broadcasts."
    ::= { ipForward 11 }

arpCurCfgReARPPeriod OBJECT-TYPE
      SYNTAX  INTEGER
      ACCESS  read-only
      STATUS  mandatory
      DESCRIPTION
              "Re-ARP Period in seconds."
      ::= { iprouting 10 }

arpNewCfgReARPPeriod OBJECT-TYPE 
      SYNTAX  INTEGER 
      ACCESS  read-write
      STATUS  mandatory 
      DESCRIPTION 
              "Re-ARP Period in seconds." 
      ::= { iprouting 11 }

ipCurCfgGwMetric OBJECT-TYPE
      SYNTAX  INTEGER {
              strict(1),
              roundrobin(2)
              }  
      ACCESS  read-only
      STATUS  mandatory
      DESCRIPTION
              "The default gateway metric."
      ::= { iprouting 12 }

ipNewCfgGwMetric OBJECT-TYPE
      SYNTAX  INTEGER {
              strict(1),
              roundrobin(2)
              }  
      ACCESS  read-write
      STATUS  mandatory
      DESCRIPTION
              "The default gateway metric."
      ::= { iprouting 13 }


-- VLAN group

vlanMaxEnt OBJECT-TYPE
	SYNTAX	INTEGER 
	ACCESS	read-only
	STATUS	mandatory
	DESCRIPTION
		"The maximum number of rows in the VLAN configuration 
		 table."
	::= { vlans 1 }

vlanCurCfgTable OBJECT-TYPE
	SYNTAX	SEQUENCE OF VlanCurCfgTableEntry
	ACCESS	not-accessible
	STATUS	mandatory
	DESCRIPTION
		"The table of VLAN configuration."
	::= { vlans 2 }

vlanCurCfgTableEntry OBJECT-TYPE
	SYNTAX	VlanCurCfgTableEntry
	ACCESS	not-accessible
	STATUS	mandatory
	DESCRIPTION
		"A row in the VLAN configuration table."
	INDEX	{ vlanCurCfgVlanId }
	::= { vlanCurCfgTable 1 }

VlanCurCfgTableEntry ::= SEQUENCE {
	vlanCurCfgVlanId 		INTEGER,
	vlanCurCfgVlanName 		DisplayString,
	vlanCurCfgPorts 		OCTET STRING,
	vlanCurCfgState 		INTEGER,
	vlanCurCfgJumbo 		INTEGER,
	vlanCurCfgBwmContract		INTEGER
	}

vlanCurCfgVlanId	OBJECT-TYPE
	SYNTAX	INTEGER  (1..4094)
	ACCESS	read-only
	STATUS	mandatory
	DESCRIPTION
		"The VLAN identifier."
	::= { vlanCurCfgTableEntry 1 }

vlanCurCfgVlanName	OBJECT-TYPE
	SYNTAX	DisplayString (SIZE(0..32))
	ACCESS	read-only
	STATUS	mandatory
	DESCRIPTION
		"The VLAN name."
	::= { vlanCurCfgTableEntry 2 }

vlanCurCfgPorts	OBJECT-TYPE
	SYNTAX	OCTET STRING (SIZE(0..16))
	ACCESS	read-only
	STATUS	mandatory
	DESCRIPTION
		"The port list in the VLAN.  The ports are presented 
		 in bitmap format.

		 in receiving order:

		   OCTET 1  OCTET 2  .....
                   xxxxxxxx xxxxxxxx ..... 
                   ||    || |_ port 8
                   ||    ||  
                   ||    ||___ port 7
                   ||    |____ port 6
                   ||      .    .   .
                   ||_________ port 1
                   |__________ reserved

		 where x : 1 - The represented port belongs to the VLAN
		           0 - The represented port does not belong to 
                               the VLAN"
	::= { vlanCurCfgTableEntry 3 }

vlanCurCfgState	OBJECT-TYPE
	SYNTAX	INTEGER  {
		other(1),
		enabled(2),
		disabled(3)
		}
	ACCESS	read-only
	STATUS	mandatory
	DESCRIPTION
		"Enable or disable a VLAN"
	::= { vlanCurCfgTableEntry 4 }

vlanCurCfgJumbo        OBJECT-TYPE
        SYNTAX  INTEGER  {
		other(1),
		enabled(2),
		disabled(3)
                }
        ACCESS  read-only
        STATUS  mandatory
        DESCRIPTION
                "Enable or Disable the Jumbo frame support for the VLAN "
        ::= { vlanCurCfgTableEntry 5 }

vlanCurCfgBwmContract OBJECT-TYPE
        SYNTAX  INTEGER  
        ACCESS  read-only
        STATUS  mandatory
        DESCRIPTION
                "Default contract number the VLAN "
        ::= { vlanCurCfgTableEntry 6 }

vlanNewCfgTable OBJECT-TYPE
	SYNTAX	SEQUENCE OF VlanNewCfgTableEntry
	ACCESS	not-accessible
	STATUS	mandatory
	DESCRIPTION
		"The table of VLAN configuration."
	::= { vlans 3 }

vlanNewCfgTableEntry OBJECT-TYPE
	SYNTAX	VlanNewCfgTableEntry
	ACCESS	not-accessible
	STATUS	mandatory
	DESCRIPTION
		"A row in the VLAN configuration table."
	INDEX	{ vlanNewCfgVlanId }
	::= { vlanNewCfgTable 1 }

VlanNewCfgTableEntry ::= SEQUENCE {
	vlanNewCfgVlanId 		INTEGER,
	vlanNewCfgVlanName 		DisplayString,
	vlanNewCfgPorts 		OCTET STRING,
	vlanNewCfgState 		INTEGER,
	vlanNewCfgJumbo 		INTEGER,
	vlanNewCfgAddPort 		INTEGER,
	vlanNewCfgRemovePort 		INTEGER,
	vlanNewCfgDelete 		INTEGER,
	vlanNewCfgBwmContract		INTEGER
	}

vlanNewCfgVlanId	OBJECT-TYPE
	SYNTAX	INTEGER  (1..4094)
	ACCESS	read-only
	STATUS	mandatory
	DESCRIPTION
		"The VLAN identifier."
	::= { vlanNewCfgTableEntry 1 }

vlanNewCfgVlanName	OBJECT-TYPE
	SYNTAX	DisplayString (SIZE(0..32))
	ACCESS	read-write
	STATUS	mandatory
	DESCRIPTION
		"The VLAN name."
	::= { vlanNewCfgTableEntry 2 }

vlanNewCfgPorts	OBJECT-TYPE
	SYNTAX	OCTET STRING (SIZE(0..16))
	ACCESS	read-only
	STATUS	mandatory
	DESCRIPTION
		"The port list in the VLAN.  The ports are presented 
		 in bitmap format.

		 in receiving order:

		   OCTET 1  OCTET 2  .....
                   xxxxxxxx xxxxxxxx ..... 
                   ||    || |_ port 8
                   ||    ||  
                   ||    ||___ port 7
                   ||    |____ port 6
                   ||      .    .   .
                   ||_________ port 1
                   |__________ reserved

		 where x : 1 - The represented port belongs to the VLAN
		           0 - The represented port does not belong to 
                               the VLAN"
	::= { vlanNewCfgTableEntry 3 }

vlanNewCfgState	OBJECT-TYPE
	SYNTAX	INTEGER  {
		other(1),
		enabled(2),
		disabled(3)
		}
	ACCESS	read-write
	STATUS	mandatory
	DESCRIPTION
		"Enable or disable a VLAN"
	::= { vlanNewCfgTableEntry 4 }

vlanNewCfgJumbo        OBJECT-TYPE
        SYNTAX  INTEGER  {
		other(1),
		enabled(2),
		disabled(3)
                }
        ACCESS  read-write
        STATUS  mandatory
        DESCRIPTION
                "Enable or Disable the Jumbo frame support for the VLAN "
        ::= { vlanNewCfgTableEntry 5 }

vlanNewCfgAddPort        OBJECT-TYPE
        SYNTAX  INTEGER
        ACCESS  read-write
        STATUS  mandatory
        DESCRIPTION
                "The port to be added to the specified VLAN.  A '0'
                 value is returned when read."
        ::= { vlanNewCfgTableEntry 6 }

vlanNewCfgRemovePort        OBJECT-TYPE
        SYNTAX  INTEGER
        ACCESS  read-write
        STATUS  mandatory
        DESCRIPTION
                "The port to be removed from the specified VLAN.  A '0'
                 value is returned when read."
        ::= { vlanNewCfgTableEntry 7 }

vlanNewCfgDelete        OBJECT-TYPE
	SYNTAX	INTEGER  {
		other(1),
		delete(2)
		}
        ACCESS  read-write
        STATUS  mandatory
        DESCRIPTION
                "This is an action object to create or delete a VLAN.
                 other(1) is returned always when read.

                 The following values are writable:
                   delete(2)...to delete a VLAN"
        ::= { vlanNewCfgTableEntry 8 }

vlanNewCfgBwmContract OBJECT-TYPE
	SYNTAX	INTEGER  
        ACCESS  read-write
        STATUS  mandatory
        DESCRIPTION
                "Default contract number for the VLAN."
        ::= { vlanNewCfgTableEntry 9 }


-- Server Load Balancing - Real Server Table

slbRealServerMaxSize OBJECT-TYPE
        SYNTAX  INTEGER 
        ACCESS  read-only 
        STATUS  mandatory 
        DESCRIPTION 
                "The maximum number of entries in SLB RealServerTable." 
        ::= { serverloadbalance 1 }


slbCurCfgRealServerTable OBJECT-TYPE
        SYNTAX  SEQUENCE OF SlbCurCfgRealServerEntry
        ACCESS  not-accessible
        STATUS  mandatory
        DESCRIPTION
		"The table of Real Server configuration in the current_config."
        ::= { serverloadbalance 2 }

slbCurCfgRealServerEntry OBJECT-TYPE
        SYNTAX  SlbCurCfgRealServerEntry
        ACCESS  not-accessible
        STATUS  mandatory
        DESCRIPTION
        	"Information about a particular Real Server configuration."
        INDEX   { slbCurCfgRealServerIndex }
        ::= { slbCurCfgRealServerTable 1 }
 
SlbCurCfgRealServerEntry ::= SEQUENCE {
        slbCurCfgRealServerIndex      INTEGER,
        slbCurCfgRealServerIpAddr     IpAddress,
	slbCurCfgRealServerWeight     INTEGER,
	slbCurCfgRealServerMaxConns   INTEGER,
	slbCurCfgRealServerTimeOut    INTEGER,
	slbCurCfgRealServerBackUp     INTEGER,
	slbCurCfgRealServerPingInterval   INTEGER,
	slbCurCfgRealServerFailRetry  INTEGER,
	slbCurCfgRealServerSuccRetry  INTEGER,
	slbCurCfgRealServerState      INTEGER,
	slbCurCfgRealServerType       INTEGER,
	slbCurCfgRealServerName       DisplayString,
	slbCurCfgRealServerUrlBmap    OCTET STRING,
        slbCurCfgRealServerCookie     INTEGER,
        slbCurCfgRealServerExcludeStr INTEGER,
	slbCurCfgRealServerSubmac     INTEGER
	}

slbCurCfgRealServerIndex OBJECT-TYPE
        SYNTAX  INTEGER
        ACCESS  read-only
        STATUS  mandatory
        DESCRIPTION
                "The real server number" 
        ::= { slbCurCfgRealServerEntry 1 }

slbCurCfgRealServerIpAddr OBJECT-TYPE
        SYNTAX  IpAddress
        ACCESS  read-only
        STATUS  mandatory
        DESCRIPTION
                "IP address of the real server identified by the instance
		 of slbRealServerIndex." 
        ::= { slbCurCfgRealServerEntry 2 }

slbCurCfgRealServerWeight OBJECT-TYPE
        SYNTAX  INTEGER (1..48)
        ACCESS  read-only
        STATUS  mandatory
        DESCRIPTION
                "The server weight." 
        ::= { slbCurCfgRealServerEntry 3 }

slbCurCfgRealServerMaxConns OBJECT-TYPE
        SYNTAX  INTEGER (0..200000)
        ACCESS  read-only
        STATUS  mandatory
        DESCRIPTION
                "The maximum number of connections that are allowed." 
        ::= { slbCurCfgRealServerEntry 4 }

slbCurCfgRealServerTimeOut OBJECT-TYPE
        SYNTAX  INTEGER (2..60)
        ACCESS  read-only
        STATUS  mandatory
        DESCRIPTION
                "The maximum number of minutes an inactive connection
		 remains open." 
        ::= { slbCurCfgRealServerEntry 5 }

slbCurCfgRealServerBackUp OBJECT-TYPE
        SYNTAX INTEGER {
            none(0)
        }
        ACCESS  read-only
        STATUS  mandatory
        DESCRIPTION
                "The backup server number for this server." 
        ::= { slbCurCfgRealServerEntry 6 }

slbCurCfgRealServerPingInterval OBJECT-TYPE
        SYNTAX  INTEGER (0..60)
        ACCESS  read-only
        STATUS  mandatory
        DESCRIPTION
		"The interval between keep-alive (ping) attempts in number 
                 of seconds. Zero means disabling ping attempt."
        ::= { slbCurCfgRealServerEntry 7 }

slbCurCfgRealServerFailRetry OBJECT-TYPE
        SYNTAX  INTEGER  (1..63)
        ACCESS  read-only
        STATUS  mandatory
        DESCRIPTION
                "The number of failed attempts to declare this server DOWN." 
        ::= { slbCurCfgRealServerEntry 8 }

slbCurCfgRealServerSuccRetry OBJECT-TYPE
        SYNTAX  INTEGER (1..63)
        ACCESS  read-only
        STATUS  mandatory
        DESCRIPTION
                "The number of successful attempts to declare a server UP." 
        ::= { slbCurCfgRealServerEntry 9 }

slbCurCfgRealServerState OBJECT-TYPE
        SYNTAX  INTEGER {
		other(1),
		enabled(2),
		disabled(3)
		}
        ACCESS  read-only
        STATUS  mandatory
        DESCRIPTION
                "Enable or disable this server." 
        ::= { slbCurCfgRealServerEntry 10 }

slbCurCfgRealServerType OBJECT-TYPE
        SYNTAX  INTEGER {
		local-server(1),
		remote-server(2)
		}
        ACCESS  read-only
        STATUS  mandatory
        DESCRIPTION
                "The server type.  It participates in global server
		 load balancing when it is configured as remote-server." 
        ::= { slbCurCfgRealServerEntry 11 }

slbCurCfgRealServerName OBJECT-TYPE 
        SYNTAX  DisplayString (SIZE(0..15))
        ACCESS  read-only 
        STATUS  mandatory 
        DESCRIPTION 
                "The name of the real server."  
        ::= { slbCurCfgRealServerEntry 12 }

slbCurCfgRealServerUrlBmap OBJECT-TYPE
        SYNTAX  OCTET STRING
        ACCESS  read-only
        STATUS  mandatory
        DESCRIPTION
                "The URL Pathes selected for URL load balancing for by the
		 real server.  The selected URL Pathes are presented in 
		 a bitmap format.

                 in receiving order:

                   OCTET 1  OCTET 2  .....
                   xxxxxxxx xxxxxxxx .....
                   ||    || |_ URL Path 9
                   ||    ||
                   ||    ||___ URL Path 8
                   ||    |____ URL Path 7
                   ||      .    .   .
                   ||_________ URL Path 2
                   |__________ URL Path 1

                 where x : 1 - The represented URL Path is selected
                           0 - The represented URL Path is not selected"
        ::= { slbCurCfgRealServerEntry 13 }

slbCurCfgRealServerCookie OBJECT-TYPE
        SYNTAX  INTEGER {
		enabled(1),
		disabled(2)
		}
        ACCESS  read-only
        STATUS  mandatory
        DESCRIPTION
                "The real server that will handle client requests that
                 don't contain an URL cookie if Cookie loadbalance
                 is enabled." 
        ::= { slbCurCfgRealServerEntry 14 }

slbCurCfgRealServerExcludeStr OBJECT-TYPE
        SYNTAX  INTEGER {
		enabled(1),
		disabled(2)
		}
        ACCESS  read-only
        STATUS  mandatory
        DESCRIPTION
                "The real server will handle requests that don't 
                 match the loadbalance string if it is enabled."
        ::= { slbCurCfgRealServerEntry 15 }

slbCurCfgRealServerSubmac OBJECT-TYPE
        SYNTAX  INTEGER {
		enabled(1),
		disabled(2)
		}
        ACCESS  read-only
        STATUS  mandatory
        DESCRIPTION
                "The real server config to enable/disable MAC SA 
		 substitution for L4 traffic. If disabled (the 
		 default) we will NOT substitute the MAC SA of
		 client-to-server frames.  If enabled, we will 
		 substitute the MAC SA."
        ::= { slbCurCfgRealServerEntry 16 }

-- Server Load Balancing - Real Server Table

slbNewCfgRealServerTable OBJECT-TYPE
        SYNTAX  SEQUENCE OF SlbNewCfgRealServerEntry
        ACCESS  not-accessible
        STATUS  mandatory
        DESCRIPTION
                "The table of Real Server configuration in the new_config."
        ::= { serverloadbalance 3 }

slbNewCfgRealServerEntry OBJECT-TYPE
        SYNTAX  SlbNewCfgRealServerEntry
        ACCESS  not-accessible
        STATUS  mandatory
        DESCRIPTION
                "Information about a particular Real Server configuration."
        INDEX   { slbNewCfgRealServerIndex }
        ::= { slbNewCfgRealServerTable 1 }
 
SlbNewCfgRealServerEntry ::= SEQUENCE {
        slbNewCfgRealServerIndex      INTEGER,
        slbNewCfgRealServerIpAddr     IpAddress,
	slbNewCfgRealServerWeight     INTEGER,
	slbNewCfgRealServerMaxConns   INTEGER,
	slbNewCfgRealServerTimeOut    INTEGER,
	slbNewCfgRealServerBackUp     INTEGER,
	slbNewCfgRealServerPingInterval   INTEGER,
	slbNewCfgRealServerFailRetry  INTEGER,
	slbNewCfgRealServerSuccRetry  INTEGER,
	slbNewCfgRealServerState      INTEGER,
	slbNewCfgRealServerDelete     INTEGER,
	slbNewCfgRealServerType       INTEGER,
	slbNewCfgRealServerName       DisplayString,
        slbNewCfgRealServerUrlBmap    OCTET STRING,
        slbNewCfgRealServerAddUrl     INTEGER,
        slbNewCfgRealServerRemUrl     INTEGER,
        slbNewCfgRealServerCookie     INTEGER,
        slbNewCfgRealServerExcludeStr INTEGER,
	slbNewCfgRealServerSubmac     INTEGER
	}

slbNewCfgRealServerIndex OBJECT-TYPE
        SYNTAX  INTEGER
        ACCESS  read-only
        STATUS  mandatory
        DESCRIPTION
                "The real server number" 
        ::= { slbNewCfgRealServerEntry 1 }

slbNewCfgRealServerIpAddr OBJECT-TYPE
        SYNTAX  IpAddress
        ACCESS  read-write
        STATUS  mandatory
        DESCRIPTION
                "IP address of the real server identified by the instance
		 of slbRealServerIndex." 
        ::= { slbNewCfgRealServerEntry 2 }

slbNewCfgRealServerWeight OBJECT-TYPE
        SYNTAX  INTEGER (1..48)
        ACCESS  read-write
        STATUS  mandatory
        DESCRIPTION
                "The server weight." 
        ::= { slbNewCfgRealServerEntry 3 }

slbNewCfgRealServerMaxConns OBJECT-TYPE
        SYNTAX  INTEGER (0..200000)
        ACCESS  read-write
        STATUS  mandatory
        DESCRIPTION
                "The maximum number of connections that are allowed." 
        ::= { slbNewCfgRealServerEntry 4 }

slbNewCfgRealServerTimeOut OBJECT-TYPE
        SYNTAX  INTEGER (2..60)
        ACCESS  read-write
        STATUS  mandatory
        DESCRIPTION
                "The maximum number of minutes an inactive connection
		 remains open." 
        ::= { slbNewCfgRealServerEntry 5 }

slbNewCfgRealServerBackUp OBJECT-TYPE
        SYNTAX INTEGER {
            none(0)
        }
        ACCESS  read-write
        STATUS  mandatory
        DESCRIPTION
                "The backup server number for this server." 
        ::= { slbNewCfgRealServerEntry 6 }

slbNewCfgRealServerPingInterval OBJECT-TYPE
        SYNTAX  INTEGER (0..60)
        ACCESS  read-write
        STATUS  mandatory
        DESCRIPTION
		"The interval between keep-alive (ping) attempts in number 
                 of seconds. Zero means disabling ping attempt."
        ::= { slbNewCfgRealServerEntry 7 }

slbNewCfgRealServerFailRetry OBJECT-TYPE
        SYNTAX  INTEGER  (1..63)
        ACCESS  read-write
        STATUS  mandatory
        DESCRIPTION
                "The number of failed attempts to declare this server DOWN." 
        ::= { slbNewCfgRealServerEntry 8 }

slbNewCfgRealServerSuccRetry OBJECT-TYPE
        SYNTAX  INTEGER (1..63)
        ACCESS  read-write
        STATUS  mandatory
        DESCRIPTION
                "The number of successful attempts to declare a server UP." 
        ::= { slbNewCfgRealServerEntry 9 }

slbNewCfgRealServerState OBJECT-TYPE
        SYNTAX  INTEGER {
		other(1),
		enabled(2),
		disabled(3)
		}
        ACCESS  read-write
        STATUS  mandatory
        DESCRIPTION
                "Enable or disable this server." 
        ::= { slbNewCfgRealServerEntry 10 }

slbNewCfgRealServerDelete OBJECT-TYPE
        SYNTAX  INTEGER {
                other(1),
                delete(2)
                }
        ACCESS  read-write
        STATUS  mandatory
        DESCRIPTION
                "By setting the value to delete(2), the entire row is
                 deleted."
        ::= { slbNewCfgRealServerEntry 11 }

slbNewCfgRealServerType OBJECT-TYPE
        SYNTAX  INTEGER {
		local-server(1),
		remote-server(2)
		}
        ACCESS  read-write
        STATUS  mandatory
        DESCRIPTION
                "The server type.  It participates in global server
		 load balancing when it is configured as remote-server." 
        ::= { slbNewCfgRealServerEntry 12 }

slbNewCfgRealServerName OBJECT-TYPE 
        SYNTAX  DisplayString (SIZE(0..15))
        ACCESS  read-write 
        STATUS  mandatory 
        DESCRIPTION 
                "The name of the real server."  
        ::= { slbNewCfgRealServerEntry 13 }

slbNewCfgRealServerUrlBmap OBJECT-TYPE
        SYNTAX  OCTET STRING
        ACCESS  read-only
        STATUS  mandatory
        DESCRIPTION
                "The URL Pathes selected for URL load balancing for by the
		 real server.  The selected URL Pathes are presented in 
		 a bitmap format.

                 in receiving order:

                   OCTET 1  OCTET 2  .....
                   xxxxxxxx xxxxxxxx .....
                   ||    || |_ URL Path 9
                   ||    ||
                   ||    ||___ URL Path 8
                   ||    |____ URL Path 7
                   ||      .    .   .
                   ||_________ URL Path 2
                   |__________ URL Path 1

                 where x : 1 - The represented URL Path is selected
                           0 - The represented URL Path is not selected"
        ::= { slbNewCfgRealServerEntry 14 }

slbNewCfgRealServerAddUrl OBJECT-TYPE
        SYNTAX  INTEGER
        ACCESS  read-write
        STATUS  mandatory
        DESCRIPTION
                "The URL Path (slbCurCfgUrlLbPathIndex) to be added to 
		 the real server. A zero is returned when read."
        ::= { slbNewCfgRealServerEntry 15 }

slbNewCfgRealServerRemUrl OBJECT-TYPE
        SYNTAX  INTEGER
        ACCESS  read-write
        STATUS  mandatory
        DESCRIPTION
                "The URL Path (slbCurCfgUrlLbPathIndex) to be removed from 
                 the real server. A zero is returned when read."
        ::= { slbNewCfgRealServerEntry 16 }

slbNewCfgRealServerCookie OBJECT-TYPE
        SYNTAX  INTEGER {
		enabled(1),
		disabled(2)
		}
        ACCESS  read-write
        STATUS  mandatory
        DESCRIPTION
                "Enable or disable real server to handle client requests
                 that don't contain a cookie if cookie loadbalance is
                 enabled." 
        ::= { slbNewCfgRealServerEntry 17 }

slbNewCfgRealServerExcludeStr OBJECT-TYPE
        SYNTAX  INTEGER {
		enabled(1),
		disabled(2)
		}
        ACCESS  read-write
        STATUS  mandatory
        DESCRIPTION
                "Enable or disable exclusionary matching string on
                 real server."
        ::= { slbNewCfgRealServerEntry 18 }

slbNewCfgRealServerSubmac OBJECT-TYPE
        SYNTAX  INTEGER {
		enabled(1),
		disabled(2)
		}
        ACCESS  read-write
        STATUS  mandatory
        DESCRIPTION
                "The real server config to enable/disable MAC SA 
		 substitution for L4 traffic. If disabled (the 
		 default) we will NOT substitute the MAC SA of
		 client-to-server frames.  If enabled, we will 
		 substitute the MAC SA."
        ::= { slbNewCfgRealServerEntry 19 }

-- Server load balancing - Virtual Server Table

slbVirtServerTableMaxSize OBJECT-TYPE
        SYNTAX  INTEGER
        ACCESS  read-only
        STATUS  mandatory
        DESCRIPTION
                "The maximum number of entries in SLB VirtServerTable."
        ::= { serverloadbalance 4 }

slbCurCfgVirtServerTable OBJECT-TYPE
        SYNTAX  SEQUENCE OF SlbCurCfgVirtualServerEntry
        ACCESS  not-accessible
        STATUS  mandatory
        DESCRIPTION
                "The table of virtual Servers."
        ::= { serverloadbalance 5 }
 
slbCurCfgVirtualServerEntry OBJECT-TYPE
        SYNTAX  SlbCurCfgVirtualServerEntry
        ACCESS  not-accessible
        STATUS  mandatory
        DESCRIPTION
                "A row in the virtual server table."
        INDEX   { slbCurCfgVirtServerIndex }
        ::= { slbCurCfgVirtServerTable 1 }
 
SlbCurCfgVirtualServerEntry ::= SEQUENCE {
        slbCurCfgVirtServerIndex     		INTEGER,
        slbCurCfgVirtServerIpAddress 		IpAddress,
        slbCurCfgVirtServerLayer3Only    	INTEGER,
        slbCurCfgVirtServerState     		INTEGER,
        slbCurCfgVirtServerDname     		DisplayString,
        slbCurCfgVirtServerCname                DisplayString,
        slbCurCfgVirtServerCoffset              INTEGER,
        slbCurCfgVirtServerClength              INTEGER,
        slbCurCfgVirtServerUriCookie            INTEGER,
	slbCurCfgVirtServerFtpParsing		INTEGER,
        slbCurCfgVirtServerUrlHashLen           INTEGER,
        slbCurCfgVirtServerHttpHdrName          DisplayString,
	slbCurCfgVirtServerBwmContract		INTEGER
        }

slbCurCfgVirtServerIndex OBJECT-TYPE
        SYNTAX  INTEGER
        ACCESS  read-only
        STATUS  mandatory
        DESCRIPTION
                "Virtual Server Number" 
        ::= { slbCurCfgVirtualServerEntry 1 }

slbCurCfgVirtServerIpAddress OBJECT-TYPE
        SYNTAX  IpAddress
        ACCESS  read-only
        STATUS  mandatory
        DESCRIPTION
                "IP address of the virtual server." 
        ::= { slbCurCfgVirtualServerEntry 2 }

slbCurCfgVirtServerLayer3Only OBJECT-TYPE 
        SYNTAX  INTEGER {
		layer3Only(1),
		disabled(2)
		}
        ACCESS  read-only 
        STATUS  mandatory 
        DESCRIPTION 
                "Enable or disable layer3 only balancing."  
        ::= { slbCurCfgVirtualServerEntry 3 }

slbCurCfgVirtServerState OBJECT-TYPE 
        SYNTAX  INTEGER {
		other(1),
		enabled(2),
		disabled(3)
		}
        ACCESS  read-only 
        STATUS  mandatory 
        DESCRIPTION 
                "Enable or disable the virtual server."  
        ::= { slbCurCfgVirtualServerEntry 4 }

slbCurCfgVirtServerDname OBJECT-TYPE 
        SYNTAX  DisplayString (SIZE(0..34))
        ACCESS  read-only 
        STATUS  mandatory 
        DESCRIPTION 
                "The domain name of the virtual server."  
        ::= { slbCurCfgVirtualServerEntry 5 }


slbCurCfgVirtServerCname OBJECT-TYPE 
        SYNTAX  DisplayString (SIZE(0..16))
        ACCESS  read-only 
        STATUS  mandatory 
        DESCRIPTION 
                "The cookie name of the virtual server used for cookie load balance."  
        ::= { slbCurCfgVirtualServerEntry 6 }

slbCurCfgVirtServerCoffset OBJECT-TYPE
        SYNTAX  INTEGER (1..128)
        ACCESS  read-only
        STATUS  mandatory
        DESCRIPTION
                "The starting byte offset of the cookie value." 
        ::= { slbCurCfgVirtualServerEntry 7 }

slbCurCfgVirtServerClength OBJECT-TYPE
        SYNTAX  INTEGER (1..128)
        ACCESS  read-only
        STATUS  mandatory
        DESCRIPTION
                "The number of bytes to extract from the cookie value." 
        ::= { slbCurCfgVirtualServerEntry 8 }

slbCurCfgVirtServerUriCookie OBJECT-TYPE 
        SYNTAX  INTEGER {
		enabled(1),
		disabled(2)
		}
        ACCESS  read-only 
        STATUS  mandatory 
        DESCRIPTION 
                "Enable or disable cookie search in URI"  
        ::= { slbCurCfgVirtualServerEntry 9 }


slbCurCfgVirtServerFtpParsing OBJECT-TYPE
	SYNTAX	INTEGER {
		enabled(1),
		disabled(2)
		}
	ACCESS	read-only
	STATUS	mandatory
	DESCRIPTION
		"Enable or Disable the ftp parsing for the virtual server."
	::= { slbCurCfgVirtualServerEntry 10 }

slbCurCfgVirtServerUrlHashLen OBJECT-TYPE
        SYNTAX  INTEGER (0..255)
        ACCESS  read-only
        STATUS  mandatory
        DESCRIPTION
                "The number of bytes used to hash onto server, A zero means
                 URL hashing disabled."
        ::= { slbCurCfgVirtualServerEntry 11 }

slbCurCfgVirtServerHttpHdrName OBJECT-TYPE
        SYNTAX  DisplayString (SIZE(0..32))
        ACCESS  read-only
        STATUS  mandatory
        DESCRIPTION
                "The HTTP header name of the virtual server."
        ::= { slbCurCfgVirtualServerEntry 12 }

slbCurCfgVirtServerBwmContract OBJECT-TYPE
        SYNTAX  INTEGER
        ACCESS  read-only
        STATUS  mandatory
        DESCRIPTION
                "The default BW contract of virtual server."
        ::= { slbCurCfgVirtualServerEntry 13 }

-- Server load balancing - Virtual Server Table

slbNewCfgVirtServerTable OBJECT-TYPE
        SYNTAX  SEQUENCE OF SlbNewCfgVirtualServerEntry
        ACCESS  not-accessible
        STATUS  mandatory
        DESCRIPTION
                "The table of virtual Servers."
        ::= { serverloadbalance 6 }
 

slbNewCfgVirtualServerEntry OBJECT-TYPE
        SYNTAX  SlbNewCfgVirtualServerEntry
        ACCESS  not-accessible
        STATUS  mandatory
        DESCRIPTION
                "A row in the virtual server table."
        INDEX   { slbNewCfgVirtServerIndex }
        ::= { slbNewCfgVirtServerTable 1 }
 
SlbNewCfgVirtualServerEntry ::= SEQUENCE {
        slbNewCfgVirtServerIndex     		INTEGER,
        slbNewCfgVirtServerIpAddress 		IpAddress,
        slbNewCfgVirtServerLayer3Only    	INTEGER,
        slbNewCfgVirtServerState     		INTEGER,
        slbNewCfgVirtServerDelete     		INTEGER,
        slbNewCfgVirtServerDname     		DisplayString,
        slbNewCfgVirtServerCname                DisplayString,
        slbNewCfgVirtServerCoffset              INTEGER,
        slbNewCfgVirtServerClength              INTEGER, 
        slbNewCfgVirtServerUriCookie            INTEGER,
	slbNewCfgVirtServerFtpParsing		INTEGER,
        slbNewCfgVirtServerUrlHashLen           INTEGER,
        slbNewCfgVirtServerHttpHdrName          DisplayString,
	slbNewCfgVirtServerBwmContract		INTEGER
        }

slbNewCfgVirtServerIndex OBJECT-TYPE
        SYNTAX  INTEGER
        ACCESS  read-only
        STATUS  mandatory
        DESCRIPTION
                "Virtual Server Number" 
        ::= { slbNewCfgVirtualServerEntry 1 }

slbNewCfgVirtServerIpAddress OBJECT-TYPE
        SYNTAX  IpAddress
        ACCESS  read-write
        STATUS  mandatory
        DESCRIPTION
                "IP address of the virtual server." 
        ::= { slbNewCfgVirtualServerEntry 2 }

slbNewCfgVirtServerLayer3Only OBJECT-TYPE 
        SYNTAX  INTEGER {
		layer3Only(1),
		disabled(2)
		}
        ACCESS  read-write 
        STATUS  mandatory 
        DESCRIPTION 
                "Enable or disable layer3 only balancing."  
        ::= { slbNewCfgVirtualServerEntry 3 }

slbNewCfgVirtServerState OBJECT-TYPE 
        SYNTAX  INTEGER {
		other(1),
		enabled(2),
		disabled(3)
		}
        ACCESS  read-write 
        STATUS  mandatory 
        DESCRIPTION 
                "Enable or disable the virtual server."  
        ::= { slbNewCfgVirtualServerEntry 4 }


slbNewCfgVirtServerDelete OBJECT-TYPE
        SYNTAX  INTEGER {
                other(1),
                delete(2)
                }
        ACCESS  read-write
        STATUS  mandatory
        DESCRIPTION
                "By setting the value to delete(2), the entire row is
                 deleted."
        ::= { slbNewCfgVirtualServerEntry 5 }

slbNewCfgVirtServerDname OBJECT-TYPE 
        SYNTAX  DisplayString (SIZE(0..34))
        ACCESS  read-write 
        STATUS  mandatory 
        DESCRIPTION 
                "The domain name of the virtual server."  
        ::= { slbNewCfgVirtualServerEntry 6 }

slbNewCfgVirtServerCname OBJECT-TYPE 
        SYNTAX  DisplayString (SIZE(0..16))
        ACCESS  read-write 
        STATUS  mandatory 
        DESCRIPTION 
                "The cookie name of the virtual server used for cookie load balance."  
        ::= { slbNewCfgVirtualServerEntry 7 }

slbNewCfgVirtServerCoffset OBJECT-TYPE
        SYNTAX  INTEGER (1..128)
        ACCESS  read-write 
        STATUS  mandatory
        DESCRIPTION
                "The starting byte offset of the cookie value." 
        ::= { slbNewCfgVirtualServerEntry 8 }

slbNewCfgVirtServerClength OBJECT-TYPE
        SYNTAX  INTEGER (1..128)
        ACCESS  read-write
        STATUS  mandatory
        DESCRIPTION
                "The number of bytes to extract from the cookie value." 
        ::= { slbNewCfgVirtualServerEntry 9 }

slbNewCfgVirtServerUriCookie OBJECT-TYPE 
        SYNTAX  INTEGER {
		enabled(1),
		disabled(2)
		}
        ACCESS  read-write 
        STATUS  mandatory 
        DESCRIPTION 
                "Enable or disable cookie search in URI"  
        ::= { slbNewCfgVirtualServerEntry 10}


slbNewCfgVirtServerFtpParsing OBJECT-TYPE
	SYNTAX	INTEGER {
		enabled(1),
		disabled(2)
		}
	ACCESS	read-write
	STATUS	mandatory
	DESCRIPTION
		"Enable or Disable the ftp parsing for the virtual server."
	::= { slbNewCfgVirtualServerEntry 11 }

slbNewCfgVirtServerUrlHashLen OBJECT-TYPE 
        SYNTAX  INTEGER (0..255)
        ACCESS  read-write 
        STATUS  mandatory 
        DESCRIPTION 
                "The number of bytes used to hash onto server, A zero means
                 URL hashing disabled."
        ::= { slbNewCfgVirtualServerEntry 12}

slbNewCfgVirtServerHttpHdrName OBJECT-TYPE 
        SYNTAX  DisplayString  (SIZE(0..32))
        ACCESS  read-write 
        STATUS  mandatory 
        DESCRIPTION 
                "The HTTP header name of the virtual server."
        ::= { slbNewCfgVirtualServerEntry 13}

slbNewCfgVirtServerBwmContract OBJECT-TYPE 
        SYNTAX  INTEGER
        ACCESS  read-write 
        STATUS  mandatory 
        DESCRIPTION 
                "The default BW contract number of the virtual server."
        ::= { slbNewCfgVirtualServerEntry 14}


-- Server load balancing - Virtual Services Table 

slbCurCfgVirtServicesTable OBJECT-TYPE
        SYNTAX  SEQUENCE OF SlbCurCfgVirtServicesEntry
        ACCESS  not-accessible
        STATUS  mandatory
        DESCRIPTION
                "The table of virtual Services."
        ::= { serverloadbalance 7 }

slbCurCfgVirtServicesEntry OBJECT-TYPE
        SYNTAX  SlbCurCfgVirtServicesEntry
        ACCESS  not-accessible
        STATUS  mandatory
        DESCRIPTION
                "A row in the virtual services table."

        INDEX   { slbCurCfgVirtServIndex, slbCurCfgVirtServiceIndex }
        ::= { slbCurCfgVirtServicesTable 1 }

SlbCurCfgVirtServicesEntry ::= SEQUENCE {
	slbCurCfgVirtServIndex         INTEGER,
        slbCurCfgVirtServiceIndex      INTEGER,
        slbCurCfgVirtServiceVirtPort   INTEGER,
        slbCurCfgVirtServiceRealGroup  INTEGER,
        slbCurCfgVirtServiceRealPort   INTEGER,
        slbCurCfgVirtServiceUDPBalance INTEGER,
        slbCurCfgVirtServicePBind      INTEGER,
        slbCurCfgVirtServiceHname      DisplayString,
        slbCurCfgVirtServiceHttpSlb    INTEGER,
	slbCurCfgVirtServiceBwmContract   INTEGER,
	slbCurCfgVirtServiceDirServerRtn  INTEGER
        }

slbCurCfgVirtServIndex OBJECT-TYPE
        SYNTAX  INTEGER
        ACCESS  read-only
        STATUS  mandatory
        DESCRIPTION
                "The number of the virtual server." 
        ::= { slbCurCfgVirtServicesEntry 1 }

slbCurCfgVirtServiceIndex OBJECT-TYPE 
        SYNTAX  INTEGER 
        ACCESS  read-only 
        STATUS  mandatory 
        DESCRIPTION 
                "The service index. This has no external meaning" 
        ::= { slbCurCfgVirtServicesEntry 2 }

slbCurCfgVirtServiceVirtPort OBJECT-TYPE  
        SYNTAX  INTEGER  
        ACCESS  read-only  
        STATUS  mandatory  
        DESCRIPTION 
                "The layer4 virtual port number of the service."  
        ::= { slbCurCfgVirtServicesEntry 3 } 

slbCurCfgVirtServiceRealGroup OBJECT-TYPE   
        SYNTAX  INTEGER   
        ACCESS  read-only   
        STATUS  mandatory   
        DESCRIPTION 
                "The real server group number for this service."   
        ::= { slbCurCfgVirtServicesEntry 4 }

slbCurCfgVirtServiceRealPort OBJECT-TYPE   
        SYNTAX  INTEGER   
        ACCESS  read-only   
        STATUS  mandatory   
        DESCRIPTION 
                "The layer4 real port number of the service."   
        ::= { slbCurCfgVirtServicesEntry 5 }

slbCurCfgVirtServiceUDPBalance OBJECT-TYPE   
        SYNTAX  INTEGER    {
		other(1),
		enabled(2),
		disabled(3),
		stateless(4)
		}
        ACCESS  read-only   
        STATUS  mandatory   
        DESCRIPTION 
                "Enable, disable or stateless the UDP balancing for 
		 the virtual port."   
        ::= { slbCurCfgVirtServicesEntry 6 }

slbCurCfgVirtServicePBind OBJECT-TYPE   
        SYNTAX  INTEGER   {
		other(1),
		enabled(2),
		disabled(3),
		sessid(4),
                cookie(5)
		}
        ACCESS  read-only   
        STATUS  mandatory   
        DESCRIPTION 
                "Enable or disable persistent bindings for the virtual port."   
        ::= { slbCurCfgVirtServicesEntry 7 }

slbCurCfgVirtServiceHname OBJECT-TYPE 
        SYNTAX  DisplayString (SIZE(0..10))
        ACCESS  read-only 
        STATUS  mandatory 
        DESCRIPTION 
                "The host name of the virtual service."  
        ::= { slbCurCfgVirtServicesEntry 8 }

slbCurCfgVirtServiceHttpSlb OBJECT-TYPE   
        SYNTAX  INTEGER   {
		disabled(1),
		urlslb(2),
                urlhash(3),
                cookie(4),
                host(5),
                browser(6),
                others(7) 
		}
        ACCESS  read-only   
        STATUS  mandatory   
        DESCRIPTION 
                "Select HTTP server loadbalancing for the virtual port."   
        ::= { slbCurCfgVirtServicesEntry 9 }

slbCurCfgVirtServiceBwmContract OBJECT-TYPE   
        SYNTAX  INTEGER   
        ACCESS  read-only   
        STATUS  mandatory   
        DESCRIPTION 
                "The BWM contract number for this service."   
        ::= { slbCurCfgVirtServicesEntry 10 }

slbCurCfgVirtServiceDirServerRtn OBJECT-TYPE   
        SYNTAX  INTEGER   {
		enabled(1),
		disabled(2)
		}
        ACCESS  read-only   
        STATUS  mandatory   
        DESCRIPTION 
                "Enable or disable direct server return feature.  To 
		 translate only MAC addresses in performing server load 
                 balancing when enabled.  This allow servers to return
		 directly to client since IP addresses have not been 
		 changed."
        ::= { slbCurCfgVirtServicesEntry 11 }

-- Server load balancing - Virtual Services Table 

slbNewCfgVirtServicesTable OBJECT-TYPE
        SYNTAX  SEQUENCE OF SlbNewCfgVirtServicesEntry
        ACCESS  not-accessible
        STATUS  mandatory
        DESCRIPTION
                "The table of virtual Services."
        ::= { serverloadbalance 8 }

slbNewCfgVirtServicesEntry OBJECT-TYPE
        SYNTAX  SlbNewCfgVirtServicesEntry
        ACCESS  not-accessible
        STATUS  mandatory
        DESCRIPTION
                "A row in the virtual services table."

        INDEX   { slbNewCfgVirtServIndex, slbNewCfgVirtServiceIndex }
        ::= { slbNewCfgVirtServicesTable 1 }

SlbNewCfgVirtServicesEntry ::= SEQUENCE {
	slbNewCfgVirtServIndex         INTEGER,
        slbNewCfgVirtServiceIndex      INTEGER,
        slbNewCfgVirtServiceVirtPort   INTEGER,
        slbNewCfgVirtServiceRealGroup  INTEGER,
        slbNewCfgVirtServiceRealPort   INTEGER,
        slbNewCfgVirtServiceUDPBalance INTEGER,
        slbNewCfgVirtServicePBind      INTEGER,
        slbNewCfgVirtServiceHname      DisplayString,
        slbNewCfgVirtServiceHttpSlb    INTEGER,
	slbNewCfgVirtServiceBwmContract   INTEGER,
	slbNewCfgVirtServiceDirServerRtn  INTEGER,
	slbNewCfgVirtServiceDelete     INTEGER
        }

slbNewCfgVirtServIndex OBJECT-TYPE
        SYNTAX  INTEGER
        ACCESS  read-only
        STATUS  mandatory
        DESCRIPTION
                "The number of the virtual server." 
        ::= { slbNewCfgVirtServicesEntry 1 }

slbNewCfgVirtServiceIndex OBJECT-TYPE 
        SYNTAX  INTEGER 
        ACCESS  read-only 
        STATUS  mandatory 
        DESCRIPTION 
                "The service index. This has no external meaning" 
        ::= { slbNewCfgVirtServicesEntry 2 }

slbNewCfgVirtServiceVirtPort OBJECT-TYPE  
        SYNTAX  INTEGER  
        ACCESS  read-write  
        STATUS  mandatory  
        DESCRIPTION 
                "The layer4 virtual port number of the service."  
        ::= { slbNewCfgVirtServicesEntry 3 } 

slbNewCfgVirtServiceRealGroup OBJECT-TYPE   
        SYNTAX  INTEGER   
        ACCESS  read-write   
        STATUS  mandatory   
        DESCRIPTION 
                "The real server group number for this service."   
        ::= { slbNewCfgVirtServicesEntry 4 }

slbNewCfgVirtServiceRealPort OBJECT-TYPE   
        SYNTAX  INTEGER   
        ACCESS  read-write   
        STATUS  mandatory   
        DESCRIPTION 
                "The layer4 real port number of the service."   
        ::= { slbNewCfgVirtServicesEntry 5 }

slbNewCfgVirtServiceUDPBalance OBJECT-TYPE   
        SYNTAX  INTEGER    {
		other(1),
		enabled(2),
		disabled(3),
		stateless(4)
		}
        ACCESS  read-write   
        STATUS  mandatory   
        DESCRIPTION 
                "Enable, disable or stateless the UDP balancing for the virtual port."   
        ::= { slbNewCfgVirtServicesEntry 6 }

slbNewCfgVirtServicePBind OBJECT-TYPE   
        SYNTAX  INTEGER   {
		other(1),
		enabled(2),
		disabled(3),
		sessid(4),
                cookie(5)
		}
        ACCESS  read-write   
        STATUS  mandatory   
        DESCRIPTION 
                "Enable or disable persistent bindings for the virtual port."   
        ::= { slbNewCfgVirtServicesEntry 7 }

slbNewCfgVirtServiceHname OBJECT-TYPE 
        SYNTAX  DisplayString (SIZE(0..10))
        ACCESS  read-write 
        STATUS  mandatory 
        DESCRIPTION 
                "The host name of the virtual service."  
        ::= { slbNewCfgVirtServicesEntry 8 }

slbNewCfgVirtServiceHttpSlb OBJECT-TYPE   
        SYNTAX  INTEGER   {
		disabled(1),
                urlslb(2),
                urlhash(3),
                cookie(4),
                host(5),
                browser(6),
                others(7)
		}
        ACCESS  read-write   
        STATUS  mandatory   
        DESCRIPTION 
                "Select HTTP server loadbalancing for the virtual port."   
        ::= { slbNewCfgVirtServicesEntry 9 }

slbNewCfgVirtServiceBwmContract OBJECT-TYPE   
        SYNTAX  INTEGER   
        ACCESS  read-write
	STATUS  mandatory   
        DESCRIPTION 
                "The BWM contract number for this service."   
        ::= { slbNewCfgVirtServicesEntry 10 }

slbNewCfgVirtServiceDirServerRtn OBJECT-TYPE
        SYNTAX  INTEGER   {
                enabled(1),
                disabled(2)
                }
        ACCESS  read-write
        STATUS  mandatory   
        DESCRIPTION 
                "Enable or disable direct server return feature.  To 
                 translate only MAC addresses in performing server load 
                 balancing when enabled.  This allow servers to return
                 directly to client since IP addresses have not been 
                 changed."
        ::= { slbNewCfgVirtServicesEntry 11 }

slbNewCfgVirtServiceDelete OBJECT-TYPE
      SYNTAX  INTEGER {
                other(1),
                delete(2)
                }
      ACCESS  read-write
      STATUS  mandatory
      DESCRIPTION
              "When set to the value of 2 (delete), the entire row
               is deleted. When read, other(1) is returned. Setting the value
               to anything other than 2(delete) has no effect on the state
               of the row."
      ::= { slbNewCfgVirtServicesEntry 12 }


-- Server load balancing - Group Table

slbGroupTableMaxSize OBJECT-TYPE
        SYNTAX  INTEGER
        ACCESS  read-only
        STATUS  mandatory
        DESCRIPTION
                "The maximum number of entries in slbCurCfgGroupTable."
        ::= { serverloadbalance 9 }

slbCurCfgGroupTable OBJECT-TYPE
        SYNTAX  SEQUENCE OF SlbCurCfgGroupEntry
        ACCESS  not-accessible
        STATUS  mandatory
        DESCRIPTION
                "The table of groups"
        ::= { serverloadbalance 10 }

slbCurCfgGroupEntry OBJECT-TYPE
        SYNTAX  SlbCurCfgGroupEntry
        ACCESS  not-accessible
        STATUS  mandatory
        DESCRIPTION
                "A row in the slbCurCfgGroupTable "
        INDEX   { slbCurCfgGroupIndex }
        ::= { slbCurCfgGroupTable 1 }

SlbCurCfgGroupEntry ::= SEQUENCE {
        slbCurCfgGroupIndex            INTEGER,
        slbCurCfgGroupRealServers      OCTET STRING,
        slbCurCfgGroupMetric           INTEGER,
        slbCurCfgGroupBackupServer     INTEGER,
        slbCurCfgGroupHealthCheckUrl   DisplayString,
        slbCurCfgGroupHealthCheckLayer INTEGER,
        slbCurCfgGroupName             DisplayString,
	slbCurCfgGroupRealThreshold    INTEGER,
        slbCurCfgGroupBackupGroup      INTEGER
        }

slbCurCfgGroupIndex OBJECT-TYPE
        SYNTAX  INTEGER
        ACCESS  read-only
        STATUS  mandatory
        DESCRIPTION
                "The group number for which the information pertains."
        ::= { slbCurCfgGroupEntry 1 }

slbCurCfgGroupRealServers    OBJECT-TYPE
        SYNTAX  OCTET STRING (SIZE(0..64))
        ACCESS  read-only
        STATUS  mandatory
        DESCRIPTION
                "The Real servers in the group.  The servers are presented
                 in bitmap format.

                 in receiving order:

		   OCTET 1  OCTET 2  .....
                   xxxxxxxx xxxxxxxx ..... 
                   |     || |_ server 9
                   |     ||  
                   |     ||___ server 8
                   |     |____ server 7
                   |       .    .   .
                   |__________ server 1
 
                 where x : 1 - The represented server belongs to the group
                           0 - The represented server does not belong to
                               the group"
	::= { slbCurCfgGroupEntry 2 }

slbCurCfgGroupMetric OBJECT-TYPE
        SYNTAX  INTEGER {
		roundRobin(1),
		leastConnections(2),
		minMisses(3),
		hash(4)
		}
        ACCESS  read-only
        STATUS  mandatory
        DESCRIPTION
                "The metric used to select next server in group."
        ::= { slbCurCfgGroupEntry 3 }

slbCurCfgGroupBackupServer OBJECT-TYPE
        SYNTAX INTEGER {
            none(0)
        }
        ACCESS  read-only
        STATUS  mandatory
        DESCRIPTION
                "The backup real server for this group."
        ::= { slbCurCfgGroupEntry 4 }

slbCurCfgGroupHealthCheckUrl OBJECT-TYPE
        SYNTAX  DisplayString (SIZE(0..32))
        ACCESS  read-only
        STATUS  mandatory
        DESCRIPTION
                "The URL used to verify HTTP content availability for 
		 the real servers of this group."

        ::= { slbCurCfgGroupEntry 5 }

slbCurCfgGroupHealthCheckLayer OBJECT-TYPE
        SYNTAX  INTEGER {
		icmp(1),
		tcp(2),
		http(3),
		dns(4),
		smtp(5),
		pop3(6),
		nntp(7),
		ftp(8),
		imap(9),
		radius(10),
		sslh(11),
		script1(12),
		script2(13),
		script3(14),
		script4(15),
		script5(16),
		script6(17),
		script7(18),
		script8(19)
		}
        ACCESS  read-only
        STATUS  mandatory
        DESCRIPTION
                "The OSI layer at which servers are health checked."
        ::= { slbCurCfgGroupEntry 6 }

slbCurCfgGroupName OBJECT-TYPE 
        SYNTAX  DisplayString (SIZE(0..15))
        ACCESS  read-only 
        STATUS  mandatory 
        DESCRIPTION 
                "The name of the real server group."  
        ::= { slbCurCfgGroupEntry 7 }

slbCurCfgGroupRealThreshold OBJECT-TYPE 
        SYNTAX  INTEGER (0..15)
        ACCESS  read-only 
        STATUS  mandatory 
        DESCRIPTION 
                "The server failure syslog threshold of the real server group."  
        ::= { slbCurCfgGroupEntry 8 }

slbCurCfgGroupBackupGroup OBJECT-TYPE
        SYNTAX INTEGER {
            none(0)
        }
        ACCESS  read-only
        STATUS  mandatory
        DESCRIPTION
                "The backup real server group for this group."
        ::= { slbCurCfgGroupEntry 9 }

-- Server load balancing - Group Table - New Configuration

slbNewCfgGroupTable OBJECT-TYPE
        SYNTAX  SEQUENCE OF SlbNewCfgGroupEntry
        ACCESS  not-accessible
        STATUS  mandatory
        DESCRIPTION
                "The table of groups"
        ::= { serverloadbalance 11 }

slbNewCfgGroupEntry OBJECT-TYPE
        SYNTAX  SlbNewCfgGroupEntry
        ACCESS  not-accessible
        STATUS  mandatory
        DESCRIPTION
                "A row in the slbNewCfgGroupTable "
        INDEX   { slbNewCfgGroupIndex }
        ::= { slbNewCfgGroupTable 1 }

SlbNewCfgGroupEntry ::= SEQUENCE {
        slbNewCfgGroupIndex            	INTEGER,
        slbNewCfgGroupRealServers      	OCTET STRING,
        slbNewCfgGroupAddServer        	INTEGER,
        slbNewCfgGroupRemoveServer     	INTEGER,
        slbNewCfgGroupMetric           	INTEGER,
        slbNewCfgGroupBackupServer     	INTEGER,
        slbNewCfgGroupDelete     	INTEGER,
        slbNewCfgGroupHealthCheckUrl    DisplayString,
        slbNewCfgGroupHealthCheckLayer  INTEGER,
        slbNewCfgGroupName              DisplayString,
	slbNewCfgGroupRealThreshold	INTEGER,
        slbNewCfgGroupBackupGroup	INTEGER
        }

slbNewCfgGroupIndex OBJECT-TYPE
        SYNTAX  INTEGER
        ACCESS  read-only
        STATUS  mandatory
        DESCRIPTION
                "The group number for which the information pertains."
        ::= { slbNewCfgGroupEntry 1 }

slbNewCfgGroupRealServers    OBJECT-TYPE
        SYNTAX  OCTET STRING (SIZE(0..64))
        ACCESS  read-only
        STATUS  mandatory
        DESCRIPTION
                "The Real servers in the group.  The servers are presented
                 in bitmap format.

                 in receiving order:

		   OCTET 1  OCTET 2  .....
                   xxxxxxxx xxxxxxxx ..... 
                   |     || |_ server 9
                   |     ||  
                   |     ||___ server 8
                   |     |____ server 7
                   |       .    .   .
                   |__________ server 1
 
                 where x : 1 - The represented server belongs to the group
                           0 - The represented server does not belong to
                               the group"
	::= { slbNewCfgGroupEntry 2 }


slbNewCfgGroupAddServer OBJECT-TYPE
        SYNTAX  INTEGER
        ACCESS  read-write
        STATUS  mandatory
        DESCRIPTION
                "The real server to be added to the group. When read,
		 0 is returned."
        ::= { slbNewCfgGroupEntry 3 }

slbNewCfgGroupRemoveServer OBJECT-TYPE 
        SYNTAX  INTEGER 
        ACCESS  read-write 
        STATUS  mandatory
        DESCRIPTION
                "The real server to be removed from the group. When read,
        	 0 is returned."
        ::= { slbNewCfgGroupEntry 4 }

slbNewCfgGroupMetric OBJECT-TYPE
        SYNTAX  INTEGER {  
		roundRobin(1),
		leastConnections(2),
		minMisses(3),
		hash(4)
        	}
        ACCESS  read-write
        STATUS  mandatory
        DESCRIPTION
                "The metric used to select next server in group."
        ::= { slbNewCfgGroupEntry 5 }

slbNewCfgGroupBackupServer OBJECT-TYPE
        SYNTAX INTEGER {
            none(0)
        }
        ACCESS  read-write
        STATUS  mandatory
        DESCRIPTION
                "The backup real server for this group."
        ::= { slbNewCfgGroupEntry 6 }

slbNewCfgGroupDelete OBJECT-TYPE
        SYNTAX  INTEGER {
		other(1),
		delete(2)
		}
        ACCESS  read-write
        STATUS  mandatory
        DESCRIPTION
                "By setting the value to delete(2), the entire group is 
		 deleted."
        ::= { slbNewCfgGroupEntry 7 }

slbNewCfgGroupHealthCheckUrl OBJECT-TYPE
        SYNTAX  DisplayString (SIZE(0..32))
        ACCESS  read-write
        STATUS  mandatory
        DESCRIPTION
                "The URL for health check among the real servers of this 
		 group."
        ::= { slbNewCfgGroupEntry 8 }

slbNewCfgGroupHealthCheckLayer OBJECT-TYPE
        SYNTAX  INTEGER {
		icmp(1),
		tcp(2),
		http(3),
		dns(4),
		smtp(5),
		pop3(6),
		nntp(7),
		ftp(8),
		imap(9),
		radius(10),
		sslh(11),
		script1(12),
		script2(13),
		script3(14),
		script4(15),
		script5(16),
		script6(17),
		script7(18),
		script8(19)
		}
        ACCESS  read-write
        STATUS  mandatory
        DESCRIPTION
                "The OSI layer at which servers are health checked."
        ::= { slbNewCfgGroupEntry 9 }

slbNewCfgGroupName OBJECT-TYPE 
        SYNTAX  DisplayString (SIZE(0..15))
        ACCESS  read-write 
        STATUS  mandatory 
        DESCRIPTION 
                "The name of the real server group."  
        ::= { slbNewCfgGroupEntry 10 }

slbNewCfgGroupRealThreshold OBJECT-TYPE 
        SYNTAX  INTEGER (0..15)
        ACCESS  read-write 
        STATUS  mandatory 
        DESCRIPTION 
                "The server failure syslog threshold of the real server group."  
        ::= { slbNewCfgGroupEntry 11 }

slbNewCfgGroupBackupGroup OBJECT-TYPE
        SYNTAX INTEGER {
            none(0)
        }
        ACCESS  read-write
        STATUS  mandatory
        DESCRIPTION
                "The backup real server group for this group."
        ::= { slbNewCfgGroupEntry 12 }


-- Server load balancing - slb port state table

slbCurCfgPortTable OBJECT-TYPE
        SYNTAX  SEQUENCE OF SlbCurCfgPortEntry
        ACCESS  not-accessible
        STATUS  mandatory
        DESCRIPTION
                "The table of ports and their SLB states"
        ::= { serverloadbalance 12 }

slbCurCfgPortEntry OBJECT-TYPE
        SYNTAX  SlbCurCfgPortEntry
        ACCESS  not-accessible
        STATUS  mandatory
        DESCRIPTION
                "A row in the slbPortTable "
        INDEX   { slbCurCfgPortIndex }
        ::= { slbCurCfgPortTable 1 }

SlbCurCfgPortEntry ::= SEQUENCE {
        slbCurCfgPortIndex              INTEGER,
        slbCurCfgPortProxyIpAddr        IpAddress,
        slbCurCfgPortSlbPipState        INTEGER,
        slbCurCfgPortSlbState           INTEGER,
        slbCurCfgPortSlbHotStandby      INTEGER,
        slbCurCfgPortSlbInterSwitch     INTEGER
        }

slbCurCfgPortIndex OBJECT-TYPE
        SYNTAX  INTEGER
        ACCESS  read-only
        STATUS  mandatory
        DESCRIPTION
                "The port number for which the SLB information pertains." 
        ::= { slbCurCfgPortEntry 1 }

slbCurCfgPortProxyIpAddr OBJECT-TYPE
        SYNTAX  IpAddress
        ACCESS  read-only 
        STATUS  mandatory
        DESCRIPTION
                "The proxy IP address of the interface."
        ::= { slbCurCfgPortEntry 2 }

slbCurCfgPortSlbState OBJECT-TYPE
        SYNTAX  INTEGER {
		none(1),
		client(2),
		server(3),
		client-server(4),
		failOver(5),
		failOver-stanby(6)
		}
        ACCESS  read-only
        STATUS  mandatory
        DESCRIPTION
                "The SLB state of the port.
		 none(1)            - not SLB port
		 client(2)          - SLB client port
		 server(3)          - SLB server port
		 client-server(4)   - SLB client and server port
		 FailOver(5)        - SLB fail over port
		 failOver-stanby(6) - SLB fail port operating as standby
                                      (a read-only state)"
        ::= { slbCurCfgPortEntry 3 }

slbCurCfgPortSlbHotStandby OBJECT-TYPE
        SYNTAX  INTEGER   {
                enabled(1),
                disabled(2)
                }
        ACCESS  read-only
        STATUS  mandatory
        DESCRIPTION
                "Enable or disable hot standby processing on the switch port."
        ::= { slbCurCfgPortEntry 4 }

slbCurCfgPortSlbInterSwitch OBJECT-TYPE
        SYNTAX  INTEGER   {
                enabled(1),
                disabled(2)
                }
        ACCESS  read-only
        STATUS  mandatory
        DESCRIPTION
                "Enable or disable inter-switch processing on the switch port."
        ::= { slbCurCfgPortEntry 5 }

slbCurCfgPortSlbPipState OBJECT-TYPE
        SYNTAX  INTEGER   {
                enabled(1),
                disabled(2)
                }
        ACCESS  read-only
        STATUS  mandatory
        DESCRIPTION
                "Enable or disable use of proxy IP address on the switch port."
        ::= { slbCurCfgPortEntry 6 }


-- Server load balancing - slb port state table

slbNewCfgPortTable OBJECT-TYPE
        SYNTAX  SEQUENCE OF SlbNewCfgPortEntry
        ACCESS  not-accessible
        STATUS  mandatory
        DESCRIPTION
                "The table of ports and their SLB states"
        ::= { serverloadbalance 13 }

slbNewCfgPortEntry OBJECT-TYPE
        SYNTAX  SlbNewCfgPortEntry
        ACCESS  not-accessible
        STATUS  mandatory
        DESCRIPTION
                "A row in the slbPortTable "
        INDEX   { slbNewCfgPortIndex }
        ::= { slbNewCfgPortTable 1 }

SlbNewCfgPortEntry ::= SEQUENCE {
        slbNewCfgPortIndex              INTEGER,
        slbNewCfgPortProxyIpAddr        IpAddress,
        slbNewCfgPortSlbPipState        INTEGER,
        slbNewCfgPortSlbState           INTEGER,
        slbNewCfgPortSlbHotStandby      INTEGER,
        slbNewCfgPortSlbInterSwitch     INTEGER
        }

slbNewCfgPortIndex OBJECT-TYPE
        SYNTAX  INTEGER
        ACCESS  read-only
        STATUS  mandatory
        DESCRIPTION
                "The port number for which the SLB information pertains." 
        ::= { slbNewCfgPortEntry 1 }

slbNewCfgPortProxyIpAddr OBJECT-TYPE 
        SYNTAX  IpAddress 
        ACCESS  read-write 
        STATUS  mandatory 
        DESCRIPTION 
                "The proxy IP address of the interface." 
        ::= { slbNewCfgPortEntry 2 }

slbNewCfgPortSlbState OBJECT-TYPE
        SYNTAX  INTEGER {
		none(1),
		client(2),
		server(3),
		client-server(4),
		failOver(5),
		failOver-stanby(6)
		}
        ACCESS  read-write
        STATUS  mandatory
        DESCRIPTION
                "The SLB state of the port.
		 none(1)            - not SLB port
		 client(2)          - SLB client port
		 server(3)          - SLB server port
		 client-server(4)   - SLB client and server port
		 FailOver(5)        - SLB fail over port
		 failOver-stanby(6) - SLB fail port operating as standby
                                      (a read-only state)"
        ::= { slbNewCfgPortEntry 3 }

slbNewCfgPortSlbHotStandby OBJECT-TYPE
        SYNTAX  INTEGER   {
                enabled(1),
                disabled(2)
                }
        ACCESS  read-write
        STATUS  mandatory
        DESCRIPTION
                "Enable or disable hot standby processing on the switch port."
        ::= { slbNewCfgPortEntry 4 }

slbNewCfgPortSlbInterSwitch OBJECT-TYPE
        SYNTAX  INTEGER   {
                enabled(1),
                disabled(2)
                }
        ACCESS  read-write
        STATUS  mandatory
        DESCRIPTION
                "Enable or disable inter-switch processing on the switch port."
        ::= { slbNewCfgPortEntry 5 }

slbNewCfgPortSlbPipState OBJECT-TYPE
        SYNTAX  INTEGER   {
                enabled(1),
                disabled(2)
                }
        ACCESS  read-write
        STATUS  mandatory
        DESCRIPTION
                "Enable or disable use of proxy IP address on the switch port."
        ::= { slbNewCfgPortEntry 6 }

slbCurCfgImask OBJECT-TYPE
        SYNTAX  IpAddress
        ACCESS  read-only
        STATUS  mandatory
        DESCRIPTION
                "The virtual and real IP address mask - corresponding to the
		 imask command of the slb configuration menu." 
        ::= { serverloadbalance 14 }

slbNewCfgImask OBJECT-TYPE
        SYNTAX  IpAddress
        ACCESS  read-write
        STATUS  mandatory
        DESCRIPTION
                "The virtual and real IP address mask - corresponding to the
                 imask command of the slb configuration menu."
        ::= { serverloadbalance 15 }

slbCurCfgMnet OBJECT-TYPE
        SYNTAX  IpAddress
        ACCESS  read-only
        STATUS  mandatory
        DESCRIPTION
                "The management network - corresponding to the
		 mnet command of the slb configuration menu." 
        ::= { serverloadbalance 19 }

slbNewCfgMnet OBJECT-TYPE
        SYNTAX  IpAddress
        ACCESS  read-write
        STATUS  mandatory
        DESCRIPTION
                "The management network - corresponding to the
		 mnet command of the slb configuration menu." 
        ::= { serverloadbalance 20 }

slbCurCfgMmask OBJECT-TYPE
        SYNTAX  IpAddress
        ACCESS  read-only
        STATUS  mandatory
        DESCRIPTION
                "The management subnet mask - corresponding to the
		 mmask command of the slb configuration menu." 
        ::= { serverloadbalance 21 }

slbNewCfgMmask OBJECT-TYPE
        SYNTAX  IpAddress
        ACCESS  read-write
        STATUS  mandatory
        DESCRIPTION
                "The management subnet mask - corresponding to the
		 mmask command of the slb configuration menu." 
        ::= { serverloadbalance 22 }

slbCurCfgRadiusAuthenString OBJECT-TYPE
        SYNTAX  DisplayString (SIZE(0..32))
        ACCESS  read-only
        STATUS  mandatory
        DESCRIPTION
                "The RADIUS authentication string.  The string is used for 
		 generating encrypted authentication string for RADIUS health 
		 check."
        ::= { serverloadbalance 23 }

slbNewCfgRadiusAuthenString OBJECT-TYPE
        SYNTAX  DisplayString (SIZE(0..32))
        ACCESS  read-write
        STATUS  mandatory
        DESCRIPTION
                "The RADIUS authentication string.  The string is used for 
		 generating encrypted authentication string for RADIUS health 
		 check."
        ::= { serverloadbalance 24 }

slbCurCfgDirectMode OBJECT-TYPE
        SYNTAX  INTEGER {
                enabled(1),
                disabled(2)
                }
        ACCESS  read-only
        STATUS  mandatory
        DESCRIPTION
                "Enable or disable direct access mode.  It allows direct
		 access to real servers and any combination of virtual
		 and real servers when set to enabled(1)."
        ::= { serverloadbalance 25 }

slbNewCfgDirectMode OBJECT-TYPE
        SYNTAX  INTEGER {
                enabled(1),
                disabled(2)
                }
        ACCESS  read-write
        STATUS  mandatory
        DESCRIPTION
                "Enable or disable direct access mode.  It allows direct
		 access to real servers and any combination of virtual
		 and real servers when set to enabled(1)."
        ::= { serverloadbalance 26 }

slbCurCfgPmask OBJECT-TYPE
        SYNTAX  IpAddress
        ACCESS  read-only
        STATUS  mandatory
        DESCRIPTION
                "The persistent mask - corresponding to the
		 pmask command of the slb configuration menu." 
        ::= { serverloadbalance 28 }

slbNewCfgPmask OBJECT-TYPE
        SYNTAX  IpAddress
        ACCESS  read-write
        STATUS  mandatory
        DESCRIPTION
                "The persistent mask - corresponding to the
		 pmask command of the slb configuration menu." 
        ::= { serverloadbalance 29 }


slbCurCfgGrace OBJECT-TYPE
        SYNTAX  INTEGER {
                enabled(1),
                disabled(2)
                }
        ACCESS  read-only
        STATUS  mandatory
        DESCRIPTION
                "Enable or disable graceful server failure.  It allows to 
		 keep the connection to the failure real servers 
		 when set to enabled(1)."
        ::= { serverloadbalance 30 }

slbNewCfgGrace OBJECT-TYPE
        SYNTAX  INTEGER {
                enabled(1),
                disabled(2)
                }
        ACCESS  read-write
        STATUS  mandatory
        DESCRIPTION
                "Enable or disable graceful server failure.  It allows to 
		 keep the connection to the failure real servers 
	         when set to enabled(1)."
        ::= { serverloadbalance 31 }

--
-- Synch Peer Switch Configuration
--
slbCurCfgPeerTable OBJECT-TYPE
    SYNTAX SEQUENCE OF SlbCurCfgPeerEntry
    ACCESS not-accessible
    STATUS mandatory
    DESCRIPTION
        "The table of Synch Peer Switch configuration in the current_config."
    ::= { serverloadbalance 32 }

slbCurCfgPeerEntry OBJECT-TYPE
    SYNTAX SlbCurCfgPeerEntry
    ACCESS not-accessible
    STATUS mandatory
    DESCRIPTION
        "Information about Synch Peer Switch configuration."
    INDEX { slbCurCfgPeerIndex }
    ::= { slbCurCfgPeerTable 1 }
 
SlbCurCfgPeerEntry ::= SEQUENCE {
    slbCurCfgPeerIndex          INTEGER,
    slbCurCfgPeerIpAddr         IpAddress,
    slbCurCfgPeerState          INTEGER
    }
 
slbCurCfgPeerIndex OBJECT-TYPE
    SYNTAX INTEGER
    ACCESS read-only
    STATUS mandatory
    DESCRIPTION
        "The index for synch peer switchs."
    ::= { slbCurCfgPeerEntry 1 }

slbCurCfgPeerIpAddr OBJECT-TYPE
    SYNTAX IpAddress
    ACCESS read-only
    STATUS mandatory
    DESCRIPTION
        "The IP address of the peer switch."
    ::= { slbCurCfgPeerEntry 2 }
 
slbCurCfgPeerState OBJECT-TYPE
    SYNTAX INTEGER {
        enable(1),
        disable(2)
        }
    ACCESS  read-only
    STATUS  mandatory
    DESCRIPTION
        "Enable or disable the peer switch."
    ::= { slbCurCfgPeerEntry 3 }
 
slbNewCfgPeerTable OBJECT-TYPE
    SYNTAX SEQUENCE OF SlbNewCfgPeerEntry
    ACCESS not-accessible
    STATUS mandatory
    DESCRIPTION
        "The table of Synch Peer Switch configuration in the new_config."
    ::= { serverloadbalance 33 }
 
slbNewCfgPeerEntry OBJECT-TYPE
    SYNTAX SlbNewCfgPeerEntry
    ACCESS not-accessible
    STATUS mandatory
    DESCRIPTION
        "Information about synch peer switch  configuration."
    INDEX { slbNewCfgPeerIndex }
    ::= { slbNewCfgPeerTable 1 }
 
SlbNewCfgPeerEntry ::= SEQUENCE {
    slbNewCfgPeerIndex          INTEGER,
    slbNewCfgPeerIpAddr         IpAddress,
    slbNewCfgPeerState          INTEGER,
    slbNewCfgPeerDelete         INTEGER
    }
 
slbNewCfgPeerIndex OBJECT-TYPE
    SYNTAX INTEGER
    ACCESS read-only
    STATUS mandatory
    DESCRIPTION
        "The index number for synch peer switchs."
    ::= { slbNewCfgPeerEntry 1 }
 
slbNewCfgPeerIpAddr OBJECT-TYPE
    SYNTAX IpAddress
    ACCESS read-write
    STATUS mandatory
    DESCRIPTION
        "The IP address of the peer switch."
    ::= { slbNewCfgPeerEntry 2 }
 
slbNewCfgPeerState OBJECT-TYPE
    SYNTAX INTEGER {
        enable(1),
        disable(2)
        }
    ACCESS  read-write
    STATUS  mandatory
    DESCRIPTION
        "Enable or disable the peer switch."
    ::= { slbNewCfgPeerEntry 3 }
 
slbNewCfgPeerDelete OBJECT-TYPE
    SYNTAX INTEGER {
        other(1),
        delete(2)
        }
    ACCESS  read-write
    STATUS  mandatory
    DESCRIPTION
        "By setting the value to delete(2), the entire row is
         deleted."
    ::= { slbNewCfgPeerEntry 4 }
 
 
slbCurCfgSyncFilt OBJECT-TYPE
        SYNTAX  INTEGER {
                enabled(1),
                disabled(2)
                }
        ACCESS  read-only
        STATUS  mandatory
        DESCRIPTION
                "Enable or disable synch filter configuration."
        ::= { serverloadbalance 34 }

slbNewCfgSyncFilt OBJECT-TYPE
        SYNTAX  INTEGER {
                enabled(1),
                disabled(2)
                }
        ACCESS  read-write
        STATUS  mandatory
        DESCRIPTION
                "Enable or disable synch filter configuration."
        ::= { serverloadbalance 35 }

slbCurCfgSyncPort OBJECT-TYPE
        SYNTAX  INTEGER {
                enabled(1),
                disabled(2)
                }
        ACCESS  read-only
        STATUS  mandatory
        DESCRIPTION
                "Enable or disable synch port configuration."
        ::= { serverloadbalance 36 }

slbNewCfgSyncPort OBJECT-TYPE
        SYNTAX  INTEGER {
                enabled(1),
                disabled(2)
                }
        ACCESS  read-write
        STATUS  mandatory
        DESCRIPTION
                "Enable or disable synch port configuration."
        ::= { serverloadbalance 37 }

slbCurCfgSyncVrrp OBJECT-TYPE
        SYNTAX  INTEGER {
                enabled(1),
                disabled(2)
                }
        ACCESS  read-only
        STATUS  mandatory
        DESCRIPTION
                "Enable or disable synch VRRP Priorities."
        ::= { serverloadbalance 38 }

slbNewCfgSyncVrrp OBJECT-TYPE
        SYNTAX  INTEGER {
                enabled(1),
                disabled(2)
                }
        ACCESS  read-write
        STATUS  mandatory
        DESCRIPTION
                "Enable or disable synch VRRP Priorities."
        ::= { serverloadbalance 39 }

slbCurCfgSyncPip OBJECT-TYPE
        SYNTAX  INTEGER {
                enabled(1),
                disabled(2)
                }
        ACCESS  read-only
        STATUS  mandatory
        DESCRIPTION
                "Enable or disable synch proxy IP addresses."
        ::= { serverloadbalance 40 }

slbNewCfgSyncPip OBJECT-TYPE
        SYNTAX  INTEGER {
                enabled(1),
                disabled(2)
                }
        ACCESS  read-write
        STATUS  mandatory
        DESCRIPTION
                "Enable or disable synch proxy IP addresses."
        ::= { serverloadbalance 41}

slbCurCfgVirtMatrixArch OBJECT-TYPE
        SYNTAX  INTEGER {
                enabled(1),
                disabled(2)
                }
        ACCESS  read-only
        STATUS  mandatory
        DESCRIPTION
                "Enable or disable Virtual Matrix Architecture."
        ::= { serverloadbalance 42 }

slbNewCfgVirtMatrixArch OBJECT-TYPE
        SYNTAX  INTEGER {
                enabled(1),
                disabled(2)
                }
        ACCESS  read-write
        STATUS  mandatory
        DESCRIPTION
                "Enable or disable Virtual Matrix Architecture."
        ::= { serverloadbalance 43}

-- SLB Switch FailOver Group

slbCurCfgFailOverTable OBJECT-TYPE
        SYNTAX  SEQUENCE OF SlbCurCfgFailOverTblEntry
        ACCESS  not-accessible
        STATUS  mandatory
        DESCRIPTION
                "The table of current switch fail-over configuration."
        ::= { slbfailover 1 }

slbCurCfgFailOverTblEntry OBJECT-TYPE
        SYNTAX  SlbCurCfgFailOverTblEntry
        ACCESS  not-accessible
        STATUS  mandatory
        DESCRIPTION
                "A row in the current switch fail-over configuration table."
        INDEX   { slbCurCfgFailOverIndex }
        ::= { slbCurCfgFailOverTable 1 }
 
SlbCurCfgFailOverTblEntry ::= SEQUENCE {
        slbCurCfgFailOverIndex            INTEGER,
        slbCurCfgFailOverPrimaryIp        IpAddress,
        slbCurCfgFailOverSecondaryIp      IpAddress,
	slbCurCfgFailOverSilenceInterval  INTEGER,
	slbCurCfgFailOverState            INTEGER,
	slbCurCfgFailOverRouteSupply      INTEGER
	}

slbCurCfgFailOverIndex OBJECT-TYPE
        SYNTAX  INTEGER
        ACCESS  read-only
        STATUS  mandatory
        DESCRIPTION
                "The index of current switch fail-over configuration table."
        ::= { slbCurCfgFailOverTblEntry 1 }

slbCurCfgFailOverPrimaryIp OBJECT-TYPE
        SYNTAX  IpAddress
        ACCESS  read-only
        STATUS  mandatory
        DESCRIPTION
                "The IP address of the Primary switch."
        ::= { slbCurCfgFailOverTblEntry 2 }

slbCurCfgFailOverSecondaryIp OBJECT-TYPE
        SYNTAX  IpAddress
        ACCESS  read-only
        STATUS  mandatory
        DESCRIPTION
                "The IP address of the Secondary switch."
        ::= { slbCurCfgFailOverTblEntry 3 }

slbCurCfgFailOverSilenceInterval OBJECT-TYPE
        SYNTAX  INTEGER (2..120)
        ACCESS  read-only
        STATUS  mandatory
        DESCRIPTION
                "Number of seconds before a silent peer is assumed down."
        ::= { slbCurCfgFailOverTblEntry 4 }

slbCurCfgFailOverState OBJECT-TYPE
        SYNTAX  INTEGER {
                other(1),
                enabled(2),
                disabled(3)
                }
        ACCESS  read-only
        STATUS  mandatory
        DESCRIPTION
                "Enable or disable slb switch failover feature."
        ::= { slbCurCfgFailOverTblEntry 5 }

slbCurCfgFailOverRouteSupply OBJECT-TYPE
        SYNTAX  INTEGER {
                enabled(1),
                disabled(2)
                }
        ACCESS  read-only
        STATUS  mandatory
        DESCRIPTION
                "Enable or disable to supply network routes update when 
		 switch is a standby switch."
        ::= { slbCurCfgFailOverTblEntry 6 }


slbNewCfgFailOverTable OBJECT-TYPE
        SYNTAX  SEQUENCE OF SlbNewCfgFailOverTblEntry
        ACCESS  not-accessible
        STATUS  mandatory
        DESCRIPTION
                "The table of new switch fail-over configuration."
        ::= { slbfailover 2 }

slbNewCfgFailOverTblEntry OBJECT-TYPE
        SYNTAX  SlbNewCfgFailOverTblEntry
        ACCESS  not-accessible
        STATUS  mandatory
        DESCRIPTION
                "A row in the new switch fail-over configuration table."
        INDEX   { slbNewCfgFailOverIndex }
        ::= { slbNewCfgFailOverTable 1 }
 
SlbNewCfgFailOverTblEntry ::= SEQUENCE {
        slbNewCfgFailOverIndex            INTEGER,
        slbNewCfgFailOverPrimaryIp        IpAddress,
        slbNewCfgFailOverSecondaryIp      IpAddress,
	slbNewCfgFailOverSilenceInterval  INTEGER,
	slbNewCfgFailOverState            INTEGER,
	slbNewCfgFailOverRouteSupply      INTEGER
	}

slbNewCfgFailOverIndex OBJECT-TYPE
        SYNTAX  INTEGER
        ACCESS  read-only
        STATUS  mandatory
        DESCRIPTION
                "The index of new switch fail-over configuration table."
        ::= { slbNewCfgFailOverTblEntry 1 }

slbNewCfgFailOverPrimaryIp OBJECT-TYPE
        SYNTAX  IpAddress
        ACCESS  read-write
        STATUS  mandatory
        DESCRIPTION
                "The IP address of the Primary switch."
        ::= { slbNewCfgFailOverTblEntry 2 }

slbNewCfgFailOverSecondaryIp OBJECT-TYPE
        SYNTAX  IpAddress
        ACCESS  read-write
        STATUS  mandatory
        DESCRIPTION
                "The IP address of the Secondary switch."
        ::= { slbNewCfgFailOverTblEntry 3 }

slbNewCfgFailOverSilenceInterval OBJECT-TYPE
        SYNTAX  INTEGER (2..120)
        ACCESS  read-write
        STATUS  mandatory
        DESCRIPTION
                "Number of seconds before a silent peer is assumed down."
        ::= { slbNewCfgFailOverTblEntry 4 }

slbNewCfgFailOverState OBJECT-TYPE
        SYNTAX  INTEGER {
                other(1),
                enabled(2),
                disabled(3)
                }
        ACCESS  read-write
        STATUS  mandatory
        DESCRIPTION
                "Enable or disable slb switch failover feature."
        ::= { slbNewCfgFailOverTblEntry 5 }

slbNewCfgFailOverRouteSupply OBJECT-TYPE
        SYNTAX  INTEGER {
                enabled(1),
                disabled(2)
                }
        ACCESS  read-only
        STATUS  mandatory
        DESCRIPTION
                "Enable or disable to supply network routes update when 
		 switch is a standby switch."
        ::= { slbNewCfgFailOverTblEntry 6 }


-- The SLB global turn on/off controls 

slbCurCfgGlobalControl OBJECT-TYPE
        SYNTAX  INTEGER { 
		other(1),
		enabled(2),
		disabled(3)
		}
        ACCESS  read-only
        STATUS  mandatory
        DESCRIPTION
                "The global state of Server Load Balancing."
        ::= { serverloadbalance 17 }

slbNewCfgGlobalControl OBJECT-TYPE
        SYNTAX  INTEGER { 
                other(1), 
                enabled(2),
                disabled(3)
                }
        ACCESS  read-write
        STATUS  mandatory
        DESCRIPTION
                "The global state of Server Load Balancing."
        ::= { serverloadbalance 18 }


-- SLB URL Group

-- SLB URL Redirection Group

slbCurCfgUrlExpTable OBJECT-TYPE
        SYNTAX  SEQUENCE OF SlbCurCfgUrlExpTableEntry
        ACCESS  not-accessible
        STATUS  mandatory
        DESCRIPTION
                "The table of URL expressions in the current_config."
        ::= { slbUrlRedir 1 }

slbCurCfgUrlExpTableEntry OBJECT-TYPE
        SYNTAX  SlbCurCfgUrlExpTableEntry
        ACCESS  not-accessible
        STATUS  mandatory
        DESCRIPTION
                "Information about a expression for URL parsing."
        INDEX   { slbCurCfgUrlExpIndex }
        ::= { slbCurCfgUrlExpTable 1 }

SlbCurCfgUrlExpTableEntry ::= SEQUENCE {
        slbCurCfgUrlExpIndex          INTEGER,
        slbCurCfgUrlExpression        DisplayString
        }

slbCurCfgUrlExpIndex OBJECT-TYPE
        SYNTAX  INTEGER
        ACCESS  read-only
        STATUS  mandatory
        DESCRIPTION
                "The URL expressions table index."
        ::= { slbCurCfgUrlExpTableEntry 1 }

slbCurCfgUrlExpression OBJECT-TYPE
        SYNTAX  DisplayString (SIZE(0..8))
        ACCESS  read-only
        STATUS  mandatory
        DESCRIPTION
                "The expressions for URL parsing."
        ::= { slbCurCfgUrlExpTableEntry 2 }


slbNewCfgUrlExpTable OBJECT-TYPE
        SYNTAX  SEQUENCE OF SlbNewCfgUrlExpTableEntry
        ACCESS  not-accessible
        STATUS  mandatory
        DESCRIPTION
                "The table of URL expressions in the new_config."
        ::= { slbUrlRedir 2 }

slbNewCfgUrlExpTableEntry OBJECT-TYPE
        SYNTAX  SlbNewCfgUrlExpTableEntry
        ACCESS  not-accessible
        STATUS  mandatory
        DESCRIPTION
                "Information about a expression for URL parsing."
        INDEX   { slbNewCfgUrlExpIndex }
        ::= { slbNewCfgUrlExpTable 1 }

SlbNewCfgUrlExpTableEntry ::= SEQUENCE {
        slbNewCfgUrlExpIndex          INTEGER,
        slbNewCfgUrlExpression        DisplayString,
        slbNewCfgUrlExpDelete         INTEGER
        }

slbNewCfgUrlExpIndex OBJECT-TYPE
        SYNTAX  INTEGER
        ACCESS  read-only
        STATUS  mandatory
        DESCRIPTION
                "The URL expressions table index."
        ::= { slbNewCfgUrlExpTableEntry 1 }

slbNewCfgUrlExpression OBJECT-TYPE
        SYNTAX  DisplayString (SIZE(0..8))
        ACCESS  read-write
        STATUS  mandatory
        DESCRIPTION
                "The expressions for URL parsing."
        ::= { slbNewCfgUrlExpTableEntry 2 }

slbNewCfgUrlExpDelete OBJECT-TYPE
      SYNTAX  INTEGER {
                other(1),
                delete(2)
                }
      ACCESS  read-write
      STATUS  mandatory
      DESCRIPTION
                "Action object to delete an URL expression.  When set to the
                 value of 2 (delete), the entire row is deleted. When read,
                 other(1) is returned. Setting the value to anything other
                 than delete(2) has no effect on the state of the row."
      ::= { slbNewCfgUrlExpTableEntry 3 }


slbCurCfgUrlRedirNonGetOrigSrv OBJECT-TYPE
        SYNTAX  INTEGER {
                enabled(1),
                disabled(2)
                }
        ACCESS  read-only
        STATUS  mandatory
        DESCRIPTION
		"This is for controlling if the switch should redirect 
		 packet to the origin server when HTTP non-GETs are detected.  

                 enabled(1) - Allow redirect traffic to the origin server
                 disabled(2)- redirect to a group of servers"
        ::= { slbUrlRedir 3 }

slbNewCfgUrlRedirNonGetOrigSrv OBJECT-TYPE
        SYNTAX  INTEGER {
                enabled(1),
                disabled(2)
                }
        ACCESS  read-write
        STATUS  mandatory
        DESCRIPTION
		"This is for controlling if the switch should redirect 
		 packet to the origin server when HTTP non-GETs are detected.  

                 enabled(1) - Allow redirect traffic to the origin server
                 disabled(2)- redirect to a group of servers"
        ::= { slbUrlRedir 4 }

slbCurCfgUrlRedirCookieOrigSrv OBJECT-TYPE
        SYNTAX  INTEGER {
                enabled(1),
                disabled(2)
                }
        ACCESS  read-only
        STATUS  mandatory
        DESCRIPTION
		"This is for controlling if the switch should redirect 
		 packet to the origin server when user cookies
		 are detected.  

                 enabled(1) - Allow redirect traffic to the origin server
                 disabled(2)- redirect to a group of servers"
        ::= { slbUrlRedir 5 }

slbNewCfgUrlRedirCookieOrigSrv OBJECT-TYPE
        SYNTAX  INTEGER {
                enabled(1),
                disabled(2)
                }
        ACCESS  read-write
        STATUS  mandatory
        DESCRIPTION
		"This is for controlling if the switch should redirect 
		 packet to the origin server when user cookies
		 are detected.  

                 enabled(1) - Allow redirect traffic to the origin server
                 disabled(2)- redirect to a group of servers"
        ::= { slbUrlRedir 6 }

slbCurCfgUrlRedirNoCacheOrigSrv OBJECT-TYPE
        SYNTAX  INTEGER {
                enabled(1),
                disabled(2)
                }
        ACCESS  read-only
        STATUS  mandatory
        DESCRIPTION
		"This is for controlling if the switch should redirect 
		 packet to the origin server when no-cache header
		 are detected.  

                 enabled(1) - Allow redirect traffic to the origin server
                 disabled(2)- redirect to a group of servers"
        ::= { slbUrlRedir 7 }

slbNewCfgUrlRedirNoCacheOrigSrv OBJECT-TYPE
        SYNTAX  INTEGER {
                enabled(1),
                disabled(2)
                }
        ACCESS  read-write
        STATUS  mandatory
        DESCRIPTION
		"This is for controlling if the switch should redirect 
		 packet to the origin server when no-cache header
		 are detected.  

                 enabled(1) - Allow redirect traffic to the origin server
                 disabled(2)- redirect to a group of servers"
        ::= { slbUrlRedir 8 }

slbCurCfgUrlRedirUriHashLength OBJECT-TYPE
        SYNTAX  INTEGER 
        ACCESS  read-only
        STATUS  mandatory
        DESCRIPTION
		"Specify the number of bytes in the URI will be  
		 used to hash onto server"
        ::= { slbUrlRedir 9 }

slbNewCfgUrlRedirUriHashLength OBJECT-TYPE
        SYNTAX  INTEGER 
        ACCESS  read-write
        STATUS  mandatory
        DESCRIPTION
                "Specify the number of bytes in the URI will be  
		 used to hash onto server"
        ::= { slbUrlRedir 10 }

slbCurCfgUrlRedirHeader OBJECT-TYPE
        SYNTAX  INTEGER {
                enabled(1),
                disabled(2)
                }
        ACCESS  read-only
        STATUS  mandatory
        DESCRIPTION
		"This is for controlling if the switch should redirect 
		 packet to the cache server based on HTTP header.

                 enabled(1) - Redirect web traffic based on HTTP header
                 disabled(2)- Redirect web traffic based on URI"
        ::= { slbUrlRedir 11 }

slbNewCfgUrlRedirHeader OBJECT-TYPE
        SYNTAX  INTEGER {
                enabled(1),
                disabled(2)
                }
        ACCESS  read-write
        STATUS  mandatory
        DESCRIPTION
		"This is for controlling if the switch should redirect 
		 packet to the cache server based on HTTP header.

                 enabled(1) - Redirect web traffic based on HTTP header
                 disabled(2)- Redirect web traffic based on URI"
        ::= { slbUrlRedir 12 }

slbCurCfgUrlRedirHeaderName OBJECT-TYPE
        SYNTAX DisplayString
        ACCESS read-only
        STATUS mandatory
        DESCRIPTION
                "HTTP header name"
        ::= { slbUrlRedir 13 }

slbNewCfgUrlRedirHeaderName OBJECT-TYPE
        SYNTAX DisplayString
        ACCESS read-write
        STATUS mandatory
        DESCRIPTION
                "HTTP header name"
        ::= { slbUrlRedir 14 }


-- SLB URL Load Balancing

slbCurCfgUrlLbPathTable OBJECT-TYPE
        SYNTAX  SEQUENCE OF SlbCurCfgUrlLbPathTableEntry
        ACCESS  not-accessible
        STATUS  mandatory
        DESCRIPTION
                "The table of URL path for URL load balancing in the 
		 current_config."
        ::= { slbUrlBalance 1 }

slbCurCfgUrlLbPathTableEntry OBJECT-TYPE
        SYNTAX  SlbCurCfgUrlLbPathTableEntry
        ACCESS  not-accessible
        STATUS  mandatory
        DESCRIPTION
                "Information about an URL path for URL load balancing."
        INDEX   { slbCurCfgUrlLbPathIndex }
        ::= { slbCurCfgUrlLbPathTable 1 }

SlbCurCfgUrlLbPathTableEntry ::= SEQUENCE {
        slbCurCfgUrlLbPathIndex   INTEGER,
        slbCurCfgUrlLbPathString  DisplayString
        }

slbCurCfgUrlLbPathIndex OBJECT-TYPE
        SYNTAX  INTEGER
        ACCESS  read-only
        STATUS  mandatory
        DESCRIPTION
                "The URL path table index."
        ::= { slbCurCfgUrlLbPathTableEntry 1 }

slbCurCfgUrlLbPathString OBJECT-TYPE
        SYNTAX  DisplayString (SIZE(0..40))
        ACCESS  read-only
        STATUS  mandatory
        DESCRIPTION
                "The URL path for URL load balancing."
        ::= { slbCurCfgUrlLbPathTableEntry 2 }

slbNewCfgUrlLbPathTable OBJECT-TYPE
        SYNTAX  SEQUENCE OF SlbNewCfgUrlLbPathTableEntry
        ACCESS  not-accessible
        STATUS  mandatory
        DESCRIPTION
                "The table of URL path for URL load balancing in the 
		 new_config."
        ::= { slbUrlBalance 2 }

slbCurCfgUrlLbErrorMsg OBJECT-TYPE
        SYNTAX  DisplayString 
        ACCESS  read-only
        STATUS  mandatory
        DESCRIPTION
                "Customize error message to send back to client when
                 switch cannot bind client's request to servers."
        ::= { slbUrlBalance 3 }

slbNewCfgUrlLbErrorMsg OBJECT-TYPE
        SYNTAX  DisplayString 
        ACCESS  read-write
        STATUS  mandatory
        DESCRIPTION
                "Customize error message to send back to client when
                 switch cannot bind client's request to servers."
        ::= { slbUrlBalance 4 }


slbNewCfgUrlLbPathTableEntry OBJECT-TYPE
        SYNTAX  SlbNewCfgUrlLbPathTableEntry
        ACCESS  not-accessible
        STATUS  mandatory
        DESCRIPTION
                "Information about an URL path for URL load balancing."
        INDEX   { slbNewCfgUrlLbPathIndex }
        ::= { slbNewCfgUrlLbPathTable 1 }

SlbNewCfgUrlLbPathTableEntry ::= SEQUENCE {
        slbNewCfgUrlLbPathIndex   INTEGER,
        slbNewCfgUrlLbPathString  DisplayString,
        slbNewCfgUrlLbPathDelete  INTEGER
        }

slbNewCfgUrlLbPathIndex OBJECT-TYPE
        SYNTAX  INTEGER
        ACCESS  read-only
        STATUS  mandatory
        DESCRIPTION
                "The URL path table index."
        ::= { slbNewCfgUrlLbPathTableEntry 1 }

slbNewCfgUrlLbPathString OBJECT-TYPE
        SYNTAX  DisplayString (SIZE(0..40))
        ACCESS  read-write
        STATUS  mandatory
        DESCRIPTION
                "The URL path for URL load balancing."
        ::= { slbNewCfgUrlLbPathTableEntry 2 }

slbNewCfgUrlLbPathDelete OBJECT-TYPE
      SYNTAX  INTEGER {
                other(1),
                delete(2)
                }
      ACCESS  read-write
      STATUS  mandatory
      DESCRIPTION
                "Action object to delete an URL Path.  When set to the
                 value of 2 (delete), the entire row is deleted. When read,
                 other(1) is returned. Setting the value to anything other
                 than delete(2) has no effect on the state of the row."
      ::= { slbNewCfgUrlLbPathTableEntry 3 }


-- Port Mirroring Group

pmCurCfgMonitoringPort OBJECT-TYPE
	SYNTAX	INTEGER 
	ACCESS	read-only
	STATUS	mandatory
	DESCRIPTION
		"The port number of the monitoring port."
	::= { portmirroring 1 }

pmNewCfgMonitoringPort OBJECT-TYPE
        SYNTAX  INTEGER
        ACCESS  read-write
        STATUS  mandatory
        DESCRIPTION
                "The port number of the monitoring port."
        ::= { portmirroring 2 }

pmCurCfgMirroredPort OBJECT-TYPE
	SYNTAX	INTEGER 
	ACCESS	read-only
	STATUS	mandatory
	DESCRIPTION
		"The port number of the mirrored port."
	::= { portmirroring 3 }

pmNewCfgMirroredPort OBJECT-TYPE
        SYNTAX  INTEGER
        ACCESS  read-write
        STATUS  mandatory
        DESCRIPTION
                "The port number of the mirrored port."
        ::= { portmirroring 4 }

pmCurCfgMonitoredTraffic OBJECT-TYPE
	SYNTAX	INTEGER {
		other(1),
		none(2),
		received(3),
		transmitted(4),
		both(5)
		}
	ACCESS	read-only
	STATUS	mandatory
	DESCRIPTION
		"The type of traffic to be monitored with respect to the 
		 mirrored port."
	::= { portmirroring 5 }

pmNewCfgMonitoredTraffic OBJECT-TYPE
        SYNTAX  INTEGER {
		other(1),
		none(2),
		received(3),
		transmitted(4),
		both(5)
                }
        ACCESS  read-write
        STATUS  mandatory
        DESCRIPTION
                "The type of traffic to be monitored with respect to the
                 mirrored port."
        ::= { portmirroring 6 }

pmCurCfgState OBJECT-TYPE
	SYNTAX	INTEGER {
		other(1),
		enabled(2),
		disabled(3)
		}
	ACCESS	read-only
	STATUS	mandatory
	DESCRIPTION
		"The state of Port mirroring."
	::= { portmirroring 7 }
 
pmNewCfgState OBJECT-TYPE
        SYNTAX  INTEGER {
		other(1),
		enabled(2),
		disabled(3)
                }
        ACCESS  read-write
        STATUS  mandatory
        DESCRIPTION
                "The state of Port mirroring."
        ::= { portmirroring 8 }


-- Trunk Group Group

trunkGroupTableMaxSize OBJECT-TYPE
        SYNTAX  INTEGER
        ACCESS  read-only
        STATUS  mandatory
        DESCRIPTION
                "The maximum number of entries in trunk group table."
        ::= { trunkgroup 1 }

trunkGroupCurCfgTable OBJECT-TYPE
        SYNTAX  SEQUENCE OF TrunkGroupCurCfgTableEntry
        ACCESS  not-accessible
        STATUS  mandatory
        DESCRIPTION
                "The table of trunk group configuration."
        ::= { trunkgroup 2 }

trunkGroupCurCfgTableEntry OBJECT-TYPE
        SYNTAX  TrunkGroupCurCfgTableEntry
        ACCESS  not-accessible
        STATUS  mandatory
        DESCRIPTION
                "A row in the trunk group configuration table."
        INDEX   { trunkGroupCurCfgIndex }
        ::= { trunkGroupCurCfgTable 1 }

TrunkGroupCurCfgTableEntry ::= SEQUENCE {
        trunkGroupCurCfgIndex          INTEGER,
        trunkGroupCurCfgPorts         OCTET STRING,
        trunkGroupCurCfgState         INTEGER,
	trunkGroupCurCfgBwmContract   INTEGER
        }
 
trunkGroupCurCfgIndex  OBJECT-TYPE
        SYNTAX  INTEGER  
        ACCESS  read-only
        STATUS  mandatory
        DESCRIPTION
                "The identifier of the trunk group."
        ::= { trunkGroupCurCfgTableEntry 1 }
 
trunkGroupCurCfgPorts    OBJECT-TYPE
        SYNTAX  OCTET STRING (SIZE(0..16))
        ACCESS  read-only
        STATUS  mandatory
        DESCRIPTION
                "The port list in the trunk group.  The ports are presented
                 in bitmap format.
 
                 in receiving order:
 
		   OCTET 1  OCTET 2  .....
                   xxxxxxxx xxxxxxxx ..... 
                   ||    || |_ port 8
                   ||    ||  
                   ||    ||___ port 7
                   ||    |____ port 6
                   ||      .    .   .
                   ||_________ port 1
                   |__________ reserved

                 where x : 1 - The represented port belongs to the trunk group
                           0 - The represented port does not belong to
                               the trunk group"
        ::= { trunkGroupCurCfgTableEntry 2 }
 
trunkGroupCurCfgState    OBJECT-TYPE
        SYNTAX  INTEGER  {
                enable(1),
                disable(2)
                }
        ACCESS  read-only
        STATUS  mandatory
        DESCRIPTION
                "Enable or disable a trunk group."
        ::= { trunkGroupCurCfgTableEntry 3 }
 
trunkGroupCurCfgBwmContract OBJECT-TYPE
        SYNTAX  INTEGER  
        ACCESS  read-only
        STATUS  mandatory
        DESCRIPTION
                "Default BW contract of a trunk group."
        ::= { trunkGroupCurCfgTableEntry 4 }
 

-- Trunk-Group  New configuration

trunkGroupNewCfgTable OBJECT-TYPE
        SYNTAX  SEQUENCE OF TrunkGroupNewCfgTableEntry
        ACCESS  not-accessible
        STATUS  mandatory
        DESCRIPTION
                "The table of trunk group configuration."
        ::= { trunkgroup 3 }

trunkGroupNewCfgTableEntry OBJECT-TYPE
        SYNTAX  TrunkGroupNewCfgTableEntry
        ACCESS  not-accessible
        STATUS  mandatory
        DESCRIPTION
                "A row in the trunk group configuration table."
        INDEX   { trunkGroupNewCfgIndex }
        ::= { trunkGroupNewCfgTable 1 }

TrunkGroupNewCfgTableEntry ::= SEQUENCE {
        trunkGroupNewCfgIndex          	INTEGER,
        trunkGroupNewCfgPorts          	OCTET STRING,
	trunkGroupNewCfgAddPort         INTEGER,
        trunkGroupNewCfgRemovePort      INTEGER,
        trunkGroupNewCfgState          	INTEGER,
	trunkGroupNewCfgDelete          INTEGER,
	trunkGroupNewCfgBwmContract     INTEGER
        }
 
trunkGroupNewCfgIndex  OBJECT-TYPE
        SYNTAX  INTEGER  
        ACCESS  read-only
        STATUS  mandatory
        DESCRIPTION
                "The identifier of the trunk group."
        ::= { trunkGroupNewCfgTableEntry 1 }
 
trunkGroupNewCfgPorts    OBJECT-TYPE
        SYNTAX  OCTET STRING (SIZE(0..16))
        ACCESS  read-only
        STATUS  mandatory
        DESCRIPTION
                "The port list in the trunk group.  The ports are presented
                 in bitmap format.
 
                 in receiving order:
 
		   OCTET 1  OCTET 2  .....
                   xxxxxxxx xxxxxxxx ..... 
                   ||    || |_ port 8
                   ||    ||  
                   ||    ||___ port 7
                   ||    |____ port 6
                   ||      .    .   .
                   ||_________ port 1
                   |__________ reserved
 
                 where x : 1 - The represented port belongs to the trunk group
                           0 - The represented port does not belong to
                               the trunk group"
        ::= { trunkGroupNewCfgTableEntry 2 }
 
trunkGroupNewCfgAddPort    OBJECT-TYPE
        SYNTAX  INTEGER
        ACCESS  read-write
        STATUS  mandatory
        DESCRIPTION
                "The port to be added in the trunk group. When read, 0
		 is returned."
        ::= { trunkGroupNewCfgTableEntry 3 }

trunkGroupNewCfgRemovePort    OBJECT-TYPE
        SYNTAX  INTEGER
        ACCESS  read-write
        STATUS  mandatory
        DESCRIPTION
                "The port to be deleted from the trunk group. when read, 0
		 is returned."
        ::= { trunkGroupNewCfgTableEntry 4 }

trunkGroupNewCfgState    OBJECT-TYPE
        SYNTAX  INTEGER  {
                enable(1),
                disable(2)
                }
        ACCESS  read-write
        STATUS  mandatory
        DESCRIPTION
                "Enable or disable a trunk group."
        ::= { trunkGroupNewCfgTableEntry 5 }
 
trunkGroupNewCfgDelete    OBJECT-TYPE
        SYNTAX  INTEGER  {
                other(1),
                delete(2)
                }
        ACCESS  read-write
        STATUS  mandatory
        DESCRIPTION
                "Setting the value to delete(2) will delete the entire
                 row. When read, other(1) is returned."
        ::= { trunkGroupNewCfgTableEntry 6 }

trunkGroupNewCfgBwmContract OBJECT-TYPE
        SYNTAX  INTEGER  
        ACCESS  read-write
        STATUS  mandatory
        DESCRIPTION
                "Default BW contract of a trunk group."
        ::= { trunkGroupNewCfgTableEntry 7 }
 

-- Filtering Group
 
fltCfgTableMaxSize OBJECT-TYPE
        SYNTAX  INTEGER
        ACCESS  read-only
        STATUS  mandatory
        DESCRIPTION
                "The maximum number of filtering table entries."
        ::= { filtering 1 }

-- Current Config Filtering Table

fltCurCfgTable OBJECT-TYPE
        SYNTAX  SEQUENCE OF FltCurCfgTableEntry
        ACCESS  not-accessible
        STATUS  mandatory
        DESCRIPTION
                "The filtering table in the new configuration block."
        ::= { filtering 2 }

fltCurCfgTableEntry OBJECT-TYPE
        SYNTAX  FltCurCfgTableEntry
        ACCESS  not-accessible
        STATUS  mandatory
        DESCRIPTION
                "A row in the filtering table."
        INDEX   { fltCurCfgIndx }
        ::= { fltCurCfgTable 1 }

FltCurCfgTableEntry ::= SEQUENCE {
        fltCurCfgIndx             INTEGER,
        fltCurCfgSrcIp            IpAddress,
        fltCurCfgSrcIpMask        IpAddress,
        fltCurCfgDstIp            IpAddress,
        fltCurCfgDstIpMask        IpAddress,
        fltCurCfgProtocol         INTEGER,
        fltCurCfgRangeLowSrcPort  INTEGER,
        fltCurCfgRangeHighSrcPort INTEGER,
        fltCurCfgRangeLowDstPort  INTEGER,
        fltCurCfgRangeHighDstPort INTEGER,
        fltCurCfgAction           INTEGER,
        fltCurCfgRedirPort        INTEGER,
        fltCurCfgRedirGroup       INTEGER,
        fltCurCfgLog              INTEGER,
        fltCurCfgState            INTEGER,
        fltCurCfgNat              INTEGER,
        fltCurCfgCache            INTEGER,
        fltCurCfgInvert           INTEGER,
        fltCurCfgClientProxy      INTEGER,
        fltCurCfgTcpAck           INTEGER,
        fltCurCfgUrlRedir         INTEGER,
	fltCurCfgSrcMac		  PhysAddress,
	fltCurCfgDstMac		  PhysAddress,
	fltCurCfgFtpNatActive     INTEGER,
	fltCurCfgAclTcpUrg        INTEGER, 
	fltCurCfgAclTcpAck        INTEGER, 
	fltCurCfgAclTcpPsh        INTEGER, 
	fltCurCfgAclTcpRst        INTEGER, 
	fltCurCfgAclTcpSyn        INTEGER, 
	fltCurCfgAclTcpFin        INTEGER,
	fltCurCfgAclIcmp	  INTEGER,
	fltCurCfgAclIpOption	  INTEGER,
	fltCurCfgBwmContract	  INTEGER,
	fltCurCfgAclIpTos	  INTEGER,
	fltCurCfgAclIpTosMask	  INTEGER,
	fltCurCfgAclIpTosNew	  INTEGER,
	fltCurCfgFwlb		  INTEGER
        }

fltCurCfgIndx OBJECT-TYPE
        SYNTAX  INTEGER
        ACCESS  read-only
        STATUS  mandatory
        DESCRIPTION
                "The filtering table index."
        ::= { fltCurCfgTableEntry 1 }

fltCurCfgSrcIp OBJECT-TYPE
        SYNTAX  IpAddress
        ACCESS  read-only
        STATUS  mandatory
        DESCRIPTION
                "The source IP address to be filtered."
        ::= { fltCurCfgTableEntry 2 }

fltCurCfgSrcIpMask OBJECT-TYPE
        SYNTAX  IpAddress
        ACCESS  read-only
        STATUS  mandatory
        DESCRIPTION
                "The source IP sub-net mask for filtering."
        ::= { fltCurCfgTableEntry 3 }

fltCurCfgDstIp OBJECT-TYPE
        SYNTAX  IpAddress
        ACCESS  read-only
        STATUS  mandatory
        DESCRIPTION
                "The destination IP address to be filtered."
        ::= { fltCurCfgTableEntry 4 }

fltCurCfgDstIpMask OBJECT-TYPE
        SYNTAX  IpAddress
        ACCESS  read-only
        STATUS  mandatory
        DESCRIPTION
                "The destination IP sub-net mask for filtering."
        ::= { fltCurCfgTableEntry 5 }

fltCurCfgProtocol OBJECT-TYPE
        SYNTAX  INTEGER 
        ACCESS  read-only
        STATUS  mandatory
        DESCRIPTION
                "The protocol to be filtered."
        ::= { fltCurCfgTableEntry 6 }

fltCurCfgRangeHighSrcPort OBJECT-TYPE
        SYNTAX  INTEGER
        ACCESS  read-only
        STATUS  mandatory
        DESCRIPTION
                "The higher source TCP/UDP port number to be filtered.
                 It applies only when protocol defined in fltCurCfgProtocol
		 is UDP or TCP.  '0' means no filtering."
        ::= { fltCurCfgTableEntry 7 }

fltCurCfgRangeLowSrcPort OBJECT-TYPE
        SYNTAX  INTEGER
        ACCESS  read-only
        STATUS  mandatory
        DESCRIPTION
                "The lower source TCP/UDP port number to be filtered.
                 It applies only when protocol defined in fltCurCfgProtocol
		 is UDP or TCP.  '0' means no filtering."
        ::= { fltCurCfgTableEntry 8 }

fltCurCfgRangeLowDstPort OBJECT-TYPE
        SYNTAX  INTEGER
        ACCESS  read-only
        STATUS  mandatory
        DESCRIPTION
                "The lower destination TCP/UDP port number to be filtered.
                 It applies only when protocol defined in fltCurCfgProtocol
		 is UDP or TCP.  '0' means no filtering."
        ::= { fltCurCfgTableEntry 9 }

fltCurCfgRangeHighDstPort OBJECT-TYPE
        SYNTAX  INTEGER
        ACCESS  read-only
        STATUS  mandatory
        DESCRIPTION
                "The higher destination TCP/UDP port number to be filtered.
                 It applies only when protocol defined in fltCurCfgProtocol
		 is UDP or TCP.  '0' means no filtering."
        ::= { fltCurCfgTableEntry 10 }

fltCurCfgAction OBJECT-TYPE
        SYNTAX  INTEGER {
                allow(1),
                deny(2),
                redirect(3),
                nat(4)       -- network address translation
                }
        ACCESS  read-only
        STATUS  mandatory
        DESCRIPTION
                "The action for the filtering rule."
        ::= { fltCurCfgTableEntry 11 }

fltCurCfgRedirPort OBJECT-TYPE
        SYNTAX  INTEGER
        ACCESS  read-only
        STATUS  mandatory
        DESCRIPTION
                "The real server port number used for redirection."
        ::= { fltCurCfgTableEntry 12 }

fltCurCfgRedirGroup OBJECT-TYPE
        SYNTAX  INTEGER
        ACCESS  read-only
        STATUS  mandatory
        DESCRIPTION
                "The real server group to be redirected to."
        ::= { fltCurCfgTableEntry 13 }

fltCurCfgLog OBJECT-TYPE
        SYNTAX  INTEGER {
                enabled(1),
                disabled(2)
                }
        ACCESS  read-only
        STATUS  mandatory
        DESCRIPTION
                "Enable or disable logging."
        ::= { fltCurCfgTableEntry 14 }

fltCurCfgState OBJECT-TYPE
        SYNTAX  INTEGER {
                enabled(1),
                disabled(2)
                }
        ACCESS  read-only
        STATUS  mandatory
        DESCRIPTION
                "The state of this filtering rule."
        ::= { fltCurCfgTableEntry 15 }

fltCurCfgNat OBJECT-TYPE
        SYNTAX  INTEGER {
                destination-address(1),
                source-address(2)
                }
        ACCESS  read-only
        STATUS  mandatory
        DESCRIPTION
                "The selection of destination or source for network address 
		 translatin."
        ::= { fltCurCfgTableEntry 16 }

fltCurCfgCache OBJECT-TYPE
        SYNTAX  INTEGER {
                enabled(1),
                disabled(2)
                }
        ACCESS  read-only
        STATUS  mandatory
        DESCRIPTION
                "Enable or disable caching sessions that match filter."
        ::= { fltCurCfgTableEntry 17 }

fltCurCfgInvert OBJECT-TYPE
        SYNTAX  INTEGER {
                invert-on(1),
                invert-off(2)
                }
        ACCESS  read-only
        STATUS  mandatory
        DESCRIPTION
                "Turn the invert logic on or off for the filter entry."
        ::= { fltCurCfgTableEntry 18 }

fltCurCfgClientProxy OBJECT-TYPE
        SYNTAX  INTEGER {
                enabled(1),
                disabled(2)
                }
        ACCESS  read-only
        STATUS  mandatory
        DESCRIPTION
                "Enable or disable client proxy."
        ::= { fltCurCfgTableEntry 19 }

fltCurCfgTcpAck OBJECT-TYPE
        SYNTAX  INTEGER {
                enabled(1),
                disabled(2)
                }
        ACCESS  read-only
        STATUS  mandatory
        DESCRIPTION
                "Enable or disable filtering on matching TCP ACK and RST flag."
        ::= { fltCurCfgTableEntry 20 }

fltCurCfgUrlRedir OBJECT-TYPE
        SYNTAX  INTEGER {
                enabled(1),
                disabled(2)
                }
        ACCESS  read-only
        STATUS  mandatory
        DESCRIPTION
                "Enable or disable URL redirection.  The URL expressions are
                 defined in slbCurCfgUrlTable."
        ::= { fltCurCfgTableEntry 21 }


fltCurCfgSrcMac OBJECT-TYPE
        SYNTAX  PhysAddress 
        ACCESS  read-only
        STATUS  mandatory
        DESCRIPTION
                "The source MAC address to be filtered."
        ::= { fltCurCfgTableEntry 22 }

fltCurCfgDstMac OBJECT-TYPE
        SYNTAX  PhysAddress 
        ACCESS  read-only
        STATUS  mandatory
        DESCRIPTION
                "The Destination MAC address to be filtered."
        ::= { fltCurCfgTableEntry 23 }

fltCurCfgFtpNatActive OBJECT-TYPE
	SYNTAX	INTEGER{
		enabled(1),
		disabled(2)
		}
	ACCESS	read-only
	STATUS  mandatory	
	DESCRIPTION
		"Enable or disable FTP NAT for active ftp only."
	::= { fltCurCfgTableEntry 24 }

-- Current Config for TCP ACL filtering Table 

fltCurCfgAclTcpUrg OBJECT-TYPE
	SYNTAX  INTEGER {
	 	enable(1),
		disable(2)
		}
	ACCESS	read-only
	STATUS  mandatory
	DESCRIPTION
		"Enable or disable TCP URG packet."
	::= { fltCurCfgTableEntry 25 }	

fltCurCfgAclTcpAck OBJECT-TYPE
	SYNTAX  INTEGER {
	 	enable(1),
		disable(2)
		}
	ACCESS	read-only
	STATUS  mandatory
	DESCRIPTION
		"Enable or disable TCP ACK packet."
	::= { fltCurCfgTableEntry 26 }	

fltCurCfgAclTcpPsh OBJECT-TYPE
	SYNTAX  INTEGER {
	 	enable(1),
		disable(2)
		}
	ACCESS	read-only
	STATUS  mandatory
	DESCRIPTION
		"Enable or disable TCP PSH packet."
	::= { fltCurCfgTableEntry 27 }	

fltCurCfgAclTcpRst OBJECT-TYPE
	SYNTAX  INTEGER {
	 	enable(1),
		disable(2)
		}
	ACCESS	read-only
	STATUS  mandatory
	DESCRIPTION
		"Enable or disable TCP RST packet."
	::= { fltCurCfgTableEntry 28 }	

fltCurCfgAclTcpSyn OBJECT-TYPE
	SYNTAX  INTEGER {
	 	enable(1),
		disable(2)
		}
	ACCESS	read-only
	STATUS  mandatory
	DESCRIPTION
		"Enable or disable TCP SYN packet."
	::= { fltCurCfgTableEntry 29 }	

fltCurCfgAclTcpFin OBJECT-TYPE
	SYNTAX  INTEGER {
	 	enable(1),
		disable(2)
		}
	ACCESS	read-only
	STATUS  mandatory
	DESCRIPTION
		"Enable or disable TCP FIN packet."
	::= { fltCurCfgTableEntry 30 }	

-- Current Config for ICMP Type ACL filtering Table 
fltCurCfgAclIcmp OBJECT-TYPE
	SYNTAX  INTEGER 
	ACCESS	read-only
	STATUS  mandatory
	DESCRIPTION
		"ICMP type to be filtered."
	::= { fltCurCfgTableEntry 31 }	

-- Current Config IP Option ACL Filtering Table

fltCurCfgAclIpOption OBJECT-TYPE
        SYNTAX  INTEGER {
                any(1),
		rroute(2),
		tstamp(3),
		loose(4),
		strict(5)
                }
        ACCESS  read-only
        STATUS  mandatory
        DESCRIPTION
                "Select an IP option to filter."
        ::= { fltCurCfgTableEntry 32 }

-- Current BW contract Filtering table

fltCurCfgBwmContract OBJECT-TYPE
	SYNTAX  INTEGER 
	ACCESS	read-only
	STATUS  mandatory
	DESCRIPTION
		"Filt default BW contract number."
	::= { fltCurCfgTableEntry 33 }	

fltCurCfgAclIpTos OBJECT-TYPE
	SYNTAX  INTEGER (0..255)
	ACCESS	read-only
	STATUS  mandatory
	DESCRIPTION
		"The IP TOS value to be filtered."
	::= { fltCurCfgTableEntry 34 }	

fltCurCfgAclIpTosMask OBJECT-TYPE
	SYNTAX  INTEGER (0..255)
	ACCESS	read-only
	STATUS  mandatory
	DESCRIPTION
		"The IP TOS mask for filtering."
	::= { fltCurCfgTableEntry 35 }	

fltCurCfgAclIpTosNew OBJECT-TYPE
	SYNTAX  INTEGER (0..255)
	ACCESS	read-only
	STATUS  mandatory
	DESCRIPTION
		"The new IP TOS value to over-write when filtering fired."
	::= { fltCurCfgTableEntry 36 }	


fltCurCfgFwlb OBJECT-TYPE
        SYNTAX  INTEGER {
                enabled(1),
                disabled(2)
                }
        ACCESS  read-only
        STATUS  mandatory
        DESCRIPTION
                "Enable or disable filtering on firewall redirect hash
		 method."
        ::= { fltCurCfgTableEntry 37 }

-- New Config Filtering Table

fltNewCfgTable OBJECT-TYPE
        SYNTAX  SEQUENCE OF FltNewCfgTableEntry
        ACCESS  not-accessible
        STATUS  mandatory
        DESCRIPTION
                "The filtering table in the new configuration block."
        ::= { filtering 3 }

fltNewCfgTableEntry OBJECT-TYPE
        SYNTAX  FltNewCfgTableEntry
        ACCESS  not-accessible
        STATUS  mandatory
        DESCRIPTION
                "A row in the filtering table."
        INDEX   { fltNewCfgIndx }
        ::= { fltNewCfgTable 1 }

FltNewCfgTableEntry ::= SEQUENCE {
        fltNewCfgIndx             INTEGER,
        fltNewCfgSrcIp            IpAddress,
        fltNewCfgSrcIpMask        IpAddress,
        fltNewCfgDstIp            IpAddress,
        fltNewCfgDstIpMask        IpAddress,
        fltNewCfgProtocol         INTEGER,
        fltNewCfgRangeLowSrcPort  INTEGER,
        fltNewCfgRangeHighSrcPort INTEGER,
        fltNewCfgRangeLowDstPort  INTEGER,
        fltNewCfgRangeHighDstPort INTEGER,
        fltNewCfgAction           INTEGER,
        fltNewCfgRedirPort        INTEGER,
        fltNewCfgRedirGroup       INTEGER,
        fltNewCfgLog              INTEGER,
        fltNewCfgState            INTEGER,
        fltNewCfgDelete           INTEGER,
        fltNewCfgNat              INTEGER,
        fltNewCfgCache            INTEGER,
        fltNewCfgInvert           INTEGER,
        fltNewCfgClientProxy      INTEGER,
        fltNewCfgTcpAck           INTEGER,
        fltNewCfgUrlRedir         INTEGER,
	fltNewCfgSrcMac		  PhysAddress,
	fltNewCfgDstMac		  PhysAddress,
	fltNewCfgFtpNatActive	  INTEGER,
	fltNewCfgAclTcpUrg        INTEGER,
	fltNewCfgAclTcpAck        INTEGER,
	fltNewCfgAclTcpPsh        INTEGER,
	fltNewCfgAclTcpRst        INTEGER,
	fltNewCfgAclTcpSyn        INTEGER,
	fltNewCfgAclTcpFin        INTEGER,
	fltNewCfgAclIcmp          INTEGER,
	fltNewCfgAclIpOption	  INTEGER,
	fltNewCfgBwmContract      INTEGER,
	fltNewCfgAclIpTos	  INTEGER,
	fltNewCfgAclIpTosMask	  INTEGER,
	fltNewCfgAclIpTosNew	  INTEGER,
	fltNewCfgFwlb		  INTEGER
        }

fltNewCfgIndx OBJECT-TYPE
        SYNTAX  INTEGER
        ACCESS  read-only
        STATUS  mandatory
        DESCRIPTION
                "The filtering table index."
        ::= { fltNewCfgTableEntry 1 }

fltNewCfgSrcIp OBJECT-TYPE
        SYNTAX  IpAddress
        ACCESS  read-write
        STATUS  mandatory
        DESCRIPTION
                "The source IP address to be filtered."
        ::= { fltNewCfgTableEntry 2 }

fltNewCfgSrcIpMask OBJECT-TYPE
        SYNTAX  IpAddress
        ACCESS  read-write
        STATUS  mandatory
        DESCRIPTION
                "The source IP sub-net mask for filtering."
        ::= { fltNewCfgTableEntry 3 }

fltNewCfgDstIp OBJECT-TYPE
        SYNTAX  IpAddress
        ACCESS  read-write
        STATUS  mandatory
        DESCRIPTION
                "The destination IP address to be filtered."
        ::= { fltNewCfgTableEntry 4 }

fltNewCfgDstIpMask OBJECT-TYPE
        SYNTAX  IpAddress
        ACCESS  read-write
        STATUS  mandatory
        DESCRIPTION
                "The destination IP sub-net mask for filtering."
        ::= { fltNewCfgTableEntry 5 }

fltNewCfgProtocol OBJECT-TYPE
        SYNTAX  INTEGER 
        ACCESS  read-write
        STATUS  mandatory
        DESCRIPTION
                "The protocol to be filtered."
        ::= { fltNewCfgTableEntry 6 }

fltNewCfgRangeHighSrcPort OBJECT-TYPE
        SYNTAX  INTEGER
        ACCESS  read-write
        STATUS  mandatory
        DESCRIPTION
                "The higher source TCP/UDP port number to be filtered.
                 It applies only when protocol defined in fltNewCfgProtocol
		 is UDP or TCP.  '0' means no filtering."
        ::= { fltNewCfgTableEntry 7 }

fltNewCfgRangeLowSrcPort OBJECT-TYPE
        SYNTAX  INTEGER
        ACCESS  read-write
        STATUS  mandatory
        DESCRIPTION
                "The lower source TCP/UDP port number to be filtered.
                 It applies only when protocol defined in fltNewCfgProtocol
		 is UDP or TCP.  '0' means no filtering."
        ::= { fltNewCfgTableEntry 8 }

fltNewCfgRangeLowDstPort OBJECT-TYPE
        SYNTAX  INTEGER
        ACCESS  read-write
        STATUS  mandatory
        DESCRIPTION
                "The lower destination TCP/UDP port number to be filtered.
                 It applies only when protocol defined in fltNewCfgProtocol
		 is UDP or TCP.  '0' means no filtering."
        ::= { fltNewCfgTableEntry 9 }

fltNewCfgRangeHighDstPort OBJECT-TYPE
        SYNTAX  INTEGER
        ACCESS  read-write
        STATUS  mandatory
        DESCRIPTION
                "The higher destination TCP/UDP port number to be filtered.
                 It applies only when protocol defined in fltNewCfgProtocol
		 is UDP or TCP.  '0' means no filtering."
        ::= { fltNewCfgTableEntry 10 }

fltNewCfgAction OBJECT-TYPE
        SYNTAX  INTEGER {
                allow(1),
                deny(2),
                redirect(3),
                nat(4)       -- network address translation
                }
        ACCESS  read-write
        STATUS  mandatory
        DESCRIPTION
                "The action for the filtering rule."
        ::= { fltNewCfgTableEntry 11 }

fltNewCfgRedirPort OBJECT-TYPE
        SYNTAX  INTEGER
        ACCESS  read-write
        STATUS  mandatory
        DESCRIPTION
                "The real server port number used for redirection."
        ::= { fltNewCfgTableEntry 12 }

fltNewCfgRedirGroup OBJECT-TYPE
        SYNTAX  INTEGER
        ACCESS  read-write
        STATUS  mandatory
        DESCRIPTION
                "The real server group to be redirected to."
        ::= { fltNewCfgTableEntry 13 }

fltNewCfgLog OBJECT-TYPE
        SYNTAX  INTEGER {
                enabled(1),
                disabled(2)
                }
        ACCESS  read-write
        STATUS  mandatory
        DESCRIPTION
                "Enable or disable logging."
        ::= { fltNewCfgTableEntry 14 }

fltNewCfgState OBJECT-TYPE
        SYNTAX  INTEGER {
                enabled(1),
                disabled(2)
                }
        ACCESS  read-write
        STATUS  mandatory
        DESCRIPTION
                "The state of this filtering rule."
        ::= { fltNewCfgTableEntry 15 }

fltNewCfgDelete OBJECT-TYPE
        SYNTAX  INTEGER {
                other(1),
                delete(2)
                }
        ACCESS  read-write
        STATUS  mandatory
        DESCRIPTION
              "When set to the value of 2 (delete), the entire row
	       is deleted. When read, other(1) is returned. Setting the value
	       to anything other than 2(delete) has no effect on the state
	       of the row."
        ::= { fltNewCfgTableEntry 16 }

fltNewCfgNat OBJECT-TYPE
        SYNTAX  INTEGER {
                destination-address(1),
                source-address(2)
                }
        ACCESS  read-write
        STATUS  mandatory
        DESCRIPTION
                "The selection of destination or source for network address 
		 translatin."
        ::= { fltNewCfgTableEntry 17 }

fltNewCfgCache OBJECT-TYPE
        SYNTAX  INTEGER {
                enabled(1),
                disabled(2)
                }
        ACCESS  read-write
        STATUS  mandatory
        DESCRIPTION
                "Enable or disable caching sessions that match filter."
        ::= { fltNewCfgTableEntry 18 }

fltNewCfgInvert OBJECT-TYPE
        SYNTAX  INTEGER {
                invert-on(1),
                invert-off(2)
                }
        ACCESS  read-write
        STATUS  mandatory
        DESCRIPTION
                "Turn the invert logic on or off for the filter entry."
        ::= { fltNewCfgTableEntry 19 }

fltNewCfgClientProxy OBJECT-TYPE
        SYNTAX  INTEGER {
                enabled(1),
                disabled(2)
                }
        ACCESS  read-write
        STATUS  mandatory
        DESCRIPTION
                "Enable or disable client proxy."
        ::= { fltNewCfgTableEntry 20 }

fltNewCfgTcpAck OBJECT-TYPE
        SYNTAX  INTEGER {
                enabled(1),
                disabled(2)
                }
        ACCESS  read-write
        STATUS  mandatory
        DESCRIPTION
                "Enable or disable filtering on matching TCP ACK and RST flag."
        ::= { fltNewCfgTableEntry 21 }

fltNewCfgUrlRedir OBJECT-TYPE
        SYNTAX  INTEGER {
                enabled(1),
                disabled(2)
                }
        ACCESS  read-write
        STATUS  mandatory
        DESCRIPTION
                "Enable or disable URL redirection.  The URL expressions are
                 defined in slbNewCfgUrlTable."
        ::= { fltNewCfgTableEntry 22 }

fltNewCfgSrcMac OBJECT-TYPE
        SYNTAX  PhysAddress 
        ACCESS  read-write
        STATUS  mandatory
        DESCRIPTION
                "The source MAC address to be filtered."
        ::= { fltNewCfgTableEntry 23 }

fltNewCfgDstMac OBJECT-TYPE
        SYNTAX  PhysAddress 
        ACCESS  read-write
        STATUS  mandatory
        DESCRIPTION
                "The Destination MAC address to be filtered."
        ::= { fltNewCfgTableEntry 24 }

fltNewCfgFtpNatActive OBJECT-TYPE
	SYNTAX	INTEGER {
		enabled(1),	
		disabled(2)
		}	
	ACCESS	read-write
	STATUS	mandatory
	DESCRIPTION
		"Enable or disable FTP NAT for active ftp."
	::= { fltNewCfgTableEntry 25 }	

-- New Config TCP Flag ACL Filtering Table
fltNewCfgAclTcpUrg OBJECT-TYPE
	SYNTAX	INTEGER {
		enable(1),
		disable(2)
		}	
	ACCESS	read-write
	STATUS	mandatory
	DESCRIPTION
		"E or disable TCP URG packet."
	::= { fltNewCfgTableEntry 26 }	

fltNewCfgAclTcpAck OBJECT-TYPE
	SYNTAX	INTEGER {
		enable(1),
		disable(2)
		}	
	ACCESS	read-write
	STATUS	mandatory
	DESCRIPTION
		"Enable or disable TCP ACK packet."
	::= { fltNewCfgTableEntry 27 }	

fltNewCfgAclTcpPsh OBJECT-TYPE
	SYNTAX	INTEGER {
		enable(1),
		disable(2)
		}	
	ACCESS	read-write
	STATUS	mandatory
	DESCRIPTION
		"Enable or disable TCP PSH packet."
	::= { fltNewCfgTableEntry 28 }	


fltNewCfgAclTcpRst OBJECT-TYPE
	SYNTAX	INTEGER {
		enable(1),
		disable(2)
		}	
	ACCESS	read-write
	STATUS	mandatory
	DESCRIPTION
		"Enable or disable TCP RST packet."
	::= { fltNewCfgTableEntry 29 }	

fltNewCfgAclTcpSyn OBJECT-TYPE
	SYNTAX	INTEGER {
		enable(1),
		disable(2)
		}	
	ACCESS	read-write
	STATUS	mandatory
	DESCRIPTION
		"Enable or disable TCP SYN packet."
	::= { fltNewCfgTableEntry 30 }	

fltNewCfgAclTcpFin OBJECT-TYPE
	SYNTAX	INTEGER {
		enable(1),
		disable(2)
		}	
	ACCESS	read-write
	STATUS	mandatory
	DESCRIPTION
		"Enable or disable TCP FIN packet."
	::= { fltNewCfgTableEntry 31 }	
-- New Config ICMP Type ACL Filtering Table

fltNewCfgAclIcmp OBJECT-TYPE
	SYNTAX	INTEGER 
	ACCESS	read-write
	STATUS	mandatory
	DESCRIPTION
		"ICMP type to be filtered."
	::= { fltNewCfgTableEntry 32 }	

-- New Config IP Option ACL Filtering Table

fltNewCfgAclIpOption OBJECT-TYPE
        SYNTAX  INTEGER {
                any(1),
                rroute(2),
                tstamp(3),
                loose(4),
                strict(5)
                }
        ACCESS  read-write
        STATUS  mandatory
        DESCRIPTION
                "Select an IP option to filter."
        ::= { fltNewCfgTableEntry 33 }

-- New Config BW Contract Filtering Table

fltNewCfgBwmContract OBJECT-TYPE
	SYNTAX	INTEGER 
	ACCESS	read-write
	STATUS	mandatory
	DESCRIPTION
		"Filt default BW contract number."
	::= { fltNewCfgTableEntry 34 }	

fltNewCfgAclIpTos OBJECT-TYPE
	SYNTAX  INTEGER (0..255)
	ACCESS	read-write
	STATUS  mandatory
	DESCRIPTION
		"The IP TOS value to be filtered."
	::= { fltNewCfgTableEntry 35 }	

fltNewCfgAclIpTosMask OBJECT-TYPE
	SYNTAX  INTEGER (0..255)
	ACCESS	read-write
	STATUS  mandatory
	DESCRIPTION
		"The IP TOS mask for filtering."
	::= { fltNewCfgTableEntry 36 }	

fltNewCfgAclIpTosNew OBJECT-TYPE
	SYNTAX  INTEGER (0..255)
	ACCESS	read-write
	STATUS  mandatory
	DESCRIPTION
		"The new IP TOS value to over-write when filtering fired."
	::= { fltNewCfgTableEntry 37 }	

fltNewCfgFwlb OBJECT-TYPE
        SYNTAX  INTEGER {
                enabled(1),
                disabled(2)
                }
        ACCESS  read-write
        STATUS  mandatory
        DESCRIPTION
                "Enable or disable filtering on firewall redirect hash
		 method."
        ::= { fltNewCfgTableEntry 38 }

-- Filtering Port Table

fltCurCfgPortTable OBJECT-TYPE
        SYNTAX  SEQUENCE OF FltCurCfgPortTableEntry
        ACCESS  not-accessible
        STATUS  mandatory
        DESCRIPTION
                "The filtering port table in the current configuration 
		 block."
        ::= { filtering 4 }

fltCurCfgPortTableEntry OBJECT-TYPE
        SYNTAX  FltCurCfgPortTableEntry
        ACCESS  not-accessible
        STATUS  mandatory
        DESCRIPTION
                "A row in the filtering port table."
        INDEX   { fltCurCfgPortIndx }
        ::= { fltCurCfgPortTable 1 }

FltCurCfgPortTableEntry ::= SEQUENCE {
        fltCurCfgPortIndx         INTEGER,
        fltCurCfgPortState        INTEGER,
        fltCurCfgPortFiltBmap     OCTET STRING
        }

fltCurCfgPortIndx OBJECT-TYPE
        SYNTAX  INTEGER
        ACCESS  read-only
        STATUS  mandatory
        DESCRIPTION
                "The port index."
        ::= { fltCurCfgPortTableEntry 1 }

fltCurCfgPortState OBJECT-TYPE
        SYNTAX  INTEGER {
                enabled(1),
                disabled(2)
                }
        ACCESS  read-only
        STATUS  mandatory
        DESCRIPTION
                "Enable or disable filtering."
        ::= { fltCurCfgPortTableEntry 2 }

fltCurCfgPortFiltBmap OBJECT-TYPE
	SYNTAX	OCTET STRING (SIZE(0..32))
	ACCESS	read-only
	STATUS	mandatory
	DESCRIPTION
		"The filtering rules applied to the port.  The filtering rules
		 are presented in bitmap format.

		 in receiving order:

		   OCTET 1  OCTET 2  .....
                   xxxxxxxx xxxxxxxx ..... 
                   ||    || |_ filter 9
                   ||    ||  
                   ||    ||___ filter 8
                   ||    |____ filter 7
                   ||      .    .   .
                   ||_________ filter 2
                   |__________ filter 1 (as index to fltCurCfgTable)

		 where x : 1 - The represented filter rule applied to the port
		           0 - The represented filter rule not applied to the 
                               port "
	::= { fltCurCfgPortTableEntry 3 }


--

fltNewCfgPortTable OBJECT-TYPE
        SYNTAX  SEQUENCE OF FltNewCfgPortTableEntry
        ACCESS  not-accessible
        STATUS  mandatory
        DESCRIPTION
                "The filtering port table in the new configuration 
		 block."
        ::= { filtering 5 }

fltNewCfgPortTableEntry OBJECT-TYPE
        SYNTAX  FltNewCfgPortTableEntry
        ACCESS  not-accessible
        STATUS  mandatory
        DESCRIPTION
                "A row in the filtering port table."
        INDEX   { fltNewCfgPortIndx }
        ::= { fltNewCfgPortTable 1 }

FltNewCfgPortTableEntry ::= SEQUENCE {
        fltNewCfgPortIndx         INTEGER,
        fltNewCfgPortState        INTEGER,
        fltNewCfgPortFiltBmap     OCTET STRING,
        fltNewCfgPortAddFiltRule  INTEGER,
        fltNewCfgPortRemFiltRule  INTEGER
        }

fltNewCfgPortIndx OBJECT-TYPE
        SYNTAX  INTEGER
        ACCESS  read-only
        STATUS  mandatory
        DESCRIPTION
                "The port index."
        ::= { fltNewCfgPortTableEntry 1 }

fltNewCfgPortState OBJECT-TYPE
        SYNTAX  INTEGER {
                enabled(1),
                disabled(2)
                }
        ACCESS  read-write
        STATUS  mandatory
        DESCRIPTION
                "Enable or disable filtering."
        ::= { fltNewCfgPortTableEntry 2 }

fltNewCfgPortFiltBmap OBJECT-TYPE
	SYNTAX	OCTET STRING (SIZE(0..32))
	ACCESS	read-only
	STATUS	mandatory
	DESCRIPTION
		"The filtering rules applied to the port.  The filtering rules
		 are presented in bitmap format.

		 in receiving order:

		   OCTET 1  OCTET 2  .....
                   xxxxxxxx xxxxxxxx ..... 
                   ||    || |_ filter 9
                   ||    ||  
                   ||    ||___ filter 8
                   ||    |____ filter 7
                   ||      .    .   .
                   ||_________ filter 2
                   |__________ filter 1 (as index to fltNewCfgTable)

		 where x : 1 - The represented filter rule applied to the port
		           0 - The represented filter rule not applied to the 
                               port "
	::= { fltNewCfgPortTableEntry 3 }

fltNewCfgPortAddFiltRule OBJECT-TYPE
      SYNTAX  INTEGER
      ACCESS  read-write
      STATUS  mandatory
      DESCRIPTION
              "This is an action object to add filtering rule to a port.  The 
		value specified with this object is the index to the 
                fltNewCfgTable for which filtering rule to be added to the 
		port. The range of the valid index is between 1 and 
		fltCurCfgTableMaxSize.  When read, the value '0' is 
		returned always."
      ::= { fltNewCfgPortTableEntry 4 }

fltNewCfgPortRemFiltRule OBJECT-TYPE
      SYNTAX  INTEGER
      ACCESS  read-write
      STATUS  mandatory
      DESCRIPTION
              "This is an action object to remove filtering rule from a port.
		The value specified with this object is the index to the 
                fltNewCfgTable for which filtering rule to be removed from
		the port. The range of the valid index is between 1 and 
		fltCurCfgTableMaxSize.  When read, the value '0' is 
		returned always."
      ::= { fltNewCfgPortTableEntry 5 }


-- Global Server Load Balancing

-- GSLB General Configuration

gslbCurCfgGenState OBJECT-TYPE
        SYNTAX  INTEGER {
                on(1),
                off(2)
                }
        ACCESS  read-only
        STATUS  mandatory
        DESCRIPTION
                "Trun on or off Distributed Server Load Balance in the
		 current_configuration block."
        ::= { gslbGeneral 1 }

gslbNewCfgGenState OBJECT-TYPE
        SYNTAX  INTEGER {
                on(1),
                off(2)
                }
        ACCESS  read-write
        STATUS  mandatory
        DESCRIPTION
                "Trun on or off Distributed Server Load Balance in the
		 new_configuration block."
        ::= { gslbGeneral 2 }

gslbCurCfgGenDnsHandoff OBJECT-TYPE
        SYNTAX  INTEGER {
                enabled(1),
                disabled(2)
                }
        ACCESS  read-only
        STATUS  mandatory
        DESCRIPTION
                "Enable/Disable DNS handoffs in the current_configuration
		 block."
        ::= { gslbGeneral 3 }

gslbNewCfgGenDnsHandoff OBJECT-TYPE
        SYNTAX  INTEGER {
                enabled(1),
                disabled(2)
                }
        ACCESS  read-write
        STATUS  mandatory
        DESCRIPTION
                "Enable/Disable DNS handoffs in the new_configuration
		 block."
        ::= { gslbGeneral 4 }

gslbCurCfgGenDnsTTL OBJECT-TYPE
        SYNTAX  INTEGER (0..120)
        ACCESS  read-only
        STATUS  mandatory
        DESCRIPTION
                "Time to live value in minute of DNS resource records in 
		 the current_configuration block."
        ::= { gslbGeneral 5 }

gslbNewCfgGenDnsTTL OBJECT-TYPE
        SYNTAX  INTEGER (0..120)
        ACCESS  read-write
        STATUS  mandatory
        DESCRIPTION
                "Time to live value in minute of DNS resource records in 
		 the new_configuration block."
        ::= { gslbGeneral 6 }

gslbCurCfgGenHttpRedirect OBJECT-TYPE
        SYNTAX  INTEGER {
                enabled(1),
                disabled(2)
                }
        ACCESS  read-only
        STATUS  mandatory
        DESCRIPTION
                "Enable/Disable DNS handoffs in the current_configuration
		 block."
        ::= { gslbGeneral 7 }

gslbNewCfgGenHttpRedirect OBJECT-TYPE
        SYNTAX  INTEGER {
                enabled(1),
                disabled(2)
                }
        ACCESS  read-write
        STATUS  mandatory
        DESCRIPTION
                "Enable/Disable DNS handoffs in the new_configuration
		 block."
        ::= { gslbGeneral 8 }

gslbCurCfgGenRemSiteUpdateInterval OBJECT-TYPE
        SYNTAX  INTEGER (1..120)
        ACCESS  read-only
        STATUS  mandatory
        DESCRIPTION
                "The time interval in minute for updating remote site status
		 in the current_configuration block."
        ::= { gslbGeneral 9 }

gslbNewCfgGenRemSiteUpdateInterval OBJECT-TYPE
        SYNTAX  INTEGER (1..120)
        ACCESS  read-write
        STATUS  mandatory
        DESCRIPTION
                "The time interval in minute for updating remote site status
		 in the new_configuration block."
        ::= { gslbGeneral 10 }

gslbCurCfgGenDnsLocalPref OBJECT-TYPE
        SYNTAX  INTEGER {
                enabled(1),
                disabled(2)
                }
        ACCESS  read-only
        STATUS  mandatory
        DESCRIPTION
                "Enable/Disable DNS responses with only local addresses."
        ::= { gslbGeneral 11 }

gslbNewCfgGenDnsLocalPref OBJECT-TYPE
        SYNTAX  INTEGER {
                enabled(1),
                disabled(2)
                }
        ACCESS  read-write
        STATUS  mandatory
        DESCRIPTION
                "Enable/Disable DNS responses with only local addresses."
        ::= { gslbGeneral 12 }

gslbCurCfgGenMinco OBJECT-TYPE
        SYNTAX  INTEGER (0..65535)
        ACCESS  read-only
        STATUS  mandatory
        DESCRIPTION
                "Minmum number of site connections in the 
		 current_configuration block."
        ::= { gslbGeneral 13 }

gslbNewCfgGenMinco OBJECT-TYPE
        SYNTAX  INTEGER (0..65535)
        ACCESS  read-write
        STATUS  mandatory
        DESCRIPTION
		 "Minmum number of site connections in the
		  new_configuration block."
        ::= { gslbGeneral 14 }

gslbCurCfgGenOne OBJECT-TYPE
        SYNTAX  INTEGER {
                enabled(1),
                disabled(2)
                }
        ACCESS  read-only
        STATUS  mandatory
        DESCRIPTION
                "Enable/Disable DNS responses with only one address
		in the current_configuration block."
        ::= { gslbGeneral 15 }

gslbNewCfgGenOne OBJECT-TYPE
        SYNTAX  INTEGER {
                enabled(1),
                disabled(2)
                }
        ACCESS  read-write
        STATUS  mandatory
        DESCRIPTION
                "Enable/Disable DNS responses with only one address
		in the new_configuration block."
        ::= { gslbGeneral 16 }

gslbCurCfgGenUsern OBJECT-TYPE
        SYNTAX  INTEGER {
                enabled(1),
                disabled(2)
                }
        ACCESS  read-only
        STATUS  mandatory
        DESCRIPTION
                "Enable/Disable HTTP redirect to real server name 
		in the current_configuration block."
        ::= { gslbGeneral 17 }

gslbNewCfgGenUsern OBJECT-TYPE
        SYNTAX  INTEGER {
                enabled(1),
                disabled(2)
                }
        ACCESS  read-write
        STATUS  mandatory
        DESCRIPTION
                "Enable/Disable HTTP redirect to real server name
		in the new_configuration block."
        ::= { gslbGeneral 18 }

gslbCurCfgGenGeo OBJECT-TYPE
        SYNTAX  INTEGER {
                enabled(1),
                disabled(2)
                }
        ACCESS  read-only
        STATUS  mandatory
        DESCRIPTION
                "Enable/Disable geographic awareness
                in the current_configuration block."
        ::= { gslbGeneral 19 }

gslbNewCfgGenGeo OBJECT-TYPE
        SYNTAX  INTEGER {
                enabled(1),
                disabled(2)
                }
        ACCESS  read-write
        STATUS  mandatory
        DESCRIPTION
                "Enable/Disable geographic awareness
                in the new_configuration block."
        ::= { gslbGeneral 20 }

-- Lookup

gslbCurCfgGenLookups OBJECT-TYPE
        SYNTAX INTEGER {
                enabled(1),
                disabled(2)
                }
        ACCESS read-only
        STATUS mandatory
        DESCRIPTION
                "Enable or disable network preference lookups."
        ::= { gslbLookup 1 }
 
gslbNewCfgGenLookups OBJECT-TYPE
        SYNTAX INTEGER {
                enabled(1),
                disabled(2)
        }
        ACCESS read-write
        STATUS mandatory
        DESCRIPTION
                "Enable or disable network preference lookups."
        ::= { gslbLookup 2 }

gslbCurCfgGenLookupDname OBJECT-TYPE
        SYNTAX DisplayString
        ACCESS read-only
        STATUS mandatory
        DESCRIPTION
                "Domain name for internal lookup table"
        ::= { gslbLookup 3 }


gslbNewCfgGenLookupDname OBJECT-TYPE
        SYNTAX DisplayString
        ACCESS read-write
        STATUS mandatory
        DESCRIPTION
                "Domain name for internal lookup table"
        ::= { gslbLookup 4 }

gslbNetwork    OBJECT IDENTIFIER ::= { gslbLookup 5 }

gslbCurCfgGenExternal OBJECT-TYPE
        SYNTAX INTEGER {
                enabled(1),
                disabled(2)
                }
        ACCESS read-only
        STATUS mandatory
        DESCRIPTION
                "Enable or disable external lookups."
        ::= { gslbLookup 6 }
 
gslbNewCfgGenExternal OBJECT-TYPE
        SYNTAX INTEGER {
                enabled(1),
                disabled(2)
                }
        ACCESS read-write
        STATUS mandatory
        DESCRIPTION
                "Enable or disable external lookups."
        ::= { gslbLookup 7 }

gslbCurCfgGenEip OBJECT-TYPE
        SYNTAX IpAddress
        ACCESS read-only
        STATUS mandatory
        DESCRIPTION
                "External lookup IP address"
        ::= { gslbLookup 8 }
 
gslbNewCfgGenEip OBJECT-TYPE
        SYNTAX IpAddress
        ACCESS read-write
        STATUS mandatory
        DESCRIPTION
                "External lookup IP address"
        ::= { gslbLookup 9 }

gslbCurCfgGenLookupPort OBJECT-TYPE
        SYNTAX INTEGER (8100..9999)
        ACCESS read-only
        STATUS mandatory
        DESCRIPTION
                "External lookup UDP port number"
        ::= { gslbLookup 10 }
 
gslbNewCfgGenLookupPort OBJECT-TYPE
        SYNTAX INTEGER (8100..9999)
        ACCESS read-write
        STATUS mandatory
        DESCRIPTION
                "External lookup UDP port number"
        ::= { gslbLookup 11 }

gslbCurCfgGenLookupTimeout OBJECT-TYPE
        SYNTAX INTEGER (1..5)
        ACCESS read-only
        STATUS mandatory
        DESCRIPTION
                "External lookup Timeout Interval"
        ::= { gslbLookup 12 }
 
gslbNewCfgGenLookupTimeout OBJECT-TYPE
        SYNTAX INTEGER (1..5)
        ACCESS read-write
        STATUS mandatory
        DESCRIPTION
                "External lookup Timeout Interval"
        ::= { gslbLookup 13 }


--
-- GSLB Internet network preference Configuration
--

gslbNetworkTableMaxSize OBJECT-TYPE
        SYNTAX INTEGER
        ACCESS read-only
        STATUS mandatory
        DESCRIPTION
                "The maximum number of GSLB Internet network preference entries."
        ::= { gslbNetwork 1 }

gslbCurCfgNetworkTable OBJECT-TYPE
        SYNTAX SEQUENCE OF GslbCurCfgNetworkTableEntry
        ACCESS not-accessible
        STATUS mandatory
        DESCRIPTION
                "The table of Internet network preference configuration
                in the current_config."
        ::= { gslbNetwork 2 }

gslbCurCfgNetworkTableEntry OBJECT-TYPE
        SYNTAX GslbCurCfgNetworkTableEntry
        ACCESS not-accessible
        STATUS mandatory
        DESCRIPTION
                "The table about a network preference entry configuration."
        INDEX { gslbCurCfgNetworkIndx }
        ::= { gslbCurCfgNetworkTable 1 }

GslbCurCfgNetworkTableEntry ::= SEQUENCE {
        gslbCurCfgNetworkIndx       INTEGER,
        gslbCurCfgNetworkSourceIp   IpAddress,
        gslbCurCfgNetworkNetMask    IpAddress,
        gslbCurCfgNetworkVip1       IpAddress,
        gslbCurCfgNetworkVip2       IpAddress
        } 

gslbCurCfgNetworkIndx  OBJECT-TYPE
        SYNTAX INTEGER
        ACCESS read-only
        STATUS mandatory
        DESCRIPTION
                "The current Internet network preference table index."
        ::= { gslbCurCfgNetworkTableEntry 1 }

gslbCurCfgNetworkSourceIp OBJECT-TYPE
        SYNTAX IpAddress
        ACCESS read-only
        STATUS mandatory
        DESCRIPTION
                "The Source IP address of the network table."
        ::= { gslbCurCfgNetworkTableEntry 2}

gslbCurCfgNetworkNetMask OBJECT-TYPE
        SYNTAX IpAddress
        ACCESS read-only
        STATUS mandatory
        DESCRIPTION
                "The Net mask of the network table."
        ::= { gslbCurCfgNetworkTableEntry 3}

gslbCurCfgNetworkVip1 OBJECT-TYPE
        SYNTAX IpAddress
        ACCESS read-only
        STATUS mandatory
        DESCRIPTION
                "The Vip1 of the network table."
        ::= { gslbCurCfgNetworkTableEntry 4}

gslbCurCfgNetworkVip2 OBJECT-TYPE
        SYNTAX IpAddress
        ACCESS read-only
        STATUS mandatory
        DESCRIPTION
                "The Vip2 of the network table."
        ::= { gslbCurCfgNetworkTableEntry 5}

gslbNewCfgNetworkTable OBJECT-TYPE
        SYNTAX SEQUENCE OF GslbNewCfgNetworkTableEntry
        ACCESS not-accessible
        STATUS mandatory
        DESCRIPTION
                "The table of Internet network preference configuration in the 
                new_config."
        ::= { gslbNetwork 3 }

gslbNewCfgNetworkTableEntry OBJECT-TYPE
        SYNTAX GslbNewCfgNetworkTableEntry
        ACCESS not-accessible
        STATUS mandatory
        DESCRIPTION
                "The table about a network preference entry configuration."
        INDEX { gslbNewCfgNetworkIndx }
        ::= { gslbNewCfgNetworkTable 1 }


GslbNewCfgNetworkTableEntry ::= SEQUENCE {
        gslbNewCfgNetworkIndx       INTEGER,
        gslbNewCfgNetworkSourceIp   IpAddress,
        gslbNewCfgNetworkNetMask    IpAddress,
        gslbNewCfgNetworkVip1       IpAddress,
        gslbNewCfgNetworkVip2       IpAddress,
        gslbNewCfgNetworkDelete     INTEGER
        } 

gslbNewCfgNetworkIndx  OBJECT-TYPE
        SYNTAX INTEGER
        ACCESS read-only
        STATUS mandatory
        DESCRIPTION
                "The new Internet network preference table index."
        ::= { gslbNewCfgNetworkTableEntry 1 }

gslbNewCfgNetworkSourceIp OBJECT-TYPE
        SYNTAX IpAddress
        ACCESS read-write
        STATUS mandatory
        DESCRIPTION
                "The Source IP address of the network table."
        ::= { gslbNewCfgNetworkTableEntry 2}

gslbNewCfgNetworkNetMask OBJECT-TYPE
        SYNTAX IpAddress
        ACCESS read-write
        STATUS mandatory
        DESCRIPTION
                "The Net mask of the network table."
        ::= { gslbNewCfgNetworkTableEntry 3}

gslbNewCfgNetworkVip1 OBJECT-TYPE
        SYNTAX IpAddress
        ACCESS read-write
        STATUS mandatory
        DESCRIPTION
                "The Vip1 of the network table."
        ::= { gslbNewCfgNetworkTableEntry 4}

gslbNewCfgNetworkVip2 OBJECT-TYPE
        SYNTAX IpAddress
        ACCESS read-write
        STATUS mandatory
        DESCRIPTION
                "The Vip2 of the network table."
        ::= { gslbNewCfgNetworkTableEntry 5}

gslbNewCfgNetworkDelete OBJECT-TYPE
        SYNTAX INTEGER {
                other(1),
                delete(2)
                }
        ACCESS read-write
        STATUS mandatory
        DESCRIPTION
                "By setting the value to delete(2), the entire row is deleted."
        ::= { gslbNewCfgNetworkTableEntry 12}

-- GSLB Domain Name Server Configuration

dnsCurCfgPrimaryIpAddr OBJECT-TYPE
        SYNTAX  IpAddress
        ACCESS  read-only
        STATUS  mandatory
        DESCRIPTION
                "The DNS primary IP address in the current_configuration block."
        ::= { gslbDNS 1 }

dnsNewCfgPrimaryIpAddr OBJECT-TYPE
        SYNTAX  IpAddress
        ACCESS  read-write
        STATUS  mandatory
        DESCRIPTION
                "The DNS primary IP address in the new_configuration block."
        ::= { gslbDNS 2 }

dnsCurCfgSecondaryIpAddr OBJECT-TYPE
        SYNTAX  IpAddress
        ACCESS  read-only
        STATUS  mandatory
        DESCRIPTION
                "The DNS primary IP address in the current_configuration block."
        ::= { gslbDNS 3 }

dnsNewCfgSecondaryIpAddr OBJECT-TYPE
        SYNTAX  IpAddress
        ACCESS  read-write
        STATUS  mandatory
        DESCRIPTION
                "The DNS primary IP address in the new_configuration block."
        ::= { gslbDNS 4 }

dnsCurCfgDomainName OBJECT-TYPE
        SYNTAX  DisplayString
        ACCESS  read-only
        STATUS  mandatory
        DESCRIPTION
                "The DNS doamin name in the current_configuration block."
        ::= { gslbDNS 5 }

dnsNewCfgDomainName OBJECT-TYPE
        SYNTAX  DisplayString
        ACCESS  read-write
        STATUS  mandatory
        DESCRIPTION
                "The DNS doamin name in the new_configuration block."
        ::= { gslbDNS 6 }


-- GSLB Remote Sites Configuration

gslbRemSiteTableMaxSize OBJECT-TYPE
        SYNTAX  INTEGER
        ACCESS  read-only
        STATUS  mandatory
        DESCRIPTION
                "The maximum number of GSLB remote sites."
        ::= { gslbSites 1 }

gslbCurCfgRemSiteTable OBJECT-TYPE
        SYNTAX  SEQUENCE OF GslbCurCfgRemSiteTableEntry
        ACCESS  not-accessible
        STATUS  mandatory
        DESCRIPTION
                "The GSLB remote sites table in the current configuration 
		 block."
        ::= { gslbSites 2 }

gslbCurCfgRemSiteTableEntry OBJECT-TYPE
        SYNTAX  GslbCurCfgRemSiteTableEntry
        ACCESS  not-accessible
        STATUS  mandatory
        DESCRIPTION
                "A row in the GSLB remote sites table."
        INDEX   { gslbCurCfgRemSiteIndx }
        ::= { gslbCurCfgRemSiteTable 1 }

GslbCurCfgRemSiteTableEntry ::= SEQUENCE {
        gslbCurCfgRemSiteIndx        INTEGER,
        gslbCurCfgRemSitePrimaryIp   IpAddress,
        gslbCurCfgRemSiteSecondaryIp IpAddress,
        gslbCurCfgRemSiteState       INTEGER,
        gslbCurCfgRemSiteUpdate      INTEGER
        }

gslbCurCfgRemSiteIndx OBJECT-TYPE
        SYNTAX  INTEGER
        ACCESS  read-only
        STATUS  mandatory
        DESCRIPTION
                "The GSLB remote sites table index."
        ::= { gslbCurCfgRemSiteTableEntry 1 }

gslbCurCfgRemSitePrimaryIp OBJECT-TYPE
        SYNTAX  IpAddress
        ACCESS  read-only
        STATUS  mandatory
        DESCRIPTION
                "The primary IP address of the remote site in the 
		 current_configuration block."
        ::= { gslbCurCfgRemSiteTableEntry 2 }

gslbCurCfgRemSiteSecondaryIp OBJECT-TYPE
        SYNTAX  IpAddress
        ACCESS  read-only
        STATUS  mandatory
        DESCRIPTION
                "The secondary IP address of the remote site in the 
		 current_configuration block."
        ::= { gslbCurCfgRemSiteTableEntry 3 }

gslbCurCfgRemSiteState OBJECT-TYPE
        SYNTAX  INTEGER {
                enabled(1),
                disabled(2)
                }
        ACCESS  read-only
        STATUS  mandatory
        DESCRIPTION
                "Enable/Disable GSLB for the remote site in the 
                 current_configuration block."
        ::= { gslbCurCfgRemSiteTableEntry 4 }

gslbCurCfgRemSiteUpdate OBJECT-TYPE
        SYNTAX  INTEGER {
                enabled(1),
                disabled(2)
                }
        ACCESS  read-only
        STATUS  mandatory
        DESCRIPTION
                "Enable/Disable GSLB for the remote site status update in the 
                 current_configuration block."
        ::= { gslbCurCfgRemSiteTableEntry 5 }

gslbNewCfgRemSiteTable OBJECT-TYPE
        SYNTAX  SEQUENCE OF GslbNewCfgRemSiteTableEntry
        ACCESS  not-accessible
        STATUS  mandatory
        DESCRIPTION
                "The GSLB remote sites table in the current configuration 
		 block."
        ::= { gslbSites 3 }

gslbNewCfgRemSiteTableEntry OBJECT-TYPE
        SYNTAX  GslbNewCfgRemSiteTableEntry
        ACCESS  not-accessible
        STATUS  mandatory
        DESCRIPTION
                "A row in the GSLB remote sites table."
        INDEX   { gslbNewCfgRemSiteIndx }
        ::= { gslbNewCfgRemSiteTable 1 }

GslbNewCfgRemSiteTableEntry ::= SEQUENCE {
        gslbNewCfgRemSiteIndx        INTEGER,
        gslbNewCfgRemSitePrimaryIp   IpAddress,
        gslbNewCfgRemSiteSecondaryIp IpAddress,
        gslbNewCfgRemSiteState       INTEGER,
        gslbNewCfgRemSiteUpdate      INTEGER
        }

gslbNewCfgRemSiteIndx OBJECT-TYPE
        SYNTAX  INTEGER
        ACCESS  read-only
        STATUS  mandatory
        DESCRIPTION
                "The GSLB remote sites table index."
        ::= { gslbNewCfgRemSiteTableEntry 1 }

gslbNewCfgRemSitePrimaryIp OBJECT-TYPE
        SYNTAX  IpAddress
        ACCESS  read-write
        STATUS  mandatory
        DESCRIPTION
                "The primary IP address of the remote site in the 
		 new_configuration block."
        ::= { gslbNewCfgRemSiteTableEntry 2 }

gslbNewCfgRemSiteSecondaryIp OBJECT-TYPE
        SYNTAX  IpAddress
        ACCESS  read-write
        STATUS  mandatory
        DESCRIPTION
                "The secondary IP address of the remote site in the 
		 new_configuration block."
        ::= { gslbNewCfgRemSiteTableEntry 3 }

gslbNewCfgRemSiteState OBJECT-TYPE
        SYNTAX  INTEGER {
                enabled(1),
                disabled(2)
                }
        ACCESS  read-write
        STATUS  mandatory
        DESCRIPTION
                "Enable/Disable GSLB for the remote site in the 
                 new_configuration block."
        ::= { gslbNewCfgRemSiteTableEntry 4 }

gslbNewCfgRemSiteUpdate OBJECT-TYPE
        SYNTAX  INTEGER {
                enabled(1),
                disabled(2)
                }
        ACCESS  read-write
        STATUS  mandatory
        DESCRIPTION
                "Enable/Disable GSLB for the remote site status update in the 
                 new_configuration block."
        ::= { gslbNewCfgRemSiteTableEntry 5 }


-- VRRP (Virtual Router Redundantcy Protocol) Group

vrrpGeneral       OBJECT IDENTIFIER ::= { vrrp 1 }

vrrpCurCfgGenState OBJECT-TYPE
        SYNTAX  INTEGER {
                enabled(1),
                disabled(2)
                }
        ACCESS  read-only
        STATUS  mandatory
        DESCRIPTION
                "Enable or disable VRRP operation globally."
        ::= { vrrpGeneral 1 }

vrrpNewCfgGenState OBJECT-TYPE
        SYNTAX  INTEGER {
                enabled(1),
                disabled(2)
                }
        ACCESS  read-write
        STATUS  mandatory
        DESCRIPTION
                "Enable or disable VRRP operation globally."
        ::= { vrrpGeneral 2 }

vrrpCurCfgGenTckVirtRtrInc OBJECT-TYPE
        SYNTAX  INTEGER (0..254)
        ACCESS  read-only
        STATUS  mandatory
        DESCRIPTION
                "The increment of VRRP virtual router priority.  The
		 priority is adjusted by tracking the state of other 
		 virtual routers."
        ::= { vrrpGeneral 3 }

vrrpNewCfgGenTckVirtRtrInc OBJECT-TYPE
        SYNTAX  INTEGER (0..254)
        ACCESS  read-write
        STATUS  mandatory
        DESCRIPTION
                "The increment of VRRP virtual router priority.  The
		 priority is adjusted by tracking the state of other 
		 virtual routers."
        ::= { vrrpGeneral 4 }

vrrpCurCfgGenTckIpIntfInc OBJECT-TYPE
        SYNTAX  INTEGER (0..254)
        ACCESS  read-only
        STATUS  mandatory
        DESCRIPTION
                "The increment of VRRP virtual router priority.  The
		 priority is adjusted by tracking the state of other 
		 router interfaces."
        ::= { vrrpGeneral 5 }

vrrpNewCfgGenTckIpIntfInc OBJECT-TYPE
        SYNTAX  INTEGER (0..254)
        ACCESS  read-write
        STATUS  mandatory
        DESCRIPTION
                "The increment of VRRP virtual router priority.  The
		 priority is adjusted by tracking the state of other 
		 router interfaces."
        ::= { vrrpGeneral 6 }

vrrpCurCfgGenTckVlanPortInc OBJECT-TYPE
        SYNTAX  INTEGER (0..254)
        ACCESS  read-only
        STATUS  mandatory
        DESCRIPTION
                "The increment of VRRP virtual router priority.  The
		 priority is adjusted by tracking the port state of 
		 ports that belongs to the same virtual LAN as the
		 virtual router."
        ::= { vrrpGeneral 7 }

vrrpNewCfgGenTckVlanPortInc OBJECT-TYPE
        SYNTAX  INTEGER (0..254)
        ACCESS  read-write
        STATUS  mandatory
        DESCRIPTION
                "The increment of VRRP virtual router priority.  The
		 priority is adjusted by tracking the port state of 
		 ports that belongs to the same virtual LAN as the
		 virtual router."
        ::= { vrrpGeneral 8 }

vrrpCurCfgGenTckL4PortInc OBJECT-TYPE
        SYNTAX  INTEGER (0..254)
        ACCESS  read-only
        STATUS  mandatory
        DESCRIPTION
                "The increment of VRRP virtual router priority.  The
		 priority is adjusted by tracking the Layer 4 port 
		 states.  This is valid when virtual server is configured
		 as a VRRP virtual router."
        ::= { vrrpGeneral 9 }

vrrpNewCfgGenTckL4PortInc OBJECT-TYPE
        SYNTAX  INTEGER (0..254)
        ACCESS  read-write
        STATUS  mandatory
        DESCRIPTION
                "The increment of VRRP virtual router priority.  The
		 priority is adjusted by tracking the Layer 4 port 
		 states.  This is valid when virtual server is configured
		 as a VRRP virtual router."
        ::= { vrrpGeneral 10 }

vrrpCurCfgGenTckRServerInc OBJECT-TYPE
        SYNTAX  INTEGER (0..254)
        ACCESS  read-only
        STATUS  mandatory
        DESCRIPTION
                "The increment of VRRP virtual router priority.  The
		 priority is adjusted by tracking the state of real 
		 servers under the virtual server which is configured 
		 as a VRRP virtual router."
        ::= { vrrpGeneral 11 }

vrrpNewCfgGenTckRServerInc OBJECT-TYPE
        SYNTAX  INTEGER (0..254)
        ACCESS  read-write
        STATUS  mandatory
        DESCRIPTION
                "The increment of VRRP virtual router priority.  The
		 priority is adjusted by tracking the state of real 
		 servers under the virtual server which is configured 
		 as a VRRP virtual router."
        ::= { vrrpGeneral 12 }

vrrpCurCfgGenTckHsrpInc OBJECT-TYPE
        SYNTAX  INTEGER (0..254)
        ACCESS  read-only
        STATUS  mandatory
        DESCRIPTION
                "The increment of VRRP virtual router priority.  The
		 priority is adjusted by tracking the HSRP advertisements."
        ::= { vrrpGeneral 13 }

vrrpNewCfgGenTckHsrpInc OBJECT-TYPE
        SYNTAX  INTEGER (0..254)
        ACCESS  read-write
        STATUS  mandatory
        DESCRIPTION
                "The increment of VRRP virtual router priority.  The
		 priority is adjusted by tracking the HSRP advertisements."
        ::= { vrrpGeneral 14 }

vrrpCurCfgGenHotstandby OBJECT-TYPE
        SYNTAX  INTEGER {
                enabled(1),
                disabled(2)
                }
        ACCESS  read-only
        STATUS  mandatory
        DESCRIPTION
                "Enable or disable hotstandby processing."
        ::= { vrrpGeneral 15 }

vrrpNewCfgGenHotstandby OBJECT-TYPE
        SYNTAX  INTEGER {
                enabled(1),
                disabled(2)
                }
        ACCESS  read-write
        STATUS  mandatory
        DESCRIPTION
                "Enable or disable hotstandby processing."
        ::= { vrrpGeneral 16 }


vrrpCurCfgVirtRtrTable OBJECT-TYPE
        SYNTAX  SEQUENCE OF VrrpCurCfgVirtRtrTableEntry
        ACCESS  not-accessible
        STATUS  mandatory
        DESCRIPTION
                "The table of VRRP virtual routers configuration in
                 current_config."
        ::= { vrrp 2 }
 
vrrpCurCfgVirtRtrTableEntry OBJECT-TYPE
        SYNTAX  VrrpCurCfgVirtRtrTableEntry
        ACCESS  not-accessible
        STATUS  mandatory
        DESCRIPTION
                "Information about a VRRP virtual router."
        INDEX   { vrrpCurCfgVirtRtrIndx }
        ::= { vrrpCurCfgVirtRtrTable 1 }
 
VrrpCurCfgVirtRtrTableEntry ::= SEQUENCE {
        vrrpCurCfgVirtRtrIndx         INTEGER,
        vrrpCurCfgVirtRtrID           INTEGER,
        vrrpCurCfgVirtRtrAddr         IpAddress,
        vrrpCurCfgVirtRtrIfIndex      INTEGER,
        vrrpCurCfgVirtRtrInterval     INTEGER,
        vrrpCurCfgVirtRtrPriority     INTEGER,
        vrrpCurCfgVirtRtrPreempt      INTEGER,
        vrrpCurCfgVirtRtrState        INTEGER,
        vrrpCurCfgVirtRtrSharing      INTEGER,
        vrrpCurCfgVirtRtrTckVirtRtr   INTEGER,
        vrrpCurCfgVirtRtrTckIpIntf    INTEGER,
        vrrpCurCfgVirtRtrTckVlanPort  INTEGER,
        vrrpCurCfgVirtRtrTckL4Port    INTEGER,
        vrrpCurCfgVirtRtrTckRServer   INTEGER,
        vrrpCurCfgVirtRtrTckHsrp      INTEGER
        }

vrrpCurCfgVirtRtrIndx OBJECT-TYPE
        SYNTAX  INTEGER
        ACCESS  read-only
        STATUS  mandatory
        DESCRIPTION
                "The VRRP virtual router table index."
        ::= { vrrpCurCfgVirtRtrTableEntry 1 }

vrrpCurCfgVirtRtrID OBJECT-TYPE
        SYNTAX  INTEGER (1..255)
        ACCESS  read-only
        STATUS  mandatory
        DESCRIPTION
                "The VRRP virtual router identifier."
        ::= { vrrpCurCfgVirtRtrTableEntry 2 }

vrrpCurCfgVirtRtrAddr OBJECT-TYPE
        SYNTAX  IpAddress
        ACCESS  read-only
        STATUS  mandatory
        DESCRIPTION
                "The VRRP virtual router IP address."
        ::= { vrrpCurCfgVirtRtrTableEntry 3 }

vrrpCurCfgVirtRtrIfIndex OBJECT-TYPE
        SYNTAX  INTEGER
        ACCESS  read-only
        STATUS  mandatory
        DESCRIPTION
                "The IfIndex that the VRRP virtual router is representing."
        ::= { vrrpCurCfgVirtRtrTableEntry 4 }

vrrpCurCfgVirtRtrInterval OBJECT-TYPE
        SYNTAX  INTEGER (1..255)
        ACCESS  read-only
        STATUS  mandatory
        DESCRIPTION
                "The time interval between VRRP advertisements in seconds."
        ::= { vrrpCurCfgVirtRtrTableEntry 5 }

vrrpCurCfgVirtRtrPriority OBJECT-TYPE
        SYNTAX  INTEGER (1..254)
        ACCESS  read-only
        STATUS  mandatory
        DESCRIPTION
                "The priority value to be used by the specified VRRP virtual
                 routers."
        ::= { vrrpCurCfgVirtRtrTableEntry 6 }

vrrpCurCfgVirtRtrPreempt OBJECT-TYPE
        SYNTAX  INTEGER {
                enabled(1),
                disabled(2)
                }
        ACCESS  read-only
        STATUS  mandatory
        DESCRIPTION
                "This is for controlling whether a higher priority Backup
                 VRRP virtual router preempts a low priority Master.

                 enabled(1)  - allow preemption
                 disabled(2) - prohibit preemption"
        ::= { vrrpCurCfgVirtRtrTableEntry 7 }

vrrpCurCfgVirtRtrState OBJECT-TYPE
        SYNTAX  INTEGER {
                enabled(1),
                disabled(2)
                }
        ACCESS  read-only
        STATUS  mandatory
        DESCRIPTION
                "Enable or disable the VRRP virtual router."
        ::= { vrrpCurCfgVirtRtrTableEntry 8 }

vrrpCurCfgVirtRtrSharing OBJECT-TYPE
        SYNTAX  INTEGER {
                enabled(1),
                disabled(2)
                }
        ACCESS  read-only
        STATUS  mandatory
        DESCRIPTION
                "Enable or disable load sharing of non-master
                 virtual router."
        ::= { vrrpCurCfgVirtRtrTableEntry 9 }

vrrpCurCfgVirtRtrTckVirtRtr OBJECT-TYPE
        SYNTAX  INTEGER {
                enabled(1),
                disabled(2)
                }
        ACCESS  read-only
        STATUS  mandatory
        DESCRIPTION
                "Enable or disable tracking other virtual routers for 
		 priority adjustment.  the priority increment is defined 
		 in vrrpCurCfgGenTckVirtRtrInc."
        ::= { vrrpCurCfgVirtRtrTableEntry 10 }

vrrpCurCfgVirtRtrTckIpIntf OBJECT-TYPE
        SYNTAX  INTEGER {
                enabled(1),
                disabled(2)
                }
        ACCESS  read-only
        STATUS  mandatory
        DESCRIPTION
                "Enable or disable tracking other router interfaces for 
		 priority adjustment.  the priority increment is defined 
		 in vrrpCurCfgGenTckIpIntfInc."
        ::= { vrrpCurCfgVirtRtrTableEntry 11 }

vrrpCurCfgVirtRtrTckVlanPort OBJECT-TYPE
        SYNTAX  INTEGER {
                enabled(1),
                disabled(2)
                }
        ACCESS  read-only
        STATUS  mandatory
        DESCRIPTION
                "Enable or disable tracking port state of VLAN ports 
		 for priority adjustment.  the priority increment is 
		 defined in vrrpCurCfgGenTckVlanPortInc."
        ::= { vrrpCurCfgVirtRtrTableEntry 12 }

vrrpCurCfgVirtRtrTckL4Port OBJECT-TYPE
        SYNTAX  INTEGER {
                enabled(1),
                disabled(2)
                }
        ACCESS  read-only
        STATUS  mandatory
        DESCRIPTION
                "Enable or disable tracking Layer 4 port states for 
		 priority adjustment.  the priority increment is defined 
		 in vrrpCurCfgGenTckL4PortInc.  This is applied when 
		 virtual server is configured as a VRRP virtual router."
        ::= { vrrpCurCfgVirtRtrTableEntry 13 }

vrrpCurCfgVirtRtrTckRServer OBJECT-TYPE
        SYNTAX  INTEGER {
                enabled(1),
                disabled(2)
                }
        ACCESS  read-only
        STATUS  mandatory
        DESCRIPTION
                "Enable or disable tracking real server states for 
		 priority adjustment.  the priority increment is defined 
		 in vrrpCurCfgGenTckRServerInc.  This is applied when 
		 virtual server is configured as a VRRP virtual router."
        ::= { vrrpCurCfgVirtRtrTableEntry 14 }


vrrpCurCfgVirtRtrTckHsrp OBJECT-TYPE
        SYNTAX  INTEGER {
                enabled(1),
                disabled(2)
                }
        ACCESS  read-only
        STATUS  mandatory
        DESCRIPTION
                "Enable or disable tracking HSRP advertisements for 
		 priority adjustment.  the priority increment is defined 
		 in vrrpCurCfgGenTckHsrpInc.  This is applied when 
		 virtual server is configured as a VRRP virtual router."
        ::= { vrrpCurCfgVirtRtrTableEntry 15 }


vrrpNewCfgVirtRtrTable OBJECT-TYPE
        SYNTAX  SEQUENCE OF VrrpNewCfgVirtRtrTableEntry
        ACCESS  not-accessible
        STATUS  mandatory
        DESCRIPTION
                "The table of VRRP virtual routers configuration in
                 current_config."
        ::= { vrrp 3 }

vrrpNewCfgVirtRtrTableEntry OBJECT-TYPE
        SYNTAX  VrrpNewCfgVirtRtrTableEntry
        ACCESS  not-accessible
        STATUS  mandatory
        DESCRIPTION
                "Information about a VRRP virtual router."
        INDEX   { vrrpNewCfgVirtRtrIndx }
        ::= { vrrpNewCfgVirtRtrTable 1 }

VrrpNewCfgVirtRtrTableEntry ::= SEQUENCE {
        vrrpNewCfgVirtRtrIndx         INTEGER,
        vrrpNewCfgVirtRtrID           INTEGER,
        vrrpNewCfgVirtRtrAddr         IpAddress,
        vrrpNewCfgVirtRtrIfIndex      INTEGER,
        vrrpNewCfgVirtRtrInterval     INTEGER,
        vrrpNewCfgVirtRtrPriority     INTEGER,
        vrrpNewCfgVirtRtrPreempt      INTEGER,
        vrrpNewCfgVirtRtrState        INTEGER,
        vrrpNewCfgVirtRtrDelete       INTEGER,
        vrrpNewCfgVirtRtrSharing      INTEGER,
        vrrpNewCfgVirtRtrTckVirtRtr   INTEGER,
        vrrpNewCfgVirtRtrTckIpIntf    INTEGER,
        vrrpNewCfgVirtRtrTckVlanPort  INTEGER,
        vrrpNewCfgVirtRtrTckL4Port    INTEGER,
        vrrpNewCfgVirtRtrTckRServer   INTEGER,
        vrrpNewCfgVirtRtrTckHsrp      INTEGER
        }

vrrpNewCfgVirtRtrIndx OBJECT-TYPE
        SYNTAX  INTEGER
        ACCESS  read-only
        STATUS  mandatory
        DESCRIPTION
                "The VRRP virtual router table index."
        ::= { vrrpNewCfgVirtRtrTableEntry 1 }

vrrpNewCfgVirtRtrID OBJECT-TYPE
        SYNTAX  INTEGER (1..255)
        ACCESS  read-write
        STATUS  mandatory
        DESCRIPTION
                "The VRRP virtual router identifier."
        ::= { vrrpNewCfgVirtRtrTableEntry 2 }

vrrpNewCfgVirtRtrAddr OBJECT-TYPE
        SYNTAX  IpAddress
        ACCESS  read-write
        STATUS  mandatory
        DESCRIPTION
                "The VRRP virtual router IP address."
        ::= { vrrpNewCfgVirtRtrTableEntry 3 }

vrrpNewCfgVirtRtrIfIndex OBJECT-TYPE
        SYNTAX  INTEGER
        ACCESS  read-write
        STATUS  mandatory
        DESCRIPTION
                "The IfIndex that the VRRP virtual router is representing."
        ::= { vrrpNewCfgVirtRtrTableEntry 4 }

vrrpNewCfgVirtRtrInterval OBJECT-TYPE
        SYNTAX  INTEGER (1..255)
        ACCESS  read-write
        STATUS  mandatory
        DESCRIPTION
                "The time interval between VRRP advertisements in seconds."
        ::= { vrrpNewCfgVirtRtrTableEntry 5 }

vrrpNewCfgVirtRtrPriority OBJECT-TYPE
        SYNTAX  INTEGER (1..254)
        ACCESS  read-write
        STATUS  mandatory
        DESCRIPTION
                "The priority value to be used by the specified VRRP virtual
                 router."
        ::= { vrrpNewCfgVirtRtrTableEntry 6 }

vrrpNewCfgVirtRtrPreempt OBJECT-TYPE
        SYNTAX  INTEGER {
                enabled(1),
                disabled(2)
                }
        ACCESS  read-write
        STATUS  mandatory
        DESCRIPTION
                "This is for controlling whether a higher priority Backup
                 VRRP virtual router preempts a low priority Master.

                 enabled(1)  - allow preemption
                 disabled(2) - prohibit preemption"
        ::= { vrrpNewCfgVirtRtrTableEntry 7 }

vrrpNewCfgVirtRtrState OBJECT-TYPE
        SYNTAX  INTEGER {
                enabled(1),
                disabled(2)
                }
        ACCESS  read-write
        STATUS  mandatory
        DESCRIPTION
                "Enable or disable the VRRP virtual router."
        ::= { vrrpNewCfgVirtRtrTableEntry 8 }

vrrpNewCfgVirtRtrDelete OBJECT-TYPE
      SYNTAX  INTEGER { 
		other(1),
                delete(2)
		}
      ACCESS  read-write
      STATUS  mandatory
      DESCRIPTION
              "When set to the value of 2 (delete), the entire row
	       is deleted. When read, other(1) is returned. Setting the value
	       to anything other than delete(2) has no effect on the state
	       of the row."
      ::= { vrrpNewCfgVirtRtrTableEntry 9 }

vrrpNewCfgVirtRtrSharing OBJECT-TYPE
        SYNTAX  INTEGER {
                enabled(1),
                disabled(2)
                }
        ACCESS  read-write
        STATUS  mandatory
        DESCRIPTION
                "Enable or disable load sharing of non-master
                 virtual router."
        ::= { vrrpNewCfgVirtRtrTableEntry 10 }

vrrpNewCfgVirtRtrTckVirtRtr OBJECT-TYPE
        SYNTAX  INTEGER {
                enabled(1),
                disabled(2)
                }
        ACCESS  read-write
        STATUS  mandatory
        DESCRIPTION
                "Enable or disable tracking other virtual routers for 
		 priority adjustment.  the priority increment is defined 
		 in vrrpNewCfgGenTckVirtRtrInc."
        ::= { vrrpNewCfgVirtRtrTableEntry 11 }

vrrpNewCfgVirtRtrTckIpIntf OBJECT-TYPE
        SYNTAX  INTEGER {
                enabled(1),
                disabled(2)
                }
        ACCESS  read-write
        STATUS  mandatory
        DESCRIPTION
                "Enable or disable tracking other router interfaces for 
		 priority adjustment.  the priority increment is defined 
		 in vrrpNewCfgGenTckIpIntfInc."
        ::= { vrrpNewCfgVirtRtrTableEntry 12 }

vrrpNewCfgVirtRtrTckVlanPort OBJECT-TYPE
        SYNTAX  INTEGER {
                enabled(1),
                disabled(2)
                }
        ACCESS  read-write
        STATUS  mandatory
        DESCRIPTION
                "Enable or disable tracking port state of VLAN ports 
		 for priority adjustment.  the priority increment is 
		 defined in vrrpNewCfgGenTckVlanPortInc."
        ::= { vrrpNewCfgVirtRtrTableEntry 13 }

vrrpNewCfgVirtRtrTckL4Port OBJECT-TYPE
        SYNTAX  INTEGER {
                enabled(1),
                disabled(2)
                }
        ACCESS  read-write
        STATUS  mandatory
        DESCRIPTION
                "Enable or disable tracking Layer 4 port states for 
		 priority adjustment.  the priority increment is defined 
		 in vrrpNewCfgGenTckL4PortInc.  This is applied when 
		 virtual server is configured as a VRRP virtual router."
        ::= { vrrpNewCfgVirtRtrTableEntry 14 }

vrrpNewCfgVirtRtrTckRServer OBJECT-TYPE
        SYNTAX  INTEGER {
                enabled(1),
                disabled(2)
                }
        ACCESS  read-write
        STATUS  mandatory
        DESCRIPTION
                "Enable or disable tracking real server states for 
		 priority adjustment.  the priority increment is defined 
		 in vrrpNewCfgGenTckRServerInc.  This is applied when 
		 virtual server is configured as a VRRP virtual router."
        ::= { vrrpNewCfgVirtRtrTableEntry 15 }

vrrpNewCfgVirtRtrTckHsrp OBJECT-TYPE
        SYNTAX  INTEGER {
                enabled(1),
                disabled(2)
                }
        ACCESS  read-write
        STATUS  mandatory
        DESCRIPTION
                "Enable or disable tracking HSRP advertisements for 
		 priority adjustment.  the priority increment is defined 
		 in vrrpNewCfgGenTckHsrpInc.  This is applied when 
		 virtual server is configured as a VRRP virtual router."
        ::= { vrrpNewCfgVirtRtrTableEntry 16 }


-- VRRP Interface Table

vrrpCurCfgIfTable OBJECT-TYPE
        SYNTAX  SEQUENCE OF VrrpCurCfgIfTableEntry
        ACCESS  not-accessible
        STATUS  mandatory
        DESCRIPTION
                "The table of VRRP interface configuration in current_config."
        ::= { vrrp 4 }
 
vrrpCurCfgIfTableEntry OBJECT-TYPE
        SYNTAX  VrrpCurCfgIfTableEntry
        ACCESS  not-accessible
        STATUS  mandatory
        DESCRIPTION
                "Information about a VRRP interface."
        INDEX   { vrrpCurCfgIfIndx }
        ::= { vrrpCurCfgIfTable 1 }
 
VrrpCurCfgIfTableEntry ::= SEQUENCE {
        vrrpCurCfgIfIndx         INTEGER,
        vrrpCurCfgIfAuthType     INTEGER,
        vrrpCurCfgIfPasswd       DisplayString
        }

vrrpCurCfgIfIndx OBJECT-TYPE
        SYNTAX  INTEGER
        ACCESS  read-only
        STATUS  mandatory
        DESCRIPTION
                "The VRRP interface index.  This is eqivalent to IfIndex."
        ::= { vrrpCurCfgIfTableEntry 1 }

vrrpCurCfgIfAuthType OBJECT-TYPE
        SYNTAX  INTEGER {
                none(1),
                simple-text-password(2)
                }
        ACCESS  read-only
        STATUS  mandatory
        DESCRIPTION
                "Type of authentication being used.
		 none(1) - no authentication
		 simple-text-password(2) - use password specified in 
                           vrrpCurCfgIfPasswd for authentication."
        ::= { vrrpCurCfgIfTableEntry 2 }

vrrpCurCfgIfPasswd OBJECT-TYPE
        SYNTAX  DisplayString (SIZE(0..8))
        ACCESS  read-only
        STATUS  mandatory
        DESCRIPTION
                "The password for authentication."
        ::= { vrrpCurCfgIfTableEntry 3 }

vrrpNewCfgIfTable OBJECT-TYPE
        SYNTAX  SEQUENCE OF VrrpNewCfgIfTableEntry
        ACCESS  not-accessible
        STATUS  mandatory
        DESCRIPTION
                "The table of VRRP interface configuration in current_config."
        ::= { vrrp 5 }
 
vrrpNewCfgIfTableEntry OBJECT-TYPE
        SYNTAX  VrrpNewCfgIfTableEntry
        ACCESS  not-accessible
        STATUS  mandatory
        DESCRIPTION
                "Information about a VRRP interface."
        INDEX   { vrrpNewCfgIfIndx }
        ::= { vrrpNewCfgIfTable 1 }
 
VrrpNewCfgIfTableEntry ::= SEQUENCE {
        vrrpNewCfgIfIndx         INTEGER,
        vrrpNewCfgIfAuthType     INTEGER,
        vrrpNewCfgIfPasswd       DisplayString,
        vrrpNewCfgIfDelete       INTEGER
        }

vrrpNewCfgIfIndx OBJECT-TYPE
        SYNTAX  INTEGER
        ACCESS  read-only
        STATUS  mandatory
        DESCRIPTION
                "The VRRP interface index.  This is eqivalent to IfIndex."
        ::= { vrrpNewCfgIfTableEntry 1 }

vrrpNewCfgIfAuthType OBJECT-TYPE
        SYNTAX  INTEGER {
                none(1),
                simple-text-password(2)
                }
        ACCESS  read-write
        STATUS  mandatory
        DESCRIPTION
                "Type of authentication being used.
		 none(1) - no authentication
		 simple-text-password(2) - use password specified in 
                           vrrpNewCfgIfPasswd for authentication."
        ::= { vrrpNewCfgIfTableEntry 2 }

vrrpNewCfgIfPasswd OBJECT-TYPE
        SYNTAX  DisplayString (SIZE(0..8))
        ACCESS  read-write
        STATUS  mandatory
        DESCRIPTION
                "The password for authentication."
        ::= { vrrpNewCfgIfTableEntry 3 }

vrrpNewCfgIfDelete OBJECT-TYPE
        SYNTAX  INTEGER {
                other(1),
                delete(2)
                }
        ACCESS  read-write
        STATUS  mandatory
        DESCRIPTION
                "When set to the value of 2 (delete), the entire row
                 is deleted. When read, other(1) is returned. Setting the value
                 to anything other than delete(2) has no effect on the state
                 of the row."
        ::= { vrrpNewCfgIfTableEntry 4 }


-- Failover Virtual Router Groups

vrrpCurCfgVirtRtrGrpTable OBJECT-TYPE
        SYNTAX  SEQUENCE OF VrrpCurCfgVirtRtrGrpTableEntry
        ACCESS  not-accessible
        STATUS  mandatory
        DESCRIPTION
                "The table of VRRP virtual router group configuration in
                 current_config."
        ::= { vrrp 6 }

vrrpCurCfgVirtRtrGrpTableEntry OBJECT-TYPE
        SYNTAX  VrrpCurCfgVirtRtrGrpTableEntry
        ACCESS  not-accessible
        STATUS  mandatory
        DESCRIPTION
                "Information about a VRRP failover virtual router."
        INDEX   { vrrpCurCfgVirtRtrGrpIndx }
        ::= { vrrpCurCfgVirtRtrGrpTable 1 }

VrrpCurCfgVirtRtrGrpTableEntry ::= SEQUENCE {
        vrrpCurCfgVirtRtrGrpIndx         INTEGER,
        vrrpCurCfgVirtRtrGrpID           INTEGER,
        vrrpCurCfgVirtRtrGrpIfIndex      INTEGER,
        vrrpCurCfgVirtRtrGrpInterval     INTEGER,
        vrrpCurCfgVirtRtrGrpPriority     INTEGER,
        vrrpCurCfgVirtRtrGrpPreempt      INTEGER,
        vrrpCurCfgVirtRtrGrpState        INTEGER,
        vrrpCurCfgVirtRtrGrpSharing      INTEGER,
        vrrpCurCfgVirtRtrGrpTckVirtRtr   INTEGER,
        vrrpCurCfgVirtRtrGrpTckIpIntf    INTEGER,
        vrrpCurCfgVirtRtrGrpTckVlanPort  INTEGER,
        vrrpCurCfgVirtRtrGrpTckL4Port    INTEGER,
        vrrpCurCfgVirtRtrGrpTckRServer   INTEGER,
        vrrpCurCfgVirtRtrGrpTckHsrp      INTEGER
        }
 
vrrpCurCfgVirtRtrGrpIndx OBJECT-TYPE
        SYNTAX  INTEGER
        ACCESS  read-only
        STATUS  mandatory
        DESCRIPTION
                "The VRRP virtual router table index."
        ::= { vrrpCurCfgVirtRtrGrpTableEntry 1 }
 
vrrpCurCfgVirtRtrGrpID OBJECT-TYPE
        SYNTAX  INTEGER (1..255)
        ACCESS  read-only
        STATUS  mandatory
        DESCRIPTION
                "The VRRP virtual router identifier."
        ::= { vrrpCurCfgVirtRtrGrpTableEntry 2 }
 
vrrpCurCfgVirtRtrGrpIfIndex OBJECT-TYPE
        SYNTAX  INTEGER
        ACCESS  read-only
        STATUS  mandatory
        DESCRIPTION
                "The IfIndex that the VRRP virtual router is representing."
        ::= { vrrpCurCfgVirtRtrGrpTableEntry 3 }

vrrpCurCfgVirtRtrGrpInterval OBJECT-TYPE
        SYNTAX  INTEGER (1..255)
        ACCESS  read-only
        STATUS  mandatory
        DESCRIPTION
                "The time interval between VRRP advertisements in seconds."
        ::= { vrrpCurCfgVirtRtrGrpTableEntry 4 }

vrrpCurCfgVirtRtrGrpPriority OBJECT-TYPE
        SYNTAX  INTEGER (1..254)
        ACCESS  read-only
        STATUS  mandatory
        DESCRIPTION
                "The priority value to be used by the specified VRRP virtual
                 routers."
        ::= { vrrpCurCfgVirtRtrGrpTableEntry 5 }

vrrpCurCfgVirtRtrGrpPreempt OBJECT-TYPE
        SYNTAX  INTEGER {
                enabled(1),
                disabled(2)
                }
        ACCESS  read-only
        STATUS  mandatory
        DESCRIPTION
                "This is for controlling whether a higher priority Backup
                 VRRP virtual router preempts a low priority Master.

                 enabled(1)  - allow preemption
                 disabled(2) - prohibit preemption"
        ::= { vrrpCurCfgVirtRtrGrpTableEntry 6 }

vrrpCurCfgVirtRtrGrpState OBJECT-TYPE
        SYNTAX  INTEGER {
                enabled(1),
                disabled(2)
                }
        ACCESS  read-only
        STATUS  mandatory
        DESCRIPTION
                "Enable or disable the VRRP virtual router."
        ::= { vrrpCurCfgVirtRtrGrpTableEntry 7 }

vrrpCurCfgVirtRtrGrpSharing OBJECT-TYPE
        SYNTAX  INTEGER {
                enabled(1),
                disabled(2)
                }
        ACCESS  read-only
        STATUS  mandatory
        DESCRIPTION
                "Enable or disable load sharing of non-master
                 virtual router."
        ::= { vrrpCurCfgVirtRtrGrpTableEntry 8 }

vrrpCurCfgVirtRtrGrpTckVirtRtr OBJECT-TYPE
        SYNTAX  INTEGER {
                enabled(1),
                disabled(2)
                }
        ACCESS  read-only
        STATUS  mandatory
        DESCRIPTION
                "Enable or disable tracking other virtual routers for
                 priority adjustment.  the priority increment is defined
                 in vrrpCurCfgGenTckVirtRtrInc."
        ::= { vrrpCurCfgVirtRtrGrpTableEntry 9 }

vrrpCurCfgVirtRtrGrpTckIpIntf OBJECT-TYPE
        SYNTAX  INTEGER {
                enabled(1),
                disabled(2)
                }
        ACCESS  read-only
        STATUS  mandatory
        DESCRIPTION
                "Enable or disable tracking other router interfaces for
                 priority adjustment.  the priority increment is defined
                 in vrrpCurCfgGenTckIpIntfInc."
        ::= { vrrpCurCfgVirtRtrGrpTableEntry 10 }

vrrpCurCfgVirtRtrGrpTckVlanPort OBJECT-TYPE
        SYNTAX  INTEGER {
                enabled(1),
                disabled(2)
                }
        ACCESS  read-only
        STATUS  mandatory
        DESCRIPTION
                "Enable or disable tracking port state of VLAN ports
                 for priority adjustment.  the priority increment is
                 defined in vrrpCurCfgGenTckVlanPortInc."
        ::= { vrrpCurCfgVirtRtrGrpTableEntry 11 }

vrrpCurCfgVirtRtrGrpTckL4Port OBJECT-TYPE
        SYNTAX  INTEGER {
                enabled(1),
                disabled(2)
                }
        ACCESS  read-only
        STATUS  mandatory
        DESCRIPTION
                "Enable or disable tracking Layer 4 port states for
                 priority adjustment.  the priority increment is defined
                 in vrrpCurCfgGenTckL4PortInc.  This is applied when
                 virtual server is configured as a VRRP virtual router."
        ::= { vrrpCurCfgVirtRtrGrpTableEntry 12 }

vrrpCurCfgVirtRtrGrpTckRServer OBJECT-TYPE
        SYNTAX  INTEGER {
                enabled(1),
                disabled(2)
                }
        ACCESS  read-only
        STATUS  mandatory
        DESCRIPTION
                "Enable or disable tracking real server states for
                 priority adjustment.  the priority increment is defined
                 in vrrpCurCfgGenTckRServerInc.  This is applied when
                 virtual server is configured as a VRRP virtual router."
        ::= { vrrpCurCfgVirtRtrGrpTableEntry 13 }


vrrpCurCfgVirtRtrGrpTckHsrp OBJECT-TYPE
        SYNTAX  INTEGER {
                enabled(1),
                disabled(2)
                }
        ACCESS  read-only
        STATUS  mandatory
        DESCRIPTION
                "Enable or disable tracking HSRP advertisements for
                 priority adjustment.  the priority increment is defined
                 in vrrpCurCfgGenTckHsrpInc.  This is applied when
                 virtual server is configured as a VRRP virtual router."
        ::= { vrrpCurCfgVirtRtrGrpTableEntry 14 }


vrrpNewCfgVirtRtrGrpTable OBJECT-TYPE
        SYNTAX  SEQUENCE OF VrrpNewCfgVirtRtrGrpTableEntry
        ACCESS  not-accessible
        STATUS  mandatory
        DESCRIPTION
                "The table of VRRP virtual router group configuration in
                 new_config."
        ::= { vrrp 7 }

vrrpNewCfgVirtRtrGrpTableEntry OBJECT-TYPE
        SYNTAX  VrrpNewCfgVirtRtrGrpTableEntry
        ACCESS  not-accessible
        STATUS  mandatory
        DESCRIPTION
                "Information about a VRRP failover virtual router."
        INDEX   { vrrpNewCfgVirtRtrGrpIndx }
        ::= { vrrpNewCfgVirtRtrGrpTable 1 }
 
VrrpNewCfgVirtRtrGrpTableEntry ::= SEQUENCE {
        vrrpNewCfgVirtRtrGrpIndx         INTEGER,
        vrrpNewCfgVirtRtrGrpID           INTEGER,
        vrrpNewCfgVirtRtrGrpIfIndex      INTEGER,
        vrrpNewCfgVirtRtrGrpInterval     INTEGER,
        vrrpNewCfgVirtRtrGrpPriority     INTEGER,
        vrrpNewCfgVirtRtrGrpPreempt      INTEGER,
        vrrpNewCfgVirtRtrGrpState        INTEGER,
        vrrpNewCfgVirtRtrGrpDelete       INTEGER,
        vrrpNewCfgVirtRtrGrpSharing      INTEGER,
        vrrpNewCfgVirtRtrGrpTckVirtRtr   INTEGER,
        vrrpNewCfgVirtRtrGrpTckIpIntf    INTEGER,
        vrrpNewCfgVirtRtrGrpTckVlanPort  INTEGER,
        vrrpNewCfgVirtRtrGrpTckL4Port    INTEGER,
        vrrpNewCfgVirtRtrGrpTckRServer   INTEGER,
        vrrpNewCfgVirtRtrGrpTckHsrp      INTEGER
        }
 
vrrpNewCfgVirtRtrGrpIndx OBJECT-TYPE
        SYNTAX  INTEGER
        ACCESS  read-only
        STATUS  mandatory
        DESCRIPTION
                "The VRRP virtual router table index."
        ::= { vrrpNewCfgVirtRtrGrpTableEntry 1 }
 
vrrpNewCfgVirtRtrGrpID OBJECT-TYPE
        SYNTAX  INTEGER (1..255)
        ACCESS  read-write
        STATUS  mandatory
        DESCRIPTION
                "The VRRP virtual router identifier."
        ::= { vrrpNewCfgVirtRtrGrpTableEntry 2 }
 
vrrpNewCfgVirtRtrGrpIfIndex OBJECT-TYPE
        SYNTAX  INTEGER
        ACCESS  read-write
        STATUS  mandatory
        DESCRIPTION
                "The IfIndex that the VRRP virtual router is representing."
        ::= { vrrpNewCfgVirtRtrGrpTableEntry 3 }

vrrpNewCfgVirtRtrGrpInterval OBJECT-TYPE
        SYNTAX  INTEGER (1..255)
        ACCESS  read-write
        STATUS  mandatory
        DESCRIPTION
                "The time interval between VRRP advertisements in seconds."
        ::= { vrrpNewCfgVirtRtrGrpTableEntry 4 }

vrrpNewCfgVirtRtrGrpPriority OBJECT-TYPE
        SYNTAX  INTEGER (1..254)
        ACCESS  read-write
        STATUS  mandatory
        DESCRIPTION
                "The priority value to be used by the specified VRRP virtual
                 router."
        ::= { vrrpNewCfgVirtRtrGrpTableEntry 5 }

vrrpNewCfgVirtRtrGrpPreempt OBJECT-TYPE
        SYNTAX  INTEGER {
                enabled(1),
                disabled(2)
                }
        ACCESS  read-write
        STATUS  mandatory
        DESCRIPTION
                "This is for controlling whether a higher priority Backup
                 VRRP virtual router preempts a low priority Master.

                 enabled(1)  - allow preemption
                 disabled(2) - prohibit preemption"
        ::= { vrrpNewCfgVirtRtrGrpTableEntry 6 }

vrrpNewCfgVirtRtrGrpState OBJECT-TYPE
        SYNTAX  INTEGER {
                enabled(1),
                disabled(2)
                }
        ACCESS  read-write
        STATUS  mandatory
        DESCRIPTION
                "Enable or disable the VRRP virtual router."
        ::= { vrrpNewCfgVirtRtrGrpTableEntry 7 }

vrrpNewCfgVirtRtrGrpDelete OBJECT-TYPE
      SYNTAX  INTEGER {
                other(1),
                delete(2)
                }
      ACCESS  read-write
      STATUS  mandatory
      DESCRIPTION
              "When set to the value of 2 (delete), the entire row
               is deleted. When read, other(1) is returned. Setting the value
               to anything other than delete(2) has no effect on the state
               of the row."
      ::= { vrrpNewCfgVirtRtrGrpTableEntry 8 }

vrrpNewCfgVirtRtrGrpSharing OBJECT-TYPE
        SYNTAX  INTEGER {
                enabled(1),
                disabled(2)
                }
        ACCESS  read-write
        STATUS  mandatory
        DESCRIPTION
                "Enable or disable load sharing of non-master
                 virtual router."
        ::= { vrrpNewCfgVirtRtrGrpTableEntry 9 }

vrrpNewCfgVirtRtrGrpTckVirtRtr OBJECT-TYPE
        SYNTAX  INTEGER {
                enabled(1),
                disabled(2)
                }
        ACCESS  read-write
        STATUS  mandatory
        DESCRIPTION
                "Enable or disable tracking other virtual routers for
                 priority adjustment.  the priority increment is defined
                 in vrrpNewCfgGenTckVirtRtrInc."
        ::= { vrrpNewCfgVirtRtrGrpTableEntry 10 }

vrrpNewCfgVirtRtrGrpTckIpIntf OBJECT-TYPE
        SYNTAX  INTEGER {
                enabled(1),
                disabled(2)
                }
        ACCESS  read-write
        STATUS  mandatory
        DESCRIPTION
                "Enable or disable tracking other router interfaces for
                 priority adjustment.  the priority increment is defined
                 in vrrpNewCfgGenTckIpIntfInc."
        ::= { vrrpNewCfgVirtRtrGrpTableEntry 11 }

vrrpNewCfgVirtRtrGrpTckVlanPort OBJECT-TYPE
        SYNTAX  INTEGER {
                enabled(1),
                disabled(2)
                }
        ACCESS  read-write
        STATUS  mandatory
        DESCRIPTION
                "Enable or disable tracking port state of VLAN ports
                 for priority adjustment.  the priority increment is
                 defined in vrrpNewCfgGenTckVlanPortInc."
        ::= { vrrpNewCfgVirtRtrGrpTableEntry 12 }

vrrpNewCfgVirtRtrGrpTckL4Port OBJECT-TYPE
        SYNTAX  INTEGER {
                enabled(1),
                disabled(2)
                }
        ACCESS  read-write
        STATUS  mandatory
        DESCRIPTION
                "Enable or disable tracking Layer 4 port states for
                 priority adjustment.  the priority increment is defined
                 in vrrpNewCfgGenTckL4PortInc.  This is applied when
                 virtual server is configured as a VRRP virtual router."
        ::= { vrrpNewCfgVirtRtrGrpTableEntry 13 }

vrrpNewCfgVirtRtrGrpTckRServer OBJECT-TYPE
        SYNTAX  INTEGER {
                enabled(1),
                disabled(2)
                }
        ACCESS  read-write
        STATUS  mandatory
        DESCRIPTION
                "Enable or disable tracking real server states for
                 priority adjustment.  the priority increment is defined
                 in vrrpNewCfgGenTckRServerInc.  This is applied when
                 virtual server is configured as a VRRP virtual router."
        ::= { vrrpNewCfgVirtRtrGrpTableEntry 14 }

vrrpNewCfgVirtRtrGrpTckHsrp OBJECT-TYPE
        SYNTAX  INTEGER {
                enabled(1),
                disabled(2)
                }
        ACCESS  read-write
        STATUS  mandatory
        DESCRIPTION
                "Enable or disable tracking HSRP advertisements for
                 priority adjustment.  the priority increment is defined
                 in vrrpNewCfgGenTckHsrpInc.  This is applied when
                 virtual server is configured as a VRRP virtual router."
        ::= { vrrpNewCfgVirtRtrGrpTableEntry 15 }


-- Statistics Group

-- RIP Statistics Group

ripStatInPkts OBJECT-TYPE
        SYNTAX  Counter
        ACCESS  read-only
        STATUS  mandatory
        DESCRIPTION
                "The total number of good RIP packets recieved."
        ::= { ripStats 1 }

ripStatOutPkts OBJECT-TYPE
        SYNTAX  Counter
        ACCESS  read-only
        STATUS  mandatory
        DESCRIPTION
                "The total number of RIP packets transmitted."
        ::= { ripStats 2 }

ripStatInErrorPkts OBJECT-TYPE
        SYNTAX  Counter
        ACCESS  read-only
        STATUS  mandatory
        DESCRIPTION
                "The total number of error RIP packets recieved."
        ::= { ripStats 3 }


-- SLB Statistics Group

-- SLB Port Maintenance Statistics Table

slbStatPortMaintTable  OBJECT-TYPE
        SYNTAX  SEQUENCE OF SlbStatPortMaintEntry
        ACCESS  not-accessible
        STATUS  mandatory
        DESCRIPTION
                "The table of SLB port maintenance statistics." 
        ::= { slbStats 1 }

slbStatPortMaintEntry OBJECT-TYPE
        SYNTAX  SlbStatPortMaintEntry
        ACCESS  not-accessible
        STATUS  mandatory
        DESCRIPTION
                "A row in the SLB port maintenance statistcs table."
        INDEX   { slbStatPortMaintPortIndex }
        ::= { slbStatPortMaintTable 1 }
 
        SlbStatPortMaintEntry ::=
              SEQUENCE {
                  slbStatPortMaintPortIndex
                      INTEGER,
                  slbStatPortMaintCurBindings
                      Gauge,
                  slbStatPortMaintBindingFails
                      Counter,
                  slbStatPortMaintNonTcpFrames
                      Counter,
                  slbStatPortMaintTcpFragments 
                      Counter,
                  slbStatPortMaintUdpDatagrams
                      Counter,
                  slbStatPortMaintIncorrectVIPs
                      Counter,
                  slbStatPortMaintIncorrectVports
                      Counter,
                  slbStatPortMaintRealServerNoAvails
                      Counter,
		  slbStatPortMaintFilteredDeniedFrames
		      Counter
        }

slbStatPortMaintPortIndex OBJECT-TYPE
        SYNTAX  INTEGER
        ACCESS  read-only
        STATUS  mandatory
        DESCRIPTION
                "The port number for which the statistics apply."
        ::= { slbStatPortMaintEntry 1 }

slbStatPortMaintCurBindings OBJECT-TYPE
        SYNTAX  Gauge 
        ACCESS  read-only
        STATUS  mandatory
        DESCRIPTION
                "The current number of bindings on the port."
        ::= { slbStatPortMaintEntry 2 }

slbStatPortMaintBindingFails OBJECT-TYPE
        SYNTAX  Counter
        ACCESS  read-only
        STATUS  mandatory
        DESCRIPTION
                "The total number of Binding failures on the port. A 
 		 Binding Failure occurs when a port runs out of binding 
		 table entries."
        ::= { slbStatPortMaintEntry 3 }

slbStatPortMaintNonTcpFrames OBJECT-TYPE
        SYNTAX  Counter
        ACCESS  read-only
        STATUS  mandatory
        DESCRIPTION
                "The total number of non-TCP/IP frames dropped on the 
		 port."
        ::= { slbStatPortMaintEntry 4 }

slbStatPortMaintTcpFragments OBJECT-TYPE
        SYNTAX  Counter
        ACCESS  read-only
        STATUS  mandatory
        DESCRIPTION
                "The total number of TCP fragments dropped on the port."
        ::= { slbStatPortMaintEntry 5 }

slbStatPortMaintUdpDatagrams OBJECT-TYPE
        SYNTAX  Counter
        ACCESS  read-only
        STATUS  mandatory
        DESCRIPTION
                "The total number of UDP datagrams dropped on the port."
        ::= { slbStatPortMaintEntry 6 }

slbStatPortMaintIncorrectVIPs OBJECT-TYPE
        SYNTAX  Counter
        ACCESS  read-only
        STATUS  mandatory
        DESCRIPTION
                "The total number of frames with incorrect VIPs that are
		 dropped on the port."
        ::= { slbStatPortMaintEntry 7 }

slbStatPortMaintIncorrectVports OBJECT-TYPE
        SYNTAX  Counter
        ACCESS  read-only
        STATUS  mandatory
        DESCRIPTION
                "The total number of frames with incorrect Virtual Port
		  that are dropped on the port."
        ::= { slbStatPortMaintEntry 8 }

slbStatPortMaintRealServerNoAvails OBJECT-TYPE
        SYNTAX  Counter
        ACCESS  read-only
        STATUS  mandatory
        DESCRIPTION
                "The total number of frames that are dropped on the port
		 because no real server is available."
        ::= { slbStatPortMaintEntry 9 }

slbStatPortMaintFilteredDeniedFrames OBJECT-TYPE
        SYNTAX  Counter
        ACCESS  read-only
        STATUS  mandatory
        DESCRIPTION
                "The total number of frames that are denied on the port
		 by the filter."
        ::= { slbStatPortMaintEntry 10 }


slbStatMaintBackupServActs OBJECT-TYPE
        SYNTAX  Counter
        ACCESS  read-only
        STATUS  mandatory
        DESCRIPTION
                "The total number of times that backup servers become
		 active due to failure of primary servers."
        ::= { slbStats 3 }

slbStatMaintOverflowServActs OBJECT-TYPE
        SYNTAX  Counter
        ACCESS  read-only
        STATUS  mandatory
        DESCRIPTION
                "The total number of times that backup servers become
		 active due to primary servers reach overflow situation."
        ::= { slbStats 4 }


-- SLB Port to Real Servers Statistics Table

slbStatPortRealServerTable  OBJECT-TYPE
        SYNTAX  SEQUENCE OF SlbStatPortRealServerEntry
        ACCESS  not-accessible
        STATUS  mandatory
        DESCRIPTION
		"The port-server statistics table.  This table shows
		 the statistics of real servers that are connectted 
		 to switch ports."
        ::= { slbStats 2 }

slbStatPortRealServerEntry OBJECT-TYPE
        SYNTAX  SlbStatPortRealServerEntry
        ACCESS  not-accessible
        STATUS  mandatory
        DESCRIPTION
		"A row in the port-server statistics table."
        INDEX   { slbStatPortRealServerPortIndex, 
		  slbStatPortRealServerServerIndex }
        ::= { slbStatPortRealServerTable 1 }

        SlbStatPortRealServerEntry ::=
              SEQUENCE {
                  slbStatPortRealServerPortIndex
                      INTEGER,
                  slbStatPortRealServerServerIndex
                      INTEGER,
                  slbStatPortRealServerCurrSessions
                      Gauge,
                  slbStatPortRealServerTotalSessions
                      Counter,
                  slbStatPortRealServerHCOctets        -- obsoleted
                      Counter64,
                  slbStatPortRealServerHCOctetsLow32
                      Counter,
                  slbStatPortRealServerHCOctetsHigh32
                      Counter
        }

slbStatPortRealServerPortIndex OBJECT-TYPE
        SYNTAX  INTEGER
        ACCESS  read-only
        STATUS  mandatory
        DESCRIPTION
                "The port number that identifies the switch port."
        ::= { slbStatPortRealServerEntry 1 }

slbStatPortRealServerServerIndex OBJECT-TYPE 
        SYNTAX  INTEGER 
        ACCESS  read-only
        STATUS  mandatory 
        DESCRIPTION 
                "The real server number that identifies the server." 
        ::= { slbStatPortRealServerEntry 2 }

slbStatPortRealServerCurrSessions OBJECT-TYPE 
        SYNTAX  Gauge
	ACCESS  read-only
        STATUS  mandatory 
        DESCRIPTION 
                "The current sessions for the real server."
        ::= { slbStatPortRealServerEntry 3 }

slbStatPortRealServerTotalSessions OBJECT-TYPE 
        SYNTAX  Counter 
        ACCESS  read-only
        STATUS  mandatory 
        DESCRIPTION 
                "The total number of sessions for the real server."
        ::= { slbStatPortRealServerEntry 4 }

slbStatPortRealServerHCOctets OBJECT-TYPE 
        SYNTAX  Counter64
        ACCESS  read-only
        STATUS  mandatory 
        DESCRIPTION 
               "The total number of octets received and transmitted out 
		 of the real server on a particular port."
        ::= { slbStatPortRealServerEntry 5 }

slbStatPortRealServerHCOctetsLow32 OBJECT-TYPE
        SYNTAX  Counter
        ACCESS  read-only
        STATUS  mandatory
        DESCRIPTION
               "The lower 32 bit value of the total octets received and
                transmitted out of the real server on a particular port."
        ::= { slbStatPortRealServerEntry 6 }

slbStatPortRealServerHCOctetsHigh32 OBJECT-TYPE
        SYNTAX  Counter
        ACCESS  read-only
        STATUS  mandatory
        DESCRIPTION
               "The higher 32 bit value of the total octets received and
                transmitted out of the real server on a particular port."
        ::= { slbStatPortRealServerEntry 7 }


-- SLB Real Servers Statistics Table

slbStatRServerTable  OBJECT-TYPE
        SYNTAX  SEQUENCE OF SlbStatRServerEntry
        ACCESS  not-accessible
        STATUS  mandatory
        DESCRIPTION
		"The real server statistics table."
        ::= { slbStats 5 }

slbStatRServerEntry OBJECT-TYPE
        SYNTAX  SlbStatRServerEntry
        ACCESS  not-accessible
        STATUS  mandatory
        DESCRIPTION
		"The statistics of a particular real server."
        INDEX   { slbStatRServerIndex }
        ::= { slbStatRServerTable 1 }

        SlbStatRServerEntry ::=
              SEQUENCE {
                  slbStatRServerIndex
                      INTEGER,
                  slbStatRServerCurrSessions
                      Gauge,
                  slbStatRServerTotalSessions
                      Counter,
                  slbStatRServerFailures
                      Counter,
                  slbStatRServerHighestSessions
                      Counter,
                  slbStatRServerHCOctets        -- obsoleted
                      Counter64,
                  slbStatRServerHCOctetsLow32
                      Counter,
                  slbStatRServerHCOctetsHigh32
                      Counter
        }

slbStatRServerIndex OBJECT-TYPE
        SYNTAX  INTEGER
        ACCESS  read-only
        STATUS  mandatory
        DESCRIPTION
                "The real server number that identifies the server." 
        ::= { slbStatRServerEntry 1 }

slbStatRServerCurrSessions OBJECT-TYPE 
        SYNTAX  Gauge
	ACCESS  read-only
        STATUS  mandatory 
        DESCRIPTION 
                "The number of sessions that are currently handled by 
		 the real server."
        ::= { slbStatRServerEntry 2 }

slbStatRServerTotalSessions OBJECT-TYPE 
        SYNTAX  Counter 
        ACCESS  read-only
        STATUS  mandatory 
        DESCRIPTION 
                "The total number of sessions that are handled by the 
		 real server."
        ::= { slbStatRServerEntry 3 }

slbStatRServerFailures OBJECT-TYPE 
        SYNTAX  Counter 
        ACCESS  read-only
        STATUS  mandatory 
        DESCRIPTION 
                "The total number of times that the real server is 
		 claimed down."
        ::= { slbStatRServerEntry 4 }

slbStatRServerHighestSessions OBJECT-TYPE 
        SYNTAX  Counter 
        ACCESS  read-only
        STATUS  mandatory 
        DESCRIPTION 
                "The highest sessions that have been handled by the real 
		 server."
        ::= { slbStatRServerEntry 5 }

slbStatRServerHCOctets OBJECT-TYPE 
        SYNTAX  Counter64
        ACCESS  read-only
        STATUS  mandatory 
        DESCRIPTION 
               "The total number of octets received and transmitted out 
		 of the real server."
        ::= { slbStatRServerEntry 6 }

slbStatRServerHCOctetsLow32 OBJECT-TYPE
        SYNTAX  Counter
        ACCESS  read-only
        STATUS  mandatory
        DESCRIPTION
               "The lower 32 bit value of octets received and transmitted out
                 of the real server."
        ::= { slbStatRServerEntry 7 }

slbStatRServerHCOctetsHigh32 OBJECT-TYPE
        SYNTAX  Counter
        ACCESS  read-only
        STATUS  mandatory
        DESCRIPTION
               "The higher 32 bit value of octets received and transmitted out
                 of the real server."
        ::= { slbStatRServerEntry 8 }


-- SLB Real Server Groups Statistics Table

slbStatGroupTable  OBJECT-TYPE
        SYNTAX  SEQUENCE OF SlbStatGroupEntry
        ACCESS  not-accessible
        STATUS  mandatory
        DESCRIPTION
		"The real server group statistics table."
        ::= { slbStats 6 }

slbStatGroupEntry OBJECT-TYPE
        SYNTAX  SlbStatGroupEntry
        ACCESS  not-accessible
        STATUS  mandatory
        DESCRIPTION
		"The statistics of a particular real server group."
        INDEX   { slbStatGroupIndex }
        ::= { slbStatGroupTable 1 }

        SlbStatGroupEntry ::=
              SEQUENCE {
                  slbStatGroupIndex
                      INTEGER,
                  slbStatGroupCurrSessions
                      Gauge,
                  slbStatGroupTotalSessions
                      Counter,
                  slbStatGroupHighestSessions
                      Counter,
                  slbStatGroupHCOctets        -- obsoleted
                      Counter64,
                  slbStatGroupHCOctetsLow32
                      Counter,
                  slbStatGroupHCOctetsHigh32
                      Counter
        }

slbStatGroupIndex OBJECT-TYPE
        SYNTAX  INTEGER
        ACCESS  read-only
        STATUS  mandatory
        DESCRIPTION
                "The real server group number that identifies the group." 
        ::= { slbStatGroupEntry 1 }

slbStatGroupCurrSessions OBJECT-TYPE 
        SYNTAX  Gauge
	ACCESS  read-only
        STATUS  mandatory 
        DESCRIPTION 
                "The number of sessions that are currently handled by 
		 the real server group."
        ::= { slbStatGroupEntry 2 }

slbStatGroupTotalSessions OBJECT-TYPE 
        SYNTAX  Counter 
        ACCESS  read-only
        STATUS  mandatory 
        DESCRIPTION 
                "The total number of sessions that are handled by the 
		 real server group."
        ::= { slbStatGroupEntry 3 }

slbStatGroupHighestSessions OBJECT-TYPE 
        SYNTAX  Counter 
        ACCESS  read-only
        STATUS  mandatory 
        DESCRIPTION 
                "The highest sessions that have been handled by the real 
		 server."
        ::= { slbStatGroupEntry 4 }

slbStatGroupHCOctets OBJECT-TYPE 
        SYNTAX  Counter64
        ACCESS  read-only
        STATUS  mandatory 
        DESCRIPTION 
               "The total number of octets received and transmitted out 
		 of the real server group."
        ::= { slbStatGroupEntry 5 }

slbStatGroupHCOctetsLow32 OBJECT-TYPE
        SYNTAX  Counter
        ACCESS  read-only
        STATUS  mandatory
        DESCRIPTION
               "The lower 32 bit value of octets received and transmitted out
                 of the real server group."
        ::= { slbStatGroupEntry 6 }

slbStatGroupHCOctetsHigh32 OBJECT-TYPE
        SYNTAX  Counter
        ACCESS  read-only
        STATUS  mandatory
        DESCRIPTION
               "The higher 32 bit value of octets received and transmitted out
                 of the real server group."
        ::= { slbStatGroupEntry 7 }


-- SLB Virtual Servers Statistics Table

slbStatVServerTable  OBJECT-TYPE
        SYNTAX  SEQUENCE OF SlbStatVServerEntry
        ACCESS  not-accessible
        STATUS  mandatory
        DESCRIPTION
		"The virtual server statistics table."
        ::= { slbStats 7 }

slbStatVServerEntry OBJECT-TYPE
        SYNTAX  SlbStatVServerEntry
        ACCESS  not-accessible
        STATUS  mandatory
        DESCRIPTION
		"The statistics of a particular virtual server group."
        INDEX   { slbStatVServerIndex }
        ::= { slbStatVServerTable 1 }

        SlbStatVServerEntry ::=
              SEQUENCE {
                  slbStatVServerIndex
                      INTEGER,
                  slbStatVServerCurrSessions
                      Gauge,
                  slbStatVServerTotalSessions
                      Counter,
                  slbStatVServerHighestSessions
                      Counter,
                  slbStatVServerHCOctets        -- obsoleted
                      Counter64,
                  slbStatVServerHCOctetsLow32
                      Counter,
                  slbStatVServerHCOctetsHigh32
                      Counter,
                  slbStatVServerHeaderHits
                      Counter,
                  slbStatVServerHeaderMisses
                      Counter,
                  slbStatVServerHeaderTotalSessions
                      Counter
        }

slbStatVServerIndex OBJECT-TYPE
        SYNTAX  INTEGER
        ACCESS  read-only
        STATUS  mandatory
        DESCRIPTION
                "The virtual server number that identifies the server." 
        ::= { slbStatVServerEntry 1 }

slbStatVServerCurrSessions OBJECT-TYPE 
        SYNTAX  Gauge
	ACCESS  read-only
        STATUS  mandatory 
        DESCRIPTION 
                "The number of sessions that are currently handled by 
		 the virtual server."
        ::= { slbStatVServerEntry 2 }

slbStatVServerTotalSessions OBJECT-TYPE 
        SYNTAX  Counter 
        ACCESS  read-only
        STATUS  mandatory 
        DESCRIPTION 
                "The total number of sessions that are handled by the 
		 virtual server."
        ::= { slbStatVServerEntry 3 }

slbStatVServerHighestSessions OBJECT-TYPE 
        SYNTAX  Counter 
        ACCESS  read-only
        STATUS  mandatory 
        DESCRIPTION 
                "The highest sessions that have been handled by the real 
		 server."
        ::= { slbStatVServerEntry 4 }

slbStatVServerHCOctets OBJECT-TYPE 
        SYNTAX  Counter64
        ACCESS  read-only
        STATUS  mandatory 
        DESCRIPTION 
               "The total number of octets received and transmitted out 
		 of the virtual server."
        ::= { slbStatVServerEntry 5 }

slbStatVServerHCOctetsLow32 OBJECT-TYPE
        SYNTAX  Counter
        ACCESS  read-only
        STATUS  mandatory
        DESCRIPTION
               "The lower 32 bit value of octets received and transmitted out
                 of the virtual server."
        ::= { slbStatVServerEntry 6 }

slbStatVServerHCOctetsHigh32 OBJECT-TYPE
        SYNTAX  Counter
        ACCESS  read-only
        STATUS  mandatory
        DESCRIPTION
               "The higher 32 bit value of octets received and transmitted out
                 of the virtual server."
        ::= { slbStatVServerEntry 7 }

--  HTTP Header LB stats 
slbStatVServerHeaderHits OBJECT-TYPE 
        SYNTAX  Counter 
        ACCESS  read-only
        STATUS  mandatory 
        DESCRIPTION 
                "The current HTTP header hits." 
        ::= { slbStatVServerEntry 8 }


slbStatVServerHeaderMisses OBJECT-TYPE 
        SYNTAX  Counter 
        ACCESS  read-only
        STATUS  mandatory 
        DESCRIPTION 
                "The current HTTP header misses."  
        ::= { slbStatVServerEntry 9 }

slbStatVServerHeaderTotalSessions OBJECT-TYPE 
        SYNTAX  Counter 
        ACCESS  read-only
        STATUS  mandatory 
        DESCRIPTION 
                "The total HTTP header sessions."
        ::= { slbStatVServerEntry 10 }

-- ARP Statistics Group

arpStatEntries OBJECT-TYPE
        SYNTAX  Gauge 
        ACCESS  read-only
        STATUS  mandatory
        DESCRIPTION
                "The current number of ARP entries."
        ::= { arpStats 1 }

arpStatHighWater OBJECT-TYPE
        SYNTAX  Gauge 
        ACCESS  read-only
        STATUS  mandatory
        DESCRIPTION
                "The highest number of ARP entries."
        ::= { arpStats 2 }

arpStatMaxEntries OBJECT-TYPE
        SYNTAX  Gauge 
        ACCESS  read-only
        STATUS  mandatory
        DESCRIPTION
                "The maximum number of ARP entries."
        ::= { arpStats 3 }

-- ROUTE Statistics Group

routeStatEntries OBJECT-TYPE
        SYNTAX  Gauge 
        ACCESS  read-only
        STATUS  mandatory
        DESCRIPTION
                "The current number of IP routes."
        ::= { routeStats 1 }

routeStatHighWater OBJECT-TYPE
        SYNTAX  Gauge 
        ACCESS  read-only
        STATUS  mandatory
        DESCRIPTION
                "The highest number of IP routes."
        ::= { routeStats 2 }

routeStatMaxEntries OBJECT-TYPE
        SYNTAX  Gauge 
        ACCESS  read-only
        STATUS  mandatory
        DESCRIPTION
                "The maximum number of IP routes."
        ::= { routeStats 3 }

-- DNS Statistics
dnsStatInGoodDnsRequests OBJECT-TYPE 
        SYNTAX  Counter 
        ACCESS  read-only
        STATUS  mandatory 
        DESCRIPTION 
                "The number of good DNS requests which are received."
        ::= { dnsStats 1 }

dnsStatInBadDnsRequests OBJECT-TYPE 
        SYNTAX  Counter 
        ACCESS  read-only
        STATUS  mandatory 
        DESCRIPTION 
                "The number of bad DNS requests which are received."
        ::= { dnsStats 2 }

-- Filter Statistics

fltStatTable  OBJECT-TYPE
        SYNTAX  SEQUENCE OF FltStatTableEntry
        ACCESS  not-accessible
        STATUS  mandatory
        DESCRIPTION
		"The filter statistics table."
        ::= { filterStats 1 }

fltStatTableEntry OBJECT-TYPE
        SYNTAX  FltStatTableEntry
        ACCESS  not-accessible
        STATUS  mandatory
        DESCRIPTION
		"A row in filter statistics table."
        INDEX   { fltStatFltIndex }
        ::= { fltStatTable 1 }

FltStatTableEntry ::=
	SEQUENCE {
	fltStatFltIndex
		INTEGER,
	fltStatFltFirings
		Counter
	}

fltStatFltIndex OBJECT-TYPE 
        SYNTAX  INTEGER 
        ACCESS  read-only
        STATUS  mandatory 
        DESCRIPTION 
                "The number that identifies the filter." 
        ::= { fltStatTableEntry 1 }

fltStatFltFirings OBJECT-TYPE 
        SYNTAX  Counter 
        ACCESS  read-only
        STATUS  mandatory 
        DESCRIPTION 
                "The number of instances that the received packet matches
		 the filter rule."
        ::= { fltStatTableEntry 2 }

-- GSLB Remote Real Server Statistics

gslbStatRemRealServerTable  OBJECT-TYPE
        SYNTAX  SEQUENCE OF GslbStatRemRealServerEntry
        ACCESS  not-accessible
        STATUS  mandatory
        DESCRIPTION
		"The GSLB remote real server statistics table."
        ::= { gslbStats 1 }

gslbStatRemRealServerEntry OBJECT-TYPE
        SYNTAX  GslbStatRemRealServerEntry
        ACCESS  not-accessible
        STATUS  mandatory
        DESCRIPTION
		"A row in the remote real server statistics table."
        INDEX   { gslbStatRemRealServerIndex }
        ::= { gslbStatRemRealServerTable 1 }

GslbStatRemRealServerEntry ::=
	SEQUENCE {
	gslbStatRemRealServerIndex
		INTEGER,
	gslbStatRemRealServerDnsHandoffs
		Counter,
	gslbStatRemRealServerHttpRedirs
		Counter
	}

gslbStatRemRealServerIndex OBJECT-TYPE 
        SYNTAX  INTEGER 
        ACCESS  read-only
        STATUS  mandatory 
        DESCRIPTION 
                "The server number that identifies the remote real server." 
        ::= { gslbStatRemRealServerEntry 1 }

gslbStatRemRealServerDnsHandoffs OBJECT-TYPE 
        SYNTAX  Counter 
        ACCESS  read-only
        STATUS  mandatory 
        DESCRIPTION 
                "The number of DNS hanfoffs by the remote real server."
        ::= { gslbStatRemRealServerEntry 2 }

gslbStatRemRealServerHttpRedirs OBJECT-TYPE 
        SYNTAX  Counter 
        ACCESS  read-only
        STATUS  mandatory 
        DESCRIPTION 
                "The number of HTTP redirections by the remote real server."
        ::= { gslbStatRemRealServerEntry 3 }


-- The GSLB Maintenance Statistics

gslbStatMaintInGoodSiteUpdates OBJECT-TYPE 
        SYNTAX  Counter 
        ACCESS  read-only
        STATUS  mandatory 
        DESCRIPTION 
                "The number of good remote site updates which are received."
        ::= { gslbMaintStats 1 }

gslbStatMaintInBadSiteUpdates OBJECT-TYPE 
        SYNTAX  Counter 
        ACCESS  read-only
        STATUS  mandatory 
        DESCRIPTION 
                "The number of bad remote site updates which are received."
        ::= { gslbMaintStats 2 }


-- The VRRP Statistics

vrrpStatInAdvers OBJECT-TYPE 
        SYNTAX  Counter 
        ACCESS  read-only
        STATUS  mandatory 
        DESCRIPTION 
                "The number of good VRRP advertisements which are received."
        ::= { vrrpStats 1 }

vrrpStatOutAdvers OBJECT-TYPE 
        SYNTAX  Counter 
        ACCESS  read-only
        STATUS  mandatory 
        DESCRIPTION 
                "The number of good VRRP advertisements which are transmitted."
        ::= { vrrpStats 2 }

vrrpStatOutBadAdvers OBJECT-TYPE 
        SYNTAX  Counter 
        ACCESS  read-only
        STATUS  mandatory 
        DESCRIPTION 
                "The number of bad VRRP advertisements which are received."
        ::= { vrrpStats 3 }

-- The FTP Passive SLB/NAT Statistics

ftpSlbStats      OBJECT IDENTIFIER ::= { ftpStats  1 }

ftpSlbStatTotal  OBJECT-TYPE
	SYNTAX  Counter
	ACCESS  read-only
	STATUS  mandatory
	DESCRIPTION
		"The total number of ftp control sesssion for SLB
		 received after FTP parsing turn on."
	::= { ftpSlbStats 1 }

ftpNatStatTotal  OBJECT-TYPE
	SYNTAX  Counter
	ACCESS  read-only
	STATUS  mandatory
	DESCRIPTION
		"The total number of FTP control session for NAT
		 received after active FTP is turn on."
	::= { ftpSlbStats 2 } 

-- The URL Redirection/Load Balancing Statistics

urlRedirStats    OBJECT IDENTIFIER ::= { urlStats  1 }

urlStatRedRedirs OBJECT-TYPE 
        SYNTAX  Counter 
        ACCESS  read-only
        STATUS  mandatory 
        DESCRIPTION 
                "The number of instances that the received packet matches
		 the specified URL expressions and redirected to specified
		 group of real servers."
        ::= { urlRedirStats 1 }

urlStatRedOrigSrvs OBJECT-TYPE 
        SYNTAX  Counter 
        ACCESS  read-only
        STATUS  mandatory 
        DESCRIPTION 
                "The number of instances that the received packet is sent
		 to the origin server due to mis-match with the specified 
		 URL expressions or detecting of HTTP non-GETs,user cookies,
		 and no-cache as users configuration."
        ::= { urlRedirStats 2 }

urlStatRedNonGets OBJECT-TYPE 
        SYNTAX  Counter 
        ACCESS  read-only
        STATUS  mandatory 
        DESCRIPTION 
                "The number of instances that the received packet contains
                 none GETs(POST ,HEAD ,PUT..) methods."
        ::= { urlRedirStats 3 }

urlStatRedCookie OBJECT-TYPE 
        SYNTAX  Counter 
        ACCESS  read-only
        STATUS  mandatory 
        DESCRIPTION 
                "The number of instances that the received packet contains
                 a 'Cookie: ' header."
        ::= { urlRedirStats 4 }

urlStatRedNoCache OBJECT-TYPE 
        SYNTAX  Counter 
        ACCESS  read-only
        STATUS  mandatory 
        DESCRIPTION 
                "The number of instances that the received packet contains
                 a no-cache header value."
        ::= { urlRedirStats 5 }

urlSlbStats    OBJECT IDENTIFIER ::= { urlStats  2 }

urlStatSlbPathTable OBJECT-TYPE
        SYNTAX  SEQUENCE OF UrlStatSlbPathTableEntry
        ACCESS  not-accessible
        STATUS  mandatory
        DESCRIPTION
                "The statistics table of instances that URL pathes matched."
        ::= { urlSlbStats 1 }

urlStatSlbPathTableEntry OBJECT-TYPE
        SYNTAX  UrlStatSlbPathTableEntry
        ACCESS  not-accessible
        STATUS  mandatory
        DESCRIPTION
                "Information about the number of instances that are 
		 load-balanced due to match of a particular URL path."
        INDEX   { slbCurCfgUrlLbPathIndex }
        ::= { urlStatSlbPathTable 1 }

UrlStatSlbPathTableEntry ::= SEQUENCE {
        urlStatSlbPathIndex       INTEGER,
        urlStatSlbPathHits        Counter
        }

urlStatSlbPathIndex OBJECT-TYPE
        SYNTAX  INTEGER
        ACCESS  read-only
        STATUS  mandatory
        DESCRIPTION
                "The URL path table index."
        ::= { urlStatSlbPathTableEntry 1 }

urlStatSlbPathHits OBJECT-TYPE
        SYNTAX  Counter
        ACCESS  read-only
        STATUS  mandatory
        DESCRIPTION
                "The number of instances that are load-balanced due to 
		 match of the particular URL path."
        ::= { urlStatSlbPathTableEntry 2 }

-- Other TCP Statistics

tcpStatCurConns OBJECT-TYPE
    SYNTAX  Gauge 
    ACCESS  read-only
    STATUS  mandatory
    DESCRIPTION
	"The total number of outstanding TCP connections have been established."
    ::= { tcpStats 1 }

tcpStatHalfOpens OBJECT-TYPE
    SYNTAX  Gauge 
    ACCESS  read-only
    STATUS  mandatory
    DESCRIPTION
	"The total number of outstanding TCP connections have been half opened.
	 This statistics is valid only when URL parsing has been truned on.
	 It is incremented when the switch respond to TCP SYN packet and 
	 decremented upon receiving TCP SYN ACK packet from the requester."
    ::= { tcpStats 2 }

--
-- Memory Statistics Group
-- This group represents Memory Statistics information
--

memStatsAllocs OBJECT-TYPE
    SYNTAX  Counter
    ACCESS  read-only
    STATUS  mandatory
    DESCRIPTION
        "The total number of memory allocations."
    ::= { memStats 1 }

memStatsFrees OBJECT-TYPE
    SYNTAX  Counter
    ACCESS  read-only
    STATUS  mandatory
    DESCRIPTION
        "The total number of memory frees."
    ::= { memStats 2 }
 
memStatsAllocFails OBJECT-TYPE
    SYNTAX  Counter
    ACCESS  read-only
    STATUS  mandatory
    DESCRIPTION
        "The total number of memory allocations failed."
    ::= { memStats 3 }
 
memStatsBytesCurr OBJECT-TYPE
    SYNTAX  Gauge 
    ACCESS  read-only
    STATUS  mandatory
    DESCRIPTION
        "The outstanding memory in bytes have been allocated."
    ::= { memStats 4 }
 
memStatsBytesHiwat OBJECT-TYPE
    SYNTAX  Gauge 
    ACCESS  read-only
    STATUS  mandatory
    DESCRIPTION
        "The highest number of bytes have even been allocated."
    ::= { memStats 5 }
 
memStatsPoolBytes OBJECT-TYPE
    SYNTAX  Gauge 
    ACCESS  read-only
    STATUS  mandatory
    DESCRIPTION
        "The total bytes in the memory pool."
    ::= { memStats 6 }
 
memStatsLargest OBJECT-TYPE
    SYNTAX  Gauge 
    ACCESS  read-only
    STATUS  mandatory
    DESCRIPTION
        "The largest block has been allocated."
    ::= { memStats 7 }
 
--
-- Packet Statistics Group
-- This group represents Packet Statistics information
--
 
pktStatsAllocs OBJECT-TYPE
    SYNTAX  Counter
    ACCESS  read-only
    STATUS  mandatory
    DESCRIPTION
        "The total packets have been allocated."
    ::= { pktStats 1 }
 
pktStatsFrees OBJECT-TYPE
    SYNTAX  Counter
    ACCESS  read-only
    STATUS  mandatory
    DESCRIPTION
        "The total packets have been freed."
    ::= { pktStats 2 }
 
pktStatsAllocFails OBJECT-TYPE
    SYNTAX  Counter
    ACCESS  read-only
    STATUS  mandatory
    DESCRIPTION
        "The total packet allocations failed."
    ::= { pktStats 3}
 
pktStatsMediums OBJECT-TYPE
    SYNTAX  Counter
    ACCESS  read-only
    STATUS  mandatory
    DESCRIPTION
        "The number of medium size packets have been allocated."
    ::= { pktStats 4}
 
pktStatsJumbos OBJECT-TYPE
    SYNTAX  Counter
    ACCESS  read-only
    STATUS  mandatory
    DESCRIPTION
        "The number of jumbo size packets have been allocated."
    ::= { pktStats 5}
 
pktStatsSmalls OBJECT-TYPE
    SYNTAX  Counter
    ACCESS  read-only
    STATUS  mandatory
    DESCRIPTION
        "The number of small size packets have been allocated."
    ::= { pktStats 6}
 


-- Information Group
-- This group represents run-time status of the system

-- Port information table

portInfoTable OBJECT-TYPE
        SYNTAX  SEQUENCE OF PortInfoTableEntry
        ACCESS  not-accessible
        STATUS  mandatory
        DESCRIPTION
                "The table of port information."
        ::= { port-info 1 }

portInfoTableEntry OBJECT-TYPE
        SYNTAX  PortInfoTableEntry
        ACCESS  not-accessible
        STATUS  mandatory
        DESCRIPTION
                "A row in the port information table."
        INDEX   { portInfoIndx }
        ::= { portInfoTable 1 }

PortInfoTableEntry ::= SEQUENCE {
        portInfoIndx        INTEGER,
        portInfoSpeed       INTEGER,
        portInfoMode        INTEGER,
        portInfoFlowCtrl    INTEGER,
        portInfoLink        INTEGER
        }

portInfoIndx OBJECT-TYPE
        SYNTAX  INTEGER  (1..255)
        ACCESS  read-only
        STATUS  mandatory
        DESCRIPTION
                "The port index."
        ::= { portInfoTableEntry 1 }

portInfoSpeed OBJECT-TYPE
        SYNTAX  INTEGER {
                other(1),
                mbs10(2),
                mbs100(3),
                mbs1000(4)
                }
        ACCESS  read-only
        STATUS  mandatory
        DESCRIPTION
                "The current operational speed of the port."
        ::= { portInfoTableEntry 2 }

portInfoMode OBJECT-TYPE
        SYNTAX  INTEGER {
                other(1),
                full-duplex(2),
                half-duplex(3)
                }
        ACCESS  read-only
        STATUS  mandatory
        DESCRIPTION
                "The current operational mode of the port."
        ::= { portInfoTableEntry 3 }

portInfoFlowCtrl OBJECT-TYPE
        SYNTAX  INTEGER {
                other(1),
                transmit(2),
                receive(3),
                both(4),
                none(5)
                }
        ACCESS  read-only
        STATUS  mandatory
        DESCRIPTION
                "The current operational flow control of the port."
        ::= { portInfoTableEntry 4 }

portInfoLink OBJECT-TYPE
        SYNTAX  INTEGER {
                up(1),
                down(2),
                disabled(3),
                inoperative(4) -- unrecognized PCI device
                }
        ACCESS  read-only
        STATUS  mandatory
        DESCRIPTION
                "The current operational link status of the port."
        ::= { portInfoTableEntry 5 }


-- SLB Switch FailOver Information Table

slbFailOverInfoTable OBJECT-TYPE
        SYNTAX  SEQUENCE OF SlbFailOverInfoEntry
        ACCESS  not-accessible
        STATUS  mandatory
        DESCRIPTION
                "The table of switch fail-over run-time status."
        ::= { slb-info 1 }

slbFailOverInfoEntry OBJECT-TYPE
        SYNTAX  SlbFailOverInfoEntry
        ACCESS  not-accessible
        STATUS  mandatory
        DESCRIPTION
                "A row in the switch fail-over information table."
        INDEX   { slbFailOverInfoIndex }
        ::= { slbFailOverInfoTable 1 }
 
SlbFailOverInfoEntry ::= SEQUENCE {
        slbFailOverInfoIndex           INTEGER,
        slbFailOverInfoPrimaryIp       IpAddress,
	slbFailOverInfoPrimaryStatus   INTEGER,
	slbFailOverInfoPrimaryState    INTEGER,
        slbFailOverInfoSecondaryIp     IpAddress,
	slbFailOverInfoSecondaryStatus INTEGER,
	slbFailOverInfoSecondaryState  INTEGER
	}

slbFailOverInfoIndex OBJECT-TYPE
        SYNTAX  INTEGER
        ACCESS  read-only
        STATUS  mandatory
        DESCRIPTION
                "The index of switch fail-over information table."
        ::= { slbFailOverInfoEntry 1 }

slbFailOverInfoPrimaryIp OBJECT-TYPE
        SYNTAX  IpAddress
        ACCESS  read-only
        STATUS  mandatory
        DESCRIPTION
                "IP address of the primary switch." 
        ::= { slbFailOverInfoEntry 2 }


slbFailOverInfoPrimaryStatus OBJECT-TYPE
        SYNTAX  INTEGER { 
                up(1), 
                down(2)
                } 
        ACCESS  read-only
        STATUS  mandatory
        DESCRIPTION
                "The current operational status of the primary switch." 
        ::= { slbFailOverInfoEntry 3 }

slbFailOverInfoPrimaryState OBJECT-TYPE
        SYNTAX  INTEGER { 
                active(1), 
                standby(2)
                } 
        ACCESS  read-only
        STATUS  mandatory
        DESCRIPTION
                "The current operational state of the primary switch." 
        ::= { slbFailOverInfoEntry 4 }

slbFailOverInfoSecondaryIp OBJECT-TYPE
        SYNTAX  IpAddress
        ACCESS  read-only
        STATUS  mandatory
        DESCRIPTION
                "IP address of the secondary switch." 
        ::= { slbFailOverInfoEntry 5 }

slbFailOverInfoSecondaryStatus OBJECT-TYPE
        SYNTAX  INTEGER { 
                up(1), 
                down(2)
                } 
        ACCESS  read-only
        STATUS  mandatory
        DESCRIPTION
                "The current operational status of the secondary switch." 
        ::= { slbFailOverInfoEntry 6 }

slbFailOverInfoSecondaryState OBJECT-TYPE
        SYNTAX  INTEGER { 
                active(1), 
                standby(2)
                } 
        ACCESS  read-only
        STATUS  mandatory
        DESCRIPTION
                "The current operational state of the secondary switch." 
        ::= { slbFailOverInfoEntry 7 }


-- Real Server Information Table

slbRealServerInfoTable OBJECT-TYPE
        SYNTAX  SEQUENCE OF SlbRealServerInfoEntry
        ACCESS  not-accessible
        STATUS  mandatory
        DESCRIPTION
                "The table of real server run-time information."
        ::= { slb-info 2 }

slbRealServerInfoEntry OBJECT-TYPE
        SYNTAX  SlbRealServerInfoEntry
        ACCESS  not-accessible
        STATUS  mandatory
        DESCRIPTION
                "A row in the real server information table."
        INDEX   { slbRealServerInfoIndex }
        ::= { slbRealServerInfoTable 1 }
 
SlbRealServerInfoEntry ::= SEQUENCE {
        slbRealServerInfoIndex           INTEGER,
        slbRealServerInfoIpAddr          IpAddress,
	slbRealServerMacAddr             PhysAddress,
	slbRealServerInfoSwitchPort      INTEGER,
	slbRealServerInfoHealthLayer     INTEGER,
	slbRealServerInfoOverflow        INTEGER,
	slbRealServerInfoState           INTEGER
	}

slbRealServerInfoIndex OBJECT-TYPE
        SYNTAX  INTEGER
        ACCESS  read-only
        STATUS  mandatory
        DESCRIPTION
                "The real server index" 
        ::= { slbRealServerInfoEntry 1 }

slbRealServerInfoIpAddr OBJECT-TYPE
        SYNTAX  IpAddress
        ACCESS  read-only
        STATUS  mandatory
        DESCRIPTION
                "IP address of the real server." 
        ::= { slbRealServerInfoEntry 2 }

slbRealServerMacAddr OBJECT-TYPE
	SYNTAX  PhysAddress
        ACCESS  read-only
        STATUS  mandatory
        DESCRIPTION
                "The MAC address of the real server." 
        ::= { slbRealServerInfoEntry 3 }

slbRealServerInfoSwitchPort OBJECT-TYPE
        SYNTAX  INTEGER
        ACCESS  read-only
        STATUS  mandatory
        DESCRIPTION
                "The switch port that the real server is connected to." 
        ::= { slbRealServerInfoEntry 4 }

slbRealServerInfoHealthLayer  OBJECT-TYPE
        SYNTAX  INTEGER { 
                other(1), 
                layer3(2),
                layer4(3)  
                } 
        ACCESS  read-only
        STATUS  mandatory
        DESCRIPTION
                "The OSI layer at whitch real server functionality is 
		 verified."
        ::= { slbRealServerInfoEntry 5 }

slbRealServerInfoOverflow OBJECT-TYPE
        SYNTAX  INTEGER {
		overflow(1),
                no-overflow(2) 
                } 
        ACCESS  read-only
        STATUS  mandatory
        DESCRIPTION
                "The overflow state of the real server." 
        ::= { slbRealServerInfoEntry 6 }

slbRealServerInfoState OBJECT-TYPE
        SYNTAX  INTEGER {
                other(1), 
                running(2),
                failed(3),
                disabled(4)
                } 
        ACCESS  read-only
        STATUS  mandatory
        DESCRIPTION
                "The state of the real server."
        ::= { slbRealServerInfoEntry 7 }


-- Run-time IP Route Table 

ipRouteInfoTable OBJECT-TYPE
        SYNTAX  SEQUENCE OF IpRouteInfoEntry
        ACCESS  not-accessible
        STATUS  mandatory
        DESCRIPTION
                "The table of run-time IP routes."
        ::= { ip-info 1 }

ipRouteInfoEntry OBJECT-TYPE
        SYNTAX  IpRouteInfoEntry
        ACCESS  not-accessible
        STATUS  mandatory
        DESCRIPTION
                "A row in the run-time IP route table"
        INDEX   { ipRouteInfoIndx }
        ::= { ipRouteInfoTable 1 }

IpRouteInfoEntry ::= SEQUENCE {
        ipRouteInfoIndx	        INTEGER,
        ipRouteInfoDestIp	IpAddress,
        ipRouteInfoMask         IpAddress,
        ipRouteInfoGateway      IpAddress,
        ipRouteInfoTag       	INTEGER,
        ipRouteInfoType       	INTEGER,
        ipRouteInfoInterface    INTEGER
        }

ipRouteInfoIndx OBJECT-TYPE
        SYNTAX  INTEGER
        ACCESS  read-only
        STATUS  mandatory
        DESCRIPTION
                "The index of this route table."
        ::= { ipRouteInfoEntry 1 }

ipRouteInfoDestIp OBJECT-TYPE
        SYNTAX  IpAddress
        ACCESS  read-only
        STATUS  mandatory
        DESCRIPTION
                "The destination IP address of this route."
        ::= { ipRouteInfoEntry 2 }

ipRouteInfoMask OBJECT-TYPE
        SYNTAX  IpAddress
        ACCESS  read-only
        STATUS  mandatory
        DESCRIPTION
                "The destination IP mask of this route."
        ::= { ipRouteInfoEntry 3 }
 
ipRouteInfoGateway OBJECT-TYPE
        SYNTAX  IpAddress
        ACCESS  read-only
        STATUS  mandatory
        DESCRIPTION
                "The next-hop router address for this route."
        ::= { ipRouteInfoEntry 4 }

ipRouteInfoTag OBJECT-TYPE
        SYNTAX  INTEGER {
		fixed(1),
  		icmp(2),
  		static(3),
		snmp(4),
		addr(5),
		rip(6),
		broadcast(7),
		martian(8),
		multicast(9)
		}
        ACCESS  read-only
        STATUS  mandatory
        DESCRIPTION
                "The tag-type for this route."
        ::= { ipRouteInfoEntry 5 }

ipRouteInfoType OBJECT-TYPE 
        SYNTAX  INTEGER {
		indirect(1),
		direct(2),
		local(3),
		broadcast(4),
		martian(5),
		multicast(6),
		other(7)
		}
        ACCESS  read-only 
        STATUS  mandatory 
        DESCRIPTION 
                "The type of the route." 
        ::= { ipRouteInfoEntry 6 }

ipRouteInfoInterface OBJECT-TYPE 
        SYNTAX  INTEGER
        ACCESS  read-only 
        STATUS  mandatory 
        DESCRIPTION 
                "The interface number for which the destination
	address is applicable." 
        ::= { ipRouteInfoEntry 7 }


arpInfoTable OBJECT-TYPE
        SYNTAX  SEQUENCE OF AgArpInfoEntry
        ACCESS  not-accessible
        STATUS  mandatory
        DESCRIPTION
                "The table of ARP entries."
        ::= { ip-info 2 }

arpInfoEntry OBJECT-TYPE
        SYNTAX  AgArpInfoEntry
        ACCESS  not-accessible
        STATUS  mandatory
        DESCRIPTION
                "A row in the ARP table"
        INDEX   { arpInfoDestIp }
        ::= { arpInfoTable 1 }

AgArpInfoEntry ::= SEQUENCE {
        arpInfoDestIp        	IpAddress,
        arpInfoMacAddr        PhysAddress,
        arpInfoVLAN        	INTEGER,
        arpInfoSrcPort        INTEGER,
        arpInfoRefPorts       INTEGER,
        arpInfoFlag           INTEGER
        }

arpInfoDestIp OBJECT-TYPE
        SYNTAX  IpAddress
        ACCESS  read-only
        STATUS  mandatory
        DESCRIPTION
                "The destination IP address of the ARP entry."

        ::= { arpInfoEntry 1 }

arpInfoMacAddr OBJECT-TYPE
        SYNTAX  PhysAddress
        ACCESS  read-only
        STATUS  mandatory
        DESCRIPTION
                "The MAC address for the ARP entry."
        ::= { arpInfoEntry 2 }

arpInfoVLAN OBJECT-TYPE 
        SYNTAX  INTEGER 
        ACCESS  read-only 
        STATUS  mandatory 
        DESCRIPTION 
                "The VLAN identifier for the ARP entry." 
        ::= { arpInfoEntry 3 }

arpInfoSrcPort OBJECT-TYPE  
        SYNTAX  INTEGER 
        ACCESS  read-only  
        STATUS  mandatory  
        DESCRIPTION  
                "The  port number on which this entry's equivalence
	is effective."  
        ::= { arpInfoEntry 4 }

arpInfoRefPorts OBJECT-TYPE   
        SYNTAX  INTEGER  
        ACCESS  read-only   
        STATUS  mandatory   
        DESCRIPTION   
                "The rference ports associated with this ARP entry."   
        ::= { arpInfoEntry 5 }

arpInfoFlag OBJECT-TYPE   
        SYNTAX  INTEGER {
		clear(1),
		unresolved(2),
		permanent(3),
		indirect(4)
		}
        ACCESS  read-only   
        STATUS  mandatory   
        DESCRIPTION   
                "The flag associated with this ARP entry."   
        ::= { arpInfoEntry 6 }


-- VRRP Information

vrrpInfoVirtRtrTable OBJECT-TYPE
        SYNTAX  SEQUENCE OF VrrpInfoVirtRtrTableEntry
        ACCESS  not-accessible
        STATUS  mandatory
        DESCRIPTION
                "The table of VRRP virtual router run-time information."
        ::= { vrrp-info 1 }

vrrpInfoVirtRtrTableEntry OBJECT-TYPE
        SYNTAX  VrrpInfoVirtRtrTableEntry
        ACCESS  not-accessible
        STATUS  mandatory
        DESCRIPTION
                "The run-time information about a VRRP virtual router."
        INDEX   { vrrpInfoVirtRtrIndex }
        ::= { vrrpInfoVirtRtrTable 1 }
 
VrrpInfoVirtRtrTableEntry ::= SEQUENCE {
        vrrpInfoVirtRtrIndex           INTEGER,
        vrrpInfoVirtRtrState           INTEGER
	}

vrrpInfoVirtRtrIndex OBJECT-TYPE
        SYNTAX  INTEGER
        ACCESS  read-only
        STATUS  mandatory
        DESCRIPTION
                "The VRRP virtual router index." 
        ::= { vrrpInfoVirtRtrTableEntry 1 }

vrrpInfoVirtRtrState OBJECT-TYPE   
        SYNTAX  INTEGER {
		init(1),
		master(2),
		backup(3)
		}
        ACCESS  read-only   
        STATUS  mandatory   
        DESCRIPTION   
                "The VRRP virtual router state."   
        ::= { vrrpInfoVirtRtrTableEntry 2 }


-- To allow configuring real server weight dynamically (For HP only)

dynSLBRealServerTable OBJECT-TYPE
        SYNTAX  SEQUENCE OF DynSLBRealServerEntry
        ACCESS  not-accessible
        STATUS  mandatory
        DESCRIPTION
                "The table of Real Servers."
        ::= { dynamicSLB 1 }

dynSLBRealServerEntry OBJECT-TYPE
        SYNTAX  DynSLBRealServerEntry
        ACCESS  not-accessible
        STATUS  mandatory
        DESCRIPTION
                "A row in the Real Server table."
        INDEX   { dynSLBRealServerIpAddr,
                  dynSLBRealServerPortNum  }
        ::= { dynSLBRealServerTable 1 }
 
DynSLBRealServerEntry ::= SEQUENCE {
        dynSLBRealServerIpAddr     IpAddress,
        dynSLBRealServerPortNum    INTEGER,
        dynSLBRealServerWeight     INTEGER
        }
 
dynSLBRealServerIpAddr OBJECT-TYPE
        SYNTAX  IpAddress
        ACCESS  read-only
        STATUS  mandatory
        DESCRIPTION
                "IP address of the Real Server."
        ::= { dynSLBRealServerEntry 1 }
 
dynSLBRealServerPortNum OBJECT-TYPE
        SYNTAX  INTEGER
        ACCESS  read-only
        STATUS  mandatory
        DESCRIPTION
                "The switch port that the Real Server is connected to."
        ::= { dynSLBRealServerEntry 2 }

dynSLBRealServerWeight OBJECT-TYPE
        SYNTAX  INTEGER
        ACCESS  read-write
        STATUS  mandatory
        DESCRIPTION
                "The Real Server weight.  The higher the server weight
                 means the Real Server is allowed to receive more traffic
                 load."
        ::= { dynSLBRealServerEntry 3 }

-- Switch Oper Commands (for Alteon internal usage only)

operSlbPortTable OBJECT-TYPE
        SYNTAX  SEQUENCE OF OperSlbPortEntry
        ACCESS  not-accessible
        STATUS  mandatory
        DESCRIPTION
                "The table of ports that the Oper commands apply to."
        ::= { operCmds 1 }

operSlbPortEntry OBJECT-TYPE
        SYNTAX  OperSlbPortEntry
        ACCESS  not-accessible
        STATUS  mandatory
        DESCRIPTION
                "A row in the operSlbPortTable "
        INDEX   { operSlbPortIndex }
        ::= { operSlbPortTable 1 }

OperSlbPortEntry ::= SEQUENCE {
        operSlbPortIndex              INTEGER,
        operSlbPortClrSessionTab      INTEGER
        }

operSlbPortIndex OBJECT-TYPE
        SYNTAX  INTEGER
        ACCESS  read-only
        STATUS  mandatory
        DESCRIPTION
                "The switch port number." 
        ::= { operSlbPortEntry 1 }

operSlbPortClrSessionTab OBJECT-TYPE
        SYNTAX  INTEGER {
		ok(1),
		clear(2)
		}
        ACCESS  read-only
        STATUS  mandatory
        DESCRIPTION
                "This an action object to clear session buinding table
		 for the specified port.  ok(1) is returned when read."
        ::= { operSlbPortEntry 2 }

radCurCfgPrimaryIpAddr OBJECT-TYPE
        SYNTAX  IpAddress
        ACCESS  read-only
        STATUS  mandatory
        DESCRIPTION
                "The IP address of the Primary RADIUS server."
        ::= { radius 1 }

radNewCfgPrimaryIpAddr OBJECT-TYPE
        SYNTAX  IpAddress
        ACCESS  read-write
        STATUS  mandatory
        DESCRIPTION
                "The IP address of the Primary RADIUS server."
        ::= { radius 2 }

radCurCfgSecondaryIpAddr OBJECT-TYPE
        SYNTAX  IpAddress
        ACCESS  read-only
        STATUS  mandatory
        DESCRIPTION
                "The IP address of the Secondary RADIUS server."
        ::= { radius 3 }

radNewCfgSecondaryIpAddr OBJECT-TYPE
        SYNTAX  IpAddress
        ACCESS  read-write
        STATUS  mandatory
        DESCRIPTION
                "The IP address of the Secondary RADIUS server."
        ::= { radius 4 }

radCurCfgPort OBJECT-TYPE
        SYNTAX  INTEGER  (1500..3000)
        ACCESS  read-only
        STATUS  mandatory
        DESCRIPTION
                "Specify the RADIUS port number."
        ::= { radius 5 }

radNewCfgPort OBJECT-TYPE
        SYNTAX  INTEGER  (1500..3000)
        ACCESS  read-write
        STATUS  mandatory
        DESCRIPTION
                "Speicfy the RADIUS port number."
        ::= { radius 6 }

radCurCfgTimeout OBJECT-TYPE
        SYNTAX  INTEGER  (1..10)
        ACCESS  read-only
        STATUS  mandatory
        DESCRIPTION
                "The maximum number of seconds before resending authentication
                 to RADIUS server."
        ::= { radius 7 }

radNewCfgTimeout OBJECT-TYPE
        SYNTAX  INTEGER  (1..10)
        ACCESS  read-write
        STATUS  mandatory
        DESCRIPTION
                "The maximum number of seconds before resending authentication
                 to RADIUS server."
        ::= { radius 8 }

radCurCfgRetries OBJECT-TYPE
        SYNTAX  INTEGER  (1..3)
        ACCESS  read-only
        STATUS  mandatory
        DESCRIPTION
                "Number of retries to the RADIUS server."
        ::= { radius 9 }

radNewCfgRetries OBJECT-TYPE
        SYNTAX  INTEGER  (1..3)
        ACCESS  read-write
        STATUS  mandatory
        DESCRIPTION
                "Number of retries to the RADIUS server."
        ::= { radius 10 }

radCurCfgState OBJECT-TYPE
        SYNTAX  INTEGER {
                other(1),
                enabled(2),
                disabled(3)
                }
        ACCESS  read-only
        STATUS  mandatory
        DESCRIPTION
                "Enable or disbale RADIUS authentication."
        ::= { radius 11 }

radNewCfgState OBJECT-TYPE
        SYNTAX  INTEGER {
                other(1),
                enabled(2),
                disabled(3)
                }
        ACCESS  read-write
        STATUS  mandatory
        DESCRIPTION
                "Enable or disable RADIUS authentication."
        ::= { radius 12 }

radCurCfgAuthenString OBJECT-TYPE
        SYNTAX  DisplayString (SIZE(0..32))
        ACCESS  read-only
        STATUS  mandatory
        DESCRIPTION
                "The RADIUS authentication string."
        ::= { radius 13 }

radNewCfgAuthenString OBJECT-TYPE
        SYNTAX  DisplayString (SIZE(0..32))
        ACCESS  read-write
        STATUS  mandatory
        DESCRIPTION
                "The RADIUS authentication string."
        ::= { radius 14 }

-- Bandwidth Management Group

bwmGeneralConfig  OBJECT IDENTIFIER ::= { bwm 1 }
bwmPolicyConfig   OBJECT IDENTIFIER ::= { bwm 2 }
bwmContractConfig OBJECT IDENTIFIER ::= { bwm 3 }


bwmCurCfgGenState OBJECT-TYPE
        SYNTAX  INTEGER {
		other(1),
		on(2),
		off(3)
		}
        ACCESS  read-only
        STATUS  mandatory
        DESCRIPTION
                "The state of BWM in the current configuration
		 block."
        ::= { bwmGeneralConfig 1 }

bwmNewCfgGenState OBJECT-TYPE
        SYNTAX  INTEGER {
		other(1),
		on(2),
		off(3)
		}
        ACCESS  read-write
        STATUS  mandatory
        DESCRIPTION
                "The state of BWM in the new configuration
		 block."
        ::= { bwmGeneralConfig 2 }

bwmCurCfgGenEnforcePolicy OBJECT-TYPE
        SYNTAX  INTEGER {
		other(1),
		enabled(2),
		disabled(3)
		}
        ACCESS  read-only
        STATUS  mandatory
        DESCRIPTION
                "The state of BWM enforce policy in the current configuration
		 block."
        ::= { bwmGeneralConfig 3 }

bwmNewCfgGenEnforcePolicy OBJECT-TYPE
        SYNTAX  INTEGER {
		other(1),
		enabled(2),
		disabled(3)
		}
        ACCESS  read-write
        STATUS  mandatory
        DESCRIPTION
                "The state of BWM enforce policy in the new configuration
		 block."
        ::= { bwmGeneralConfig 4 }

bwmCurCfgGenSmtpUser OBJECT-TYPE
        SYNTAX  DisplayString (SIZE(0..127))
        ACCESS  read-only
        STATUS  mandatory
        DESCRIPTION
                "The SMTP user name for BWM in the current configuration
		 block."
        ::= { bwmGeneralConfig 5 }
 
bwmNewCfgGenSmtpUser OBJECT-TYPE
        SYNTAX  DisplayString (SIZE(0..127))
        ACCESS  read-write
        STATUS  mandatory
        DESCRIPTION
                "The SMTP user name for BWM in the new configuration
		 block."
        ::= { bwmGeneralConfig 6 }
 
bwmPolicyTableMaxEnt OBJECT-TYPE
        SYNTAX  INTEGER
        ACCESS  read-only
        STATUS  mandatory
        DESCRIPTION
                "The maximum number of rows in the BWM policy
                 configuration table."
        ::= { bwmPolicyConfig 1 }

bwmCurCfgPolicyTable OBJECT-TYPE
        SYNTAX  SEQUENCE OF BwmCurCfgPolicyTableEntry
        ACCESS  not-accessible
        STATUS  mandatory
        DESCRIPTION
                "The table of BWM traffic policy configuration
                 in the current_configuration block."
        ::= { bwmPolicyConfig 2 }
 
bwmCurCfgPolicyTableEntry OBJECT-TYPE
        SYNTAX  BwmCurCfgPolicyTableEntry
        ACCESS  not-accessible
        STATUS  mandatory
        DESCRIPTION
                "A row in the BWM traffic policy configuration
                 table in the current_configuration block."
        INDEX   { bwmCurCfgPolicyIndx }
        ::= { bwmCurCfgPolicyTable 1 }
 
BwmCurCfgPolicyTableEntry ::= SEQUENCE {
        bwmCurCfgPolicyIndx          INTEGER,
        bwmCurCfgPolicyTosIn	     INTEGER,
	bwmCurCfgPolicyTosOut	     INTEGER,
        bwmCurCfgPolicyHard          DisplayString,
        bwmCurCfgPolicySoft          DisplayString,
        bwmCurCfgPolicyResv          DisplayString,
        bwmCurCfgPolicyBuffer        INTEGER
        }
 
bwmCurCfgPolicyIndx OBJECT-TYPE
        SYNTAX  INTEGER  (1..64)
        ACCESS  read-only
        STATUS  mandatory
        DESCRIPTION
                "The index of the row in BWM traffic policy
                 configurations table."
        ::= { bwmCurCfgPolicyTableEntry 1 }
 
bwmCurCfgPolicyTosIn OBJECT-TYPE
        SYNTAX  INTEGER (0..255)
        ACCESS  read-only
        STATUS  mandatory
        DESCRIPTION
                "This is IP TOS in the profile state of the traffic policy"
        ::= { bwmCurCfgPolicyTableEntry 2 }

bwmCurCfgPolicyTosOut OBJECT-TYPE
        SYNTAX  INTEGER (0..255)
        ACCESS  read-only
        STATUS  mandatory
        DESCRIPTION
                "This is IP TOS out of profile state of the traffic policy"
        ::= { bwmCurCfgPolicyTableEntry 3 }

bwmCurCfgPolicyHard OBJECT-TYPE
        SYNTAX  DisplayString (SIZE(0..4))
        ACCESS  read-only
        STATUS  mandatory
        DESCRIPTION
                "The hard speed limit for the traffic policy."
        ::= { bwmCurCfgPolicyTableEntry 4 }
 
bwmCurCfgPolicySoft OBJECT-TYPE
        SYNTAX  DisplayString (SIZE(0..4))
        ACCESS  read-only
        STATUS  mandatory
        DESCRIPTION
                "The soft speed limit for the traffic policy."
        ::= { bwmCurCfgPolicyTableEntry 5 }
 
bwmCurCfgPolicyResv OBJECT-TYPE
        SYNTAX  DisplayString (SIZE(0..4))
        ACCESS  read-only
        STATUS  mandatory
        DESCRIPTION
                "The reservation speed limit for the traffic policy."
        ::= { bwmCurCfgPolicyTableEntry 6 }
 
bwmCurCfgPolicyBuffer OBJECT-TYPE
        SYNTAX  INTEGER (8192..512000)
        ACCESS  read-only
        STATUS  mandatory
        DESCRIPTION
                "The buffer limit for the traffic policy."
        ::= { bwmCurCfgPolicyTableEntry 7 }
 
bwmNewCfgPolicyTable OBJECT-TYPE
        SYNTAX  SEQUENCE OF BwmNewCfgPolicyTableEntry
        ACCESS  not-accessible
        STATUS  mandatory
        DESCRIPTION
                "The table of BWM traffi policy configuration
                 in the current_configuration block."
        ::= { bwmPolicyConfig 3 }
 
bwmNewCfgPolicyTableEntry OBJECT-TYPE
        SYNTAX  BwmNewCfgPolicyTableEntry
        ACCESS  not-accessible
        STATUS  mandatory
        DESCRIPTION
                "A row in the BWM traffic policy configuration
                 table in the current_configuration block."
        INDEX   { bwmNewCfgPolicyIndx }
        ::= { bwmNewCfgPolicyTable 1 }
 
BwmNewCfgPolicyTableEntry ::= SEQUENCE {
        bwmNewCfgPolicyIndx          INTEGER,
        bwmNewCfgPolicyTosIn	     INTEGER,
	bwmNewCfgPolicyTosOut	     INTEGER,
        bwmNewCfgPolicyHard          DisplayString,
        bwmNewCfgPolicySoft          DisplayString,
        bwmNewCfgPolicyResv          DisplayString,
        bwmNewCfgPolicyBuffer        INTEGER
        }

bwmNewCfgPolicyIndx OBJECT-TYPE
        SYNTAX  INTEGER  (1..64)
        ACCESS  read-only
        STATUS  mandatory
        DESCRIPTION
                "The index of the row in BWM traffic policy
                 configurations table."
        ::= { bwmNewCfgPolicyTableEntry 1 }
 
bwmNewCfgPolicyTosIn OBJECT-TYPE
        SYNTAX  INTEGER (0..255)
        ACCESS  read-write
        STATUS  mandatory
        DESCRIPTION
                "This is IP TOS in the profile state of the traffic policy"
        ::= { bwmNewCfgPolicyTableEntry 2 }

bwmNewCfgPolicyTosOut OBJECT-TYPE
        SYNTAX  INTEGER (0..255)
        ACCESS  read-write
        STATUS  mandatory
        DESCRIPTION
                "This is IP TOS out of profile state of the traffic policy"
        ::= { bwmNewCfgPolicyTableEntry 3 }

bwmNewCfgPolicyHard OBJECT-TYPE
        SYNTAX  DisplayString (SIZE(0..5)) 
        ACCESS  read-write
        STATUS  mandatory
        DESCRIPTION
                "The hard speed limit for the traffic policy."
        ::= { bwmNewCfgPolicyTableEntry 4 }
 
bwmNewCfgPolicySoft OBJECT-TYPE
        SYNTAX  DisplayString (SIZE(0..5))
        ACCESS  read-write
        STATUS  mandatory
        DESCRIPTION
                "The soft speed limit for the traffic policy."
        ::= { bwmNewCfgPolicyTableEntry 5 }
 
bwmNewCfgPolicyResv OBJECT-TYPE
        SYNTAX  DisplayString (SIZE(0..5))
        ACCESS  read-write
        STATUS  mandatory
        DESCRIPTION
                "The reservation speed limit for the traffic policy."
        ::= { bwmNewCfgPolicyTableEntry 6 }
 
bwmNewCfgPolicyBuffer OBJECT-TYPE
        SYNTAX  INTEGER (8192..512000)
        ACCESS  read-write
        STATUS  mandatory
        DESCRIPTION
                "The buffer limit for the traffic policy."
        ::= { bwmNewCfgPolicyTableEntry 7 }
 
-- BWM Contract Config Table
 
bwmContractTableMaxEnt OBJECT-TYPE
        SYNTAX  INTEGER
        ACCESS  read-only
        STATUS  mandatory
        DESCRIPTION
                "The maximum number of rows in the BWM contract
                 configuration table."
        ::= { bwmContractConfig 1 }
 
bwmCurCfgContractTable OBJECT-TYPE
        SYNTAX  SEQUENCE OF BwmContractCurCfgTableEntry
        ACCESS  not-accessible
        STATUS  mandatory
        DESCRIPTION
                "The table of BWM traffic contract configuration
                 in the current_configuration block."
        ::= { bwmContractConfig 2 }
 
bwmCurCfgContractTableEntry OBJECT-TYPE
        SYNTAX  BwmContractCurCfgTableEntry
        ACCESS  not-accessible
        STATUS  mandatory
        DESCRIPTION
                "A row in the BWM traffic contract configuration
                 table in the current_configuration block."
        INDEX   { bwmCurCfgContractIndx }
        ::= { bwmCurCfgContractTable 1 }
 
BwmContractCurCfgTableEntry ::= SEQUENCE {
        bwmCurCfgContractIndx        INTEGER,
        bwmCurCfgContractName        DisplayString,
        bwmCurCfgContractState       INTEGER,
        bwmCurCfgContractPolicy      INTEGER,
	bwmCurCfgContractPrec	     INTEGER,
	bwmCurCfgContractUseTos	     INTEGER,
	bwmCurCfgContractHistory     INTEGER
        }
 
bwmCurCfgContractIndx OBJECT-TYPE
        SYNTAX  INTEGER  (1..255)
        ACCESS  read-only
        STATUS  mandatory
        DESCRIPTION
                "The index of the row in BWM traffic contract
                 configurations table."
        ::= { bwmCurCfgContractTableEntry 1 }
 
 
bwmCurCfgContractName   OBJECT-TYPE
        SYNTAX  DisplayString (SIZE(0..64))
        ACCESS  read-only
        STATUS  mandatory
        DESCRIPTION
                "The traffic contract name."
        ::= { bwmCurCfgContractTableEntry 2 }
 
bwmCurCfgContractState OBJECT-TYPE
        SYNTAX  INTEGER {
                other(1),
                enabled(2),
                disabled(3)
                }
        ACCESS  read-only
        STATUS  mandatory
        DESCRIPTION
                "This is the state of the traffic contract."
        ::= { bwmCurCfgContractTableEntry 3 }
 
bwmCurCfgContractPolicy OBJECT-TYPE
        SYNTAX  INTEGER (1..64)
        ACCESS  read-only
        STATUS  mandatory
        DESCRIPTION
                "This is policy number of the traffic contract"
        ::= { bwmCurCfgContractTableEntry 4 }
 
bwmCurCfgContractPrec OBJECT-TYPE
        SYNTAX  INTEGER (1..255)
        ACCESS  read-only
        STATUS  mandatory
        DESCRIPTION
                "The precedence value of the traffic contract"
        ::= { bwmCurCfgContractTableEntry 5 }
 
bwmCurCfgContractUseTos OBJECT-TYPE
        SYNTAX  INTEGER {
                other(1),
                enabled(2),
                disabled(3)
                }
        ACCESS  read-only
        STATUS  mandatory
        DESCRIPTION
                "Enable/disable the TOS overwrite of the traffic contract."
        ::= { bwmCurCfgContractTableEntry 6 }
 
bwmCurCfgContractHistory OBJECT-TYPE
        SYNTAX  INTEGER {
                other(1),
                enabled(2),
                disabled(3)
                }
        ACCESS  read-only
        STATUS  mandatory
        DESCRIPTION
                "Enable/disable save contract statistics on the TFTP server
		 of the traffic contract."
        ::= { bwmCurCfgContractTableEntry 7 }
 
bwmNewCfgContractTable OBJECT-TYPE
        SYNTAX  SEQUENCE OF BwmContractNewCfgTableEntry
        ACCESS  not-accessible
        STATUS  mandatory
        DESCRIPTION
                "The table of BWM traffic contract configuration
                 in the current_configuration block."
        ::= { bwmContractConfig 3 }
 
bwmNewCfgContractTableEntry OBJECT-TYPE
        SYNTAX  BwmContractNewCfgTableEntry
        ACCESS  not-accessible
        STATUS  mandatory
        DESCRIPTION
                "A row in the BWM traffic contract configuration
                 table in the current_configuration block."
        INDEX   { bwmNewCfgContractIndx }
        ::= { bwmNewCfgContractTable 1 }
 
BwmContractNewCfgTableEntry ::= SEQUENCE {
        bwmNewCfgContractIndx        INTEGER,
        bwmNewCfgContractName        DisplayString,
        bwmNewCfgContractState       INTEGER,
        bwmNewCfgContractPolicy      INTEGER,
        bwmNewCfgContractDelete      INTEGER,
	bwmNewCfgContractPrec	     INTEGER,
	bwmNewCfgContractUseTos	     INTEGER,
	bwmNewCfgContractHistory     INTEGER
        }
 
bwmNewCfgContractIndx OBJECT-TYPE
        SYNTAX  INTEGER  (1..255)
        ACCESS  read-only
        STATUS  mandatory
        DESCRIPTION
                "The index of the row in BWM traffic contract
                 configurations table."
        ::= { bwmNewCfgContractTableEntry 1 }
bwmNewCfgContractName   OBJECT-TYPE
        SYNTAX  DisplayString (SIZE(0..64))
        ACCESS  read-write
        STATUS  mandatory
        DESCRIPTION
                "The traffic contract name."
        ::= { bwmNewCfgContractTableEntry 2 }
 
bwmNewCfgContractState OBJECT-TYPE
        SYNTAX  INTEGER {
                other(1),
                enabled(2),
                disabled(3)
                }
        ACCESS  read-write
        STATUS  mandatory
        DESCRIPTION
                "This is the state of the traffic contract."
        ::= { bwmNewCfgContractTableEntry 3 }
 
bwmNewCfgContractPolicy OBJECT-TYPE
        SYNTAX  INTEGER (1..64)
        ACCESS  read-write
        STATUS  mandatory
        DESCRIPTION
                "This is policy number of the traffic contract"
        ::= { bwmNewCfgContractTableEntry 4 }
 
bwmNewCfgContractDelete OBJECT-TYPE
        SYNTAX  INTEGER  {
                other(1),
                delete(2)
                }
        ACCESS  read-write
        STATUS  mandatory
        DESCRIPTION
              "When set to the value of 2 (delete), the entire row
               is deleted. When read, other(1) is returned. Setting the value
               to anything other than 2(delete) has no effect on the state
               of the row."
        ::= { bwmNewCfgContractTableEntry 5 }
 
bwmNewCfgContractPrec OBJECT-TYPE
        SYNTAX  INTEGER (1..255)
        ACCESS  read-write
        STATUS  mandatory
        DESCRIPTION
                "The precedence value of the traffic contract"
        ::= { bwmNewCfgContractTableEntry 6 }
 
bwmNewCfgContractUseTos OBJECT-TYPE
        SYNTAX  INTEGER {
                other(1),
                enabled(2),
                disabled(3)
                }
        ACCESS  read-write
        STATUS  mandatory
        DESCRIPTION
                "Enable/disable the TOS overwrite of the traffic contract."
        ::= { bwmNewCfgContractTableEntry 7 }
 
bwmNewCfgContractHistory OBJECT-TYPE
        SYNTAX  INTEGER {
                other(1),
                enabled(2),
                disabled(3)
                }
        ACCESS  read-write
        STATUS  mandatory
        DESCRIPTION
                "Enable/disable save contract statistics on the TFTP server
		 of the traffic contract."
        ::= { bwmNewCfgContractTableEntry 8 }
 
 
-- BWM Traffic Contract Statistics Table
 
bwmStatTcTable  OBJECT-TYPE
        SYNTAX  SEQUENCE OF BwmStatTcEntry
        ACCESS  not-accessible
        STATUS  mandatory
        DESCRIPTION
                "The table of Bandwidth Management Traffic Contract statistics." 
        ::= { bwmStats 1 }
 
bwmStatTcEntry OBJECT-TYPE
        SYNTAX  BwmStatTcEntry
        ACCESS  not-accessible
        STATUS  mandatory
        DESCRIPTION
                "A row in the BWM traffic contract table."
        INDEX   { bwmStatTcContractIndex }
        ::= { bwmStatTcTable 1 }

        BwmStatTcEntry ::=
              SEQUENCE {
                  bwmStatTcContractIndex
                      INTEGER,
                  bwmStatTcName
                      DisplayString,
                  bwmStatTcOutoct
                      Counter,
                  bwmStatTcOutdisoct
                      Counter,
                  bwmStatTcBufferUsed
                      Counter,
                  bwmStatTcBufferMax
                      Counter
        }
 
bwmStatTcContractIndex OBJECT-TYPE
        SYNTAX  INTEGER
        ACCESS  read-only
        STATUS  mandatory
        DESCRIPTION
                "The contract queue number for which the statistics apply."
        ::= { bwmStatTcEntry 1 }
 
bwmStatTcName OBJECT-TYPE
        SYNTAX  DisplayString (SIZE(0..16))
        ACCESS  read-only
        STATUS  mandatory
        DESCRIPTION
                "The name of the traffic contract queue."
        ::= { bwmStatTcEntry 2 }
 
bwmStatTcOutoct OBJECT-TYPE
        SYNTAX  Counter
        ACCESS  read-only
        STATUS  mandatory
        DESCRIPTION
                "The total number of octets sent out from the traffic
                 contract queue."
        ::= { bwmStatTcEntry 3 }
 
bwmStatTcOutdisoct OBJECT-TYPE
        SYNTAX  Counter
        ACCESS  read-only
        STATUS  mandatory
        DESCRIPTION
                "The total number of octets dropped from the traffic
                 contract queue."
        ::= { bwmStatTcEntry 4 }
 
bwmStatTcBufferUsed OBJECT-TYPE
        SYNTAX  Counter
        ACCESS  read-only
        STATUS  mandatory
        DESCRIPTION
                "The total number of buffers used by the traffic contract
                 queue."
        ::= { bwmStatTcEntry 5 }
 
bwmStatTcBufferMax OBJECT-TYPE
        SYNTAX  Counter
        ACCESS  read-only
        STATUS  mandatory
        DESCRIPTION
                "The total number of buffers assigned to the traffic
                 contract queue."
        ::= { bwmStatTcEntry 6 }
 
-- BWM Traffic Contract Rate Statistics Table
 
bwmStatTcrTable  OBJECT-TYPE
        SYNTAX  SEQUENCE OF BwmStatTcrEntry
        ACCESS  not-accessible
        STATUS  mandatory
        DESCRIPTION
                "The table of Bandwidth Management Traffic Contract
                 Rate statistics."
        ::= { bwmStats 2 }
 
bwmStatTcrEntry OBJECT-TYPE
        SYNTAX  BwmStatTcrEntry
        ACCESS  not-accessible
        STATUS  mandatory
        DESCRIPTION
                "A row in the BWM traffic contract rate table."
        INDEX   { bwmStatTcrContractIndex }
        ::= { bwmStatTcrTable 1 }
 
        BwmStatTcrEntry ::=
              SEQUENCE {
                  bwmStatTcrContractIndex
                      INTEGER,
                  bwmStatTcrName
                      DisplayString,
                  bwmStatTcrRate
                      INTEGER,
                  bwmStatTcrOutoct
                      Counter,
                  bwmStatTcrOutdisoct
                      Counter,
                  bwmStatTcrBufferUsed
                      Counter,
                  bwmStatTcrBufferMax
                      Counter
        }
 
bwmStatTcrContractIndex OBJECT-TYPE
        SYNTAX  INTEGER
        ACCESS  read-only
        STATUS  mandatory
        DESCRIPTION
                "The contract queue number for which the statistics apply."
        ::= { bwmStatTcrEntry 1 }
 
bwmStatTcrName OBJECT-TYPE
        SYNTAX  DisplayString (SIZE(0..16))
        ACCESS  read-only
        STATUS  mandatory
        DESCRIPTION
                "The name of the traffic contract queue."
        ::= { bwmStatTcrEntry 2 }
 
bwmStatTcrRate OBJECT-TYPE
        SYNTAX  INTEGER
        ACCESS  read-only
        STATUS  mandatory
        DESCRIPTION
                "The rate of octets sent out from the traffic
                 contract queue."
        ::= { bwmStatTcrEntry 3 }
 
bwmStatTcrOutoct OBJECT-TYPE
        SYNTAX  Counter
        ACCESS  read-only
        STATUS  mandatory
        DESCRIPTION
                "The of octets sent out from the traffic
                 contract queue."
        ::= { bwmStatTcrEntry 4 }
 
bwmStatTcrOutdisoct OBJECT-TYPE
        SYNTAX  Counter
        ACCESS  read-only
        STATUS  mandatory
        DESCRIPTION
                "The total number of octets dropped from the traffic
                 contract queue."
        ::= { bwmStatTcrEntry 5 }
 
bwmStatTcrBufferUsed OBJECT-TYPE
        SYNTAX  Counter
        ACCESS  read-only
        STATUS  mandatory
        DESCRIPTION
                "The total number of buffers used by the traffic contract
                 queue."
        ::= { bwmStatTcrEntry 6 }
 
bwmStatTcrBufferMax OBJECT-TYPE
        SYNTAX  Counter
        ACCESS  read-only
        STATUS  mandatory
        DESCRIPTION
                "The total number of buffers assigned to the traffic
                 contract queue."
        ::= { bwmStatTcrEntry 7 }
 
-- BWM Switch Port Traffic Contract Statistics Table
 
bwmStatSpTcTable  OBJECT-TYPE
        SYNTAX  SEQUENCE OF BwmStatSpTcEntry
        ACCESS  not-accessible
        STATUS  mandatory
        DESCRIPTION
                "The table of Bandwidth Management Switch Port
                Traffic Contract statistics."
        ::= { bwmStats 3 }
 
bwmStatSpTcEntry OBJECT-TYPE
        SYNTAX  BwmStatSpTcEntry
        ACCESS  not-accessible
        STATUS  mandatory
        DESCRIPTION
                "A row in the BWM SP traffic contract table."
        INDEX   { bwmStatSpTcPortIndex, bwmStatSpTcContractIndex }
        ::= { bwmStatSpTcTable 1 }
 
        BwmStatSpTcEntry ::=
              SEQUENCE {
                  bwmStatSpTcPortIndex
                      INTEGER,
                  bwmStatSpTcContractIndex
                      INTEGER,
                  bwmStatSpTcName
                      DisplayString,
                  bwmStatSpTcOutoct
                      Counter,
                  bwmStatSpTcOutdisoct
                      Counter,
                  bwmStatSpTcBufferUsed
                      Counter,
                  bwmStatSpTcBufferMax
                      Counter
        }
 
bwmStatSpTcPortIndex OBJECT-TYPE
        SYNTAX  INTEGER
        ACCESS  read-only
        STATUS  mandatory
        DESCRIPTION
                "The Switch Port number for which the statistics apply."
        ::= { bwmStatSpTcEntry 1 }
 
bwmStatSpTcContractIndex OBJECT-TYPE
        SYNTAX  INTEGER
        ACCESS  read-only
        STATUS  mandatory
        DESCRIPTION
                "The contract queue number for which the statistics apply."
        ::= { bwmStatSpTcEntry 2 }
 
bwmStatSpTcName OBJECT-TYPE
        SYNTAX  DisplayString (SIZE(0..16))
        ACCESS  read-only
        STATUS  mandatory
        DESCRIPTION
                "The name of the traffic contract queue."
        ::= { bwmStatSpTcEntry 3 }
 
bwmStatSpTcOutoct OBJECT-TYPE
        SYNTAX  Counter
        ACCESS  read-only
        STATUS  mandatory
        DESCRIPTION
                "The total number of octets sent out from the traffic
                 contract queue."
        ::= { bwmStatSpTcEntry 4 }
 
bwmStatSpTcOutdisoct OBJECT-TYPE
        SYNTAX  Counter
        ACCESS  read-only
        STATUS  mandatory
        DESCRIPTION
                "The total number of octets dropped from the traffic
                 contract queue."
        ::= { bwmStatSpTcEntry 5 }
 
bwmStatSpTcBufferUsed OBJECT-TYPE
        SYNTAX  Counter
        ACCESS  read-only
        STATUS  mandatory
        DESCRIPTION
                "The total number of buffers used by the traffic contract
                 queue."
        ::= { bwmStatSpTcEntry 6 }
 
bwmStatSpTcBufferMax OBJECT-TYPE
        SYNTAX  Counter
        ACCESS  read-only
        STATUS  mandatory
        DESCRIPTION
                "The total number of buffers assigned to the traffic
                 contract queue."
        ::= { bwmStatSpTcEntry 7 }
 
-- BWM Switch Port Traffic Contract Rate Statistics Table
 
bwmStatSpTcrTable  OBJECT-TYPE
        SYNTAX  SEQUENCE OF BwmStatSpTcrEntry
        ACCESS  not-accessible
        STATUS  mandatory
        DESCRIPTION
                "The table of Bandwidth Management Switch Port
                Traffic Contract Rate statistics."
        ::= { bwmStats 4 }
 
bwmStatSpTcrEntry OBJECT-TYPE
        SYNTAX  BwmStatSpTcrEntry
        ACCESS  not-accessible
        STATUS  mandatory
        DESCRIPTION
                "A row in the BWM traffic contract rate table."
        INDEX   { bwmStatSpTcrPortIndex, bwmStatSpTcrContractIndex }
        ::= { bwmStatSpTcrTable 1 }
 
        BwmStatSpTcrEntry ::=
              SEQUENCE {
                  bwmStatSpTcrPortIndex
                      INTEGER,
                  bwmStatSpTcrContractIndex
                      INTEGER,
                  bwmStatSpTcrName
                      DisplayString,
                  bwmStatSpTcrRate
                      INTEGER,
                  bwmStatSpTcrOutoct
                      Counter,
                  bwmStatSpTcrOutdisoct
                      Counter,
                  bwmStatSpTcrBufferUsed
                      Counter,
                  bwmStatSpTcrBufferMax
                      Counter
        }
 
bwmStatSpTcrPortIndex OBJECT-TYPE
        SYNTAX  INTEGER
        ACCESS  read-only
        STATUS  mandatory
        DESCRIPTION
                "The switch port number for which the statistics apply."
        ::= { bwmStatSpTcrEntry 1 }
 
bwmStatSpTcrContractIndex OBJECT-TYPE
        SYNTAX  INTEGER
        ACCESS  read-only
        STATUS  mandatory
        DESCRIPTION
                "The contract queue number for which the statistics apply."
        ::= { bwmStatSpTcrEntry 2 }
 
bwmStatSpTcrName OBJECT-TYPE
        SYNTAX  DisplayString (SIZE(0..16))
        ACCESS  read-only
        STATUS  mandatory
        DESCRIPTION
                "The name of the traffic contract queue."
        ::= { bwmStatSpTcrEntry 3 }
 
bwmStatSpTcrRate OBJECT-TYPE
        SYNTAX  INTEGER
        ACCESS  read-only
        STATUS  mandatory
        DESCRIPTION
                "The rate of octets sent out from the traffic
                 contract queue."
        ::= { bwmStatSpTcrEntry 4 }
 
bwmStatSpTcrOutoct OBJECT-TYPE
        SYNTAX  Counter
        ACCESS  read-only
        STATUS  mandatory
        DESCRIPTION
                "The of octets sent out from the traffic
                 contract queue."
        ::= { bwmStatSpTcrEntry 5 }
 
bwmStatSpTcrOutdisoct OBJECT-TYPE
        SYNTAX  Counter
        ACCESS  read-only
        STATUS  mandatory
        DESCRIPTION
                "The total number of octets dropped from the traffic
                 contract queue."
        ::= { bwmStatSpTcrEntry 6 }
 
bwmStatSpTcrBufferUsed OBJECT-TYPE
        SYNTAX  Counter
        ACCESS  read-only
        STATUS  mandatory
        DESCRIPTION
                "The total number of buffers used by the traffic contract
                 queue."
        ::= { bwmStatSpTcrEntry 7 }
 
bwmStatSpTcrBufferMax OBJECT-TYPE
        SYNTAX  Counter
        ACCESS  read-only
        STATUS  mandatory
        DESCRIPTION
                "The total number of buffers assigned to the traffic
                 contract queue."
        ::= { bwmStatSpTcrEntry 8 }
  

END
