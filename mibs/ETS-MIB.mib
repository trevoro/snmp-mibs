ETS-MIB DEFINITIONS ::= BEGIN

IMPORTS
    IpAddress, MODULE-IDENTITY , OBJECT-TYPE               FROM SNMPv2-SMI
    TEXTUAL-CONVENTION, DisplayString				FROM SNMPv2-TC
	 OBJECT-GROUP, MODULE-COMPLIANCE 				FROM SNMPv2-CONF
	 enterprises											FROM RFC1155-SMI;

    aii         OBJECT IDENTIFIER ::= { enterprises 539 }


aiEts MODULE-IDENTITY
       LAST-UPDATED "9703131900Z"
       ORGANIZATION "Applied Innovation Inc."
       CONTACT-INFO
                  "

                   Postal: Applied Innovation Inc.
                           5800 Innovation Drive
                           Dublin, Ohio 43017-3271

                   Tel:    614-798-2000
                   Fax:    614-798-1770
                   E-Mail: snmp@aiinet.com"
       DESCRIPTION
	       "This MIB provides configuration and status information
               for a 196IETS project."
   ::= { aii 17 }




aiEtsSystem     OBJECT IDENTIFIER ::= { aiEts 1 }

aiCardType      OBJECT-TYPE
                SYNTAX          INTEGER { headEndCard(1), remoteEndCard(2) }
                MAX-ACCESS      read-write
                STATUS          current
                DESCRIPTION
                        "indicates whether this is a head end AI196IETS 
                         card, or a remote end AI196IETS card."
                DEFVAL {remoteEndCard}
    ::= { aiEtsSystem 1 }

aiPollRetryLimit OBJECT-TYPE
                SYNTAX          INTEGER (0..15)
                MAX-ACCESS      read-write
                STATUS          current
                DESCRIPTION
                        "the number of retries attempted following an E2A
                         Timeout, before the E2A RTU's communication
                         state is deemed to have failed."
                DEFVAL {2}
    ::= { aiEtsSystem 2 }

aiHealthMessageInterval OBJECT-TYPE
                SYNTAX          INTEGER (30..65535)
                MAX-ACCESS      read-write
                STATUS          current
                DESCRIPTION
                        "the period of time (in seconds) with-in which the 
                         remote end card must send a health message.  If 
                         the head end card does not receive the message 
                         within this period, it closes the connection to 
                         the remote end card."
                DEFVAL {60}
    ::= { aiEtsSystem 3 }

aiReconnectionTimeOutPeriod OBJECT-TYPE
                SYNTAX          INTEGER (10..65535)
                MAX-ACCESS      read-write
                STATUS          current
                DESCRIPTION
                        "the period of time (in seconds) that the head end 
                         card waits before attempting to re-establish a 
                         connection with a remote end card."
                DEFVAL {60}
    ::= { aiEtsSystem 4 }





aiEtsConnectionTable OBJECT-TYPE
                SYNTAX          SEQUENCE OF AIEtsConnectionEntry
                MAX-ACCESS      not-accessible
                STATUS          current
                DESCRIPTION
                        "Entries define the text associated with the head 
                        end/remote end connections."
    ::= { aiEts 2 }

aiEtsConnectionEntry OBJECT-TYPE
                SYNTAX          AIEtsConnectionEntry
                MAX-ACCESS      not-accessible
                STATUS          current
                DESCRIPTION
                        "Information about a particular ETS Connection."
                INDEX           {aiConnectionIndex}
    ::= { aiEtsConnectionTable 1 }

AIEtsConnectionEntry ::= SEQUENCE {
                        aiConnectionIndex INTEGER,
                        aiIpAddress IpAddress,
                        aiConnectionStatus INTEGER
                        }

aiConnectionIndex OBJECT-TYPE
                SYNTAX          INTEGER (1..64)
                MAX-ACCESS      read-only
                STATUS          current
                DESCRIPTION
                        "there can be up to 64 head end/remote end 
                         connections."
    ::= { aiEtsConnectionEntry 1 }

aiIpAddress   OBJECT-TYPE
              SYNTAX  IpAddress
              MAX-ACCESS  read-only
              STATUS  current
              DESCRIPTION
                      "The IP address to which this 196IETS card is 
                       connected."
    ::= { aiEtsConnectionEntry 2 }


aiConnectionStatus OBJECT-TYPE
                SYNTAX          INTEGER {
                                          noActiveConnection(1),
                                          connecting(2),
                                          activeConnection(3),
                                          suspended(4)
                                        }
                MAX-ACCESS      read-only
                STATUS          current
                DESCRIPTION
                        "indicates the current status of the head 
                         end/remote end connection."
                DEFVAL {noActiveConnection}
    ::= { aiEtsConnectionEntry 3 }





aiE2aLinkTable  OBJECT-TYPE
                SYNTAX          SEQUENCE OF AIE2aLinkEntry
                MAX-ACCESS      not-accessible
                STATUS          current
                DESCRIPTION
                        "Entries define the text associated with the head 
                        end/remote end connections."
    ::= { aiEts 3 }

aiE2aLinkEntry  OBJECT-TYPE
                SYNTAX          AIE2aLinkEntry
                MAX-ACCESS      not-accessible
                STATUS          current
                DESCRIPTION
                        "Information about a particular E2A Link."
                INDEX           {aiE2aLinkIndex}
    ::= { aiE2aLinkTable 1 }

AIE2aLinkEntry ::= SEQUENCE {
                        aiE2aLinkIndex INTEGER,
                        aiProvisioned INTEGER,
                        aiLinkStatus INTEGER,
                        aiBaudRate INTEGER,
                        aiProtocol INTEGER,
                        aiTxMessages INTEGER,
                        aiTxWords INTEGER,
                        aiTxErrors INTEGER,
                        aiRxMessages INTEGER,
                        aiRxWords INTEGER,
                        aiRxErrors INTEGER,
                        aiRxTimeouts INTEGER,
			aiFlushes INTEGER
                       }

aiE2aLinkIndex  OBJECT-TYPE
                SYNTAX          INTEGER (1..16)
                MAX-ACCESS      read-only
                STATUS          current
                DESCRIPTION
                        "each 196IETS card can have 16 E2A links.  Head 
                         end cards connect to NMA, remote end cards 
                         connect to E2A RTUs."
    ::= { aiE2aLinkEntry 1 }

aiProvisioned   OBJECT-TYPE
                SYNTAX          INTEGER { notProvisioned(1), provisioned(2) }
                MAX-ACCESS      read-write
                STATUS          current
                DESCRIPTION
                        "allows each E2A link to be put in and out of  
                         service."
                DEFVAL {provisioned}
    ::= { aiE2aLinkEntry 2 }

aiLinkStatus    OBJECT-TYPE
                SYNTAX          INTEGER { linkOnLine(1), linkOffLine(2) }
                MAX-ACCESS      read-only
                STATUS          current
                DESCRIPTION
                        "whether there are any communicating E2A RTUs on 
                         this link."
                DEFVAL {linkOffLine}
    ::= { aiE2aLinkEntry 3 }

aiBaudRate      OBJECT-TYPE
                SYNTAX          INTEGER { e2aBaud600(1), e2aBaud1200(2) }
                MAX-ACCESS      read-only
                STATUS          current
                DESCRIPTION
                        "baud rate for this E2A link."
                DEFVAL {e2aBaud1200}
    ::= { aiE2aLinkEntry 4 }

aiProtocol      OBJECT-TYPE
                SYNTAX          INTEGER { protocolE2(1), protocolE2A(2) }
                MAX-ACCESS      read-only
                STATUS          current
                DESCRIPTION
                        "protocol used on this E2A link."
                DEFVAL {protocolE2A}
    ::= { aiE2aLinkEntry 5 }

aiTxMessages    OBJECT-TYPE
                SYNTAX          INTEGER (0..'ffffffff'h)
                MAX-ACCESS      read-only
                STATUS          current
                DESCRIPTION
                        "number of E2A messages transmitted since power up 
                         on this E2A link."
    ::= { aiE2aLinkEntry 6 }

aiTxWords       OBJECT-TYPE
                SYNTAX          INTEGER (0..'ffffffff'h)
                MAX-ACCESS      read-only
                STATUS          current
                DESCRIPTION
                        "number of E2A words transmitted since power up 
                         on this E2A link."
    ::= { aiE2aLinkEntry 7 }

aiTxErrors      OBJECT-TYPE
                SYNTAX          INTEGER (0..'ffffffff'h)
                MAX-ACCESS      read-only
                STATUS          current
                DESCRIPTION
                        "number of E2A transmit errors since power up 
                         on this E2A link."
    ::= { aiE2aLinkEntry 8 }

aiRxMessages    OBJECT-TYPE
                SYNTAX          INTEGER (0..'ffffffff'h)
                MAX-ACCESS      read-only
                STATUS          current
                DESCRIPTION
                        "number of E2A messages received since power up 
                         on this E2A link."
    ::= { aiE2aLinkEntry 9 }

aiRxWords       OBJECT-TYPE
                SYNTAX          INTEGER (0..'ffffffff'h)
                MAX-ACCESS      read-only
                STATUS          current
                DESCRIPTION
                        "number of E2A words received since power up 
                         on this E2A link."
    ::= { aiE2aLinkEntry 10 }

aiRxErrors      OBJECT-TYPE
                SYNTAX          INTEGER (0..'ffffffff'h)
                MAX-ACCESS      read-only
                STATUS          current
                DESCRIPTION
                        "number of E2A receive errors since power up 
                         on this E2A link."
    ::= { aiE2aLinkEntry 11 }

aiRxTimeouts    OBJECT-TYPE
                SYNTAX          INTEGER (0..'ffffffff'h)
                MAX-ACCESS      read-only
                STATUS          current
                DESCRIPTION
                        "number of timeouts when expecting receipt 
                         of E2A messages since power up on this E2A 
                         link."
    ::= { aiE2aLinkEntry 12 }

aiFlushes       OBJECT-TYPE
                SYNTAX          INTEGER (0..'ffffffff'h)
                MAX-ACCESS      read-only
                STATUS          current
                DESCRIPTION
                        "number of times the link has been flushed since 
                         power up."
    ::= { aiE2aLinkEntry 13 }





aiE2aRtuTable   OBJECT-TYPE
                SYNTAX          SEQUENCE OF AIE2aRtuEntry
                MAX-ACCESS      not-accessible
                STATUS          current
                DESCRIPTION
                        "Entries define the E2A RTUs connected to the 
                         AI196IETS card."
    ::= { aiEts 4 }

aiE2aRtuEntry     OBJECT-TYPE
                SYNTAX          AIE2aRtuEntry
                MAX-ACCESS      not-accessible
                STATUS          current
                DESCRIPTION
                        "Information about a particular E2A RTU on the 
                         AI196IETS card."
                INDEX           {aiE2aRtuIndex}
    ::= { aiE2aRtuTable 1 }


AIE2aRtuEntry ::= SEQUENCE {
                        aiE2aRtuIndex INTEGER,
                        aiE2aLink INTEGER,
                        aiRtuAddress INTEGER,
                        aiRtuType INTEGER,
                        aiCommunicationState INTEGER,
                        aiInitialPoll INTEGER,
                        aiEtsConnectionIndex INTEGER,
			aiE2aRequests INTEGER,
			aiE2aResponses INTEGER,
                        aiPollRequests INTEGER,
                        aiPollResponses INTEGER,
                        aiLatchingRequests INTEGER,
                        aiLatchingResponses INTEGER,
                        aiMomentaryRequests INTEGER,
                        aiMomentaryResponses INTEGER,
                        aiTestRequests INTEGER,
			aiTestResponses INTEGER,
			aiUnknownRequests INTEGER,
			aiUnknownResponses INTEGER
                        }

aiE2aRtuIndex   OBJECT-TYPE
                SYNTAX          INTEGER (1..4096)
                MAX-ACCESS      read-only
                STATUS          current
                DESCRIPTION
                        "each of 16 E2A Links can have 256 RTU addresses, 
                         4096 addressable RTUs in total:
                                E2A RTU Indexes 1..256 map to E2A Link 1
                                E2A RTU Indexes 257..512 map to E2A Link 2
                                E2A RTU Indexes 513..768 map to E2A Link 3
                                E2A RTU Indexes 769..1024 map to E2A Link 4
                                E2A RTU Indexes 1025..1280 map to E2A Link 5
                                E2A RTU Indexes 1281..1536 map to E2A Link 6
                                E2A RTU Indexes 1537..1792 map to E2A Link 7
                                E2A RTU Indexes 1793..2048 map to E2A Link 8
                                E2A RTU Indexes 2049..2304 map to E2A Link 9
                                E2A RTU Indexes 2305..2560 map to E2A Link 10
                                E2A RTU Indexes 2561..2816 map to E2A Link 11
                                E2A RTU Indexes 2817..3072 map to E2A Link 12
                                E2A RTU Indexes 3073..3328 map to E2A Link 13
                                E2A RTU Indexes 3329..3584 map to E2A Link 14
                                E2A RTU Indexes 3585..3840 map to E2A Link 15
                                E2A RTU Indexes 3841..4096 map to E2A Link 16"
    ::= { aiE2aRtuEntry 1 }

aiE2aLink       OBJECT-TYPE
                SYNTAX          INTEGER (1..16)
                MAX-ACCESS      read-only
                STATUS          current
                DESCRIPTION
                        "the E2A Link this E2A RTU resides on."
    ::= { aiE2aRtuEntry 2 }

aiRtuAddress    OBJECT-TYPE
                SYNTAX          INTEGER (1..256)
                MAX-ACCESS      read-only
                STATUS          current
                DESCRIPTION
                        "the address of the E2A RTU on the e2aLinkIndex."
    ::= { aiE2aRtuEntry 3 }

aiRtuType       OBJECT-TYPE
                SYNTAX          INTEGER { e2aSacRtu(1), e2aAprRtu(2), e2aDasRtu(3) }
                MAX-ACCESS      read-only
                STATUS          current
                DESCRIPTION
                        "The model type of the E2A RTU."
    ::= { aiE2aRtuEntry 4 }

aiCommunicationState OBJECT-TYPE
                SYNTAX          INTEGER { rtuOffLine(1), rtuOnLine(2) }
                MAX-ACCESS      read-only
                STATUS          current
                DESCRIPTION
                        "whether communication with the RTU is normal or 
                         failed."
                DEFVAL {rtuOffLine}
    ::= { aiE2aRtuEntry 5 }

aiInitialPoll   OBJECT-TYPE
                SYNTAX          INTEGER (0..1)
                MAX-ACCESS      read-only
                STATUS          current
                DESCRIPTION
                        "whether or not this RTU is in initial poll mode.  An 
                         RTU is in initial poll mode when all of its RTU Displays 
                         have not yet been polled.  This object only has meaning 
                         when the AI196IETS card is configured as a remote end 
                         card.  0=normal poll mode, 1=initial poll mode."
                DEFVAL {1}
    ::= { aiE2aRtuEntry 6 }

aiEtsConnectionIndex OBJECT-TYPE
                SYNTAX          INTEGER (0..64)
                MAX-ACCESS      read-only
                STATUS          current
                DESCRIPTION
                        "index into the etsConnectionTable of the connection 
                         associated with this RTU.  A value of 0 indicates that 
                         there is no active connection."
                DEFVAL {0}
   ::= { aiE2aRtuEntry 7 }

aiE2aRequests    OBJECT-TYPE
                SYNTAX          INTEGER (0..'ffffffff'h)
                MAX-ACCESS      read-only
                STATUS          current
                DESCRIPTION
                        "number of E2A requests since power up 
                         for this RTU."
    ::= { aiE2aRtuEntry 8 }

aiE2aResponses   OBJECT-TYPE
                SYNTAX          INTEGER (0..'ffffffff'h)
                MAX-ACCESS      read-only
                STATUS          current
                DESCRIPTION
                        "number of E2A responses since power up 
                         for this RTU."
    ::= { aiE2aRtuEntry 9 }

aiPollRequests  OBJECT-TYPE
                SYNTAX          INTEGER (0..'ffffffff'h)
                MAX-ACCESS      read-only
                STATUS          current
                DESCRIPTION
                        "number of E2A poll requests since power up 
                         for this RTU."
    ::= { aiE2aRtuEntry 10 }

aiPollResponses OBJECT-TYPE
                SYNTAX          INTEGER (0..'ffffffff'h)
                MAX-ACCESS      read-only
                STATUS          current
                DESCRIPTION
                        "number of E2A poll responses since power up 
                         for this RTU."
    ::= { aiE2aRtuEntry 11 }

aiLatchingRequests OBJECT-TYPE
                SYNTAX          INTEGER (0..'ffffffff'h)
                MAX-ACCESS      read-only
                STATUS          current
                DESCRIPTION
                        "number of E2A latching control requests since power up 
                         for this RTU."
    ::= { aiE2aRtuEntry 12 }

aiLatchingResponses OBJECT-TYPE
                SYNTAX          INTEGER (0..'ffffffff'h)
                MAX-ACCESS      read-only
                STATUS          current
                DESCRIPTION
                        "number of E2A latching control responses since power up 
                         for this RTU."
    ::= { aiE2aRtuEntry 13 }

aiMomentaryRequests OBJECT-TYPE
                SYNTAX          INTEGER (0..'ffffffff'h)
                MAX-ACCESS      read-only
                STATUS          current
                DESCRIPTION
                        "number of E2A momentary control requests since power up 
                         for this RTU."
    ::= { aiE2aRtuEntry 14 }

aiMomentaryResponses OBJECT-TYPE
                SYNTAX          INTEGER (0..'ffffffff'h)
                MAX-ACCESS      read-only
                STATUS          current
                DESCRIPTION
                        "number of E2A momentary control responses since power up 
                         for this RTU."
    ::= { aiE2aRtuEntry 15 }

aiTestRequests    OBJECT-TYPE
                SYNTAX          INTEGER (0..'ffffffff'h)
                MAX-ACCESS      read-only
                STATUS          current
                DESCRIPTION
                        "number of E2A test requests since power up 
                         on this RTU."
    ::= { aiE2aRtuEntry 16 }

aiTestResponses   OBJECT-TYPE
                SYNTAX          INTEGER (0..'ffffffff'h)
                MAX-ACCESS      read-only
                STATUS          current
                DESCRIPTION
                        "number of E2A test responses since power up 
                         on this RTU."
    ::= { aiE2aRtuEntry 17 }

aiUnknownRequests OBJECT-TYPE
                SYNTAX          INTEGER (0..'ffffffff'h)
                MAX-ACCESS      read-only
                STATUS          current
                DESCRIPTION
                        "number of unknown E2A requests since power up 
                         on this RTU."
    ::= { aiE2aRtuEntry 18 }

aiUnknownResponses OBJECT-TYPE
                SYNTAX          INTEGER (0..'ffffffff'h)
                MAX-ACCESS      read-only
                STATUS          current
                DESCRIPTION
                        "number of unknown E2A responses since power up 
                         on this RTU."
    ::= { aiE2aRtuEntry 19 }


END
