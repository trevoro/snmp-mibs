ONEFS-TRAP-MIB DEFINITIONS ::= BEGIN

IMPORTS
	NOTIFICATION-TYPE, MODULE-IDENTITY, OBJECT-TYPE,
	Integer32, Unsigned32, Counter32, Counter64, TimeTicks
		FROM SNMPv2-SMI
	TEXTUAL-CONVENTION, PhysAddress, MacAddress, DisplayString
		FROM SNMPv2-TC
	IpAddress
		FROM RFC1155-SMI
	MODULE-COMPLIANCE, OBJECT-GROUP, NOTIFICATION-GROUP
		FROM SNMPv2-CONF
	onefs, TimeTicks64
		FROM ONEFS-MIB;

oneFSTraps 	MODULE-IDENTITY
	LAST-UPDATED "0201172301Z"
	ORGANIZATION "COMPANY_NAME"
	CONTACT-INFO
	       "COMPANY_NAME
		Support phone: SUPPORT_PHONE
		Support E-mail: SUPPORT_EMAIL
	       "
	DESCRIPTION
	       "This is the OneFS trap MIB"
	::= { onefs 251 }
oneFSTrapByPriority	OBJECT IDENTIFIER ::= { oneFSTraps 1 }
oneFSTrapByFacility	OBJECT IDENTIFIER ::= { oneFSTraps 2 }

oneFSTrapCrit	NOTIFICATION-TYPE
	STATUS		current
	DESCRIPTION
		"This notification is triggered everytime an emergency 
		 occurs on an appliance
		"
	::= { oneFSTrapByPriority 1 }

oneFSTrapWarn	NOTIFICATION-TYPE
	STATUS		current
	DESCRIPTION
		"This notification is triggered everytime an alert 
		 occurs on an appliance
		"
	::= { oneFSTrapByPriority 2 }

oneFSTrapInfo	NOTIFICATION-TYPE
	STATUS		current
	DESCRIPTION
		"This notification is triggered everytime a critical event 
		 occurs on an appliance
		"
	::= { oneFSTrapByPriority 3 }

oneFSTrapEmrg  NOTIFICATION-TYPE
    STATUS          current
    DESCRIPTION
        "This notification is triggered everytime an emergency 
        occurs on an appliance
               "
    ::= { oneFSTrapByPriority 4 }

oneFSTrapDefault	NOTIFICATION-TYPE
	STATUS		current
	DESCRIPTION
		"This notification is triggered everytime a critical event 
		 occurs on an appliance
		"
	::= { oneFSTrapByFacility 1 }


oneFSTrapNode	NOTIFICATION-TYPE
	STATUS		current
	DESCRIPTION
		"This notification is triggered everytime a critical event 
		 occurs on an appliance
		"
	::= { oneFSTrapByFacility 2 }


oneFSTrapWindowsNetworking	NOTIFICATION-TYPE
	STATUS		current
	DESCRIPTION
		"This notification is triggered everytime a critical event 
		 occurs on an appliance
		"
	::= { oneFSTrapByFacility 3 }


oneFSTrapProcesses	NOTIFICATION-TYPE
	STATUS		current
	DESCRIPTION
		"This notification is triggered everytime a critical event 
		 occurs on an appliance
		"
	::= { oneFSTrapByFacility 4 }


oneFSTrapPower	NOTIFICATION-TYPE
	STATUS		current
	DESCRIPTION
		"This notification is triggered everytime a critical event 
		 occurs on an appliance
		"
	::= { oneFSTrapByFacility 5 }


oneFSTrapSpace	NOTIFICATION-TYPE
	STATUS		current
	DESCRIPTION
		"This notification is triggered everytime a critical event 
		 occurs on an appliance
		"
	::= { oneFSTrapByFacility 6 }


oneFSTrapRestripe	NOTIFICATION-TYPE
	STATUS		current
	DESCRIPTION
		"This notification is triggered everytime a critical event 
		 occurs on an appliance
		"
	::= { oneFSTrapByFacility 7 }


oneFSTrapGeneral	NOTIFICATION-TYPE
	STATUS		current
	DESCRIPTION
		"This notification is triggered everytime a critical event 
		 occurs on an appliance
		"
	::= { oneFSTrapByFacility 8 }


oneFSTrapNVRAM	NOTIFICATION-TYPE
	STATUS		current
	DESCRIPTION
		"This notification is triggered everytime a critical event 
		 occurs on an appliance
		"
	::= { oneFSTrapByFacility 9 }


oneFSTrapTemp  NOTIFICATION-TYPE
	STATUS		current
	DESCRIPTION
		"This notification is triggered everytime a critical event 
		 occurs on an appliance
		"
	::= { oneFSTrapByFacility 10 }


oneFSTrapFan	NOTIFICATION-TYPE
	STATUS		current
	DESCRIPTION
		"This notification is triggered everytime a critical event 
		 occurs on an appliance
		"
	::= { oneFSTrapByFacility 11 }


oneFSTrapFilesystem	NOTIFICATION-TYPE
	STATUS		current
	DESCRIPTION
		"This notification is triggered everytime a critical event 
		 occurs on an appliance
		"
	::= { oneFSTrapByFacility 12 }


oneFSTrapDisk	NOTIFICATION-TYPE
	STATUS		current
	DESCRIPTION
		"This notification is triggered everytime a critical event 
		 occurs on an appliance
		"
	::= { oneFSTrapByFacility 13 }


oneFSTrapCPU	NOTIFICATION-TYPE
	STATUS		current
	DESCRIPTION
		"This notification is triggered everytime a critical event 
		 occurs on an appliance
		"
	::= { oneFSTrapByFacility 14 }

oneFSTrapTest	NOTIFICATION-TYPE
	STATUS		current
	DESCRIPTION
		"This notification is triggered everytime a critical event 
		 occurs on an appliance
		"
	::= { oneFSTrapByFacility 15 }

oneFSTrapLicensing	NOTIFICATION-TYPE
	STATUS		current
	DESCRIPTION
		"This notification is triggered everytime a licensing event 
		 occurs on an appliance
		"
	::= { oneFSTrapByFacility 16 }

oneFSTrapSnapshots	NOTIFICATION-TYPE
	STATUS		current
	DESCRIPTION
		"This notification is triggered everytime a snapshots event 
		 occurs on an appliance
		"
	::= { oneFSTrapByFacility 17 }

oneFSTrapSmartQuotas      NOTIFICATION-TYPE
        STATUS          current
        DESCRIPTION
                "This notification is triggered everytime a SmartQuotas event
                 occurs on an appliance
                "
        ::= { oneFSTrapByFacility 18 }

END
