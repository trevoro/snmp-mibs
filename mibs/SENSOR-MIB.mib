SENSOR-MIB DEFINITIONS ::= BEGIN

	IMPORTS
		MODULE-IDENTITY,OBJECT-TYPE,NOTIFICATION-TYPE,Integer32
			FROM SNMPv2-SMI
		TEXTUAL-CONVENTION,TimeStamp,TruthValue,DisplayString
			FROM SNMPv2-TC
		MODULE-COMPLIANCE,OBJECT-GROUP
			FROM SNMPv2-CONF
		blueCoatMgmt
			 FROM BLUECOAT-MIB;

	deviceSensorMIB MODULE-IDENTITY
		LAST-UPDATED "0211060300Z"
		ORGANIZATION "Blue Coat Systems, Inc."
		CONTACT-INFO
		"support@bluecoat.com"
		DESCRIPTION
			"The deviceSensorMIB is used to monitor
			the values of sensors"
		::= { blueCoatMgmt 1 }

deviceSensorMIBObjects
		OBJECT IDENTIFIER ::= { deviceSensorMIB 1 }

deviceSensorMIBNotifications
		OBJECT IDENTIFIER ::= { deviceSensorMIB 2 }

deviceSensorMIBNotificationsPrefix
		OBJECT IDENTIFIER ::= { deviceSensorMIBNotifications 0 }

-- textual conventions

SensorUnits ::= TEXTUAL-CONVENTION
	STATUS		 current
	DESCRIPTION
		"Sensor measurement unit types. Valid values are:
		other		: a measure other than those listed below.
		truthvalue	: value takes { true(1), false(2) }.
		specialEnum : value takes user defined enumerated values.
		volts		: electrical potential.
		celsius 	: temperature.
		rpm 		: revolutions per minute.
		"
	SYNTAX INTEGER {
		other(1),
		truthvalue(2),
		specialEnum(3),
		volts(4),
		celsius(5),
		rpm(6)
	}

SensorCode ::= TEXTUAL-CONVENTION
	STATUS		 current
	DESCRIPTION
		"Interpretation of the current sensor value."
	SYNTAX INTEGER {
		ok(1),
		unknown(2),
		not-installed(3),
		voltage-low-warning(4),
		voltage-low-critical(5),
		no-power(6),
		voltage-high-warning(7),
		voltage-high-critical(8),
		voltage-high-severe(9),
		temperature-high-warning(10),
		temperature-high-critical(11),
		temperature-high-severe(12),
		fan-slow-warning(13),
		fan-slow-critical(14),
		fan-stopped(15)
	}

ExpBase10 ::= TEXTUAL-CONVENTION
	STATUS		 current
	DESCRIPTION
		"Exponent base 10 for the current sensor value.
		 For example '-1' means value*(1/10).
		"
	SYNTAX INTEGER (-24..24)

SensorValue ::= TEXTUAL-CONVENTION
	STATUS		 current
	DESCRIPTION
		"For sensors that measure volts
		and celsius,
		this item is a fixed point number.

		For sensors that measure rpm, this item
		can take only nonnegative values.

		For sensors of type truthvalue, this item
		can take only two values: true(1), false(2).

		For sensors of type specialEnum, this item
		can take any value."
	SYNTAX INTEGER (-1000000000..1000000000)

SensorStatus ::= TEXTUAL-CONVENTION
	STATUS		 current
	DESCRIPTION
		"Indicates the operational status of the sensor.

		ok(1) means the agent can read the sensor
		value.

		unavailable(2) means that the agent presently
		can not report the sensor value.

		nonoperational(3) means that the sensor is broken."
	SYNTAX INTEGER {
		ok(1),
		unavailable(2),
		nonoperational(3)
	}

--
-- MIB variables
--

deviceSensorValues
	OBJECT IDENTIFIER ::= { deviceSensorMIBObjects 1 }


--
-- deviceSensorValueTable
--

deviceSensorValueTable OBJECT-TYPE
	SYNTAX		  SEQUENCE OF DeviceSensorValueEntry
	MAX-ACCESS	  not-accessible
	STATUS		  current
	DESCRIPTION
		"Table of sensors."
	::= { deviceSensorValues 1 }

deviceSensorValueEntry OBJECT-TYPE
	SYNTAX		  DeviceSensorValueEntry
	MAX-ACCESS	  not-accessible
	STATUS		  current
	DESCRIPTION
		"An deviceSensorValueTable entry describes the
		present reading of a sensor, the measurement units
		and sensor operational status."
	INDEX		  { deviceSensorIndex }
	::= { deviceSensorValueTable 1 }

DeviceSensorValueEntry ::= SEQUENCE {
	deviceSensorIndex		INTEGER,
	deviceSensorTrapEnabled	TruthValue,
	deviceSensorUnits		SensorUnits,
	deviceSensorScale		ExpBase10,
	deviceSensorValue		SensorValue,
	deviceSensorCode 		SensorCode,
	deviceSensorStatus		SensorStatus,
	deviceSensorTimeStamp	TimeStamp,
	deviceSensorName 		DisplayString
	}

deviceSensorIndex	OBJECT-TYPE
	SYNTAX		INTEGER (1..2147483647)
	MAX-ACCESS	not-accessible
	STATUS		current
	DESCRIPTION
			"An arbitrary value which uniquely identifies the sensor"
	::= { deviceSensorValueEntry 1 }

deviceSensorTrapEnabled OBJECT-TYPE
	SYNTAX		  TruthValue
	MAX-ACCESS	  read-write
	STATUS		  current
	DESCRIPTION
		"This variable controls generation of
		deviceSensorTrap for this sensor.

		When this variable is true(1), generation of
		deviceSensorTrap is enabled.  When this
		variable is false(2), generation of
		deviceSensorTrap is disabled.

		The default start-up value is true(1)."
	::= { deviceSensorValueEntry 2 }

deviceSensorUnits OBJECT-TYPE
	SYNTAX		  SensorUnits
	MAX-ACCESS	  read-only
	STATUS		  current
	DESCRIPTION
		"This variable indicates the type of data
		reported by the deviceSensorValue.

		This variable is set by the agent at start-up
		and the value does not change during operation."
	::= { deviceSensorValueEntry 3 }

deviceSensorScale  OBJECT-TYPE
	SYNTAX		  ExpBase10
	MAX-ACCESS	  read-only
	STATUS		  current
	DESCRIPTION
		"Power of 10 to apply to the value
		reported by the deviceSensorValue.

		This variable is set by the agent at start-up
		and the value does not change during operation."
	::= { deviceSensorValueEntry 4 }

deviceSensorValue OBJECT-TYPE
	SYNTAX		  SensorValue
	MAX-ACCESS	  read-only
	STATUS		  current
	DESCRIPTION
		"This variable reports the most recent measurement seen
		by the sensor.

		To correctly display or interpret this variable's value,
		you must also know deviceSensorUnits.
		"
	::= { deviceSensorValueEntry 5 }

deviceSensorCode OBJECT-TYPE
	SYNTAX		  SensorCode
	MAX-ACCESS	  read-only
	STATUS		  current
	DESCRIPTION
		"This variable reports how to interpret deviceSensorValue
		by the sensor."

	::= { deviceSensorValueEntry 6 }

deviceSensorStatus OBJECT-TYPE
	SYNTAX		  SensorStatus
	MAX-ACCESS	  read-only
	STATUS		  current
	DESCRIPTION
		"This variable indicates the present operational status
		of the sensor."
	::= { deviceSensorValueEntry 7 }

deviceSensorTimeStamp OBJECT-TYPE
	SYNTAX		  TimeStamp
	MAX-ACCESS	  read-only
	STATUS		  current
	DESCRIPTION
		"This variable indicates the age of the value reported by
		deviceSensorValue."
	::= { deviceSensorValueEntry 8 }

deviceSensorName OBJECT-TYPE
	SYNTAX		DisplayString
	MAX-ACCESS	read-only
	STATUS		current
	DESCRIPTION
			"The textual name of the sensor."
	::= { deviceSensorValueEntry 9  }
--
-- notifications
-- "enterprise".0 for v1 v2 compatibility
--

deviceSensorTrap NOTIFICATION-TYPE
	OBJECTS { deviceSensorName, deviceSensorValue, deviceSensorCode }
	STATUS current
	DESCRIPTION
		"The sensor value warrants a notification."
	::= { deviceSensorMIBNotificationsPrefix 1 }


END
