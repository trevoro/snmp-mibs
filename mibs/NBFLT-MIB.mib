NBFLT-MIB DEFINITIONS ::= BEGIN

IMPORTS
ngen
  FROM NT-Reference-MIB
OBJECT-TYPE
  FROM RFC-1212
TRAP-TYPE
  FROM RFC-1215
  Counter FROM RFC1155-SMI
  DisplayString FROM SNMPv2-TC;

-- Not used because of SMI v1
-- nbFltModule MODULE-IDENTITY
--    LAST-UPDATED "9807081200Z"
--    ORGANIZATION "Nortel, Northern Telecom"
--    CONTACT-INFO "Toronto Multimedia Applications Centre"
--    DESCRIPTION  "This MIB contains definitions for the MAS Fault Manager"

nGenBase		OBJECT IDENTIFIER ::= {ngen 1}
nbFltMngmt		OBJECT IDENTIFIER ::= {nGenBase 5}
nbFltSNMPAgent          OBJECT IDENTIFIER ::= {nbFltMngmt 1}

--
-- The following variables define the internal state of MAS SNMP agent
--
nbFltSNMPAgentStatus	OBJECT IDENTIFIER ::= {nbFltSNMPAgent 1}

nbFltTrapOnAlarm OBJECT-TYPE
    SYNTAX            INTEGER {off(0), on(1)}
    ACCESS	          read-write
    STATUS	          mandatory
    DESCRIPTION       "Allows turning on or off forwarding of MAS alarms as 
traps.
                      If this variable has the 'on' value, each alarm will 
be propagated
                      as a trap. In case of the 'off' value it will not be."
    ::= {nbFltSNMPAgentStatus 1}

nbFltAgentRunningState OBJECT-TYPE
    SYNTAX            INTEGER {notRegistered(0), registered(1)}
    ACCESS            read-only
    STATUS            mandatory
    DESCRIPTION       "Defines the current state of the interaction between 
the SNMP
                      Agent and the MAS Fault Management system.
                      If the MAS SNMP Agent is unable to register with the 
MAS
                      Fault Mngmt system after startup, it will report a 
'notRegistered' value.
                      When registered, will report a 'registered' value."
    ::= {nbFltSNMPAgentStatus 2}

nbFltAlarmTrapFormat OBJECT IDENTIFIER ::= {nbFltSNMPAgent 2}

nbFltAlarmSymposiumTrapFormat OBJECT-TYPE
    SYNTAX            INTEGER {off(0), on(1)}
    ACCESS            read-write
    STATUS            mandatory
    DESCRIPTION	      "Turns on or off generating traps in MAS format."
    ::= {nbFltAlarmTrapFormat 1}

nbFltAlarmCybeleTrapFormat OBJECT-TYPE
    SYNTAX            INTEGER {off(0), on(1)}
    ACCESS            read-write
    STATUS            mandatory
    DESCRIPTION	      "Turns on or off generating traps in Cybele format."
    ::= {nbFltAlarmTrapFormat 2}

--
-- The following values define the variables used in MAS SNMP traps
--
nbFltTrapObjects 		OBJECT IDENTIFIER ::= {nbFltMngmt 2}

nbFltAlarmTrapObjects	OBJECT IDENTIFIER ::= {nbFltTrapObjects 1}

nbFltAlarmSequence OBJECT-TYPE
    SYNTAX            Counter
    ACCESS            not-accessible
    STATUS            mandatory
    DESCRIPTION       "This object defines the alarm sequence number"
    ::= {nbFltAlarmTrapObjects 1}

nbFltAlarmTimeStamp OBJECT-TYPE
    SYNTAX            DisplayString(SIZE(0..16))
    ACCESS            not-accessible
    STATUS            mandatory
    DESCRIPTION       "This object defines the time when alarm was raised"
    ::= {nbFltAlarmTrapObjects 2}

nbFltAlarmEventCode OBJECT-TYPE
    SYNTAX            INTEGER
    ACCESS            not-accessible
    STATUS            mandatory
    DESCRIPTION       "This object defines the MAS event code for the 
generated alarm."
    ::= {nbFltAlarmTrapObjects 3}

nbFltAlarmEventType OBJECT-TYPE
    SYNTAX            INTEGER {unknown(0),
	                           set(1),
							   clear(2),
							   message(4)}
    ACCESS            not-accessible
    STATUS            mandatory
    DESCRIPTION       "This object defines the type of the event."
    ::= {nbFltAlarmTrapObjects 4}

nbFltAlarmEventSeverity OBJECT-TYPE
    SYNTAX            INTEGER {indeterminate(0),
                               critical(1),
                               major(2),
                               minor(3)}
    ACCESS            not-accessible
    STATUS            mandatory
    DESCRIPTION       "This object defines the severity of the reported 
alarm."
    ::= {nbFltAlarmTrapObjects 5}

nbFltAlarmTenantID OBJECT-TYPE
    SYNTAX            INTEGER
    ACCESS            not-accessible
    STATUS            mandatory
    DESCRIPTION       "This object defines the tenant ID"
    ::= {nbFltAlarmTrapObjects 6}

nbFltAlarmCustomerID OBJECT-TYPE
    SYNTAX            INTEGER
    ACCESS            not-accessible
    STATUS            mandatory
    DESCRIPTION       "This object defines the customer ID"
    ::= {nbFltAlarmTrapObjects 7}

nbFltAlarmOriginator OBJECT-TYPE
    SYNTAX            DisplayString(SIZE(0..32))
    ACCESS            not-accessible
    STATUS            mandatory
    DESCRIPTION       "This object describes the subsystem which raised the 
alarm."
    ::= {nbFltAlarmTrapObjects 8}

nbFltAlarmDescription OBJECT-TYPE
    SYNTAX            DisplayString(SIZE(0..256))
    ACCESS            not-accessible
    STATUS            mandatory
    DESCRIPTION       "This object describes what happened in the system, 
which caused
                      the alarm to occur."
    ::= {nbFltAlarmTrapObjects 9}

--
-- Traps definition
--
nbFltTraps   	OBJECT IDENTIFIER ::= {nbFltMngmt 3}

nbSymposiumAlarmTrap TRAP-TYPE
    ENTERPRISE nbFltTraps
    VARIABLES {nbFltAlarmSequence,
               nbFltAlarmTimeStamp,
               nbFltAlarmEventCode,
               nbFltAlarmEventType,
               nbFltAlarmEventSeverity,
               nbFltAlarmTenantID,
               nbFltAlarmCustomerID,
               nbFltAlarmOriginator,
               nbFltAlarmDescription}
    DESCRIPTION "MAS Trap conveying information about raised alarm."
    ::= 1

END
