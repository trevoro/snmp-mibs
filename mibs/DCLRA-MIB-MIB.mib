DCLRA-MIB-MIB DEFINITIONS ::= BEGIN

IMPORTS
	enterprises, Counter, Gauge
		FROM RFC1155-SMI
	Counter64 FROM SNMPv2-SMI
	InternationalDisplayString
		FROM HOST-RESOURCES-MIB
	OBJECT-TYPE
		FROM RFC-1212
	DisplayString
		FROM RFC1213-MIB
	Dmi-Date,
	dmiEventDateTime,dmiCompId,dmiEventSeverity,
	dmiEventStateKey,dmiEventAssociatedGroup,
	dmiEventSystem,dmiEventSubSystem
		FROM DMTF-DMI-MIB;

DmiCounter			::= Counter
DmiCounter64		::= Counter64
DmiGauge			::= Gauge
DmiInteger			::= INTEGER
DmiOctetstring		::= OCTET STRING
DmiDisplaystring	::= DisplayString
DmiCompId	::= INTEGER
DmiGroupId	::= INTEGER

dmtf                	OBJECT IDENTIFIER ::= { enterprises 412 }
dmtfStdMifs         	OBJECT IDENTIFIER ::= { dmtf 2 }
dmtfDynOids         	OBJECT IDENTIFIER ::= { dmtf 3 }

SdMTFComponentID ::= SEQUENCE { 
	manufacturerAtt1	DmiDisplaystring,
	productAtt2	DmiDisplaystring,
	versionAtt3	DmiDisplaystring,
	serialNumberAtt4	DmiDisplaystring,
	installationAtt5	Dmi-Date,
	verifyAtt6	DmiInteger
}
dmtfServiceLayerMIF	OBJECT IDENTIFIER ::= { dmtfStdMifs 1 }

dMTFComponentIDTable OBJECT-TYPE
	SYNTAX		SEQUENCE OF SdMTFComponentID
	ACCESS		not-accessible
	STATUS		mandatory
	DESCRIPTION	"This group defines the attributes common to all components.
 This group is required."
	::= { dmtfServiceLayerMIF 1 }

dMTFComponentIDEntry OBJECT-TYPE
	SYNTAX		SdMTFComponentID
	ACCESS		not-accessible
	STATUS		mandatory
	DESCRIPTION	"This group defines the attributes common to all components.
 This group is required."
	INDEX		{ DmiCompId,DmiGroupId }
	::= { dMTFComponentIDTable 1 }


manufacturerAtt1 OBJECT-TYPE
	SYNTAX		DmiDisplaystring
	ACCESS		read-only
	STATUS		mandatory
	DESCRIPTION	"Manufacturer of this system."
	REFERENCE "'DMTF|ComponentID|001' 1"
	::= { dMTFComponentIDEntry 1 }

productAtt2 OBJECT-TYPE
	SYNTAX		DmiDisplaystring
	ACCESS		read-only
	STATUS		mandatory
	DESCRIPTION	"Product name for this system."
	REFERENCE "'DMTF|ComponentID|001' 2"
	::= { dMTFComponentIDEntry 2 }

versionAtt3 OBJECT-TYPE
	SYNTAX		DmiDisplaystring
	ACCESS		read-only
	STATUS		mandatory
	DESCRIPTION	"Version number of this system."
	REFERENCE "'DMTF|ComponentID|001' 3"
	::= { dMTFComponentIDEntry 3 }

serialNumberAtt4 OBJECT-TYPE
	SYNTAX		DmiDisplaystring
	ACCESS		read-only
	STATUS		mandatory
	DESCRIPTION	"Serial number for this system."
	REFERENCE "'DMTF|ComponentID|001' 4"
	::= { dMTFComponentIDEntry 4 }

installationAtt5 OBJECT-TYPE
	SYNTAX		Dmi-Date
	ACCESS		read-only
	STATUS		mandatory
	DESCRIPTION	"The time and date when this component was installed."
	REFERENCE "'DMTF|ComponentID|001' 5"
	::= { dMTFComponentIDEntry 5 }

verifyAtt6 OBJECT-TYPE
	SYNTAX		INTEGER { 
		anErrorOccurredCheckStatusCode(0),
		thisComponentDoesNotExist(1),
		verificationIsNotSupported(2),
		reserved(3),
		thisComponentExistsButTheFunctionalityIsUntested(4),
		thisComponentExistsButTheFunctionalityIsUnknown(5),
		thisComponentExistsAndIsNotFunctioningCorrectly(6),
		thisComponentExistsAndIsFunctioningCorrectly(7)
	}
	ACCESS		read-only
	STATUS		mandatory
	DESCRIPTION	"A code that provides a level of verification that the component
is still installed and working."
	REFERENCE "'DMTF|ComponentID|001' 6"
	::= { dMTFComponentIDEntry 6 }

SdellLRAActionTable ::= SEQUENCE { 
	dellLRAActionTableState INTEGER,
	actionNameAtt1	DmiInteger,
	actionResponseAtt2	DmiDisplaystring,
	actionExecuteAtt3	DmiDisplaystring,
	actionSourceAtt4	DmiDisplaystring,
	uDPInformationAtt5	DmiDisplaystring
}

dell        OBJECT IDENTIFIER ::= { enterprises 674 } 
server2        OBJECT IDENTIFIER ::= { dell 10891 } 

dellLRAActionTableTable OBJECT-TYPE
	SYNTAX		SEQUENCE OF SdellLRAActionTable
	ACCESS		not-accessible
	STATUS		mandatory
	DESCRIPTION	"This table describes the actions to be performed whenever
a particular indication is generated."
	::= { server2 313 }

dellLRAActionTableEntry OBJECT-TYPE
	SYNTAX		SdellLRAActionTable
	ACCESS		not-accessible
	STATUS		mandatory
	DESCRIPTION	"This table describes the actions to be performed whenever
a particular indication is generated."
	INDEX		{ DmiCompId,DmiGroupId, actionNameAtt1 }
	::= { dellLRAActionTableTable 1 }


dellLRAActionTableState OBJECT-TYPE
	SYNTAX		INTEGER { 
		active(1),
		notInService(2),
		notReady(3),
		createAndGo(4),
		createAndWait(5),
		destroy(6)
	}
	ACCESS		read-write
	STATUS		mandatory
	REFERENCE "'Dell|LRA ActionTable|001' 0"
	::= { dellLRAActionTableEntry 0 }

actionNameAtt1 OBJECT-TYPE
	SYNTAX		INTEGER { 
		unknown(0),
		adaptecHostAdapterFailed(3),
		adaptecLogicalUnitFailed(7),
		aPCSystemOnLowUtilityPower(13),
		aPCSystemOnLowBatteryPower(14),
		temperatureSensorDetectedAFailure(160),
		fanSensorDetectedAFailure(168),
		voltageSensorDetectedAFailure(172),
		temperatureSensorWarningDetected(200),
		voltageSensorWarningDetected(202),
		fanSensorWarningDetected(204),
		currentSensorDetectedAFailure(206),
		currentSensorWarningDetected(208),
		powerSupplyLostRedundancyDetected(210),
		powerSupplyDegradedRedundancyDetected(212),
		powerSupplyDetectedAFailure(214),
		chassisIntrusionDetected(220),
		lostConnectionToDiskPod(225)
	}
	ACCESS		read-only
	STATUS		mandatory
	DESCRIPTION	"This specifies the Dell trap which generates the action"
	REFERENCE "'Dell|LRA ActionTable|001' 1"
	::= { dellLRAActionTableEntry 1 }

actionResponseAtt2 OBJECT-TYPE
	SYNTAX		DmiDisplaystring
	ACCESS		read-write
	STATUS		mandatory
	DESCRIPTION	"This is a secure bit field which specifies which actions
are to be performed.Bitfield is as follows:   0x001 = Beep  0x002 = Console
Alert  0x004 = Broadcast  0x008 = Shutdown OS  0x010 = Reset  0x020 = Power
Cycle  0x040 = Power Off  0x080 = Log Reset/PowerCycle/PowerOff  0x100 =
Execute Application (uses actionExecute string)"
	REFERENCE "'Dell|LRA ActionTable|001' 2"
	::= { dellLRAActionTableEntry 2 }

actionExecuteAtt3 OBJECT-TYPE
	SYNTAX		DmiDisplaystring
	ACCESS		read-write
	STATUS		mandatory
	DESCRIPTION	"This takes an argument of the application to execute & arguments
if the Execute Application bit is set.  Specialized argument fields exist:
 %A - Address of MIF generating alert: cid,gid,(keys) %N - Name of alert
(Temperature sensor detected a failure) %L - Location of alert (Harrier 1
<Backplane Top>) %T - Trap number of alert (260) %S - Severity of alert"
	REFERENCE "'Dell|LRA ActionTable|001' 3"
	::= { dellLRAActionTableEntry 3 }

actionSourceAtt4 OBJECT-TYPE
	SYNTAX		DmiDisplaystring
	ACCESS		read-only
	STATUS		mandatory
	DESCRIPTION	"This contains a combined key for mapping non-dell indications
to a LRA format. Format is: MIFNAME;GID;KEY;AID;# MIFNAME - Text name of
MIF GID     - Group ID KEY     - Row index AID     - Attribute ID #     
 - Trap number to map to"
	REFERENCE "'Dell|LRA ActionTable|001' 4"
	::= { dellLRAActionTableEntry 4 }

uDPInformationAtt5 OBJECT-TYPE
	SYNTAX		DmiDisplaystring
	ACCESS		read-write
	STATUS		mandatory
	DESCRIPTION	"Account Information for LRA Execute User applications."
	REFERENCE "'Dell|LRA ActionTable|001' 5"
	::= { dellLRAActionTableEntry 5 }

SdellLRACapabilities ::= SEQUENCE { 
	lRACapabilitiesAtt1	DmiInteger
}

dellLRACapabilitiesTable OBJECT-TYPE
	SYNTAX		SEQUENCE OF SdellLRACapabilities
	ACCESS		not-accessible
	STATUS		mandatory
	DESCRIPTION	"This class's attribute describes which LRA capabilities can
be performed on this machine."
	::= { server2 314 }

dellLRACapabilitiesEntry OBJECT-TYPE
	SYNTAX		SdellLRACapabilities
	ACCESS		not-accessible
	STATUS		mandatory
	DESCRIPTION	"This class's attribute describes which LRA capabilities can
be performed on this machine."
	INDEX		{ DmiCompId,DmiGroupId }
	::= { dellLRACapabilitiesTable 1 }


lRACapabilitiesAtt1 OBJECT-TYPE
	SYNTAX		DmiInteger
	ACCESS		read-only
	STATUS		mandatory
	DESCRIPTION	"This value describes what LRA actions may be taken on this
system."
	REFERENCE "'Dell|LRA Capabilities|001' 1"
	::= { dellLRACapabilitiesEntry 1 }

SdellLRABeepAction ::= SEQUENCE { 
	beepClearAtt1	DmiDisplaystring,
	beepDelayAtt2	DmiDisplaystring
}

dellLRABeepActionTable OBJECT-TYPE
	SYNTAX		SEQUENCE OF SdellLRABeepAction
	ACCESS		not-accessible
	STATUS		mandatory
	DESCRIPTION	"This group describes information for the beep response whenever
a particular indication is generated."
	::= { server2 315 }

dellLRABeepActionEntry OBJECT-TYPE
	SYNTAX		SdellLRABeepAction
	ACCESS		not-accessible
	STATUS		mandatory
	DESCRIPTION	"This group describes information for the beep response whenever
a particular indication is generated."
	INDEX		{ DmiCompId,DmiGroupId }
	::= { dellLRABeepActionTable 1 }


beepClearAtt1 OBJECT-TYPE
	SYNTAX		DmiDisplaystring
	ACCESS		read-write
	STATUS		mandatory
	DESCRIPTION	"Setting this field to a non-zero number will cancel the current
beeping event"
	REFERENCE "'Dell|LRA Beep Action|001' 1"
	::= { dellLRABeepActionEntry 1 }

beepDelayAtt2 OBJECT-TYPE
	SYNTAX		DmiDisplaystring
	ACCESS		read-write
	STATUS		mandatory
	DESCRIPTION	"Sleep time (in seconds) between repeating beeps"
	REFERENCE "'Dell|LRA Beep Action|001' 2"
	::= { dellLRABeepActionEntry 2 }

SdELLSystemsManagementSoftware ::= SEQUENCE { 
	productAtt1	DmiDisplaystring,
	versionAtt2	DmiDisplaystring,
	buildNumberAtt3	DmiInteger,
	descriptionAtt4	DmiDisplaystring,
	supportedProtocolsAtt5	DmiInteger,
	preferredProtocolAtt6	DmiInteger,
	dMIRPCTypesAtt7	DmiDisplaystring
}

dELLSystemsManagementSoftwareTable OBJECT-TYPE
	SYNTAX		SEQUENCE OF SdELLSystemsManagementSoftware
	ACCESS		not-accessible
	STATUS		mandatory
	DESCRIPTION	"This group defines the attributes of the management software
which instruments this component."
	::= { server2 400 }

dELLSystemsManagementSoftwareEntry OBJECT-TYPE
	SYNTAX		SdELLSystemsManagementSoftware
	ACCESS		not-accessible
	STATUS		mandatory
	DESCRIPTION	"This group defines the attributes of the management software
which instruments this component."
	INDEX		{ DmiCompId,DmiGroupId }
	::= { dELLSystemsManagementSoftwareTable 1 }


productAtt1 OBJECT-TYPE
	SYNTAX		DmiDisplaystring
	ACCESS		read-only
	STATUS		mandatory
	DESCRIPTION	"The name of the Systems Management Software product that
instruments this component."
	REFERENCE "'DELL|Systems Management Software|001' 1"
	::= { dELLSystemsManagementSoftwareEntry 1 }

versionAtt2 OBJECT-TYPE
	SYNTAX		DmiDisplaystring
	ACCESS		read-only
	STATUS		mandatory
	DESCRIPTION	"The version for the Systems Management Software."
	REFERENCE "'DELL|Systems Management Software|001' 2"
	::= { dELLSystemsManagementSoftwareEntry 2 }

buildNumberAtt3 OBJECT-TYPE
	SYNTAX		DmiInteger
	ACCESS		read-only
	STATUS		mandatory
	DESCRIPTION	"The build number of this Systems Management Software product."
	REFERENCE "'DELL|Systems Management Software|001' 3"
	::= { dELLSystemsManagementSoftwareEntry 3 }

descriptionAtt4 OBJECT-TYPE
	SYNTAX		DmiDisplaystring
	ACCESS		read-only
	STATUS		mandatory
	DESCRIPTION	"A description of this Systems Management Software product."
	REFERENCE "'DELL|Systems Management Software|001' 4"
	::= { dELLSystemsManagementSoftwareEntry 4 }

supportedProtocolsAtt5 OBJECT-TYPE
	SYNTAX		DmiInteger
	ACCESS		read-only
	STATUS		mandatory
	DESCRIPTION	"This is a bit map field which is used to list protocols which
can be used to access the systems management information.  This is a bit
map where a value of 1 indicates that the protocol is supported.  Values
are based on the Protocol-Type enum. Mappers will be listed in this list,
but not as preferred protocols."
	REFERENCE "'DELL|Systems Management Software|001' 5"
	::= { dELLSystemsManagementSoftwareEntry 5 }

preferredProtocolAtt6 OBJECT-TYPE
	SYNTAX		INTEGER { 
		sNMP(1),
		dMIRPC(2),
		cIMOM(4)
	}
	ACCESS		read-only
	STATUS		mandatory
	DESCRIPTION	"This is a field which is used to indicate which protocol
is the preferred method for gathering management information.  This is value
is set by the instrumentation based on performance and features of protocols
available."
	REFERENCE "'DELL|Systems Management Software|001' 6"
	::= { dELLSystemsManagementSoftwareEntry 6 }

dMIRPCTypesAtt7 OBJECT-TYPE
	SYNTAX		DmiDisplaystring
	ACCESS		read-only
	STATUS		mandatory
	DESCRIPTION	"This field describes the RPC type, if any, for instance DCE:ncac
-ip-tcp or ONC:tcpip. A semi-colon may seperate multiple supports, such as
DCE:ncasn-ip-tcp;ONC:tcpip. This field should be empty if DMI RPC is not
supported."
	REFERENCE "'DELL|Systems Management Software|001' 7"
	::= { dELLSystemsManagementSoftwareEntry 7 }

END

-- ######################################################
-- ######################################################
-- ######################################################
-- #### Start of MIB E:\HIP151\server\mibs\clean-oldbase.mib
-- 
-- ****************************************************************
-- Modified by CleanMib for Build (BLD-431) on 10/25/99 15:15:41
-- ****************************************************************

-- HIP Version = w000  
--  
-- MIB generated by miftomib version 1.0a
