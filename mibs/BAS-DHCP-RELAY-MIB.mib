BAS-DHCP-RELAY-MIB DEFINITIONS ::= BEGIN

IMPORTS
    MODULE-IDENTITY, OBJECT-TYPE, Counter32, Integer32,
    IpAddress                                                   FROM SNMPv2-SMI
    RowStatus                                                   FROM SNMPv2-TC
    BasChassisId, BasSlotId, BasInterfaceId, BasLogicalPortId,   
    BasSubnetClass, basDhcpRelay                                FROM BAS-MIB;

basDhcpRelayMIB MODULE-IDENTITY
    LAST-UPDATED "9902031415Z"
    ORGANIZATION "Broadband Access Systems, Inc."
    CONTACT-INFO
        " Tech Support
          Broadband Access Systems, Inc.
          201 Forest Street
          Marlborough, MA 01752
          USA

          508-485-8200
          support@basystems.com"
    DESCRIPTION
        "The MIB module defines the configuration MIB objects
         for Broadband Access Systems, Inc. DHCP Relay functionality
         extensions."
    ::= { basDhcpRelay 1 }


-- the BAS DHCP Relay table

-- The BAS DHCP Relay table contains BAS proprietaryinformation on
-- the entity's Traffic Generation.

basDhcpRelayTable OBJECT-TYPE
    SYNTAX      SEQUENCE OF BasDhcpRelayEntry
    MAX-ACCESS  not-accessible
    STATUS      current
    DESCRIPTION
        "A list of DHCP Relay entries."
    ::= { basDhcpRelayMIB 1 }

basDhcpRelayEntry OBJECT-TYPE
    SYNTAX      BasDhcpRelayEntry
    MAX-ACCESS  not-accessible
    STATUS      current
    DESCRIPTION
        "An entry containing management information applicable
        to a particular DHCP Relay."
    INDEX {basDhcpRelayChassis,
	   basDhcpRelaySlot,
	   basDhcpRelayIf,
	   basDhcpRelayLPort
           }
    ::= { basDhcpRelayTable 1 }

BasDhcpRelayEntry ::=
    SEQUENCE {
    basDhcpRelayChassis	    BasChassisId,   
    basDhcpRelaySlot	    BasSlotId,      
    basDhcpRelayIf	    BasInterfaceId, 
    basDhcpRelayLPort       BasLogicalPortId,
    basDhcpRelayEnable      INTEGER,
    basDhcpRelayDiscover    Counter32,
    basDhcpRelayOffer       Counter32,
    basDhcpRelayRequest     Counter32,
    basDhcpRelayDecline     Counter32,
    basDhcpRelayNak         Counter32,
    basDhcpRelayInform      Counter32,
    basDhcpRelayAck         Counter32,
    basDhcpRelayRelease     Counter32,
    basDhcpRelayHelper      INTEGER,
    basDhcpRelayAlwaysBroadcast INTEGER,
    basDhcpRelayDuplicateResponse INTEGER,
    basDhcpRelayBasEnable INTEGER,
    basDhcpRelayBogusAgentDrops         Counter32,
    basDhcpRelayBogusGiaddrDrops        Counter32,
    basDhcpRelayServerPacketErrors      Counter32,
    basDhcpRelayClientPacketErrors      Counter32,
    basDhcpRelayAddAgentOptions         INTEGER,
    basDhcpRelayDropAgentMismatch       INTEGER,
    basDhcpRelayCorruptAgentOptions     Counter32,
    basDhcpRelayMissingAgentOption      Counter32,
    basDhcpRelayBadCircuitId            Counter32,
    basDhcpRelayMissingCircuitId        Counter32,
    basDhcpRelayMaxAgentOptionPacketLength Integer32,
    basDhcpRelayAgentRelayMode          INTEGER
    }
    
basDhcpRelayChassis OBJECT-TYPE
    SYNTAX		BasChassisId
    MAX-ACCESS	not-accessible
    STATUS		current
    DESCRIPTION
        "The BAS Chassis ID of the Card."
    ::= { basDhcpRelayEntry 1 }

basDhcpRelaySlot OBJECT-TYPE
    SYNTAX		BasSlotId
    MAX-ACCESS	not-accessible
    STATUS		current
    DESCRIPTION
        "The BAS Slot ID of the Card."
    ::= { basDhcpRelayEntry 2 }

basDhcpRelayIf OBJECT-TYPE
    SYNTAX		BasInterfaceId
    MAX-ACCESS	not-accessible
    STATUS		current
    DESCRIPTION
        "The BAS interface ID of the Card."
    ::= { basDhcpRelayEntry 3 }

basDhcpRelayLPort OBJECT-TYPE
    SYNTAX		BasLogicalPortId
    MAX-ACCESS	not-accessible
    STATUS		current
    DESCRIPTION
        "The BAS logical port ID of the Card."
    ::= { basDhcpRelayEntry 4 }

basDhcpRelayEnable OBJECT-TYPE
    SYNTAX      INTEGER {
                enable(1),
                disable(2)
                }
    MAX-ACCESS  read-write
    STATUS      current
    DESCRIPTION
        "Enable and disable DHCP relay on the card."
    DEFVAL {1}
    ::= { basDhcpRelayEntry 5 }

basDhcpRelayDiscover OBJECT-TYPE
    SYNTAX      Counter32
    MAX-ACCESS  read-only
    STATUS      current
    DESCRIPTION
        "Number of Discover messages."
    ::= { basDhcpRelayEntry 6 }

basDhcpRelayOffer OBJECT-TYPE
    SYNTAX      Counter32
    MAX-ACCESS  read-only
    STATUS      current
    DESCRIPTION
        "Number of Offer messages."
    ::= { basDhcpRelayEntry 7 }

basDhcpRelayRequest OBJECT-TYPE
    SYNTAX      Counter32
    MAX-ACCESS  read-only
    STATUS      current
    DESCRIPTION
        "Number of Request messages."
    ::= { basDhcpRelayEntry 8 }

basDhcpRelayDecline OBJECT-TYPE
    SYNTAX      Counter32
    MAX-ACCESS  read-only
    STATUS      current
    DESCRIPTION
        "Number of Decline messages."
    ::= { basDhcpRelayEntry 9 }

basDhcpRelayNak OBJECT-TYPE
    SYNTAX      Counter32
    MAX-ACCESS  read-only
    STATUS      current
    DESCRIPTION
        "Number of Nak messages."
    ::= { basDhcpRelayEntry 10 }

basDhcpRelayInform OBJECT-TYPE
    SYNTAX      Counter32
    MAX-ACCESS  read-only
    STATUS      current
    DESCRIPTION
        "Number of Inform messages."
    ::= { basDhcpRelayEntry 11 }

basDhcpRelayAck OBJECT-TYPE
    SYNTAX      Counter32
    MAX-ACCESS  read-only
    STATUS      current
    DESCRIPTION
        "Number of Ack messages."
    ::= { basDhcpRelayEntry 12 }

basDhcpRelayRelease OBJECT-TYPE
    SYNTAX      Counter32
    MAX-ACCESS  read-only
    STATUS      current
    DESCRIPTION
        "Number of Release messages."
    ::= { basDhcpRelayEntry 13 }

basDhcpRelayHelper OBJECT-TYPE
    SYNTAX      INTEGER {
                   enable(1),
                   disable(2)
                }
    MAX-ACCESS  read-write
    STATUS      current
    DESCRIPTION
        "Enable gateway selection based on primary/secondary interface address."
    ::= { basDhcpRelayEntry 14 }

basDhcpRelayAlwaysBroadcast OBJECT-TYPE
    SYNTAX      INTEGER {
                   enable(1),
                   disable(2)
                }
    MAX-ACCESS  read-write
    STATUS      current
    DESCRIPTION
        "Enable always broadcasting response to the client."
    ::= { basDhcpRelayEntry 15 }

basDhcpRelayDuplicateResponse OBJECT-TYPE
    SYNTAX      INTEGER {
                   enable(1),
                   disable(2)
                }
    MAX-ACCESS  read-write
    STATUS      current
    DESCRIPTION
        "Enable sending response to client in unicast and broadcast mode."
    ::= { basDhcpRelayEntry 16 }

basDhcpRelayBasEnable OBJECT-TYPE
    SYNTAX      INTEGER {
                   enable(1),
                   disable(2)
                }
    MAX-ACCESS  read-write
    STATUS      current
    DESCRIPTION
        "Enable BAS proprietory solution."
    ::= { basDhcpRelayEntry 17 }

basDhcpRelayBogusAgentDrops         OBJECT-TYPE
    SYNTAX      Counter32
    MAX-ACCESS  read-only
    STATUS      current
    DESCRIPTION
        "Packets dropped because agent option
        field was specified and we're not relaying
        packets that already have an agent option
        specified."
    ::= { basDhcpRelayEntry 18 }

basDhcpRelayBogusGiaddrDrops        OBJECT-TYPE
    SYNTAX      Counter32
    MAX-ACCESS  read-only
    STATUS      current
    DESCRIPTION
        "Packets sent to us to relay back to a
        client, but with a bogus giaddr."
    ::= { basDhcpRelayEntry 19 }

basDhcpRelayServerPacketErrors      OBJECT-TYPE
    SYNTAX      Counter32
    MAX-ACCESS  read-only
    STATUS      current
    DESCRIPTION
        "Errors sending packets to servers."
    ::= { basDhcpRelayEntry 20 }

basDhcpRelayClientPacketErrors      OBJECT-TYPE
    SYNTAX      Counter32
    MAX-ACCESS  read-only
    STATUS      current
    DESCRIPTION
        "Errors sending packets to clients."
    ::= { basDhcpRelayEntry 21 }

basDhcpRelayAddAgentOptions         OBJECT-TYPE
    SYNTAX      INTEGER {
                enable(1),
                disable(2)
                }
    MAX-ACCESS  read-write
    STATUS      current
    DESCRIPTION
        "If nonzero, add relay agent options."
    ::= { basDhcpRelayEntry 22 }

basDhcpRelayDropAgentMismatch       OBJECT-TYPE
    SYNTAX      INTEGER {
                enable(1),
                disable(2)
                }
    MAX-ACCESS  read-write
    STATUS      current
    DESCRIPTION
        "If nonzero, drop server replies that
        don't contain a Relay Agent Information
        option whose Agent ID suboption matches
        our giaddr."
    ::= { basDhcpRelayEntry 23 }

basDhcpRelayCorruptAgentOptions     OBJECT-TYPE
    SYNTAX      Counter32
    MAX-ACCESS  read-only
    STATUS      current
    DESCRIPTION
        "Number of packets dropped because
        relay agent information option was bad."
    ::= { basDhcpRelayEntry 24 }

basDhcpRelayMissingAgentOption      OBJECT-TYPE
    SYNTAX      Counter32
    MAX-ACCESS  read-only
    STATUS      current
    DESCRIPTION
        "Number of packets dropped because no
        RAI option matching our ID was found."
    ::= { basDhcpRelayEntry 25 }

basDhcpRelayBadCircuitId            OBJECT-TYPE
    SYNTAX      Counter32
    MAX-ACCESS  read-only
    STATUS      current
    DESCRIPTION
        "Circuit ID option in matching RAI option
        did not match any known circuit ID"
    ::= { basDhcpRelayEntry 26 }

basDhcpRelayMissingCircuitId        OBJECT-TYPE
    SYNTAX      Counter32
    MAX-ACCESS  read-only
    STATUS      current
    DESCRIPTION
        "Circuit ID option in matching RAI option
        was missing."
    ::= { basDhcpRelayEntry 27 }

basDhcpRelayMaxAgentOptionPacketLength  OBJECT-TYPE
    SYNTAX      Integer32 (576..1518)
    MAX-ACCESS  read-write
    STATUS      current
    DESCRIPTION
        "If nonzero, drop server replies that
        don't contain a Relay Agent Information
        option whose Agent ID suboption matches
        our giaddr."
    ::= { basDhcpRelayEntry 28 }

basDhcpRelayAgentRelayMode OBJECT-TYPE
    SYNTAX      INTEGER {
                forwardAndAppend(1),
                forwardAndReplace(2),	
                forwardUntouched(3),	
                discard(4)
                }
    MAX-ACCESS  read-write
    STATUS      current
    DESCRIPTION
        "What to do about packets we're asked to relay that
        already have a relay option: 
        forward_and_append,	/* Forward and append our own relay option. */
        forward_and_replace,	/* Forward, but replace theirs with ours. */
        forward_untouched,	/* Forward without changes. */
        discard } agent_relay_mode = forward_and_replace"
    DEFVAL {2}
    ::= { basDhcpRelayEntry 29 }

-- the BAS DHCP Relay Server table

-- The BAS DHCP Relay Server Server table contains BAS proprietaryinformation on
-- the entity's DHCP Relay Server.

basDhcpRelayServerTable OBJECT-TYPE
    SYNTAX      SEQUENCE OF BasDhcpRelayServerEntry
    MAX-ACCESS  not-accessible
    STATUS      current
    DESCRIPTION
        "A list of DHCP Relay Server entries."
    ::= { basDhcpRelayMIB 2 }

basDhcpRelayServerEntry OBJECT-TYPE
    SYNTAX      BasDhcpRelayServerEntry
    MAX-ACCESS  not-accessible
    STATUS      current
    DESCRIPTION
        "An entry containing management information applicable
        to a particular DHCP Relay Server."
    INDEX {basDhcpRelayServerChassis,
	   basDhcpRelayServerSlot,
	   basDhcpRelayServerIf,
	   basDhcpRelayServerLPort,
           basDhcpRelayServerAddress,
           basDhcpRelayServerType
           }
    ::= { basDhcpRelayServerTable 1 }

BasDhcpRelayServerEntry ::=
    SEQUENCE {
    basDhcpRelayServerChassis	  BasChassisId,   
    basDhcpRelayServerSlot	  BasSlotId,      
    basDhcpRelayServerIf	  BasInterfaceId, 
    basDhcpRelayServerLPort       BasLogicalPortId,
    basDhcpRelayServerAddress     IpAddress,
    basDhcpRelayServerType        BasSubnetClass,
    basDhcpRelayServerStatus      RowStatus
    }
    
    
basDhcpRelayServerChassis OBJECT-TYPE
    SYNTAX		BasChassisId
    MAX-ACCESS	not-accessible
    STATUS		current
    DESCRIPTION
        "The BAS Chassis ID of the Card."
    ::= { basDhcpRelayServerEntry 1 }

basDhcpRelayServerSlot OBJECT-TYPE
    SYNTAX		BasSlotId
    MAX-ACCESS	not-accessible
    STATUS		current
    DESCRIPTION
        "The BAS Slot ID of the Card."
    ::= { basDhcpRelayServerEntry 2 }

basDhcpRelayServerIf OBJECT-TYPE
    SYNTAX		BasInterfaceId
    MAX-ACCESS	not-accessible
    STATUS		current
    DESCRIPTION
        "The BAS interface ID of the Card."
    ::= { basDhcpRelayServerEntry 3 }

basDhcpRelayServerLPort OBJECT-TYPE
    SYNTAX		BasLogicalPortId
    MAX-ACCESS	not-accessible
    STATUS		current
    DESCRIPTION
        "The BAS logical port ID of the Card."
    ::= { basDhcpRelayServerEntry 4 }

basDhcpRelayServerAddress OBJECT-TYPE
    SYNTAX      IpAddress 
    MAX-ACCESS  not-accessible
    STATUS      current
    DESCRIPTION
        "Address of DHCP Relay Server on this forwarder."
    DEFVAL {2}
    ::= { basDhcpRelayServerEntry 5 }

basDhcpRelayServerType OBJECT-TYPE
    SYNTAX      BasSubnetClass
    MAX-ACCESS  not-accessible
    STATUS      current
    DESCRIPTION
        "Type of DHCP server. When picking a DHCP server, \
        choice is made depending on type."
    DEFVAL {1}
    ::= { basDhcpRelayServerEntry 6 }

basDhcpRelayServerStatus OBJECT-TYPE
    SYNTAX      RowStatus
    MAX-ACCESS  read-create
    STATUS      current
    DESCRIPTION
        "Adding and deleting the Server."
    DEFVAL {1}
    ::= { basDhcpRelayServerEntry 7 }

END
