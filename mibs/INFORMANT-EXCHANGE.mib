INFORMANT-EXCHANGE DEFINITIONS ::= BEGIN

IMPORTS
    MODULE-IDENTITY, OBJECT-TYPE, OBJECT-IDENTITY, Gauge32
        FROM SNMPv2-SMI
    InstanceName, informant
        FROM WTCS;

exchange MODULE-IDENTITY
    LAST-UPDATED "200505171900Z"
    ORGANIZATION "Informant Systems, Inc."
    CONTACT-INFO
            "        Garth Williams
                Tel: +1 780 433 7973
             E-mail: garth.williams@wtcs.org"
    DESCRIPTION
            "The MIB module for SNMP Informant Exchange
             performance counter entries."
    REVISION      "200505171900Z"
    DESCRIPTION
            "Added additional counters that are in
             Exchange 2003 and the Intelligent Message
             Filter extension. Also added additional
             Exchange counters that were missed in the
             previous release."
    REVISION      "200402290627Z"
    DESCRIPTION
            "Changed the syntax of the datapoints from
             integer to gauge."
    REVISION      "200402070849Z"
    DESCRIPTION
            "The initial revision of this MIB module."
    ::= { informant 5 }

activeSync OBJECT IDENTIFIER
    ::= { exchange 1 }

asClientItemAddsPerSec OBJECT-TYPE
    SYNTAX     Gauge32
    MAX-ACCESS read-only
    STATUS     current
    DESCRIPTION
	    "The number of client item adds (within the
	    sync command) processed per second by Exchange
	    ActiveSync."
    ::= { activeSync 1 }

asClientItemChangesPerSec OBJECT-TYPE
    SYNTAX     Gauge32
    MAX-ACCESS read-only
    STATUS     current
    DESCRIPTION
	    "The number of client item changes (within the
	    sync command) processed per second by Exchange
	    ActiveSync."
    ::= { activeSync 2 }

asClientItemDeletesPerSec OBJECT-TYPE
    SYNTAX     Gauge32
    MAX-ACCESS read-only
    STATUS     current
    DESCRIPTION
	    "The number of client item deletes (within the
	    sync command) processed per second by Exchange
	    ActiveSync."
    ::= { activeSync 3 }

asClientItemFetchesPerSec OBJECT-TYPE
    SYNTAX     Gauge32
    MAX-ACCESS read-only
    STATUS     current
    DESCRIPTION
	    "The number of client item fetches (within the
	    sync command) processed per second by Exchange
	    ActiveSync."
    ::= { activeSync 4 }

asClientSyncItemsPerSec OBJECT-TYPE
    SYNTAX     Gauge32
    MAX-ACCESS read-only
    STATUS     current
    DESCRIPTION
	    "The number of client item adds, changes,
	    deletes, and fetches (within the sync command)
	    processed per second by Exchange ActiveSync."
    ::= { activeSync 5 }

asCreateCollectionCommandsPerSec OBJECT-TYPE
    SYNTAX     Gauge32
    MAX-ACCESS read-only
    STATUS     current
    DESCRIPTION
	    "The number of CreateCollection commands
	    processed per second by Exchange ActiveSync.
	    The CreateCollection command is called when a
	    user creates a folder from the client."
    ::= { activeSync 6 }

asCurrentActiveDirectoryRequests OBJECT-TYPE
    SYNTAX     Gauge32
    MAX-ACCESS read-only
    STATUS     current
    DESCRIPTION
	    "Current outstanding requests to Active
	    Directory."
    ::= { activeSync 7 }

asCurrentUsers OBJECT-TYPE
    SYNTAX     Gauge32
    MAX-ACCESS read-only
    STATUS     current
    DESCRIPTION
	    "The number of users currently accessing
	    Exchange ActiveSync."
    ::= { activeSync 8 }

asDeleteCollectionCommandsPerSec OBJECT-TYPE
    SYNTAX     Gauge32
    MAX-ACCESS read-only
    STATUS     current
    DESCRIPTION
	    "The number of DeleteCollection commands
	    processed per second by Exchange ActiveSync.
	    The DeleteCollection command is called when a
	    user deletes a folder from the client."
    ::= { activeSync 9 }

asMailboxServerIORequestsPerSec OBJECT-TYPE
    SYNTAX     Gauge32
    MAX-ACCESS read-only
    STATUS     current
    DESCRIPTION
	    "The number of input/output requests sent per
	    second to the Exchange mailbox server(s) from
	    Exchange ActiveSync."
    ::= { activeSync 10 }

asMailboxServerItemAddsPerSec OBJECT-TYPE
    SYNTAX     Gauge32
    MAX-ACCESS read-only
    STATUS     current
    DESCRIPTION
	    "The number of Exchange mailbox server item
	    adds (within the sync command) processed per
	    second by Exchange ActiveSync."
    ::= { activeSync 11 }

asMailboxServerItemChangesPerSec OBJECT-TYPE
    SYNTAX     Gauge32
    MAX-ACCESS read-only
    STATUS     current
    DESCRIPTION
	    "The number of Exchange mailbox server item
	    changes (within the sync command) processed per
	    second by Exchange ActiveSync."
    ::= { activeSync 12 }

asMailboxServerItemDeletesPerSec OBJECT-TYPE
    SYNTAX     Gauge32
    MAX-ACCESS read-only
    STATUS     current
    DESCRIPTION
	    "The number of Exchange mailbox server item
	    deletes (within the sync command) processed per
	    second by Exchange ActiveSync."
    ::= { activeSync 13 }

asMailboxServerItemSoftDelPerSec OBJECT-TYPE
    SYNTAX     Gauge32
    MAX-ACCESS read-only
    STATUS     current
    DESCRIPTION
	    "The number of Exchange mailbox server item
	    soft deletes processed per second by Exchange
	    ActiveSync.  Soft deletes occur when items move
	    out of filter range."
    ::= { activeSync 14 }

asMailboxServerSyncItemsPerSec OBJECT-TYPE
    SYNTAX     Gauge32
    MAX-ACCESS read-only
    STATUS     current
    DESCRIPTION
	    "The number of Exchange mailbox server adds,
	    changes, deletes, and soft deletes (within the
	    sync command) sent to the client per second by
	    Exchange ActiveSync."
    ::= { activeSync 15 }

asFolderCreateCommandsPerSec OBJECT-TYPE
    SYNTAX     Gauge32
    MAX-ACCESS read-only
    STATUS     current
    DESCRIPTION
	    "The number of FolderCreate commands processed
	    per second by Exchange ActiveSync. The
	    FolderCreate command is called when a user
	    creates a folder from the client."
    ::= { activeSync 16 }

asFolderDeleteCommandsPerSec OBJECT-TYPE
    SYNTAX     Gauge32
    MAX-ACCESS read-only
    STATUS     current
    DESCRIPTION
	    "The number of FolderDelete commands processed
	    per second by Exchange ActiveSync. The
	    FolderDelete command is called when a user
	    deletes a folder from the client."
    ::= { activeSync 17 }

asFolderSyncCommandsPerSec OBJECT-TYPE
    SYNTAX     Gauge32
    MAX-ACCESS read-only
    STATUS     current
    DESCRIPTION
	    "The number of FolderSync commands processed
	    per second by Exchange ActiveSync. The
	    FolderSync command is called when a user
	    synchronizes their folder hierarchy."
    ::= { activeSync 18 }

asFolderUpdateCommandsPerSec OBJECT-TYPE
    SYNTAX     Gauge32
    MAX-ACCESS read-only
    STATUS     current
    DESCRIPTION
	    "The number of FolderUpdate commands processed
	    per second by Exchange ActiveSync. The
	    FolderUpdate command is called when a user
	    moves/renames a folder from the client."
    ::= { activeSync 19 }

asGetAttachmentCommandsPerSec OBJECT-TYPE
    SYNTAX     Gauge32
    MAX-ACCESS read-only
    STATUS     current
    DESCRIPTION
	    "The number of GetAttachment commands processed
	    per second by Exchange ActiveSync. The
	    GetAttachment command is called when a user
	    retrieves a mail attachment from the client."
    ::= { activeSync 20 }

asGetHierarchyCommandsPerSec OBJECT-TYPE
    SYNTAX     Gauge32
    MAX-ACCESS read-only
    STATUS     current
    DESCRIPTION
	    "The number of GetHierarchy commands processed
	    per second by Exchange ActiveSync. The
	    GetHierarchy command is called when a user
	    fetches their folder hierarchy."
    ::= { activeSync 21 }

asGetItemEstimateCommandsPerSec OBJECT-TYPE
    SYNTAX     Gauge32
    MAX-ACCESS read-only
    STATUS     current
    DESCRIPTION
	    "The number of GetItemEstimate commands
	    processed per second by Exchange ActiveSync.
	    The GetItemEstimate command checks for the
	    number of items that need to be synchronized."
    ::= { activeSync 22 }

asMeetingResponseCommandsPerSec OBJECT-TYPE
    SYNTAX     Gauge32
    MAX-ACCESS read-only
    STATUS     current
    DESCRIPTION
	    "The number of MeetingResponse commands
	    processed per second by Exchange ActiveSync.
	    The MeetingResponse command is called when a
	    user responds to a meeting request from the
	    client."
    ::= { activeSync 23 }

asMoveCollectionCommandsPerSec OBJECT-TYPE
    SYNTAX     Gauge32
    MAX-ACCESS read-only
    STATUS     current
    DESCRIPTION
	    "The number of MoveCollection commands
	    processed per second by Exchange ActiveSync.
	    The MoveCollection command is called when a
	    user moves a folder from the client."
    ::= { activeSync 24 }

asMoveItemsCommandsPerSec OBJECT-TYPE
    SYNTAX     Gauge32
    MAX-ACCESS read-only
    STATUS     current
    DESCRIPTION
	    "The number of MoveItems commands processed per
	    second by Exchange ActiveSync. The MoveItem
	    command is called when a user moves an item
	    between folders from the client."
    ::= { activeSync 25 }

asNotifyCommandsPerSec OBJECT-TYPE
    SYNTAX     Gauge32
    MAX-ACCESS read-only
    STATUS     current
    DESCRIPTION
	    "The number of Notify commands processed per
	    second by Exchange ActiveSync. The Notify
	    command is called by the client to provision
	    itself to receive notifications."
    ::= { activeSync 26 }

asOutstandingMailboxSrvrConnRqst OBJECT-TYPE
    SYNTAX     Gauge32
    MAX-ACCESS read-only
    STATUS     current
    DESCRIPTION
	    "The number of pending connection requests from
	    Exchange ActiveSync to the Exchange mailbox
	    server(s)."
    ::= { activeSync 27 }

asOutstandingMailboxServerIORqst OBJECT-TYPE
    SYNTAX     Gauge32
    MAX-ACCESS read-only
    STATUS     current
    DESCRIPTION
	    "The number of pending input/output requests
	    from Exchange ActiveSync to the Exchange
	    mailbox server(s)."
    ::= { activeSync 28 }

asSendMailCommandsPerSec OBJECT-TYPE
    SYNTAX     Gauge32
    MAX-ACCESS read-only
    STATUS     current
    DESCRIPTION
	    "The number of SendMail commands processed per
	    second by Exchange ActiveSync. The SendMail
	    command is called when a user sends mail from
	    the client."
    ::= { activeSync 29 }

asSmartForwardCommandsPerSec OBJECT-TYPE
    SYNTAX     Gauge32
    MAX-ACCESS read-only
    STATUS     current
    DESCRIPTION
	    "The number of SmartForward commands processed
	    per second by Exchange ActiveSync. The
	    SmartForward command is called when a user
	    forwards an existing mail item from the
	    client."
    ::= { activeSync 30 }

asSmartReplyCommandsPerSec OBJECT-TYPE
    SYNTAX     Gauge32
    MAX-ACCESS read-only
    STATUS     current
    DESCRIPTION
	    "The number of SmartReply commands processed
	    per second by Exchange ActiveSync. The
	    SmartReply command is called when a user
	    replies to mail from the client."
    ::= { activeSync 31 }

asSyncCommandsPerSec OBJECT-TYPE
    SYNTAX     Gauge32
    MAX-ACCESS read-only
    STATUS     current
    DESCRIPTION
	    "The number of Sync commands processed per
	    second by Exchange ActiveSync."
    ::= { activeSync 32 }

asTotalClientItemAdds OBJECT-TYPE
    SYNTAX     Gauge32
    MAX-ACCESS read-only
    STATUS     current
    DESCRIPTION
	    "The total number of client item adds (within
	    the sync command) processed by Exchange
	    ActiveSync."
    ::= { activeSync 33 }

asTotalClientItemChanges OBJECT-TYPE
    SYNTAX     Gauge32
    MAX-ACCESS read-only
    STATUS     current
    DESCRIPTION
	    "The total number of client item changes
	    (within the sync command) processed by Exchange
	    ActiveSync."
    ::= { activeSync 34 }

asTotalClientItemDeletes OBJECT-TYPE
    SYNTAX     Gauge32
    MAX-ACCESS read-only
    STATUS     current
    DESCRIPTION
	    "The total number of client item deletes
	    (within the sync command) processed by Exchange
	    ActiveSync."
    ::= { activeSync 35 }

asTotalClientItemFetches OBJECT-TYPE
    SYNTAX     Gauge32
    MAX-ACCESS read-only
    STATUS     current
    DESCRIPTION
	    "The total number of client item fetches
	    (within the sync command) processed by Exchange
	    ActiveSync."
    ::= { activeSync 36 }

asTotalClientSyncItems OBJECT-TYPE
    SYNTAX     Gauge32
    MAX-ACCESS read-only
    STATUS     current
    DESCRIPTION
	    "The total number of client item adds, changes,
	    and deletes (within the sync command) sent from
	    the client."
    ::= { activeSync 37 }

asTotalCreateCollectionCommands OBJECT-TYPE
    SYNTAX     Gauge32
    MAX-ACCESS read-only
    STATUS     current
    DESCRIPTION
	    "The total number of CreateCollection commands
	    processed by Exchange ActiveSync. The
	    CreateCollection command is called when a user
	    creates a folder from the client."
    ::= { activeSync 38 }

asTotalDeleteCollectionCommands OBJECT-TYPE
    SYNTAX     Gauge32
    MAX-ACCESS read-only
    STATUS     current
    DESCRIPTION
	    "The total number of DeleteCollection commands
	    processed by Exchange ActiveSync. The
	    DeleteCollection command is called when a user
	    deletes a folder from the client."
    ::= { activeSync 39 }

asTotalMailboxServerItemAdds OBJECT-TYPE
    SYNTAX     Gauge32
    MAX-ACCESS read-only
    STATUS     current
    DESCRIPTION
	    "The total number of Exchange mailbox server
	    item adds (within the sync command) processed
	    by Exchange ActiveSync."
    ::= { activeSync 40 }

asTotalMailboxServerItemChanges OBJECT-TYPE
    SYNTAX     Gauge32
    MAX-ACCESS read-only
    STATUS     current
    DESCRIPTION
	    "The total number of Exchange mailbox server
	    item changes (within the sync command)
	    processed by Exchange ActiveSync."
    ::= { activeSync 41 }

asTotalMailboxServerItemDeletes OBJECT-TYPE
    SYNTAX     Gauge32
    MAX-ACCESS read-only
    STATUS     current
    DESCRIPTION
	    "The total number of Exchange mailbox server
	    item deletes (within the sync command)
	    processed by Exchange ActiveSync."
    ::= { activeSync 42 }

asTotalMailboxServerItemSoftDel OBJECT-TYPE
    SYNTAX     Gauge32
    MAX-ACCESS read-only
    STATUS     current
    DESCRIPTION
	    "The total number of Exchange mailbox server
	    item soft deletes processed by Exchange
	    ActiveSync.  Soft deletes occur when items move
	    out of filter range."
    ::= { activeSync 43 }

asTotalMailboxServerSyncItems OBJECT-TYPE
    SYNTAX     Gauge32
    MAX-ACCESS read-only
    STATUS     current
    DESCRIPTION
	    "The total number of Exchange mailbox server
	    adds, changes, and deletes (within the sync
	    command) sent to the client."
    ::= { activeSync 44 }

asTotalFolderCreateCommands OBJECT-TYPE
    SYNTAX     Gauge32
    MAX-ACCESS read-only
    STATUS     current
    DESCRIPTION
	    "The total number of FolderCreate commands
	    processed by Exchange ActiveSync. The
	    FolderCreate command is called when a user
	    creates a folder from the client."
    ::= { activeSync 45 }

asTotalFolderDeleteCommands OBJECT-TYPE
    SYNTAX     Gauge32
    MAX-ACCESS read-only
    STATUS     current
    DESCRIPTION
	    "The total number of FolderDelete commands
	    processed by Exchange ActiveSync. The
	    FolderDelete command is called when a user
	    deletes a folder from the client."
    ::= { activeSync 46 }

asTotalFolderSyncCommands OBJECT-TYPE
    SYNTAX     Gauge32
    MAX-ACCESS read-only
    STATUS     current
    DESCRIPTION
	    "The total number of FolderSync commands
	    processed by Exchange ActiveSync. The
	    FolderSync command is called when a user
	    synchronizes their folder hierarchy."
    ::= { activeSync 47 }

asTotalFolderUpdateCommands OBJECT-TYPE
    SYNTAX     Gauge32
    MAX-ACCESS read-only
    STATUS     current
    DESCRIPTION
	    "The total number of FolderUpdate commands
	    processed by Exchange ActiveSync. The
	    FolderUpdate command is called when a user
	    moves/renames a folder from the client."
    ::= { activeSync 48 }

asTotalGetAttachmentCommands OBJECT-TYPE
    SYNTAX     Gauge32
    MAX-ACCESS read-only
    STATUS     current
    DESCRIPTION
	    "The total number of GetAttachment commands
	    processed by Exchange ActiveSync. The
	    GetAttachment command is called when a user
	    retrieves a mail attachment from the client."
    ::= { activeSync 49 }

asTotalGetHierarchyCommands OBJECT-TYPE
    SYNTAX     Gauge32
    MAX-ACCESS read-only
    STATUS     current
    DESCRIPTION
	    "The total number of GetHierarchy commands
	    processed by Exchange ActiveSync. The
	    GetHierarchy command is called when a user
	    fetches their folder hierarchy."
    ::= { activeSync 50 }

asTotalGetItemEstimateCommands OBJECT-TYPE
    SYNTAX     Gauge32
    MAX-ACCESS read-only
    STATUS     current
    DESCRIPTION
	    "The total number of GetItemEstimate commands
	    processed by Exchange ActiveSync. The
	    GetItemEstimate command checks for the number
	    of items that need to be synchronized."
    ::= { activeSync 51 }

asTotalMeetingResponseCommands OBJECT-TYPE
    SYNTAX     Gauge32
    MAX-ACCESS read-only
    STATUS     current
    DESCRIPTION
	    "The total number of MeetingResponse commands
	    processed by Exchange ActiveSync. The
	    MeetingResponse command is called when a user
	    responds to a meeting request from the client."
    ::= { activeSync 52 }

asTotalMoveCollectionCommands OBJECT-TYPE
    SYNTAX     Gauge32
    MAX-ACCESS read-only
    STATUS     current
    DESCRIPTION
	    "The total number of MoveCollection commands
	    processed by Exchange ActiveSync. The
	    MoveCollection command is called when a user
	    moves a folder from the client."
    ::= { activeSync 53 }

asTotalMoveItemsCommands OBJECT-TYPE
    SYNTAX     Gauge32
    MAX-ACCESS read-only
    STATUS     current
    DESCRIPTION
	    "The total number of MoveItems commands
	    processed by Exchange ActiveSync. The MoveItem
	    command is called when a user moves an item
	    between folders from the client."
    ::= { activeSync 54 }

asTotalNotifyCommands OBJECT-TYPE
    SYNTAX     Gauge32
    MAX-ACCESS read-only
    STATUS     current
    DESCRIPTION
	    "The total number of Notify commands processed
	    by Exchange ActiveSync. The Notify command is
	    called by the client to provision itself to
	    receive notifications."
    ::= { activeSync 55 }

asTotalSendMailCommands OBJECT-TYPE
    SYNTAX     Gauge32
    MAX-ACCESS read-only
    STATUS     current
    DESCRIPTION
	    "The total number of SendMail commands
	    processed by Exchange ActiveSync. The SendMail
	    command is called when a user sends mail from
	    the client."
    ::= { activeSync 56 }

asTotalSmartForwardCommands OBJECT-TYPE
    SYNTAX     Gauge32
    MAX-ACCESS read-only
    STATUS     current
    DESCRIPTION
	    "The total number of SmartForward commands
	    processed by Exchange ActiveSync. The
	    SmartForward command is called when a user
	    forwards an existing mail item from the
	    client."
    ::= { activeSync 57 }

asTotalSmartReplyCommands OBJECT-TYPE
    SYNTAX     Gauge32
    MAX-ACCESS read-only
    STATUS     current
    DESCRIPTION
	    "The total number of SmartReply commands
	    processed by Exchange ActiveSync. The
	    SmartReply command is called when a user
	    replies to mail from the client."
    ::= { activeSync 58 }

asTotalSyncCommands OBJECT-TYPE
    SYNTAX     Gauge32
    MAX-ACCESS read-only
    STATUS     current
    DESCRIPTION
	    "The total number of Sync commands processed by
	    Exchange ActiveSync."
    ::= { activeSync 59 }

asTotalUnrecognizedRequests OBJECT-TYPE
    SYNTAX     Gauge32
    MAX-ACCESS read-only
    STATUS     current
    DESCRIPTION
	    "The total number of unrecognized requests
	    received by Exchange ActiveSync."
    ::= { activeSync 60 }

asTotalUsers OBJECT-TYPE
    SYNTAX     Gauge32
    MAX-ACCESS read-only
    STATUS     current
    DESCRIPTION
	    "Total number of users who have accessed
	    Exchange ActiveSync."
    ::= { activeSync 61 }

activeSyncNotifyOmaPush OBJECT-IDENTITY
    STATUS     current
    DESCRIPTION
	    "Displays performance statistics for Exchange
	    ActiveSync Notifications"
    ::= { exchange 2 }

asnopCatNotifyBifurcatedTotal OBJECT-TYPE
    SYNTAX     Gauge32
    MAX-ACCESS read-only
    STATUS     current
    DESCRIPTION
	    "Number of notifications bifurcated by mobile
	    categorizer due to multiple devices"
    ::= { activeSyncNotifyOmaPush 1 }

asnopCatNotifyDiscardedTotal OBJECT-TYPE
    SYNTAX     Gauge32
    MAX-ACCESS read-only
    STATUS     current
    DESCRIPTION
	    "Number of notifications discarded by mobile
	    categorizer due to errors"
    ::= { activeSyncNotifyOmaPush 2 }

asnopCatNotifyExpiredTotal OBJECT-TYPE
    SYNTAX     Gauge32
    MAX-ACCESS read-only
    STATUS     current
    DESCRIPTION
	    "Number of notifications discarded by mobile
	    categorizer due to expiry"
    ::= { activeSyncNotifyOmaPush 3 }

asnopCatNotifyIgnoredTotal OBJECT-TYPE
    SYNTAX     Gauge32
    MAX-ACCESS read-only
    STATUS     current
    DESCRIPTION
	    "Number of notifications ignored by mobile
	    categorizer due to batching"
    ::= { activeSyncNotifyOmaPush 4 }

asnopCatNotifyProcessedTotal OBJECT-TYPE
    SYNTAX     Gauge32
    MAX-ACCESS read-only
    STATUS     current
    DESCRIPTION
	    "Number of notifications processed by mobile
	    categorizer"
    ::= { activeSyncNotifyOmaPush 5 }

asnopCatNotifyProcessedPerSec OBJECT-TYPE
    SYNTAX     Gauge32
    MAX-ACCESS read-only
    STATUS     current
    DESCRIPTION
	    "Number of notifications processed by mobile
	    categorizer per second"
    ::= { activeSyncNotifyOmaPush 6 }

asnopCatNotifySentTotal OBJECT-TYPE
    SYNTAX     Gauge32
    MAX-ACCESS read-only
    STATUS     current
    DESCRIPTION
	    "Number of successful notifications sent by
	    mobile categorizer"
    ::= { activeSyncNotifyOmaPush 7 }

asnopCatNotifySentPerSec OBJECT-TYPE
    SYNTAX     Gauge32
    MAX-ACCESS read-only
    STATUS     current
    DESCRIPTION
	    "Number of successful notifications sent by
	    mobile categorizer per second"
    ::= { activeSyncNotifyOmaPush 8 }

asnopOmaSinkNotifyDiscardTotal OBJECT-TYPE
    SYNTAX     Gauge32
    MAX-ACCESS read-only
    STATUS     current
    DESCRIPTION
	    "Number of notifications discarded by omasink
	    due to errors"
    ::= { activeSyncNotifyOmaPush 9 }

asnopOmaSinkNotifyDiscardPerSec OBJECT-TYPE
    SYNTAX     Gauge32
    MAX-ACCESS read-only
    STATUS     current
    DESCRIPTION
	    "Number of notifications discarded by omasink
	    per second"
    ::= { activeSyncNotifyOmaPush 10 }

asnopOmaSinkNotifyIgnoredTotal OBJECT-TYPE
    SYNTAX     Gauge32
    MAX-ACCESS read-only
    STATUS     current
    DESCRIPTION
	    "Number of notifications ignored by omasink"
    ::= { activeSyncNotifyOmaPush 11 }

asnopOmaSinkNotifyIgnoredPerSec OBJECT-TYPE
    SYNTAX     Gauge32
    MAX-ACCESS read-only
    STATUS     current
    DESCRIPTION
	    "Number of notifications ignored by omasink per
	    second"
    ::= { activeSyncNotifyOmaPush 12 }

asnopOmaSinkNotifySentTotal OBJECT-TYPE
    SYNTAX     Gauge32
    MAX-ACCESS read-only
    STATUS     current
    DESCRIPTION
	    "Number of successful notifications sent by
	    omasink"
    ::= { activeSyncNotifyOmaPush 13 }

asnopOmaSinkNotifySentPerSec OBJECT-TYPE
    SYNTAX     Gauge32
    MAX-ACCESS read-only
    STATUS     current
    DESCRIPTION
	    "Number of successful notifications sent by
	    omasink per second"
    ::= { activeSyncNotifyOmaPush 14 }

asnopOmaSinkOnSaveEventsTotal OBJECT-TYPE
    SYNTAX     Gauge32
    MAX-ACCESS read-only
    STATUS     current
    DESCRIPTION
	    "Number of times the OnSave event has been
	    triggered on omasink bindings"
    ::= { activeSyncNotifyOmaPush 15 }

asnopOmaSinkOnSaveEventsPerSec OBJECT-TYPE
    SYNTAX     Gauge32
    MAX-ACCESS read-only
    STATUS     current
    DESCRIPTION
	    "Number of times the OnSave event has been
	    triggered on omasink bindings per second"
    ::= { activeSyncNotifyOmaPush 16 }

addressListServiceTable OBJECT-TYPE
    SYNTAX     SEQUENCE OF ALEntry
    MAX-ACCESS not-accessible
    STATUS     current
    DESCRIPTION
	    "Microsoft Exchange Address List Service"
    ::= { exchange 3 }

addressListServiceEntry OBJECT-TYPE
    SYNTAX     ALEntry
    MAX-ACCESS not-accessible
    STATUS     current
    DESCRIPTION
	    "Performance information for one particular
	    instance of ''MSExchangeAL' object."
    INDEX      { alsInstance }
    ::= { addressListServiceTable 1 }

ALEntry ::= SEQUENCE {
    alsInstance InstanceName,
    alsActiveAddressListThreads Gauge32,
    alsActiveRecipientThreads Gauge32,
    alsAddressListModifications Gauge32,
    alsAddressListsQueueLength Gauge32,
    alsLDAPModifyCalsls Gauge32,
    alsLDAPModifyCalslsPerSec Gauge32,
    alsLDAPModifyFailures Gauge32,
    alsLDAPModifyFailuresPerSec Gauge32,
    alsLDAPResults Gauge32,
    alsLDAPResultsPerSec Gauge32,
    alsLDAPSearchCalsls Gauge32,
    alsLDAPSearchCalslsPerSec Gauge32,
    alsRecipientModifications Gauge32,
    alsRecipientsPerSec Gauge32,
    alsRecipientsQueueLength Gauge32
}

alsInstance OBJECT-TYPE
    SYNTAX     InstanceName
    MAX-ACCESS read-only
    STATUS     current
    DESCRIPTION
	    "Instance name."
    ::= { addressListServiceEntry 1 }

alsActiveAddressListThreads OBJECT-TYPE
    SYNTAX     Gauge32
    MAX-ACCESS read-only
    STATUS     current
    DESCRIPTION
	    "Active Address List Threads"
    ::= { addressListServiceEntry 2 }

alsActiveRecipientThreads OBJECT-TYPE
    SYNTAX     Gauge32
    MAX-ACCESS read-only
    STATUS     current
    DESCRIPTION
	    "Active Recipient Threads"
    ::= { addressListServiceEntry 3 }

alsAddressListModifications OBJECT-TYPE
    SYNTAX     Gauge32
    MAX-ACCESS read-only
    STATUS     current
    DESCRIPTION
	    "Address List Modifications"
    ::= { addressListServiceEntry 4 }

alsAddressListsQueueLength OBJECT-TYPE
    SYNTAX     Gauge32
    MAX-ACCESS read-only
    STATUS     current
    DESCRIPTION
	    "Address Lists Queue Length"
    ::= { addressListServiceEntry 5 }

alsLDAPModifyCalsls OBJECT-TYPE
    SYNTAX     Gauge32
    MAX-ACCESS read-only
    STATUS     current
    DESCRIPTION
	    "LDAP Modify calls"
    ::= { addressListServiceEntry 6 }

alsLDAPModifyCalslsPerSec OBJECT-TYPE
    SYNTAX     Gauge32
    MAX-ACCESS read-only
    STATUS     current
    DESCRIPTION
	    "LDAP Modify calls/sec"
    ::= { addressListServiceEntry 7 }

alsLDAPModifyFailures OBJECT-TYPE
    SYNTAX     Gauge32
    MAX-ACCESS read-only
    STATUS     current
    DESCRIPTION
	    "LDAP Modify failures"
    ::= { addressListServiceEntry 8 }

alsLDAPModifyFailuresPerSec OBJECT-TYPE
    SYNTAX     Gauge32
    MAX-ACCESS read-only
    STATUS     current
    DESCRIPTION
	    "LDAP Modify failures/sec"
    ::= { addressListServiceEntry 9 }

alsLDAPResults OBJECT-TYPE
    SYNTAX     Gauge32
    MAX-ACCESS read-only
    STATUS     current
    DESCRIPTION
	    "LDAP Results"
    ::= { addressListServiceEntry 10 }

alsLDAPResultsPerSec OBJECT-TYPE
    SYNTAX     Gauge32
    MAX-ACCESS read-only
    STATUS     current
    DESCRIPTION
	    "LDAP Results/sec"
    ::= { addressListServiceEntry 11 }

alsLDAPSearchCalsls OBJECT-TYPE
    SYNTAX     Gauge32
    MAX-ACCESS read-only
    STATUS     current
    DESCRIPTION
	    "LDAP Search calls"
    ::= { addressListServiceEntry 12 }

alsLDAPSearchCalslsPerSec OBJECT-TYPE
    SYNTAX     Gauge32
    MAX-ACCESS read-only
    STATUS     current
    DESCRIPTION
	    "LDAP Search calls/sec"
    ::= { addressListServiceEntry 13 }

alsRecipientModifications OBJECT-TYPE
    SYNTAX     Gauge32
    MAX-ACCESS read-only
    STATUS     current
    DESCRIPTION
	    "Recipient Modifications"
    ::= { addressListServiceEntry 14 }

alsRecipientsPerSec OBJECT-TYPE
    SYNTAX     Gauge32
    MAX-ACCESS read-only
    STATUS     current
    DESCRIPTION
	    "Recipients /sec"
    ::= { addressListServiceEntry 15 }

alsRecipientsQueueLength OBJECT-TYPE
    SYNTAX     Gauge32
    MAX-ACCESS read-only
    STATUS     current
    DESCRIPTION
	    "Recipients Queue Length"
    ::= { addressListServiceEntry 16 }

databaseTable OBJECT-TYPE
    SYNTAX     SEQUENCE OF DatabaseEntry
    MAX-ACCESS not-accessible
    STATUS     current
    DESCRIPTION
	    "Database provides performance statistics for
	    each process using the ESE high performance
	    embedded database management system."
    ::= { exchange 4 }

databaseEntry OBJECT-TYPE
    SYNTAX     DatabaseEntry
    MAX-ACCESS not-accessible
    STATUS     current
    DESCRIPTION
	    "Performance information for one particular
	    instance of ''Database' object."
    INDEX      { dbInstance }
    ::= { databaseTable 1 }

DatabaseEntry ::= SEQUENCE {
    dbInstance InstanceName,
    dbDatabaseCachePercentHit Gauge32,
    dbDatabaseCacheSize Gauge32,
    dbDatabasePageEvictionsPerSec Gauge32,
    dbDatabasePageFaultStallsPerSec Gauge32,
    dbDatabasePageFaultsPerSec Gauge32,
    dbLogRecordStallsPerSec Gauge32,
    dbLogThreadsWaiting Gauge32,
    dbLogWritesPerSec Gauge32,
    dbPagesConverted Gauge32,
    dbPagesConvertedPerSec Gauge32,
    dbRecordsConverted Gauge32,
    dbRecordsConvertedPerSec Gauge32,
    dbSessionsPercentUsed Gauge32,
    dbSessionsInUse Gauge32,
    dbTableOpenCachePercentHit Gauge32,
    dbTableOpenCacheHitsPerSec Gauge32,
    dbTableOpenCacheMissesPerSec Gauge32,
    dbTableOpensPerSec Gauge32,
    dbIODatabaseReadsPerSec Gauge32,
    dbIODatabaseWritesPerSec Gauge32,
    dbIOLogReadsPerSec Gauge32,
    dbIOLogWritesPerSec Gauge32
}

dbInstance OBJECT-TYPE
    SYNTAX     InstanceName
    MAX-ACCESS read-only
    STATUS     current
    DESCRIPTION
	    "Instance name."
    ::= { databaseEntry 1 }

dbDatabaseCachePercentHit OBJECT-TYPE
    SYNTAX     Gauge32
    MAX-ACCESS read-only
    STATUS     current
    DESCRIPTION
	    "Database Cache % Hit is the percentage of
	    database file page requests that were fulfilled
	    by the database cache without causing a file
	    operation.	If this percentage is too low, the
	    database cache size may be too small."
    ::= { databaseEntry 2 }

dbDatabaseCacheSize OBJECT-TYPE
    SYNTAX     Gauge32
    MAX-ACCESS read-only
    STATUS     current
    DESCRIPTION
	    "Database Cache Size is the amount of system
	    memory used by the database cache manager to
	    hold commonly used information from the
	    database file(s) to prevent file operations. 
	    If the database cache size seems to be too
	    small for optimal performance and the"
    ::= { databaseEntry 3 }

dbDatabasePageEvictionsPerSec OBJECT-TYPE
    SYNTAX     Gauge32
    MAX-ACCESS read-only
    STATUS     current
    DESCRIPTION
	    "Database Page Evictions/sec is the rate that
	    database file page requests that require the
	    database cache manager to allocate a new page
	    from the database cache force another database
	    page out of the cache.  The eviction count is
	    charged when the page is a"
    ::= { databaseEntry 4 }

dbDatabasePageFaultStallsPerSec OBJECT-TYPE
    SYNTAX     Gauge32
    MAX-ACCESS read-only
    STATUS     current
    DESCRIPTION
	    "Database Page Fault Stalls/sec is the rate of
	    page faults that cannot be serviced because
	    there are no pages available for allocation
	    from the database cache.  If this counter is
	    non-zero most of the time, the clean threshold
	    may be too low."
    ::= { databaseEntry 5 }

dbDatabasePageFaultsPerSec OBJECT-TYPE
    SYNTAX     Gauge32
    MAX-ACCESS read-only
    STATUS     current
    DESCRIPTION
	    "Database Page Faults/sec is the rate that
	    database file page requests require the
	    database cache manager to allocate a new page
	    from the database cache."
    ::= { databaseEntry 6 }

dbLogRecordStallsPerSec OBJECT-TYPE
    SYNTAX     Gauge32
    MAX-ACCESS read-only
    STATUS     current
    DESCRIPTION
	    "Log Record Stalls/sec is the number of log
	    records that cannot be added to the log buffers
	    per second because they are full.  If this
	    counter is non-zero most of the time, the log
	    buffer size may be a bottleneck."
    ::= { databaseEntry 7 }

dbLogThreadsWaiting OBJECT-TYPE
    SYNTAX     Gauge32
    MAX-ACCESS read-only
    STATUS     current
    DESCRIPTION
	    "Log Threads Waiting is the number of threads
	    waiting for their data to be written to the log
	    in order to complete an update of the database.
	     If this number is too high, the log may be a
	    bottleneck."
    ::= { databaseEntry 8 }

dbLogWritesPerSec OBJECT-TYPE
    SYNTAX     Gauge32
    MAX-ACCESS read-only
    STATUS     current
    DESCRIPTION
	    "Log Writes/sec is the number of times the log
	    buffers are written to the log file(s) per
	    second.  If this number approaches the maximum
	    write rate for the media holding the log
	    file(s), the log may be a bottleneck."
    ::= { databaseEntry 9 }

dbPagesConverted OBJECT-TYPE
    SYNTAX     Gauge32
    MAX-ACCESS read-only
    STATUS     current
    DESCRIPTION
	    "Pages Converted is the count of database pages
	    that have been converted from an older format"
    ::= { databaseEntry 10 }

dbPagesConvertedPerSec OBJECT-TYPE
    SYNTAX     Gauge32
    MAX-ACCESS read-only
    STATUS     current
    DESCRIPTION
	    "Pages Converted/sec is the count of times per
	    second a database page is converted from an
	    older database format"
    ::= { databaseEntry 11 }

dbRecordsConverted OBJECT-TYPE
    SYNTAX     Gauge32
    MAX-ACCESS read-only
    STATUS     current
    DESCRIPTION
	    "Records Converted is the count of database
	    records that have been converted from an older
	    format"
    ::= { databaseEntry 12 }

dbRecordsConvertedPerSec OBJECT-TYPE
    SYNTAX     Gauge32
    MAX-ACCESS read-only
    STATUS     current
    DESCRIPTION
	    "Records Converted/sec is the count of times
	    per second a database record is converted from
	    an older database format"
    ::= { databaseEntry 13 }

dbSessionsPercentUsed OBJECT-TYPE
    SYNTAX     Gauge32
    MAX-ACCESS read-only
    STATUS     current
    DESCRIPTION
	    "Sessions % Used is the percentage of database
	    sessions currently open for use by client
	    threads.  [Dev Only]"
    ::= { databaseEntry 14 }

dbSessionsInUse OBJECT-TYPE
    SYNTAX     Gauge32
    MAX-ACCESS read-only
    STATUS     current
    DESCRIPTION
	    "Sessions In Use is the number of database
	    sessions currently open for use by client
	    threads.  [Dev Only]"
    ::= { databaseEntry 15 }

dbTableOpenCachePercentHit OBJECT-TYPE
    SYNTAX     Gauge32
    MAX-ACCESS read-only
    STATUS     current
    DESCRIPTION
	    "Table Open Cache % Hit is the percentage of
	    database tables opened using cached schema
	    information.  If this percentage is too low,
	    the table cache size may be too small."
    ::= { databaseEntry 16 }

dbTableOpenCacheHitsPerSec OBJECT-TYPE
    SYNTAX     Gauge32
    MAX-ACCESS read-only
    STATUS     current
    DESCRIPTION
	    "Table Open Cache Hits/sec is the number of
	    database tables opened using cached schema
	    information per second.  If this rate is too
	    low, the table cache size may be too small."
    ::= { databaseEntry 17 }

dbTableOpenCacheMissesPerSec OBJECT-TYPE
    SYNTAX     Gauge32
    MAX-ACCESS read-only
    STATUS     current
    DESCRIPTION
	    "Table Open Cache Misses/sec is the number of
	    database tables opened without using cached
	    schema information per second.  If this rate is
	    too high, the table cache size may be too
	    small."
    ::= { databaseEntry 18 }

dbTableOpensPerSec OBJECT-TYPE
    SYNTAX     Gauge32
    MAX-ACCESS read-only
    STATUS     current
    DESCRIPTION
	    "Table Opens/sec is the number of database
	    tables opened per second."
    ::= { databaseEntry 19 }

dbIODatabaseReadsPerSec OBJECT-TYPE
    SYNTAX     Gauge32
    MAX-ACCESS read-only
    STATUS     current
    DESCRIPTION
	    "I/O Database Reads/sec is the rate of database
	    read operations completed."
    ::= { databaseEntry 20 }

dbIODatabaseWritesPerSec OBJECT-TYPE
    SYNTAX     Gauge32
    MAX-ACCESS read-only
    STATUS     current
    DESCRIPTION
	    "I/O Database Writes/sec is the rate of
	    database write operations completed."
    ::= { databaseEntry 21 }

dbIOLogReadsPerSec OBJECT-TYPE
    SYNTAX     Gauge32
    MAX-ACCESS read-only
    STATUS     current
    DESCRIPTION
	    "I/O Log Reads/sec is the rate of logfile read
	    operations completed."
    ::= { databaseEntry 22 }

dbIOLogWritesPerSec OBJECT-TYPE
    SYNTAX     Gauge32
    MAX-ACCESS read-only
    STATUS     current
    DESCRIPTION
	    "I/O Log Writes/sec is the rate of logfile
	    write operations completed."
    ::= { databaseEntry 23 }

databaseInstancesTable OBJECT-TYPE
    SYNTAX     SEQUENCE OF DatabaseInstancesEntry
    MAX-ACCESS not-accessible
    STATUS     current
    DESCRIPTION
	    "Instances in this process"
    ::= { exchange 5 }

databaseInstancesEntry OBJECT-TYPE
    SYNTAX     DatabaseInstancesEntry
    MAX-ACCESS not-accessible
    STATUS     current
    DESCRIPTION
	    "Performance information for one particular
	    instance of 'Database ==> Instances' object."
    INDEX      { dbiInstance }
    ::= { databaseInstancesTable 1 }

DatabaseInstancesEntry ::= SEQUENCE {
    dbiInstance InstanceName,
    dbiLogGenerationCheckpointDepth Gauge32,
    dbiLogRecordStallsPerSec Gauge32,
    dbiLogThreadsWaiting Gauge32,
    dbiLogWritesPerSec Gauge32,
    dbiPagesConverted Gauge32,
    dbiPagesConvertedPerSec Gauge32,
    dbiRecordsConverted Gauge32,
    dbiRecordsConvertedPerSec Gauge32,
    dbiSessionsPercentUsed Gauge32,
    dbiSessionsInUse Gauge32,
    dbiTableOpenCachePercentHit Gauge32,
    dbiTableOpenCacheHitsPerSec Gauge32,
    dbiTableOpenCacheMissesPerSec Gauge32,
    dbiTableOpensPerSec Gauge32,
    dbiIODatabaseReadsPerSec Gauge32,
    dbiIODatabaseWritesPerSec Gauge32,
    dbiIOLogReadsPerSec Gauge32,
    dbiIOLogWritesPerSec Gauge32
}

dbiInstance OBJECT-TYPE
    SYNTAX     InstanceName
    MAX-ACCESS read-only
    STATUS     current
    DESCRIPTION
	    "Instance name."
    ::= { databaseInstancesEntry 1 }

dbiLogGenerationCheckpointDepth OBJECT-TYPE
    SYNTAX     Gauge32
    MAX-ACCESS read-only
    STATUS     current
    DESCRIPTION
	    "Log Generation Checkpoint Depth represents the
	    amount of work, in count of log files, that
	    will need to be redone or undone to the 
	    database file(s) if the process crashes."
    ::= { databaseInstancesEntry 2 }

dbiLogRecordStallsPerSec OBJECT-TYPE
    SYNTAX     Gauge32
    MAX-ACCESS read-only
    STATUS     current
    DESCRIPTION
	    "Log Record Stalls/sec is the number of log
	    records that cannot be added to the log buffers
	    per second because they are full.  If this
	    counter is non-zero most of the time, the log
	    buffer size may be a bottleneck."
    ::= { databaseInstancesEntry 3 }

dbiLogThreadsWaiting OBJECT-TYPE
    SYNTAX     Gauge32
    MAX-ACCESS read-only
    STATUS     current
    DESCRIPTION
	    "Log Threads Waiting is the number of threads
	    waiting for their data to be written to the log
	    in order to complete an update of the database.
	     If this number is too high, the log may be a
	    bottleneck."
    ::= { databaseInstancesEntry 4 }

dbiLogWritesPerSec OBJECT-TYPE
    SYNTAX     Gauge32
    MAX-ACCESS read-only
    STATUS     current
    DESCRIPTION
	    "Log Writes/sec is the number of times the log
	    buffers are written to the log file(s) per
	    second.  If this number approaches the maximum
	    write rate for the media holding the log
	    file(s), the log may be a bottleneck."
    ::= { databaseInstancesEntry 5 }

dbiPagesConverted OBJECT-TYPE
    SYNTAX     Gauge32
    MAX-ACCESS read-only
    STATUS     current
    DESCRIPTION
	    "Pages Converted is the count of database pages
	    that have been converted from an older format"
    ::= { databaseInstancesEntry 6 }

dbiPagesConvertedPerSec OBJECT-TYPE
    SYNTAX     Gauge32
    MAX-ACCESS read-only
    STATUS     current
    DESCRIPTION
	    "Pages Converted/sec is the count of times per
	    second a database page is converted from an
	    older database format"
    ::= { databaseInstancesEntry 7 }

dbiRecordsConverted OBJECT-TYPE
    SYNTAX     Gauge32
    MAX-ACCESS read-only
    STATUS     current
    DESCRIPTION
	    "Records Converted is the count of database
	    records that have been converted from an older
	    format"
    ::= { databaseInstancesEntry 8 }

dbiRecordsConvertedPerSec OBJECT-TYPE
    SYNTAX     Gauge32
    MAX-ACCESS read-only
    STATUS     current
    DESCRIPTION
	    "Records Converted/sec is the count of times
	    per second a database record is converted from
	    an older database format"
    ::= { databaseInstancesEntry 9 }

dbiSessionsPercentUsed OBJECT-TYPE
    SYNTAX     Gauge32
    MAX-ACCESS read-only
    STATUS     current
    DESCRIPTION
	    "Sessions % Used is the percentage of database
	    sessions currently open for use by client
	    threads.  [Dev Only]"
    ::= { databaseInstancesEntry 10 }

dbiSessionsInUse OBJECT-TYPE
    SYNTAX     Gauge32
    MAX-ACCESS read-only
    STATUS     current
    DESCRIPTION
	    "Sessions In Use is the number of database
	    sessions currently open for use by client
	    threads.  [Dev Only]"
    ::= { databaseInstancesEntry 11 }

dbiTableOpenCachePercentHit OBJECT-TYPE
    SYNTAX     Gauge32
    MAX-ACCESS read-only
    STATUS     current
    DESCRIPTION
	    "Table Open Cache % Hit is the percentage of
	    database tables opened using cached schema
	    information.  If this percentage is too low,
	    the table cache size may be too small."
    ::= { databaseInstancesEntry 12 }

dbiTableOpenCacheHitsPerSec OBJECT-TYPE
    SYNTAX     Gauge32
    MAX-ACCESS read-only
    STATUS     current
    DESCRIPTION
	    "Table Open Cache Hits/sec is the number of
	    database tables opened using cached schema
	    information per second.  If this rate is too
	    low, the table cache size may be too small."
    ::= { databaseInstancesEntry 13 }

dbiTableOpenCacheMissesPerSec OBJECT-TYPE
    SYNTAX     Gauge32
    MAX-ACCESS read-only
    STATUS     current
    DESCRIPTION
	    "Table Open Cache Misses/sec is the number of
	    database tables opened without using cached
	    schema information per second.  If this rate is
	    too high, the table cache size may be too
	    small."
    ::= { databaseInstancesEntry 14 }

dbiTableOpensPerSec OBJECT-TYPE
    SYNTAX     Gauge32
    MAX-ACCESS read-only
    STATUS     current
    DESCRIPTION
	    "Table Opens/sec is the number of database
	    tables opened per second."
    ::= { databaseInstancesEntry 15 }

dbiIODatabaseReadsPerSec OBJECT-TYPE
    SYNTAX     Gauge32
    MAX-ACCESS read-only
    STATUS     current
    DESCRIPTION
	    "I/O Database Reads/sec is the rate of database
	    read operations completed."
    ::= { databaseInstancesEntry 16 }

dbiIODatabaseWritesPerSec OBJECT-TYPE
    SYNTAX     Gauge32
    MAX-ACCESS read-only
    STATUS     current
    DESCRIPTION
	    "I/O Database Writes/sec is the rate of
	    database write operations completed."
    ::= { databaseInstancesEntry 17 }

dbiIOLogReadsPerSec OBJECT-TYPE
    SYNTAX     Gauge32
    MAX-ACCESS read-only
    STATUS     current
    DESCRIPTION
	    "I/O Log Reads/sec is the rate of logfile read
	    operations completed."
    ::= { databaseInstancesEntry 18 }

dbiIOLogWritesPerSec OBJECT-TYPE
    SYNTAX     Gauge32
    MAX-ACCESS read-only
    STATUS     current
    DESCRIPTION
	    "I/O Log Writes/sec is the rate of logfile
	    write operations completed."
    ::= { databaseInstancesEntry 19 }

dsAccessCachesTable OBJECT-TYPE
    SYNTAX     SEQUENCE OF DSAccessCachesEntry
    MAX-ACCESS not-accessible
    STATUS     current
    DESCRIPTION
	    "One instance per Cache Instance: global Cache
	    Instance data."
    ::= { exchange 6 }

dsAccessCachesEntry OBJECT-TYPE
    SYNTAX     DSAccessCachesEntry
    MAX-ACCESS not-accessible
    STATUS     current
    DESCRIPTION
	    "Performance information for one particular
	    instance of 'MSExchangeDSAccess Caches'
	    object."
    INDEX      { dsacInstance }
    ::= { dsAccessCachesTable 1 }

DSAccessCachesEntry ::= SEQUENCE {
    dsacInstance InstanceName,
    dsacCacheExpireTotalConfigData Gauge32,
    dsacCacheExpireTotalUserData Gauge32,
    dsacCacheExpirePerSecConfigData Gauge32,
    dsacCacheExpirePerSecUserData Gauge32,
    dsacCacheHitsTotal Gauge32,
    dsacCacheHitsPerSec Gauge32,
    dsacCacheInsertsTotalConfigData Gauge32,
    dsacCacheInsertsTotalUserData Gauge32,
    dsacCacheInsertsPerSecConfigData Gauge32,
    dsacCacheInsertsPerSecUserData Gauge32,
    dsacCacheMissesTotal Gauge32,
    dsacCacheMissesPerSec Gauge32,
    dsacDNEntryConfigData Gauge32,
    dsacDNEntryUserData Gauge32,
    dsacDNEntryMemConfigData Gauge32,
    dsacDNEntryMemUserData Gauge32,
    dsacLDAPSearchesTotal Gauge32,
    dsacLDAPSearchesPerSec Gauge32,
    dsacNotFndDNEntryConfigData Gauge32,
    dsacNotFndDNEntryUserData Gauge32,
    dsacNotFndDNEntryMemConfigData Gauge32,
    dsacNotFndDNEntryMemUserData Gauge32,
    dsacNotFndGUIDEntryConfigData Gauge32,
    dsacNotFndGUIDEntryUserData Gauge32,
    dsacNotFndGUIDEntryMemConfigData Gauge32,
    dsacNotFndGUIDEntryMemUserData Gauge32,
    dsacOutstandingAsyncNotifies Gauge32,
    dsacOutstandingAsyncReads Gauge32,
    dsacOutstandingAsyncSearches Gauge32,
    dsacSearchEntryConfigData Gauge32,
    dsacSearchEntryUserData Gauge32,
    dsacSearchEntryMemConfigData Gauge32,
    dsacSearchEntryMemUserData Gauge32,
    dsacTotalEntryConfigData Gauge32,
    dsacTotalEntryUserData Gauge32,
    dsacTotalEntryMemConfigData Gauge32,
    dsacTotalEntryMemUserData Gauge32
}

dsacInstance OBJECT-TYPE
    SYNTAX     InstanceName
    MAX-ACCESS read-only
    STATUS     current
    DESCRIPTION
	    "Instance name."
    ::= { dsAccessCachesEntry 1 }

dsacCacheExpireTotalConfigData OBJECT-TYPE
    SYNTAX     Gauge32
    MAX-ACCESS read-only
    STATUS     current
    DESCRIPTION
	    "Cache Expiries Total (Configuration Data) is
	    the total number of configuration data objects
	    expired from the cache since system
	    initialization."
    ::= { dsAccessCachesEntry 2 }

dsacCacheExpireTotalUserData OBJECT-TYPE
    SYNTAX     Gauge32
    MAX-ACCESS read-only
    STATUS     current
    DESCRIPTION
	    "Cache Expiries Total (User Data) is the total
	    number of user data objects expired from the
	    cache since system initialization."
    ::= { dsAccessCachesEntry 3 }

dsacCacheExpirePerSecConfigData OBJECT-TYPE
    SYNTAX     Gauge32
    MAX-ACCESS read-only
    STATUS     current
    DESCRIPTION
	    "Cache Expiries/Sec (Configuration Data) is the
	    number of configuration data objects expired
	    from the cache per second."
    ::= { dsAccessCachesEntry 4 }

dsacCacheExpirePerSecUserData OBJECT-TYPE
    SYNTAX     Gauge32
    MAX-ACCESS read-only
    STATUS     current
    DESCRIPTION
	    "Cache Expiries/Sec (User Data) is the number
	    of user data objects expired from the cache per
	    second."
    ::= { dsAccessCachesEntry 5 }

dsacCacheHitsTotal OBJECT-TYPE
    SYNTAX     Gauge32
    MAX-ACCESS read-only
    STATUS     current
    DESCRIPTION
	    "Cache Hits Total is the total number of
	    'object found in cache' events since system
	    initialization."
    ::= { dsAccessCachesEntry 6 }

dsacCacheHitsPerSec OBJECT-TYPE
    SYNTAX     Gauge32
    MAX-ACCESS read-only
    STATUS     current
    DESCRIPTION
	    "Cache Hits/Sec is the number of  'object found
	    in cache' events per second."
    ::= { dsAccessCachesEntry 7 }

dsacCacheInsertsTotalConfigData OBJECT-TYPE
    SYNTAX     Gauge32
    MAX-ACCESS read-only
    STATUS     current
    DESCRIPTION
	    "Cache Inserts Total (Configuration Data) is
	    the total number of configuration data objects
	    inserted into the cache since system
	    initialization."
    ::= { dsAccessCachesEntry 8 }

dsacCacheInsertsTotalUserData OBJECT-TYPE
    SYNTAX     Gauge32
    MAX-ACCESS read-only
    STATUS     current
    DESCRIPTION
	    "Cache Inserts Total (User Data) is the total
	    number of user data objects inserted into the
	    cache since system initialization."
    ::= { dsAccessCachesEntry 9 }

dsacCacheInsertsPerSecConfigData OBJECT-TYPE
    SYNTAX     Gauge32
    MAX-ACCESS read-only
    STATUS     current
    DESCRIPTION
	    "Cache Inserts/Sec (Configuration Data) is the
	    number of configuration data objects inserted
	    into the cache per second."
    ::= { dsAccessCachesEntry 10 }

dsacCacheInsertsPerSecUserData OBJECT-TYPE
    SYNTAX     Gauge32
    MAX-ACCESS read-only
    STATUS     current
    DESCRIPTION
	    "Cache Inserts/Sec (User Data) is the number of
	    user data objects inserted into the cache per
	    second."
    ::= { dsAccessCachesEntry 11 }

dsacCacheMissesTotal OBJECT-TYPE
    SYNTAX     Gauge32
    MAX-ACCESS read-only
    STATUS     current
    DESCRIPTION
	    "Cache Misses Total is the total number of
	    'object not found in cache' events since system
	    initialization."
    ::= { dsAccessCachesEntry 12 }

dsacCacheMissesPerSec OBJECT-TYPE
    SYNTAX     Gauge32
    MAX-ACCESS read-only
    STATUS     current
    DESCRIPTION
	    "Cache Misses/Sec is the number of 'object not
	    found in cache' events per second."
    ::= { dsAccessCachesEntry 13 }

dsacDNEntryConfigData OBJECT-TYPE
    SYNTAX     Gauge32
    MAX-ACCESS read-only
    STATUS     current
    DESCRIPTION
	    "DN Entries (Configuration Data) is the total
	    number of configuration data DN object type
	    entries in the cache."
    ::= { dsAccessCachesEntry 14 }

dsacDNEntryUserData OBJECT-TYPE
    SYNTAX     Gauge32
    MAX-ACCESS read-only
    STATUS     current
    DESCRIPTION
	    "DN Entries (User Data) is the total number of
	    user data DN object type entries in the cache."
    ::= { dsAccessCachesEntry 15 }

dsacDNEntryMemConfigData OBJECT-TYPE
    SYNTAX     Gauge32
    MAX-ACCESS read-only
    STATUS     current
    DESCRIPTION
	    "DN Entries Memory (Configuration Data) is the
	    memory occupied by all configuration data DN
	    Entries in the cache (in bytes)"
    ::= { dsAccessCachesEntry 16 }

dsacDNEntryMemUserData OBJECT-TYPE
    SYNTAX     Gauge32
    MAX-ACCESS read-only
    STATUS     current
    DESCRIPTION
	    "DN Entries Memory (User Data) is the memory
	    occupied by all user data DN Entries in the
	    cache (in bytes)"
    ::= { dsAccessCachesEntry 17 }

dsacLDAPSearchesTotal OBJECT-TYPE
    SYNTAX     Gauge32
    MAX-ACCESS read-only
    STATUS     current
    DESCRIPTION
	    "LDAP Searches Total is the total number of
	    LDAP search requests issued since system
	    initialization."
    ::= { dsAccessCachesEntry 18 }

dsacLDAPSearchesPerSec OBJECT-TYPE
    SYNTAX     Gauge32
    MAX-ACCESS read-only
    STATUS     current
    DESCRIPTION
	    "LDAP Searches/Sec is the number of LDAP search
	    requests issued per second."
    ::= { dsAccessCachesEntry 19 }

dsacNotFndDNEntryConfigData OBJECT-TYPE
    SYNTAX     Gauge32
    MAX-ACCESS read-only
    STATUS     current
    DESCRIPTION
	    "Not Found DN Entries (Configuration Data) is
	    the total number of configuration data 'Not
	    Found DN' type entries in the cache."
    ::= { dsAccessCachesEntry 20 }

dsacNotFndDNEntryUserData OBJECT-TYPE
    SYNTAX     Gauge32
    MAX-ACCESS read-only
    STATUS     current
    DESCRIPTION
	    "Not Found DN Entries (User Data) is the total
	    number of user data 'Not Found DN' type entries
	    in the cache."
    ::= { dsAccessCachesEntry 21 }

dsacNotFndDNEntryMemConfigData OBJECT-TYPE
    SYNTAX     Gauge32
    MAX-ACCESS read-only
    STATUS     current
    DESCRIPTION
	    "Not Found DN Entries Memory (Configuration
	    Data) is the memory occupied by all
	    configuration data 'Not Found DN' Entries in
	    the cache (in bytes)"
    ::= { dsAccessCachesEntry 22 }

dsacNotFndDNEntryMemUserData OBJECT-TYPE
    SYNTAX     Gauge32
    MAX-ACCESS read-only
    STATUS     current
    DESCRIPTION
	    "Not Found DN Entries Memory (User Data) is the
	    memory occupied by all user data 'Not Found DN'
	    Entries in the cache (in bytes)"
    ::= { dsAccessCachesEntry 23 }

dsacNotFndGUIDEntryConfigData OBJECT-TYPE
    SYNTAX     Gauge32
    MAX-ACCESS read-only
    STATUS     current
    DESCRIPTION
	    "Not Found GUID Entries (Configuration Data) is
	    the total number of configuration data 'Not
	    Found GUID' type entries in the cache."
    ::= { dsAccessCachesEntry 24 }

dsacNotFndGUIDEntryUserData OBJECT-TYPE
    SYNTAX     Gauge32
    MAX-ACCESS read-only
    STATUS     current
    DESCRIPTION
	    "Not Found GUID Entries (User Data) is the
	    total number of user data 'Not Found GUID' type
	    entries in the cache."
    ::= { dsAccessCachesEntry 25 }

dsacNotFndGUIDEntryMemConfigData OBJECT-TYPE
    SYNTAX     Gauge32
    MAX-ACCESS read-only
    STATUS     current
    DESCRIPTION
	    "Not Found GUID Entries Memory (Configuration
	    Data) is the memory occupied by all
	    configuration data 'Not Found GUID' Entries in
	    the cache (in bytes)"
    ::= { dsAccessCachesEntry 26 }

dsacNotFndGUIDEntryMemUserData OBJECT-TYPE
    SYNTAX     Gauge32
    MAX-ACCESS read-only
    STATUS     current
    DESCRIPTION
	    "Not Found GUID Entries Memory (User Data) is
	    the memory occupied by all user data 'Not Found
	    GUID' Entries in the cache (in bytes)"
    ::= { dsAccessCachesEntry 27 }

dsacOutstandingAsyncNotifies OBJECT-TYPE
    SYNTAX     Gauge32
    MAX-ACCESS read-only
    STATUS     current
    DESCRIPTION
	    "Outstanding Async Notifies is the number of
	    outstanding ldap notification requests."
    ::= { dsAccessCachesEntry 28 }

dsacOutstandingAsyncReads OBJECT-TYPE
    SYNTAX     Gauge32
    MAX-ACCESS read-only
    STATUS     current
    DESCRIPTION
	    "Outstanding Async Reads is the number of
	    outstanding ldap read requests."
    ::= { dsAccessCachesEntry 29 }

dsacOutstandingAsyncSearches OBJECT-TYPE
    SYNTAX     Gauge32
    MAX-ACCESS read-only
    STATUS     current
    DESCRIPTION
	    "Outstanding Async Searches is the number of
	    outstanding ldap search requests."
    ::= { dsAccessCachesEntry 30 }

dsacSearchEntryConfigData OBJECT-TYPE
    SYNTAX     Gauge32
    MAX-ACCESS read-only
    STATUS     current
    DESCRIPTION
	    "Search Entries (Configuration Data) is the
	    total number of configuration data search type
	    entries in the cache."
    ::= { dsAccessCachesEntry 31 }

dsacSearchEntryUserData OBJECT-TYPE
    SYNTAX     Gauge32
    MAX-ACCESS read-only
    STATUS     current
    DESCRIPTION
	    "Search Entries (User Data) is the total number
	    of user data search type entries in the cache."
    ::= { dsAccessCachesEntry 32 }

dsacSearchEntryMemConfigData OBJECT-TYPE
    SYNTAX     Gauge32
    MAX-ACCESS read-only
    STATUS     current
    DESCRIPTION
	    "Search Entries Memory (Configuration Data) is
	    the memory occupied by all configuration data
	    search entries in the cache (in bytes)"
    ::= { dsAccessCachesEntry 33 }

dsacSearchEntryMemUserData OBJECT-TYPE
    SYNTAX     Gauge32
    MAX-ACCESS read-only
    STATUS     current
    DESCRIPTION
	    "Search Entries Memory (User Data) is the
	    memory occupied by all user data search entries
	    in the cache (in bytes)"
    ::= { dsAccessCachesEntry 34 }

dsacTotalEntryConfigData OBJECT-TYPE
    SYNTAX     Gauge32
    MAX-ACCESS read-only
    STATUS     current
    DESCRIPTION
	    "Total Entries (Configuration Data) is the
	    total number of configuration data entries in
	    the cache. This includes 'DN', 'Search', 'Not
	    Found DN' and 'Not Found GUID' type entries."
    ::= { dsAccessCachesEntry 35 }

dsacTotalEntryUserData OBJECT-TYPE
    SYNTAX     Gauge32
    MAX-ACCESS read-only
    STATUS     current
    DESCRIPTION
	    "Total Entries (User Data) is the total number
	    of user data entries in the cache. This
	    includes 'DN', 'Search', 'Not Found DN' and
	    'Not Found GUID' type entries."
    ::= { dsAccessCachesEntry 36 }

dsacTotalEntryMemConfigData OBJECT-TYPE
    SYNTAX     Gauge32
    MAX-ACCESS read-only
    STATUS     current
    DESCRIPTION
	    "Total Entries Memory (Configuration Data) is
	    the memory occupied by all configuration data
	    entry objects in the cache (in bytes)."
    ::= { dsAccessCachesEntry 37 }

dsacTotalEntryMemUserData OBJECT-TYPE
    SYNTAX     Gauge32
    MAX-ACCESS read-only
    STATUS     current
    DESCRIPTION
	    "Total Entries Memory (User Data) is the memory
	    occupied by all user data entry objects in the
	    cache (in bytes)."
    ::= { dsAccessCachesEntry 38 }

dsAccessDomainControllersTable OBJECT-TYPE
    SYNTAX     SEQUENCE OF DSAccessDomainControllersEntry
    MAX-ACCESS not-accessible
    STATUS     current
    DESCRIPTION
	    "One instance per Domain Controller:
	    cross-process Domain Controller data."
    ::= { exchange 7 }

dsAccessDomainControllersEntry OBJECT-TYPE
    SYNTAX     DSAccessDomainControllersEntry
    MAX-ACCESS not-accessible
    STATUS     current
    DESCRIPTION
	    "Performance information for one particular
	    instance of 'MSExchangeDSAccess Domain
	    Controllers' object."
    INDEX      { dssadcInstance }
    ::= { dsAccessDomainControllersTable 1 }

DSAccessDomainControllersEntry ::= SEQUENCE {
    dssadcInstance InstanceName,
    dssadcBindFailuresPerMinute Gauge32,
    dssadcCriticalDataFlag Gauge32,
    dssadcDsGetDcNameElapsedTime Gauge32,
    dssadcGCCapableFlag Gauge32,
    dssadcIsSynchronizedFlag Gauge32,
    dssadcKerberosTicketLifetime Gauge32,
    dssadcLDAPDisconnectsPerMinute Gauge32,
    dssadcLDAPFatalErrorsPerMinute Gauge32,
    dssadcLDAPReadTime Gauge32,
    dssadcLDAPReadCallsPerSec Gauge32,
    dssadcLDAPSearchTime Gauge32,
    dssadcLDAPSearchCallsPerSec Gauge32,
    dssadcLDAPSrchTimedOutPerMinute Gauge32,
    dssadcLDAPConnectionLifetime Gauge32,
    dssadcLocalSiteFlag Gauge32,
    dssadcNetlogonFlag Gauge32,
    dssadcNumOfOutstandingRequests Gauge32,
    dssadcOSVersionFlag Gauge32,
    dssadcPDCFlag Gauge32,
    dssadcReachabilityBitmask Gauge32,
    dssadcSACLRightFlag Gauge32,
    dssadcUserSearchFailedPerMinute Gauge32,
    dssadcGethostbynameElapsedTime Gauge32
}

dssadcInstance OBJECT-TYPE
    SYNTAX     InstanceName
    MAX-ACCESS read-only
    STATUS     current
    DESCRIPTION
	    "Instance name."
    ::= { dsAccessDomainControllersEntry 1 }

dssadcBindFailuresPerMinute OBJECT-TYPE
    SYNTAX     Gauge32
    MAX-ACCESS read-only
    STATUS     current
    DESCRIPTION
	    "Bind failures per minute is the number of LDAP
	    bind calls failed during the last minute"
    ::= { dsAccessDomainControllersEntry 2 }

dssadcCriticalDataFlag OBJECT-TYPE
    SYNTAX     Gauge32
    MAX-ACCESS read-only
    STATUS     current
    DESCRIPTION
	    "Critical Data flag is 1 if the DC contains the
	    Exchange server account, 0 otherwise"
    ::= { dsAccessDomainControllersEntry 3 }

dssadcDsGetDcNameElapsedTime OBJECT-TYPE
    SYNTAX     Gauge32
    MAX-ACCESS read-only
    STATUS     current
    DESCRIPTION
	    "DsGetDcName elapsed time is the total time (in
	    ms) spent in DsGetDcName call to the DC"
    ::= { dsAccessDomainControllersEntry 4 }

dssadcGCCapableFlag OBJECT-TYPE
    SYNTAX     Gauge32
    MAX-ACCESS read-only
    STATUS     current
    DESCRIPTION
	    "GC capable flag is 1 if the DC is also a GC, 0
	    otherwise"
    ::= { dsAccessDomainControllersEntry 5 }

dssadcIsSynchronizedFlag OBJECT-TYPE
    SYNTAX     Gauge32
    MAX-ACCESS read-only
    STATUS     current
    DESCRIPTION
	    "IsSynchronized flag is 1 if the DC is
	    synchronized, 0 otherwise"
    ::= { dsAccessDomainControllersEntry 6 }

dssadcKerberosTicketLifetime OBJECT-TYPE
    SYNTAX     Gauge32
    MAX-ACCESS read-only
    STATUS     current
    DESCRIPTION
	    "Kerberos ticket lifetime (in seconds) is an
	    average life time of the last 16 connections
	    closed due to Kerberos ticket expiration"
    ::= { dsAccessDomainControllersEntry 7 }

dssadcLDAPDisconnectsPerMinute OBJECT-TYPE
    SYNTAX     Gauge32
    MAX-ACCESS read-only
    STATUS     current
    DESCRIPTION
	    "LDAP Disconnects per minute is the number of
	    LDAP errors that caused DSAccess to mark the DC
	    down during the last minute"
    ::= { dsAccessDomainControllersEntry 8 }

dssadcLDAPFatalErrorsPerMinute OBJECT-TYPE
    SYNTAX     Gauge32
    MAX-ACCESS read-only
    STATUS     current
    DESCRIPTION
	    "LDAP Fatal errors per minute is the number of
	    LDAP errors that caused DSAccess to close the
	    LDAP connection without marking the DC down
	    during the last minute"
    ::= { dsAccessDomainControllersEntry 9 }

dssadcLDAPReadTime OBJECT-TYPE
    SYNTAX     Gauge32
    MAX-ACCESS read-only
    STATUS     current
    DESCRIPTION
	    "LDAP Read Time for a given DC is the time (in
	    ms) taken to send an LDAP read request to the
	    specified DC and receive a response"
    ::= { dsAccessDomainControllersEntry 10 }

dssadcLDAPReadCallsPerSec OBJECT-TYPE
    SYNTAX     Gauge32
    MAX-ACCESS read-only
    STATUS     current
    DESCRIPTION
	    "LDAP Read calls/Sec is the number of Depth 0
	    LDAP search calls made by this process per
	    second"
    ::= { dsAccessDomainControllersEntry 11 }

dssadcLDAPSearchTime OBJECT-TYPE
    SYNTAX     Gauge32
    MAX-ACCESS read-only
    STATUS     current
    DESCRIPTION
	    "LDAP Search Time is the time (in ms) taken to
	    send an LDAP search request and receive a
	    response"
    ::= { dsAccessDomainControllersEntry 12 }

dssadcLDAPSearchCallsPerSec OBJECT-TYPE
    SYNTAX     Gauge32
    MAX-ACCESS read-only
    STATUS     current
    DESCRIPTION
	    "LDAP Search calls/Sec is the number of Depth 1
	    or 2 LDAP Search calls made by this process per
	    second"
    ::= { dsAccessDomainControllersEntry 13 }

dssadcLDAPSrchTimedOutPerMinute OBJECT-TYPE
    SYNTAX     Gauge32
    MAX-ACCESS read-only
    STATUS     current
    DESCRIPTION
	    "LDAP Search timed out per minute is the number
	    of LDAP searches returned LDAP_TIMEOUT during
	    the last minute"
    ::= { dsAccessDomainControllersEntry 14 }

dssadcLDAPConnectionLifetime OBJECT-TYPE
    SYNTAX     Gauge32
    MAX-ACCESS read-only
    STATUS     current
    DESCRIPTION
	    "LDAP connection lifetime (in seconds) is an
	    average life time of the last 16 connections
	    closed (excludes ones closed due to Kerberos
	    ticket expiration)"
    ::= { dsAccessDomainControllersEntry 15 }

dssadcLocalSiteFlag OBJECT-TYPE
    SYNTAX     Gauge32
    MAX-ACCESS read-only
    STATUS     current
    DESCRIPTION
	    "Local site flag is 1 if the DC belongs to the
	    local site, 0 otherwise"
    ::= { dsAccessDomainControllersEntry 16 }

dssadcNetlogonFlag OBJECT-TYPE
    SYNTAX     Gauge32
    MAX-ACCESS read-only
    STATUS     current
    DESCRIPTION
	    "Netlogon flag is 1 when DsGetDcName to the DC
	    succeeds, indicating that NetLogon service is
	    running, 0 otherwise"
    ::= { dsAccessDomainControllersEntry 17 }

dssadcNumOfOutstandingRequests OBJECT-TYPE
    SYNTAX     Gauge32
    MAX-ACCESS read-only
    STATUS     current
    DESCRIPTION
	    "Number of outstanding requests is the current
	    number of pending LDAP searches to the DC"
    ::= { dsAccessDomainControllersEntry 18 }

dssadcOSVersionFlag OBJECT-TYPE
    SYNTAX     Gauge32
    MAX-ACCESS read-only
    STATUS     current
    DESCRIPTION
	    "OS Version flag is 1 when the DC satisfies
	    DSAccess OS/Service Pack requirements, 0
	    otherwise"
    ::= { dsAccessDomainControllersEntry 19 }

dssadcPDCFlag OBJECT-TYPE
    SYNTAX     Gauge32
    MAX-ACCESS read-only
    STATUS     current
    DESCRIPTION
	    "PDC flag is 1if the DC is also a PDC, 0
	    otherwise"
    ::= { dsAccessDomainControllersEntry 20 }

dssadcReachabilityBitmask OBJECT-TYPE
    SYNTAX     Gauge32
    MAX-ACCESS read-only
    STATUS     current
    DESCRIPTION
	    "Reachability bitmask shows how the DC is
	    reachable by using lowest 3 bits for DC, CDC
	    and GC-used ports."
    ::= { dsAccessDomainControllersEntry 21 }

dssadcSACLRightFlag OBJECT-TYPE
    SYNTAX     Gauge32
    MAX-ACCESS read-only
    STATUS     current
    DESCRIPTION
	    "SACL right flag is 1 if the Exchange server
	    has a SeSecurityPrivilege on the DC, 0
	    otherwise"
    ::= { dsAccessDomainControllersEntry 22 }

dssadcUserSearchFailedPerMinute OBJECT-TYPE
    SYNTAX     Gauge32
    MAX-ACCESS read-only
    STATUS     current
    DESCRIPTION
	    "User searches failed per minute is the number
	    of DSAccess client's searches failed during the
	    last minute"
    ::= { dsAccessDomainControllersEntry 23 }

dssadcGethostbynameElapsedTime OBJECT-TYPE
    SYNTAX     Gauge32
    MAX-ACCESS read-only
    STATUS     current
    DESCRIPTION
	    "gethostbyname elapsed time is the total time
	    (in ms) spent in gethostbyname call trying to
	    find the DC's IP address"
    ::= { dsAccessDomainControllersEntry 24 }

dsAccessGlobalCounters OBJECT-IDENTITY
    STATUS     current
    DESCRIPTION
	    "MSExchangeDSAccess Global Counters contain
	    summary information that is not process or DC
	    specific"
    ::= { exchange 8 }

dsagcDNSQueryDurationTime OBJECT-TYPE
    SYNTAX     Gauge32
    MAX-ACCESS read-only
    STATUS     current
    DESCRIPTION
	    "DNS Query duration time shows how long (in ms)
	    the most recent DNSQuery call took"
    ::= { dsAccessGlobalCounters 1 }

dsagcInSiteDomainControllers OBJECT-TYPE
    SYNTAX     Gauge32
    MAX-ACCESS read-only
    STATUS     current
    DESCRIPTION
	    "In-site Domain Controllers is the number of
	    suitable Domain Controllers in the local site"
    ::= { dsAccessGlobalCounters 2 }

dsagcInSiteGlobalCatalogs OBJECT-TYPE
    SYNTAX     Gauge32
    MAX-ACCESS read-only
    STATUS     current
    DESCRIPTION
	    "In-site Global Catalogs is the number of
	    suitable Global Catalogs in the local site"
    ::= { dsAccessGlobalCounters 3 }

dsagcOutOfSiteDomainControllers OBJECT-TYPE
    SYNTAX     Gauge32
    MAX-ACCESS read-only
    STATUS     current
    DESCRIPTION
	    "Out-of-site Domain Controllers is the number
	    of suitable Domain Controllers outside the
	    local site"
    ::= { dsAccessGlobalCounters 4 }

dsagcOutOfSiteGlobalCatalogs OBJECT-TYPE
    SYNTAX     Gauge32
    MAX-ACCESS read-only
    STATUS     current
    DESCRIPTION
	    "Out-of-site Global Catalogs is the number of
	    suitable Global Catalogs outside the local
	    site"
    ::= { dsAccessGlobalCounters 5 }

dsagcTopologyDscvryDurationTime OBJECT-TYPE
    SYNTAX     Gauge32
    MAX-ACCESS read-only
    STATUS     current
    DESCRIPTION
	    "Topology Discovery duration time shows how
	    long (in msec) the most recent Topology
	    discovery took"
    ::= { dsAccessGlobalCounters 6 }

dsAccessProcessesTable OBJECT-TYPE
    SYNTAX     SEQUENCE OF DSAccessProcessesEntry
    MAX-ACCESS not-accessible
    STATUS     current
    DESCRIPTION
	    "One instance per client process"
    ::= { exchange 9 }

dsAccessProcessesEntry OBJECT-TYPE
    SYNTAX     DSAccessProcessesEntry
    MAX-ACCESS not-accessible
    STATUS     current
    DESCRIPTION
	    "Performance information for one particular
	    instance of 'MSExchangeDSAccess Processes'
	    object."
    INDEX      { dsapInstance }
    ::= { dsAccessProcessesTable 1 }

DSAccessProcessesEntry ::= SEQUENCE {
    dsapInstance InstanceName,
    dsapLDAPReadTime Gauge32,
    dsapLDAPReadCallsPerSec Gauge32,
    dsapLDAPSearchTime Gauge32,
    dsapLDAPSearchCallsPerSec Gauge32,
    dsapProcessID Gauge32
}

dsapInstance OBJECT-TYPE
    SYNTAX     InstanceName
    MAX-ACCESS read-only
    STATUS     current
    DESCRIPTION
	    "Instance name."
    ::= { dsAccessProcessesEntry 1 }

dsapLDAPReadTime OBJECT-TYPE
    SYNTAX     Gauge32
    MAX-ACCESS read-only
    STATUS     current
    DESCRIPTION
	    "LDAP Read Time is the time (in ms) taken to
	    send an LDAP read request and receive a
	    response"
    ::= { dsAccessProcessesEntry 2 }

dsapLDAPReadCallsPerSec OBJECT-TYPE
    SYNTAX     Gauge32
    MAX-ACCESS read-only
    STATUS     current
    DESCRIPTION
	    "LDAP Read calls/Sec is the number of Depth 0
	    LDAP search calls made by this process per
	    second"
    ::= { dsAccessProcessesEntry 3 }

dsapLDAPSearchTime OBJECT-TYPE
    SYNTAX     Gauge32
    MAX-ACCESS read-only
    STATUS     current
    DESCRIPTION
	    "LDAP Search Time is the time (in ms) taken to
	    send an LDAP search request and receive a
	    response"
    ::= { dsAccessProcessesEntry 4 }

dsapLDAPSearchCallsPerSec OBJECT-TYPE
    SYNTAX     Gauge32
    MAX-ACCESS read-only
    STATUS     current
    DESCRIPTION
	    "LDAP Search calls/Sec is the number of Depth 1
	    or 2 LDAP Search calls made by this process per
	    second"
    ::= { dsAccessProcessesEntry 5 }

dsapProcessID OBJECT-TYPE
    SYNTAX     Gauge32
    MAX-ACCESS read-only
    STATUS     current
    DESCRIPTION
	    "The system Process ID of this process
	    instance"
    ::= { dsAccessProcessesEntry 6 }

epoxyTable OBJECT-TYPE
    SYNTAX     SEQUENCE OF EpoxyEntry
    MAX-ACCESS not-accessible
    STATUS     current
    DESCRIPTION
	    "This object represents global counters for the
	    Exchange sub-component Epoxy."
    ::= { exchange 10 }

epoxyEntry OBJECT-TYPE
    SYNTAX     EpoxyEntry
    MAX-ACCESS not-accessible
    STATUS     current
    DESCRIPTION
	    "Performance information for one particular
	    instance of 'Epoxy' object."
    INDEX      { epoxyInstance }
    ::= { epoxyTable 1 }

EpoxyEntry ::= SEQUENCE {
    epoxyInstance InstanceName,
    epoxyBlocksAllocated Gauge32,
    epoxyBytesAllocated Gauge32,
    epoxyClientOutQueueLength Gauge32,
    epoxyEnqueuesByClient Gauge32,
    epoxyEnqueuesByStore Gauge32,
    epoxyPQCSsFailedOnClient Gauge32,
    epoxyPQCSsFailedOnStore Gauge32,
    epoxySegmentsAllocated Gauge32,
    epoxyStoreOutQueueLength Gauge32
}

epoxyInstance OBJECT-TYPE
    SYNTAX     InstanceName
    MAX-ACCESS read-only
    STATUS     current
    DESCRIPTION
	    "Instance name."
    ::= { epoxyEntry 1 }

epoxyBlocksAllocated OBJECT-TYPE
    SYNTAX     Gauge32
    MAX-ACCESS read-only
    STATUS     current
    DESCRIPTION
	    "Total number of blocks currently allocated
	    from epoxy shared memory."
    ::= { epoxyEntry 2 }

epoxyBytesAllocated OBJECT-TYPE
    SYNTAX     Gauge32
    MAX-ACCESS read-only
    STATUS     current
    DESCRIPTION
	    "Total number of bytes currently allocated from
	    epoxy shared memory."
    ::= { epoxyEntry 3 }

epoxyClientOutQueueLength OBJECT-TYPE
    SYNTAX     Gauge32
    MAX-ACCESS read-only
    STATUS     current
    DESCRIPTION
	    "Number of requests waiting to be processed by
	    the Exchange store"
    ::= { epoxyEntry 4 }

epoxyEnqueuesByClient OBJECT-TYPE
    SYNTAX     Gauge32
    MAX-ACCESS read-only
    STATUS     current
    DESCRIPTION
	    "Total number of enqueues done by client"
    ::= { epoxyEntry 5 }

epoxyEnqueuesByStore OBJECT-TYPE
    SYNTAX     Gauge32
    MAX-ACCESS read-only
    STATUS     current
    DESCRIPTION
	    "Total number of enqueues done by store"
    ::= { epoxyEntry 6 }

epoxyPQCSsFailedOnClient OBJECT-TYPE
    SYNTAX     Gauge32
    MAX-ACCESS read-only
    STATUS     current
    DESCRIPTION
	    "Total number of PostQueuedCompletionStatus
	    failures on client"
    ::= { epoxyEntry 7 }

epoxyPQCSsFailedOnStore OBJECT-TYPE
    SYNTAX     Gauge32
    MAX-ACCESS read-only
    STATUS     current
    DESCRIPTION
	    "Total number of PostQueuedCompletionStatus
	    failures on store"
    ::= { epoxyEntry 8 }

epoxySegmentsAllocated OBJECT-TYPE
    SYNTAX     Gauge32
    MAX-ACCESS read-only
    STATUS     current
    DESCRIPTION
	    "Total number of segments currently allocated
	    from epoxy shared memory."
    ::= { epoxyEntry 9 }

epoxyStoreOutQueueLength OBJECT-TYPE
    SYNTAX     Gauge32
    MAX-ACCESS read-only
    STATUS     current
    DESCRIPTION
	    "Number of requests waiting to be picked up by
	    the Internet Information Services protocol
	    handlers"
    ::= { epoxyEntry 10 }

eventService OBJECT-IDENTITY
    STATUS     current
    DESCRIPTION
	    "Only one instance : global ES performance
	    data"
    ::= { exchange 11 }

esAvgEventTime OBJECT-TYPE
    SYNTAX     Gauge32
    MAX-ACCESS read-only
    STATUS     current
    DESCRIPTION
	    "Average time (in ms) spent in each event."
    ::= { eventService 1 }

esAvgScriptTime OBJECT-TYPE
    SYNTAX     Gauge32
    MAX-ACCESS read-only
    STATUS     current
    DESCRIPTION
	    "Average time (in ms) spent in each script
	    executed."
    ::= { eventService 2 }

esHandlerTime OBJECT-TYPE
    SYNTAX     Gauge32
    MAX-ACCESS read-only
    STATUS     current
    DESCRIPTION
	    "Total time (in ms) spent in a handler."
    ::= { eventService 3 }

esNotificationsExecuting OBJECT-TYPE
    SYNTAX     Gauge32
    MAX-ACCESS read-only
    STATUS     current
    DESCRIPTION
	    "Notifications from Store that are currently
	    being processed"
    ::= { eventService 4 }

esNotifyQueue OBJECT-TYPE
    SYNTAX     Gauge32
    MAX-ACCESS read-only
    STATUS     current
    DESCRIPTION
	    "Queue of Store Notifications waiting to be
	    processed."
    ::= { eventService 5 }

esNotifyTime OBJECT-TYPE
    SYNTAX     Gauge32
    MAX-ACCESS read-only
    STATUS     current
    DESCRIPTION
	    "Total time (in ms) spent processing
	    notifications."
    ::= { eventService 6 }

esNotifyTimeLast OBJECT-TYPE
    SYNTAX     Gauge32
    MAX-ACCESS read-only
    STATUS     current
    DESCRIPTION
	    "Time (in ms) spent processing last
	    notification."
    ::= { eventService 7 }

esScriptTime OBJECT-TYPE
    SYNTAX     Gauge32
    MAX-ACCESS read-only
    STATUS     current
    DESCRIPTION
	    "Total time (in ms) spent in all scripts."
    ::= { eventService 8 }

esScriptTimeouts OBJECT-TYPE
    SYNTAX     Gauge32
    MAX-ACCESS read-only
    STATUS     current
    DESCRIPTION
	    "Count of scripts that have timed out."
    ::= { eventService 9 }

esTotalEvents OBJECT-TYPE
    SYNTAX     Gauge32
    MAX-ACCESS read-only
    STATUS     current
    DESCRIPTION
	    "Total number of events that have fired since
	    the service has started."
    ::= { eventService 10 }

esTotalScripts OBJECT-TYPE
    SYNTAX     Gauge32
    MAX-ACCESS read-only
    STATUS     current
    DESCRIPTION
	    "Total number of scripts that have executed
	    since the service has started."
    ::= { eventService 11 }

httpExtensionsTable OBJECT-TYPE
    SYNTAX     SEQUENCE OF HTTPExtensionsEntry
    MAX-ACCESS not-accessible
    STATUS     current
    DESCRIPTION
	    "HTTP Extensions for Microsoft Exchange Server"
    ::= { exchange 12 }

httpExtensionsEntry OBJECT-TYPE
    SYNTAX     HTTPExtensionsEntry
    MAX-ACCESS not-accessible
    STATUS     current
    DESCRIPTION
	    "Performance information for one particular
	    instance of 'Exchange Server HTTP Extensions'
	    object."
    INDEX      { httpExtInstance }
    ::= { httpExtensionsTable 1 }

HTTPExtensionsEntry ::= SEQUENCE {
    httpExtInstance InstanceName,
    httpExtBCOPYRequestsPerSec Gauge32,
    httpExtBDELETERequestsPerSec Gauge32,
    httpExtBMOVERequestsPerSec Gauge32,
    httpExtBPROPFINDRequestsPerSec Gauge32,
    httpExtBPROPPATCHRequestsPerSec Gauge32,
    httpExtBadRequestErrorsPerSec Gauge32,
    httpExtCOPYRequestsPerSec Gauge32,
    httpExtConflictRspnsPerSec Gauge32,
    httpExtCreatedRspnsPerSec Gauge32,
    httpExtCurrentRequests Gauge32,
    httpExtDELETERequestsPerSec Gauge32,
    httpExtForbiddenRspnsPerSec Gauge32,
    httpExtGETRequestsPerSec Gauge32,
    httpExtHEADRequestsPerSec Gauge32,
    httpExtIFSCacheHitsTotal Gauge32,
    httpExtIFSCacheHitsPerSecond Gauge32,
    httpExtIFSCacheMissesTotal Gauge32,
    httpExtIFSCacheMissesPerSecond Gauge32,
    httpExtIFSCacheUtilization Gauge32,
    httpExtLOCKRequestsPerSec Gauge32,
    httpExtLockedErrorsPerSec Gauge32,
    httpExtMKCOLRequestsPerSec Gauge32,
    httpExtMOVERequestsPerSec Gauge32,
    httpExtMethodFailureRspnsPerSec Gauge32,
    httpExtMethodNotAllowRspnsPerSec Gauge32,
    httpExtMovedTempRspnsPerSec Gauge32,
    httpExtMultiStatusRspnsPerSec Gauge32,
    httpExtNoContentRspnsPerSec Gauge32,
    httpExtNotAcceptableRspnsPerSec Gauge32,
    httpExtNotFoundErrorsPerSec Gauge32,
    httpExtNotImplementedRspnsPerSec Gauge32,
    httpExtOPTIONSRequestsPerSec Gauge32,
    httpExtOkRspnsPerSec Gauge32,
    httpExtOtherRequestsPerSec Gauge32,
    httpExtPOLLRequestsPerSec Gauge32,
    httpExtPOSTRequestsPerSec Gauge32,
    httpExtPROPFINDRequestsPerSec Gauge32,
    httpExtPROPPATCHRequestsPerSec Gauge32,
    httpExtPUTRequestsPerSec Gauge32,
    httpExtPrecondFailRspnPerSec Gauge32,
    httpExtRedirectedRequestsPerSec Gauge32,
    httpExtRedirectPerSecFromBackEnd Gauge32,
    httpExtRequestsPerSec Gauge32,
    httpExtSEARCHRequestsPerSec Gauge32,
    httpExtSUBSCRIBERequestsPerSec Gauge32,
    httpExtServerErrorsPerSec Gauge32,
    httpExtServiceUnavailRspnsPerSec Gauge32,
    httpExtTotalBCOPYRequests Gauge32,
    httpExtTotalBDELETERequests Gauge32,
    httpExtTotalBMOVERequests Gauge32,
    httpExtTotalBPROPFINDRequests Gauge32,
    httpExtTotalBPROPPATCHRequests Gauge32,
    httpExtTotalBadRequestErrors Gauge32,
    httpExtTotalCOPYRequests Gauge32,
    httpExtTotalConflictRspns Gauge32,
    httpExtTotalCreatedRspns Gauge32,
    httpExtTotalDELETERequests Gauge32,
    httpExtTotalExceptions Gauge32,
    httpExtTotalForbiddenRspns Gauge32,
    httpExtTotalGETRequests Gauge32,
    httpExtTotalHEADRequests Gauge32,
    httpExtTotalISAPIExtensionRqsts Gauge32,
    httpExtTotalLOCKRequests Gauge32,
    httpExtTotalLockedErrors Gauge32,
    httpExtTotalMKCOLRequests Gauge32,
    httpExtTotalMOVERequests Gauge32,
    httpExtTotalMethodFailureRspns Gauge32,
    httpExtTotalMethodNotAllowedRspn Gauge32,
    httpExtTotalMovedTemporarilyRspn Gauge32,
    httpExtTotalMultiStatusRspns Gauge32,
    httpExtTotalNoContentRspns Gauge32,
    httpExtTotalNotAcceptableRspns Gauge32,
    httpExtTotalNotFoundErrors Gauge32,
    httpExtTotalNotImplementedRspns Gauge32,
    httpExtTotalOPTIONSRequests Gauge32,
    httpExtTotalOkRspns Gauge32,
    httpExtTotalOtherRequests Gauge32,
    httpExtTotalPOLLRequests Gauge32,
    httpExtTotalPOSTRequests Gauge32,
    httpExtTotalPROPFINDRequests Gauge32,
    httpExtTotalPROPPATCHRequests Gauge32,
    httpExtTotalPUTRequests Gauge32,
    httpExtTotalPreconditionFailRspn Gauge32,
    httpExtTotalRedirectedRequests Gauge32,
    httpExtTotalRedirectsFromBackEnd Gauge32,
    httpExtTotalRequests Gauge32,
    httpExtTotalSEARCHRequests Gauge32,
    httpExtTotalSUBSCRIBERequests Gauge32,
    httpExtTotalServerErrors Gauge32,
    httpExtTotalServiceUnavailRspns Gauge32,
    httpExtTotalUNLOCKRequests Gauge32,
    httpExtTotalUNSUBSCRIBERequests Gauge32,
    httpExtTotalUnauthorizedErrors Gauge32,
    httpExtTotalUnprocessEntityRspns Gauge32,
    httpExtTotalUnsupportedMediaRspn Gauge32,
    httpExtUNLOCKRequestsPerSec Gauge32,
    httpExtUNSUBSCRIBERequestsPerSec Gauge32,
    httpExtUnauthorizedErrorsPerSec Gauge32,
    httpExtUnprocessEntityRspnPerSec Gauge32,
    httpExtUnsupportMediaRspnsPerSec Gauge32
}

httpExtInstance OBJECT-TYPE
    SYNTAX     InstanceName
    MAX-ACCESS read-only
    STATUS     current
    DESCRIPTION
	    "Instance name."
    ::= { httpExtensionsEntry 1 }

httpExtBCOPYRequestsPerSec OBJECT-TYPE
    SYNTAX     Gauge32
    MAX-ACCESS read-only
    STATUS     current
    DESCRIPTION
	    "The rate at which the server receives HTTP
	    BCOPY requests."
    ::= { httpExtensionsEntry 2 }

httpExtBDELETERequestsPerSec OBJECT-TYPE
    SYNTAX     Gauge32
    MAX-ACCESS read-only
    STATUS     current
    DESCRIPTION
	    "The rate at which the server receives HTTP
	    BDELETE requests."
    ::= { httpExtensionsEntry 3 }

httpExtBMOVERequestsPerSec OBJECT-TYPE
    SYNTAX     Gauge32
    MAX-ACCESS read-only
    STATUS     current
    DESCRIPTION
	    "The rate at which the server receives HTTP
	    BMOVE requests."
    ::= { httpExtensionsEntry 4 }

httpExtBPROPFINDRequestsPerSec OBJECT-TYPE
    SYNTAX     Gauge32
    MAX-ACCESS read-only
    STATUS     current
    DESCRIPTION
	    "The rate at which the server receives HTTP
	    BPROPFIND requests."
    ::= { httpExtensionsEntry 5 }

httpExtBPROPPATCHRequestsPerSec OBJECT-TYPE
    SYNTAX     Gauge32
    MAX-ACCESS read-only
    STATUS     current
    DESCRIPTION
	    "The rate at which the server receives HTTP
	    BPROPPATCH requests."
    ::= { httpExtensionsEntry 6 }

httpExtBadRequestErrorsPerSec OBJECT-TYPE
    SYNTAX     Gauge32
    MAX-ACCESS read-only
    STATUS     current
    DESCRIPTION
	    "The rate at which the server is sending '400
	    Bad Request' HTTP responses to clients."
    ::= { httpExtensionsEntry 7 }

httpExtCOPYRequestsPerSec OBJECT-TYPE
    SYNTAX     Gauge32
    MAX-ACCESS read-only
    STATUS     current
    DESCRIPTION
	    "The rate at which the server receives HTTP
	    COPY requests."
    ::= { httpExtensionsEntry 8 }

httpExtConflictRspnsPerSec OBJECT-TYPE
    SYNTAX     Gauge32
    MAX-ACCESS read-only
    STATUS     current
    DESCRIPTION
	    "The rate at which the server is sending '409
	    Conflict' HTTP responses to clients."
    ::= { httpExtensionsEntry 9 }

httpExtCreatedRspnsPerSec OBJECT-TYPE
    SYNTAX     Gauge32
    MAX-ACCESS read-only
    STATUS     current
    DESCRIPTION
	    "The rate at which the server is sending '201
	    Created' HTTP responses to clients."
    ::= { httpExtensionsEntry 10 }

httpExtCurrentRequests OBJECT-TYPE
    SYNTAX     Gauge32
    MAX-ACCESS read-only
    STATUS     current
    DESCRIPTION
	    "The number of HTTP requests that the server is
	    currently processing."
    ::= { httpExtensionsEntry 11 }

httpExtDELETERequestsPerSec OBJECT-TYPE
    SYNTAX     Gauge32
    MAX-ACCESS read-only
    STATUS     current
    DESCRIPTION
	    "The rate at which the server receives HTTP
	    DELETE requests."
    ::= { httpExtensionsEntry 12 }

httpExtForbiddenRspnsPerSec OBJECT-TYPE
    SYNTAX     Gauge32
    MAX-ACCESS read-only
    STATUS     current
    DESCRIPTION
	    "The rate at which the server is sending '403
	    Forbidden' HTTP responses to clients."
    ::= { httpExtensionsEntry 13 }

httpExtGETRequestsPerSec OBJECT-TYPE
    SYNTAX     Gauge32
    MAX-ACCESS read-only
    STATUS     current
    DESCRIPTION
	    "The rate at which the server receives HTTP GET
	    requests."
    ::= { httpExtensionsEntry 14 }

httpExtHEADRequestsPerSec OBJECT-TYPE
    SYNTAX     Gauge32
    MAX-ACCESS read-only
    STATUS     current
    DESCRIPTION
	    "The rate at which the server receives HTTP
	    HEAD requests."
    ::= { httpExtensionsEntry 15 }

httpExtIFSCacheHitsTotal OBJECT-TYPE
    SYNTAX     Gauge32
    MAX-ACCESS read-only
    STATUS     current
    DESCRIPTION
	    "The total number of sucessful file handle
	    retrievals from the IFS File Handle cache since
	    service startup."
    ::= { httpExtensionsEntry 16 }

httpExtIFSCacheHitsPerSecond OBJECT-TYPE
    SYNTAX     Gauge32
    MAX-ACCESS read-only
    STATUS     current
    DESCRIPTION
	    "The rate at which IFS File Handle cache is
	    successfuly used rather than the store to get a
	    file handle."
    ::= { httpExtensionsEntry 17 }

httpExtIFSCacheMissesTotal OBJECT-TYPE
    SYNTAX     Gauge32
    MAX-ACCESS read-only
    STATUS     current
    DESCRIPTION
	    "The total number of unsucessful queries to the
	    IFS File Handle cache since service startup."
    ::= { httpExtensionsEntry 18 }

httpExtIFSCacheMissesPerSecond OBJECT-TYPE
    SYNTAX     Gauge32
    MAX-ACCESS read-only
    STATUS     current
    DESCRIPTION
	    "The rate at which IFS File Handle cache is
	    unsuccessfuly queried."
    ::= { httpExtensionsEntry 19 }

httpExtIFSCacheUtilization OBJECT-TYPE
    SYNTAX     Gauge32
    MAX-ACCESS read-only
    STATUS     current
    DESCRIPTION
	    "The number of items currently in the IFS File
	    Handle cache."
    ::= { httpExtensionsEntry 20 }

httpExtLOCKRequestsPerSec OBJECT-TYPE
    SYNTAX     Gauge32
    MAX-ACCESS read-only
    STATUS     current
    DESCRIPTION
	    "The rate at which the server receives HTTP
	    LOCK requests."
    ::= { httpExtensionsEntry 21 }

httpExtLockedErrorsPerSec OBJECT-TYPE
    SYNTAX     Gauge32
    MAX-ACCESS read-only
    STATUS     current
    DESCRIPTION
	    "The rate at which the server is sending '423
	    Locked' HTTP responses to clients."
    ::= { httpExtensionsEntry 22 }

httpExtMKCOLRequestsPerSec OBJECT-TYPE
    SYNTAX     Gauge32
    MAX-ACCESS read-only
    STATUS     current
    DESCRIPTION
	    "The rate at which the server receives HTTP
	    MKCOL requests."
    ::= { httpExtensionsEntry 23 }

httpExtMOVERequestsPerSec OBJECT-TYPE
    SYNTAX     Gauge32
    MAX-ACCESS read-only
    STATUS     current
    DESCRIPTION
	    "The rate at which the server receives HTTP
	    MOVE requests."
    ::= { httpExtensionsEntry 24 }

httpExtMethodFailureRspnsPerSec OBJECT-TYPE
    SYNTAX     Gauge32
    MAX-ACCESS read-only
    STATUS     current
    DESCRIPTION
	    "The rate at which the server is sending '424
	    Method Failure' HTTP responses to clients."
    ::= { httpExtensionsEntry 25 }

httpExtMethodNotAllowRspnsPerSec OBJECT-TYPE
    SYNTAX     Gauge32
    MAX-ACCESS read-only
    STATUS     current
    DESCRIPTION
	    "The rate at which the server is sending '405
	    Method Not Allowed' HTTP responses to clients."
    ::= { httpExtensionsEntry 26 }

httpExtMovedTempRspnsPerSec OBJECT-TYPE
    SYNTAX     Gauge32
    MAX-ACCESS read-only
    STATUS     current
    DESCRIPTION
	    "The rate at which the server is sending '302
	    Moved Temporarily' HTTP responses to clients."
    ::= { httpExtensionsEntry 27 }

httpExtMultiStatusRspnsPerSec OBJECT-TYPE
    SYNTAX     Gauge32
    MAX-ACCESS read-only
    STATUS     current
    DESCRIPTION
	    "The rate at which the server is sending '207
	    Multi-Status' HTTP responses to clients."
    ::= { httpExtensionsEntry 28 }

httpExtNoContentRspnsPerSec OBJECT-TYPE
    SYNTAX     Gauge32
    MAX-ACCESS read-only
    STATUS     current
    DESCRIPTION
	    "The rate at which the server is sending '204
	    No Content' HTTP responses to clients."
    ::= { httpExtensionsEntry 29 }

httpExtNotAcceptableRspnsPerSec OBJECT-TYPE
    SYNTAX     Gauge32
    MAX-ACCESS read-only
    STATUS     current
    DESCRIPTION
	    "The rate at which the server is sending '406
	    Not Acceptable' HTTP responses to clients."
    ::= { httpExtensionsEntry 30 }

httpExtNotFoundErrorsPerSec OBJECT-TYPE
    SYNTAX     Gauge32
    MAX-ACCESS read-only
    STATUS     current
    DESCRIPTION
	    "The rate at which the server is sending '404
	    Not Found' HTTP responses to clients."
    ::= { httpExtensionsEntry 31 }

httpExtNotImplementedRspnsPerSec OBJECT-TYPE
    SYNTAX     Gauge32
    MAX-ACCESS read-only
    STATUS     current
    DESCRIPTION
	    "The rate at which the server is sending '501
	    Not Implemented' HTTP responses to clients."
    ::= { httpExtensionsEntry 32 }

httpExtOPTIONSRequestsPerSec OBJECT-TYPE
    SYNTAX     Gauge32
    MAX-ACCESS read-only
    STATUS     current
    DESCRIPTION
	    "The rate at which the server receives HTTP
	    OPTIONS requests."
    ::= { httpExtensionsEntry 33 }

httpExtOkRspnsPerSec OBJECT-TYPE
    SYNTAX     Gauge32
    MAX-ACCESS read-only
    STATUS     current
    DESCRIPTION
	    "The rate at which the server is sending '200
	    OK' HTTP responses to clients."
    ::= { httpExtensionsEntry 34 }

httpExtOtherRequestsPerSec OBJECT-TYPE
    SYNTAX     Gauge32
    MAX-ACCESS read-only
    STATUS     current
    DESCRIPTION
	    "The rate at which the server receives HTTP
	    requests using methods other than OPTIONS, GET,
	    HEAD, PUT, POST, DELETE, COPY, MOVE, MKCOL,
	    PROPFIND, PROPPATCH, LOCK, UNLOCK, SEARCH,
	    POLL, SUBSCRIBE, UNSUBSCRIBE, BDELETE, BCOPY,
	    BMOVE, BPROPPATCH and BPROPFIND"
    ::= { httpExtensionsEntry 35 }

httpExtPOLLRequestsPerSec OBJECT-TYPE
    SYNTAX     Gauge32
    MAX-ACCESS read-only
    STATUS     current
    DESCRIPTION
	    "The rate at which the server receives HTTP
	    POLL requests."
    ::= { httpExtensionsEntry 36 }

httpExtPOSTRequestsPerSec OBJECT-TYPE
    SYNTAX     Gauge32
    MAX-ACCESS read-only
    STATUS     current
    DESCRIPTION
	    "The rate at which the server receives HTTP
	    POST requests."
    ::= { httpExtensionsEntry 37 }

httpExtPROPFINDRequestsPerSec OBJECT-TYPE
    SYNTAX     Gauge32
    MAX-ACCESS read-only
    STATUS     current
    DESCRIPTION
	    "The rate at which the server receives HTTP
	    PROPFIND requests."
    ::= { httpExtensionsEntry 38 }

httpExtPROPPATCHRequestsPerSec OBJECT-TYPE
    SYNTAX     Gauge32
    MAX-ACCESS read-only
    STATUS     current
    DESCRIPTION
	    "The rate at which the server receives HTTP
	    PROPPATCH requests."
    ::= { httpExtensionsEntry 39 }

httpExtPUTRequestsPerSec OBJECT-TYPE
    SYNTAX     Gauge32
    MAX-ACCESS read-only
    STATUS     current
    DESCRIPTION
	    "The rate at which the server receives HTTP PUT
	    requests."
    ::= { httpExtensionsEntry 40 }

httpExtPrecondFailRspnPerSec OBJECT-TYPE
    SYNTAX     Gauge32
    MAX-ACCESS read-only
    STATUS     current
    DESCRIPTION
	    "The rate at which the server is sending '412
	    Precondition Failed' HTTP responses to
	    clients."
    ::= { httpExtensionsEntry 41 }

httpExtRedirectedRequestsPerSec OBJECT-TYPE
    SYNTAX     Gauge32
    MAX-ACCESS read-only
    STATUS     current
    DESCRIPTION
	    "The rate at which the server is redirecting
	    HTTP requests to other locations."
    ::= { httpExtensionsEntry 42 }

httpExtRedirectPerSecFromBackEnd OBJECT-TYPE
    SYNTAX     Gauge32
    MAX-ACCESS read-only
    STATUS     current
    DESCRIPTION
	    "The rate of redirect messages received by the
	    server."
    ::= { httpExtensionsEntry 43 }

httpExtRequestsPerSec OBJECT-TYPE
    SYNTAX     Gauge32
    MAX-ACCESS read-only
    STATUS     current
    DESCRIPTION
	    "The rate at which the server receives all HTTP
	    requests."
    ::= { httpExtensionsEntry 44 }

httpExtSEARCHRequestsPerSec OBJECT-TYPE
    SYNTAX     Gauge32
    MAX-ACCESS read-only
    STATUS     current
    DESCRIPTION
	    "The rate at which the server receives HTTP
	    SEARCH requests."
    ::= { httpExtensionsEntry 45 }

httpExtSUBSCRIBERequestsPerSec OBJECT-TYPE
    SYNTAX     Gauge32
    MAX-ACCESS read-only
    STATUS     current
    DESCRIPTION
	    "The rate at which the server receives HTTP
	    SUBSCRIBE requests."
    ::= { httpExtensionsEntry 46 }

httpExtServerErrorsPerSec OBJECT-TYPE
    SYNTAX     Gauge32
    MAX-ACCESS read-only
    STATUS     current
    DESCRIPTION
	    "The rate at which the server is sending '500
	    Server Error' HTTP responses to clients."
    ::= { httpExtensionsEntry 47 }

httpExtServiceUnavailRspnsPerSec OBJECT-TYPE
    SYNTAX     Gauge32
    MAX-ACCESS read-only
    STATUS     current
    DESCRIPTION
	    "The rate at which the server is sending '503
	    Service Unavailable' HTTP responses to
	    clients."
    ::= { httpExtensionsEntry 48 }

httpExtTotalBCOPYRequests OBJECT-TYPE
    SYNTAX     Gauge32
    MAX-ACCESS read-only
    STATUS     current
    DESCRIPTION
	    "The number of HTTP BCOPY requests received by
	    the server since service startup."
    ::= { httpExtensionsEntry 49 }

httpExtTotalBDELETERequests OBJECT-TYPE
    SYNTAX     Gauge32
    MAX-ACCESS read-only
    STATUS     current
    DESCRIPTION
	    "The number of HTTP BDELETE requests received
	    by the server since service startup."
    ::= { httpExtensionsEntry 50 }

httpExtTotalBMOVERequests OBJECT-TYPE
    SYNTAX     Gauge32
    MAX-ACCESS read-only
    STATUS     current
    DESCRIPTION
	    "The number of HTTP BMOVE requests received by
	    the server since service startup."
    ::= { httpExtensionsEntry 51 }

httpExtTotalBPROPFINDRequests OBJECT-TYPE
    SYNTAX     Gauge32
    MAX-ACCESS read-only
    STATUS     current
    DESCRIPTION
	    "The number of HTTP BPROPFIND requests received
	    by the server since service startup."
    ::= { httpExtensionsEntry 52 }

httpExtTotalBPROPPATCHRequests OBJECT-TYPE
    SYNTAX     Gauge32
    MAX-ACCESS read-only
    STATUS     current
    DESCRIPTION
	    "The number of HTTP BPROPPATCH requests
	    received by the server since service startup."
    ::= { httpExtensionsEntry 53 }

httpExtTotalBadRequestErrors OBJECT-TYPE
    SYNTAX     Gauge32
    MAX-ACCESS read-only
    STATUS     current
    DESCRIPTION
	    "The number of '400 Bad Request' HTTP responses
	    sent by the server since service startup."
    ::= { httpExtensionsEntry 54 }

httpExtTotalCOPYRequests OBJECT-TYPE
    SYNTAX     Gauge32
    MAX-ACCESS read-only
    STATUS     current
    DESCRIPTION
	    "The number of HTTP COPY requests received by
	    the server since service startup."
    ::= { httpExtensionsEntry 55 }

httpExtTotalConflictRspns OBJECT-TYPE
    SYNTAX     Gauge32
    MAX-ACCESS read-only
    STATUS     current
    DESCRIPTION
	    "The number of '409 Conflict' HTTP responses
	    sent by the server since service startup."
    ::= { httpExtensionsEntry 56 }

httpExtTotalCreatedRspns OBJECT-TYPE
    SYNTAX     Gauge32
    MAX-ACCESS read-only
    STATUS     current
    DESCRIPTION
	    "The number of '201 Created' HTTP responses
	    sent by the server since service startup."
    ::= { httpExtensionsEntry 57 }

httpExtTotalDELETERequests OBJECT-TYPE
    SYNTAX     Gauge32
    MAX-ACCESS read-only
    STATUS     current
    DESCRIPTION
	    "The number of HTTP DELETE requests received by
	    the server since service startup."
    ::= { httpExtensionsEntry 58 }

httpExtTotalExceptions OBJECT-TYPE
    SYNTAX     Gauge32
    MAX-ACCESS read-only
    STATUS     current
    DESCRIPTION
	    "The number of exceptions that have occurred
	    since service startup."
    ::= { httpExtensionsEntry 59 }

httpExtTotalForbiddenRspns OBJECT-TYPE
    SYNTAX     Gauge32
    MAX-ACCESS read-only
    STATUS     current
    DESCRIPTION
	    "The number of '403 Forbidden' HTTP responses
	    sent by the server since service startup."
    ::= { httpExtensionsEntry 60 }

httpExtTotalGETRequests OBJECT-TYPE
    SYNTAX     Gauge32
    MAX-ACCESS read-only
    STATUS     current
    DESCRIPTION
	    "The number of HTTP GET requests received by
	    the server since service startup."
    ::= { httpExtensionsEntry 61 }

httpExtTotalHEADRequests OBJECT-TYPE
    SYNTAX     Gauge32
    MAX-ACCESS read-only
    STATUS     current
    DESCRIPTION
	    "The number of HTTP HEAD requests received by
	    the server since service startup."
    ::= { httpExtensionsEntry 62 }

httpExtTotalISAPIExtensionRqsts OBJECT-TYPE
    SYNTAX     Gauge32
    MAX-ACCESS read-only
    STATUS     current
    DESCRIPTION
	    "The number of HTTP requests executed by an
	    ISAPI Extension since service startup."
    ::= { httpExtensionsEntry 63 }

httpExtTotalLOCKRequests OBJECT-TYPE
    SYNTAX     Gauge32
    MAX-ACCESS read-only
    STATUS     current
    DESCRIPTION
	    "The number of HTTP LOCK requests received by
	    the server since service startup."
    ::= { httpExtensionsEntry 64 }

httpExtTotalLockedErrors OBJECT-TYPE
    SYNTAX     Gauge32
    MAX-ACCESS read-only
    STATUS     current
    DESCRIPTION
	    "The number of '423 Locked' HTTP responses sent
	    by the server since service startup."
    ::= { httpExtensionsEntry 65 }

httpExtTotalMKCOLRequests OBJECT-TYPE
    SYNTAX     Gauge32
    MAX-ACCESS read-only
    STATUS     current
    DESCRIPTION
	    "The number of HTTP MKCOL requests received by
	    the server since service startup."
    ::= { httpExtensionsEntry 66 }

httpExtTotalMOVERequests OBJECT-TYPE
    SYNTAX     Gauge32
    MAX-ACCESS read-only
    STATUS     current
    DESCRIPTION
	    "The number of HTTP MOVE requests received by
	    the server since service startup."
    ::= { httpExtensionsEntry 67 }

httpExtTotalMethodFailureRspns OBJECT-TYPE
    SYNTAX     Gauge32
    MAX-ACCESS read-only
    STATUS     current
    DESCRIPTION
	    "The number of '424 Method Failure' HTTP
	    responses sent by the server since service
	    startup."
    ::= { httpExtensionsEntry 68 }

httpExtTotalMethodNotAllowedRspn OBJECT-TYPE
    SYNTAX     Gauge32
    MAX-ACCESS read-only
    STATUS     current
    DESCRIPTION
	    "The number of '405 Method Not Allowed' HTTP
	    responses sent by the server since service
	    startup."
    ::= { httpExtensionsEntry 69 }

httpExtTotalMovedTemporarilyRspn OBJECT-TYPE
    SYNTAX     Gauge32
    MAX-ACCESS read-only
    STATUS     current
    DESCRIPTION
	    "The number of '302 Moved Temporarily' HTTP
	    responses sent by the server since service
	    startup."
    ::= { httpExtensionsEntry 70 }

httpExtTotalMultiStatusRspns OBJECT-TYPE
    SYNTAX     Gauge32
    MAX-ACCESS read-only
    STATUS     current
    DESCRIPTION
	    "The number of '207 Multi-Status' HTTP
	    responses sent by the server since service
	    startup."
    ::= { httpExtensionsEntry 71 }

httpExtTotalNoContentRspns OBJECT-TYPE
    SYNTAX     Gauge32
    MAX-ACCESS read-only
    STATUS     current
    DESCRIPTION
	    "The number of '204 No Content' HTTP responses
	    sent by the server since service startup."
    ::= { httpExtensionsEntry 72 }

httpExtTotalNotAcceptableRspns OBJECT-TYPE
    SYNTAX     Gauge32
    MAX-ACCESS read-only
    STATUS     current
    DESCRIPTION
	    "The number of '406 Not Acceptable' HTTP
	    responses sent by the server since service
	    startup."
    ::= { httpExtensionsEntry 73 }

httpExtTotalNotFoundErrors OBJECT-TYPE
    SYNTAX     Gauge32
    MAX-ACCESS read-only
    STATUS     current
    DESCRIPTION
	    "The number of '404 Not Found' HTTP responses
	    sent by the server since service startup."
    ::= { httpExtensionsEntry 74 }

httpExtTotalNotImplementedRspns OBJECT-TYPE
    SYNTAX     Gauge32
    MAX-ACCESS read-only
    STATUS     current
    DESCRIPTION
	    "The number of '501 Not Implemented' HTTP
	    responses sent by the server since service
	    startup."
    ::= { httpExtensionsEntry 75 }

httpExtTotalOPTIONSRequests OBJECT-TYPE
    SYNTAX     Gauge32
    MAX-ACCESS read-only
    STATUS     current
    DESCRIPTION
	    "The number of HTTP OPTIONS requests received
	    by the server since service startup."
    ::= { httpExtensionsEntry 76 }

httpExtTotalOkRspns OBJECT-TYPE
    SYNTAX     Gauge32
    MAX-ACCESS read-only
    STATUS     current
    DESCRIPTION
	    "The number of '200 OK' HTTP responses sent by
	    the server since service startup."
    ::= { httpExtensionsEntry 77 }

httpExtTotalOtherRequests OBJECT-TYPE
    SYNTAX     Gauge32
    MAX-ACCESS read-only
    STATUS     current
    DESCRIPTION
	    "The number of HTTP requests using methods
	    other than OPTIONS, GET, HEAD, PUT, POST,
	    DELETE, COPY, MOVE, MKCOL, PROPFIND, PROPPATCH,
	    LOCK, UNLOCK, SEARCH, POLL, SUBSCRIBE,
	    UNSUBSCRIBE, BDELETE, BCOPY, BMOVE, BPROPPATCH
	    and BPROPFIND received by the server "
    ::= { httpExtensionsEntry 78 }

httpExtTotalPOLLRequests OBJECT-TYPE
    SYNTAX     Gauge32
    MAX-ACCESS read-only
    STATUS     current
    DESCRIPTION
	    "The number of HTTP POLL requests received by
	    the server since service startup."
    ::= { httpExtensionsEntry 79 }

httpExtTotalPOSTRequests OBJECT-TYPE
    SYNTAX     Gauge32
    MAX-ACCESS read-only
    STATUS     current
    DESCRIPTION
	    "The number of HTTP POST requests received by
	    the server since service startup."
    ::= { httpExtensionsEntry 80 }

httpExtTotalPROPFINDRequests OBJECT-TYPE
    SYNTAX     Gauge32
    MAX-ACCESS read-only
    STATUS     current
    DESCRIPTION
	    "The number of HTTP PROPFIND requests received
	    by the server since service startup."
    ::= { httpExtensionsEntry 81 }

httpExtTotalPROPPATCHRequests OBJECT-TYPE
    SYNTAX     Gauge32
    MAX-ACCESS read-only
    STATUS     current
    DESCRIPTION
	    "The number of HTTP PROPPATCH requests received
	    by the server since service startup."
    ::= { httpExtensionsEntry 82 }

httpExtTotalPUTRequests OBJECT-TYPE
    SYNTAX     Gauge32
    MAX-ACCESS read-only
    STATUS     current
    DESCRIPTION
	    "The number of HTTP PUT requests received by
	    the server since service startup."
    ::= { httpExtensionsEntry 83 }

httpExtTotalPreconditionFailRspn OBJECT-TYPE
    SYNTAX     Gauge32
    MAX-ACCESS read-only
    STATUS     current
    DESCRIPTION
	    "The number of '412 Precondition Failed' HTTP
	    responses sent by the server since service
	    startup."
    ::= { httpExtensionsEntry 84 }

httpExtTotalRedirectedRequests OBJECT-TYPE
    SYNTAX     Gauge32
    MAX-ACCESS read-only
    STATUS     current
    DESCRIPTION
	    "The number of HTTP requests redirected to
	    another URL by the server since service
	    startup."
    ::= { httpExtensionsEntry 85 }

httpExtTotalRedirectsFromBackEnd OBJECT-TYPE
    SYNTAX     Gauge32
    MAX-ACCESS read-only
    STATUS     current
    DESCRIPTION
	    "The number of redirect messages received by
	    the server since service startup."
    ::= { httpExtensionsEntry 86 }

httpExtTotalRequests OBJECT-TYPE
    SYNTAX     Gauge32
    MAX-ACCESS read-only
    STATUS     current
    DESCRIPTION
	    "The number of all HTTP requests received by
	    the server since service startup."
    ::= { httpExtensionsEntry 87 }

httpExtTotalSEARCHRequests OBJECT-TYPE
    SYNTAX     Gauge32
    MAX-ACCESS read-only
    STATUS     current
    DESCRIPTION
	    "The number of HTTP SEARCH requests received by
	    the server since service startup."
    ::= { httpExtensionsEntry 88 }

httpExtTotalSUBSCRIBERequests OBJECT-TYPE
    SYNTAX     Gauge32
    MAX-ACCESS read-only
    STATUS     current
    DESCRIPTION
	    "The number of HTTP SUBSCRIBE requests received
	    by the server since service startup."
    ::= { httpExtensionsEntry 89 }

httpExtTotalServerErrors OBJECT-TYPE
    SYNTAX     Gauge32
    MAX-ACCESS read-only
    STATUS     current
    DESCRIPTION
	    "The number of '500 Server Error' HTTP
	    responses sent by the server since service
	    startup."
    ::= { httpExtensionsEntry 90 }

httpExtTotalServiceUnavailRspns OBJECT-TYPE
    SYNTAX     Gauge32
    MAX-ACCESS read-only
    STATUS     current
    DESCRIPTION
	    "The number of '503 Service Unavailable' HTTP
	    responses sent by the server since service
	    startup."
    ::= { httpExtensionsEntry 91 }

httpExtTotalUNLOCKRequests OBJECT-TYPE
    SYNTAX     Gauge32
    MAX-ACCESS read-only
    STATUS     current
    DESCRIPTION
	    "The number of HTTP UNLOCK requests received by
	    the server since service startup."
    ::= { httpExtensionsEntry 92 }

httpExtTotalUNSUBSCRIBERequests OBJECT-TYPE
    SYNTAX     Gauge32
    MAX-ACCESS read-only
    STATUS     current
    DESCRIPTION
	    "The number of HTTP UNSUBSCRIBE requests
	    received by the server since service startup."
    ::= { httpExtensionsEntry 93 }

httpExtTotalUnauthorizedErrors OBJECT-TYPE
    SYNTAX     Gauge32
    MAX-ACCESS read-only
    STATUS     current
    DESCRIPTION
	    "The number of '401 Unauthorized' HTTP
	    responses sent by the server since service
	    startup."
    ::= { httpExtensionsEntry 94 }

httpExtTotalUnprocessEntityRspns OBJECT-TYPE
    SYNTAX     Gauge32
    MAX-ACCESS read-only
    STATUS     current
    DESCRIPTION
	    "The number of '422 Unprocessable Entity' HTTP
	    responses sent by the server since service
	    startup."
    ::= { httpExtensionsEntry 95 }

httpExtTotalUnsupportedMediaRspn OBJECT-TYPE
    SYNTAX     Gauge32
    MAX-ACCESS read-only
    STATUS     current
    DESCRIPTION
	    "The number of '415 Unsupported Media Type'
	    HTTP responses sent by the server since service
	    startup."
    ::= { httpExtensionsEntry 96 }

httpExtUNLOCKRequestsPerSec OBJECT-TYPE
    SYNTAX     Gauge32
    MAX-ACCESS read-only
    STATUS     current
    DESCRIPTION
	    "The rate at which the server receives HTTP
	    UNLOCK requests."
    ::= { httpExtensionsEntry 97 }

httpExtUNSUBSCRIBERequestsPerSec OBJECT-TYPE
    SYNTAX     Gauge32
    MAX-ACCESS read-only
    STATUS     current
    DESCRIPTION
	    "The rate at which the server receives HTTP
	    UNSUBSCRIBE requests."
    ::= { httpExtensionsEntry 98 }

httpExtUnauthorizedErrorsPerSec OBJECT-TYPE
    SYNTAX     Gauge32
    MAX-ACCESS read-only
    STATUS     current
    DESCRIPTION
	    "The rate at which the server is sending '401
	    Unauthorized' HTTP responses to clients."
    ::= { httpExtensionsEntry 99 }

httpExtUnprocessEntityRspnPerSec OBJECT-TYPE
    SYNTAX     Gauge32
    MAX-ACCESS read-only
    STATUS     current
    DESCRIPTION
	    "The rate at which the server is sending '422
	    Unprocessable Entity' HTTP responses to
	    clients."
    ::= { httpExtensionsEntry 100 }

httpExtUnsupportMediaRspnsPerSec OBJECT-TYPE
    SYNTAX     Gauge32
    MAX-ACCESS read-only
    STATUS     current
    DESCRIPTION
	    "The rate at which the server is sending '415
	    Unsupported Media Type' HTTP responses to
	    clients."
    ::= { httpExtensionsEntry 101 }

imap4Table OBJECT-TYPE
    SYNTAX     SEQUENCE OF IMAP4Entry
    MAX-ACCESS not-accessible
    STATUS     current
    DESCRIPTION
	    "A table containing performance information for
	    instances of 'MSExchangeIMAP4' objects."
    ::= { exchange 13 }

imap4Entry OBJECT-TYPE
    SYNTAX     IMAP4Entry
    MAX-ACCESS not-accessible
    STATUS     current
    DESCRIPTION
	    "Performance information for one particular
	    instance of 'MSExchangeIMAP4' object."
    INDEX      { imap4Instance }
    ::= { imap4Table 1 }

IMAP4Entry ::= SEQUENCE {
    imap4Instance InstanceName,
    imap4APPENDFailures Gauge32,
    imap4APPENDRate Gauge32,
    imap4APPENDTotal Gauge32,
    imap4AUTHENTICATEFailures Gauge32,
    imap4AUTHENTICATERate Gauge32,
    imap4AUTHENTICATETotal Gauge32,
    imap4CAPABILITYFailures Gauge32,
    imap4CAPABILITYRate Gauge32,
    imap4CAPABILITYTotal Gauge32,
    imap4CHECKFailures Gauge32,
    imap4CHECKRate Gauge32,
    imap4CHECKTotal Gauge32,
    imap4CLOSEFailures Gauge32,
    imap4CLOSERate Gauge32,
    imap4CLOSETotal Gauge32,
    imap4COPYFailures Gauge32,
    imap4COPYRate Gauge32,
    imap4COPYTotal Gauge32,
    imap4CREATEFailures Gauge32,
    imap4CREATERate Gauge32,
    imap4CREATETotal Gauge32,
    imap4ConnectionsCurrent Gauge32,
    imap4ConnectionsFailed Gauge32,
    imap4ConnectionsRejected Gauge32,
    imap4ConnectionsTotal Gauge32,
    imap4DELETEFailures Gauge32,
    imap4DELETERate Gauge32,
    imap4DELETETotal Gauge32,
    imap4EXAMINEFailures Gauge32,
    imap4EXAMINERate Gauge32,
    imap4EXAMINETotal Gauge32,
    imap4EXPUNGEFailures Gauge32,
    imap4EXPUNGERate Gauge32,
    imap4EXPUNGETotal Gauge32,
    imap4FETCHFailures Gauge32,
    imap4FETCHRate Gauge32,
    imap4FETCHTotal Gauge32,
    imap4IDLEFailures Gauge32,
    imap4IDLERate Gauge32,
    imap4IDLETotal Gauge32,
    imap4InvalidCommands Gauge32,
    imap4InvalidCommandsRate Gauge32,
    imap4LISTFailures Gauge32,
    imap4LISTRate Gauge32,
    imap4LISTTotal Gauge32,
    imap4LOGINFailures Gauge32,
    imap4LOGINRate Gauge32,
    imap4LOGINTotal Gauge32,
    imap4LOGOUTFailures Gauge32,
    imap4LOGOUTRate Gauge32,
    imap4LOGOUTTotal Gauge32,
    imap4LSUBFailures Gauge32,
    imap4LSUBRate Gauge32,
    imap4LSUBTotal Gauge32,
    imap4NAMESPACEFailures Gauge32,
    imap4NAMESPACERate Gauge32,
    imap4NAMESPACETotal Gauge32,
    imap4NOOPFailures Gauge32,
    imap4NOOPRate Gauge32,
    imap4NOOPTotal Gauge32,
    imap4RENAMEFailures Gauge32,
    imap4RENAMERate Gauge32,
    imap4RENAMETotal Gauge32,
    imap4RLISTFailures Gauge32,
    imap4RLISTRate Gauge32,
    imap4RLISTTotal Gauge32,
    imap4RLSUBFailures Gauge32,
    imap4RLSUBRate Gauge32,
    imap4RLSUBTotal Gauge32,
    imap4SEARCHFailures Gauge32,
    imap4SEARCHRate Gauge32,
    imap4SEARCHTotal Gauge32,
    imap4SELECTFailures Gauge32,
    imap4SELECTRate Gauge32,
    imap4SELECTTotal Gauge32,
    imap4STATUSFailures Gauge32,
    imap4STATUSRate Gauge32,
    imap4STATUSTotal Gauge32,
    imap4STOREFailures Gauge32,
    imap4STORERate Gauge32,
    imap4STORETotal Gauge32,
    imap4SUBSCRIBEFailures Gauge32,
    imap4SUBSCRIBERate Gauge32,
    imap4SUBSCRIBETotal Gauge32,
    imap4UIDFailures Gauge32,
    imap4UIDRate Gauge32,
    imap4UIDTotal Gauge32,
    imap4UNSUBSCRIBEFailures Gauge32,
    imap4UNSUBSCRIBERate Gauge32,
    imap4UNSUBSCRIBETotal Gauge32
}

imap4Instance OBJECT-TYPE
    SYNTAX     InstanceName
    MAX-ACCESS read-only
    STATUS     current
    DESCRIPTION
	    "Instance name."
    ::= { imap4Entry 1 }

imap4APPENDFailures OBJECT-TYPE
    SYNTAX     Gauge32
    MAX-ACCESS read-only
    STATUS     current
    DESCRIPTION
	    "Total number of APPEND failures since startup"
    ::= { imap4Entry 2 }

imap4APPENDRate OBJECT-TYPE
    SYNTAX     Gauge32
    MAX-ACCESS read-only
    STATUS     current
    DESCRIPTION
	    "Number of APPEND commands per sec"
    ::= { imap4Entry 3 }

imap4APPENDTotal OBJECT-TYPE
    SYNTAX     Gauge32
    MAX-ACCESS read-only
    STATUS     current
    DESCRIPTION
	    "Total number of APPEND commands received since
	    startup"
    ::= { imap4Entry 4 }

imap4AUTHENTICATEFailures OBJECT-TYPE
    SYNTAX     Gauge32
    MAX-ACCESS read-only
    STATUS     current
    DESCRIPTION
	    "Total number of AUTHENTICATE failures since
	    startup"
    ::= { imap4Entry 5 }

imap4AUTHENTICATERate OBJECT-TYPE
    SYNTAX     Gauge32
    MAX-ACCESS read-only
    STATUS     current
    DESCRIPTION
	    "Number of AUTHENTICATE commands per sec"
    ::= { imap4Entry 6 }

imap4AUTHENTICATETotal OBJECT-TYPE
    SYNTAX     Gauge32
    MAX-ACCESS read-only
    STATUS     current
    DESCRIPTION
	    "Total number of AUTHENTICATE commands received
	    since startup"
    ::= { imap4Entry 7 }

imap4CAPABILITYFailures OBJECT-TYPE
    SYNTAX     Gauge32
    MAX-ACCESS read-only
    STATUS     current
    DESCRIPTION
	    "Total number of CAPABILITY failures since
	    startup"
    ::= { imap4Entry 8 }

imap4CAPABILITYRate OBJECT-TYPE
    SYNTAX     Gauge32
    MAX-ACCESS read-only
    STATUS     current
    DESCRIPTION
	    "Number of CAPABILITY commands per sec"
    ::= { imap4Entry 9 }

imap4CAPABILITYTotal OBJECT-TYPE
    SYNTAX     Gauge32
    MAX-ACCESS read-only
    STATUS     current
    DESCRIPTION
	    "Total number of CAPABILITY commands received
	    since startup"
    ::= { imap4Entry 10 }

imap4CHECKFailures OBJECT-TYPE
    SYNTAX     Gauge32
    MAX-ACCESS read-only
    STATUS     current
    DESCRIPTION
	    "Total number of CHECK failures since startup"
    ::= { imap4Entry 11 }

imap4CHECKRate OBJECT-TYPE
    SYNTAX     Gauge32
    MAX-ACCESS read-only
    STATUS     current
    DESCRIPTION
	    "Number of CHECK commands per sec"
    ::= { imap4Entry 12 }

imap4CHECKTotal OBJECT-TYPE
    SYNTAX     Gauge32
    MAX-ACCESS read-only
    STATUS     current
    DESCRIPTION
	    "Total number of CHECK commands received since
	    startup"
    ::= { imap4Entry 13 }

imap4CLOSEFailures OBJECT-TYPE
    SYNTAX     Gauge32
    MAX-ACCESS read-only
    STATUS     current
    DESCRIPTION
	    "Total number of CLOSE failures since startup"
    ::= { imap4Entry 14 }

imap4CLOSERate OBJECT-TYPE
    SYNTAX     Gauge32
    MAX-ACCESS read-only
    STATUS     current
    DESCRIPTION
	    "Number of CLOSE commands per sec"
    ::= { imap4Entry 15 }

imap4CLOSETotal OBJECT-TYPE
    SYNTAX     Gauge32
    MAX-ACCESS read-only
    STATUS     current
    DESCRIPTION
	    "Total number of CLOSE commands received since
	    startup"
    ::= { imap4Entry 16 }

imap4COPYFailures OBJECT-TYPE
    SYNTAX     Gauge32
    MAX-ACCESS read-only
    STATUS     current
    DESCRIPTION
	    "Total number of COPY failures since startup"
    ::= { imap4Entry 17 }

imap4COPYRate OBJECT-TYPE
    SYNTAX     Gauge32
    MAX-ACCESS read-only
    STATUS     current
    DESCRIPTION
	    "Number of COPY commands per sec"
    ::= { imap4Entry 18 }

imap4COPYTotal OBJECT-TYPE
    SYNTAX     Gauge32
    MAX-ACCESS read-only
    STATUS     current
    DESCRIPTION
	    "Total number of COPY commands received since
	    startup"
    ::= { imap4Entry 19 }

imap4CREATEFailures OBJECT-TYPE
    SYNTAX     Gauge32
    MAX-ACCESS read-only
    STATUS     current
    DESCRIPTION
	    "Total number of CREATE failures since startup"
    ::= { imap4Entry 20 }

imap4CREATERate OBJECT-TYPE
    SYNTAX     Gauge32
    MAX-ACCESS read-only
    STATUS     current
    DESCRIPTION
	    "Number of CREATE commands per sec"
    ::= { imap4Entry 21 }

imap4CREATETotal OBJECT-TYPE
    SYNTAX     Gauge32
    MAX-ACCESS read-only
    STATUS     current
    DESCRIPTION
	    "Total number of CREATE commands received since
	    startup"
    ::= { imap4Entry 22 }

imap4ConnectionsCurrent OBJECT-TYPE
    SYNTAX     Gauge32
    MAX-ACCESS read-only
    STATUS     current
    DESCRIPTION
	    "Total number of current connections"
    ::= { imap4Entry 23 }

imap4ConnectionsFailed OBJECT-TYPE
    SYNTAX     Gauge32
    MAX-ACCESS read-only
    STATUS     current
    DESCRIPTION
	    "Total number of failed connections since
	    startup"
    ::= { imap4Entry 24 }

imap4ConnectionsRejected OBJECT-TYPE
    SYNTAX     Gauge32
    MAX-ACCESS read-only
    STATUS     current
    DESCRIPTION
	    "Total number of rejected connections since
	    startup"
    ::= { imap4Entry 25 }

imap4ConnectionsTotal OBJECT-TYPE
    SYNTAX     Gauge32
    MAX-ACCESS read-only
    STATUS     current
    DESCRIPTION
	    "Total number of connections since startup"
    ::= { imap4Entry 26 }

imap4DELETEFailures OBJECT-TYPE
    SYNTAX     Gauge32
    MAX-ACCESS read-only
    STATUS     current
    DESCRIPTION
	    "Total number of DELETE failures since startup"
    ::= { imap4Entry 27 }

imap4DELETERate OBJECT-TYPE
    SYNTAX     Gauge32
    MAX-ACCESS read-only
    STATUS     current
    DESCRIPTION
	    "Number of DELETE commands per sec"
    ::= { imap4Entry 28 }

imap4DELETETotal OBJECT-TYPE
    SYNTAX     Gauge32
    MAX-ACCESS read-only
    STATUS     current
    DESCRIPTION
	    "Total number of DELETE commands received since
	    startup"
    ::= { imap4Entry 29 }

imap4EXAMINEFailures OBJECT-TYPE
    SYNTAX     Gauge32
    MAX-ACCESS read-only
    STATUS     current
    DESCRIPTION
	    "Total number of EXAMINE failures since
	    startup"
    ::= { imap4Entry 30 }

imap4EXAMINERate OBJECT-TYPE
    SYNTAX     Gauge32
    MAX-ACCESS read-only
    STATUS     current
    DESCRIPTION
	    "Number of EXAMINE commands per sec"
    ::= { imap4Entry 31 }

imap4EXAMINETotal OBJECT-TYPE
    SYNTAX     Gauge32
    MAX-ACCESS read-only
    STATUS     current
    DESCRIPTION
	    "Total number of EXAMINE commands received
	    since startup"
    ::= { imap4Entry 32 }

imap4EXPUNGEFailures OBJECT-TYPE
    SYNTAX     Gauge32
    MAX-ACCESS read-only
    STATUS     current
    DESCRIPTION
	    "Total number of EXPUNGE failures since
	    startup"
    ::= { imap4Entry 33 }

imap4EXPUNGERate OBJECT-TYPE
    SYNTAX     Gauge32
    MAX-ACCESS read-only
    STATUS     current
    DESCRIPTION
	    "Number of EXPUNGE commands per sec"
    ::= { imap4Entry 34 }

imap4EXPUNGETotal OBJECT-TYPE
    SYNTAX     Gauge32
    MAX-ACCESS read-only
    STATUS     current
    DESCRIPTION
	    "Total number of EXPUNGE commands received
	    since startup"
    ::= { imap4Entry 35 }

imap4FETCHFailures OBJECT-TYPE
    SYNTAX     Gauge32
    MAX-ACCESS read-only
    STATUS     current
    DESCRIPTION
	    "Total number of FETCH failures since startup"
    ::= { imap4Entry 36 }

imap4FETCHRate OBJECT-TYPE
    SYNTAX     Gauge32
    MAX-ACCESS read-only
    STATUS     current
    DESCRIPTION
	    "Number of FETCH commands per sec"
    ::= { imap4Entry 37 }

imap4FETCHTotal OBJECT-TYPE
    SYNTAX     Gauge32
    MAX-ACCESS read-only
    STATUS     current
    DESCRIPTION
	    "Total number of FETCH commands received since
	    startup"
    ::= { imap4Entry 38 }

imap4IDLEFailures OBJECT-TYPE
    SYNTAX     Gauge32
    MAX-ACCESS read-only
    STATUS     current
    DESCRIPTION
	    "Total number of IDLE failures since startup"
    ::= { imap4Entry 39 }

imap4IDLERate OBJECT-TYPE
    SYNTAX     Gauge32
    MAX-ACCESS read-only
    STATUS     current
    DESCRIPTION
	    "Number of IDLE commands per sec"
    ::= { imap4Entry 40 }

imap4IDLETotal OBJECT-TYPE
    SYNTAX     Gauge32
    MAX-ACCESS read-only
    STATUS     current
    DESCRIPTION
	    "Total number of IDLE commands received since
	    startup"
    ::= { imap4Entry 41 }

imap4InvalidCommands OBJECT-TYPE
    SYNTAX     Gauge32
    MAX-ACCESS read-only
    STATUS     current
    DESCRIPTION
	    "Total number of invalid commands since
	    startup"
    ::= { imap4Entry 42 }

imap4InvalidCommandsRate OBJECT-TYPE
    SYNTAX     Gauge32
    MAX-ACCESS read-only
    STATUS     current
    DESCRIPTION
	    "Number of invalid commands per second"
    ::= { imap4Entry 43 }

imap4LISTFailures OBJECT-TYPE
    SYNTAX     Gauge32
    MAX-ACCESS read-only
    STATUS     current
    DESCRIPTION
	    "Total number of LIST failures since startup"
    ::= { imap4Entry 44 }

imap4LISTRate OBJECT-TYPE
    SYNTAX     Gauge32
    MAX-ACCESS read-only
    STATUS     current
    DESCRIPTION
	    "Number of LIST commands per sec"
    ::= { imap4Entry 45 }

imap4LISTTotal OBJECT-TYPE
    SYNTAX     Gauge32
    MAX-ACCESS read-only
    STATUS     current
    DESCRIPTION
	    "Total number of LIST commands received since
	    startup"
    ::= { imap4Entry 46 }

imap4LOGINFailures OBJECT-TYPE
    SYNTAX     Gauge32
    MAX-ACCESS read-only
    STATUS     current
    DESCRIPTION
	    "Total number of LOGIN failures since startup"
    ::= { imap4Entry 47 }

imap4LOGINRate OBJECT-TYPE
    SYNTAX     Gauge32
    MAX-ACCESS read-only
    STATUS     current
    DESCRIPTION
	    "Number of LOGIN commands per sec"
    ::= { imap4Entry 48 }

imap4LOGINTotal OBJECT-TYPE
    SYNTAX     Gauge32
    MAX-ACCESS read-only
    STATUS     current
    DESCRIPTION
	    "Total number of LOGIN commands received since
	    startup"
    ::= { imap4Entry 49 }

imap4LOGOUTFailures OBJECT-TYPE
    SYNTAX     Gauge32
    MAX-ACCESS read-only
    STATUS     current
    DESCRIPTION
	    "Total number of LOGOUT failures since startup"
    ::= { imap4Entry 50 }

imap4LOGOUTRate OBJECT-TYPE
    SYNTAX     Gauge32
    MAX-ACCESS read-only
    STATUS     current
    DESCRIPTION
	    "Number of LOGOUT commands per sec"
    ::= { imap4Entry 51 }

imap4LOGOUTTotal OBJECT-TYPE
    SYNTAX     Gauge32
    MAX-ACCESS read-only
    STATUS     current
    DESCRIPTION
	    "Total number of LOGOUT commands received since
	    startup"
    ::= { imap4Entry 52 }

imap4LSUBFailures OBJECT-TYPE
    SYNTAX     Gauge32
    MAX-ACCESS read-only
    STATUS     current
    DESCRIPTION
	    "Total number of LSUB failures since startup"
    ::= { imap4Entry 53 }

imap4LSUBRate OBJECT-TYPE
    SYNTAX     Gauge32
    MAX-ACCESS read-only
    STATUS     current
    DESCRIPTION
	    "Number of LSUB commands per sec"
    ::= { imap4Entry 54 }

imap4LSUBTotal OBJECT-TYPE
    SYNTAX     Gauge32
    MAX-ACCESS read-only
    STATUS     current
    DESCRIPTION
	    "Total number of LSUB commands received since
	    startup"
    ::= { imap4Entry 55 }

imap4NAMESPACEFailures OBJECT-TYPE
    SYNTAX     Gauge32
    MAX-ACCESS read-only
    STATUS     current
    DESCRIPTION
	    "Total number of NAMESPACE failures since
	    startup"
    ::= { imap4Entry 56 }

imap4NAMESPACERate OBJECT-TYPE
    SYNTAX     Gauge32
    MAX-ACCESS read-only
    STATUS     current
    DESCRIPTION
	    "Number of NAMESPACE commands per sec"
    ::= { imap4Entry 57 }

imap4NAMESPACETotal OBJECT-TYPE
    SYNTAX     Gauge32
    MAX-ACCESS read-only
    STATUS     current
    DESCRIPTION
	    "Total number of NAMESPACE commands received
	    since startup"
    ::= { imap4Entry 58 }

imap4NOOPFailures OBJECT-TYPE
    SYNTAX     Gauge32
    MAX-ACCESS read-only
    STATUS     current
    DESCRIPTION
	    "Total number of NOOP failures since startup"
    ::= { imap4Entry 59 }

imap4NOOPRate OBJECT-TYPE
    SYNTAX     Gauge32
    MAX-ACCESS read-only
    STATUS     current
    DESCRIPTION
	    "Number of NOOP commands per sec"
    ::= { imap4Entry 60 }

imap4NOOPTotal OBJECT-TYPE
    SYNTAX     Gauge32
    MAX-ACCESS read-only
    STATUS     current
    DESCRIPTION
	    "Total number of NOOP commands received since
	    startup"
    ::= { imap4Entry 61 }

imap4RENAMEFailures OBJECT-TYPE
    SYNTAX     Gauge32
    MAX-ACCESS read-only
    STATUS     current
    DESCRIPTION
	    "Total number of RENAME failures since startup"
    ::= { imap4Entry 62 }

imap4RENAMERate OBJECT-TYPE
    SYNTAX     Gauge32
    MAX-ACCESS read-only
    STATUS     current
    DESCRIPTION
	    "Number of RENAME commands per sec"
    ::= { imap4Entry 63 }

imap4RENAMETotal OBJECT-TYPE
    SYNTAX     Gauge32
    MAX-ACCESS read-only
    STATUS     current
    DESCRIPTION
	    "Total number of RENAME commands received since
	    startup"
    ::= { imap4Entry 64 }

imap4RLISTFailures OBJECT-TYPE
    SYNTAX     Gauge32
    MAX-ACCESS read-only
    STATUS     current
    DESCRIPTION
	    "Total number of RLIST failures since startup"
    ::= { imap4Entry 65 }

imap4RLISTRate OBJECT-TYPE
    SYNTAX     Gauge32
    MAX-ACCESS read-only
    STATUS     current
    DESCRIPTION
	    "Number of RLIST commands per sec"
    ::= { imap4Entry 66 }

imap4RLISTTotal OBJECT-TYPE
    SYNTAX     Gauge32
    MAX-ACCESS read-only
    STATUS     current
    DESCRIPTION
	    "Total number of RLIST commands received since
	    startup"
    ::= { imap4Entry 67 }

imap4RLSUBFailures OBJECT-TYPE
    SYNTAX     Gauge32
    MAX-ACCESS read-only
    STATUS     current
    DESCRIPTION
	    "Total number of RLSUB failures since startup"
    ::= { imap4Entry 68 }

imap4RLSUBRate OBJECT-TYPE
    SYNTAX     Gauge32
    MAX-ACCESS read-only
    STATUS     current
    DESCRIPTION
	    "Number of RLSUB commands per sec"
    ::= { imap4Entry 69 }

imap4RLSUBTotal OBJECT-TYPE
    SYNTAX     Gauge32
    MAX-ACCESS read-only
    STATUS     current
    DESCRIPTION
	    "Total number of RLSUB commands received since
	    startup"
    ::= { imap4Entry 70 }

imap4SEARCHFailures OBJECT-TYPE
    SYNTAX     Gauge32
    MAX-ACCESS read-only
    STATUS     current
    DESCRIPTION
	    "Total number of SEARCH failures since startup"
    ::= { imap4Entry 71 }

imap4SEARCHRate OBJECT-TYPE
    SYNTAX     Gauge32
    MAX-ACCESS read-only
    STATUS     current
    DESCRIPTION
	    "Number of SEARCH commands per sec"
    ::= { imap4Entry 72 }

imap4SEARCHTotal OBJECT-TYPE
    SYNTAX     Gauge32
    MAX-ACCESS read-only
    STATUS     current
    DESCRIPTION
	    "Total number of SEARCH commands received since
	    startup"
    ::= { imap4Entry 73 }

imap4SELECTFailures OBJECT-TYPE
    SYNTAX     Gauge32
    MAX-ACCESS read-only
    STATUS     current
    DESCRIPTION
	    "Total number of SELECT failures since startup"
    ::= { imap4Entry 74 }

imap4SELECTRate OBJECT-TYPE
    SYNTAX     Gauge32
    MAX-ACCESS read-only
    STATUS     current
    DESCRIPTION
	    "Number of SELECT commands per sec"
    ::= { imap4Entry 75 }

imap4SELECTTotal OBJECT-TYPE
    SYNTAX     Gauge32
    MAX-ACCESS read-only
    STATUS     current
    DESCRIPTION
	    "Total number of SELECT commands received since
	    startup"
    ::= { imap4Entry 76 }

imap4STATUSFailures OBJECT-TYPE
    SYNTAX     Gauge32
    MAX-ACCESS read-only
    STATUS     current
    DESCRIPTION
	    "Total number of STATUS failures since startup"
    ::= { imap4Entry 77 }

imap4STATUSRate OBJECT-TYPE
    SYNTAX     Gauge32
    MAX-ACCESS read-only
    STATUS     current
    DESCRIPTION
	    "Number of STATUS commands per sec"
    ::= { imap4Entry 78 }

imap4STATUSTotal OBJECT-TYPE
    SYNTAX     Gauge32
    MAX-ACCESS read-only
    STATUS     current
    DESCRIPTION
	    "Total number of STATUS commands received since
	    startup"
    ::= { imap4Entry 79 }

imap4STOREFailures OBJECT-TYPE
    SYNTAX     Gauge32
    MAX-ACCESS read-only
    STATUS     current
    DESCRIPTION
	    "Total number of STORE failures since startup"
    ::= { imap4Entry 80 }

imap4STORERate OBJECT-TYPE
    SYNTAX     Gauge32
    MAX-ACCESS read-only
    STATUS     current
    DESCRIPTION
	    "Number of STORE commands per sec"
    ::= { imap4Entry 81 }

imap4STORETotal OBJECT-TYPE
    SYNTAX     Gauge32
    MAX-ACCESS read-only
    STATUS     current
    DESCRIPTION
	    "Total number of STORE commands received since
	    startup"
    ::= { imap4Entry 82 }

imap4SUBSCRIBEFailures OBJECT-TYPE
    SYNTAX     Gauge32
    MAX-ACCESS read-only
    STATUS     current
    DESCRIPTION
	    "Total number of SUBSCRIBE failures since
	    startup"
    ::= { imap4Entry 83 }

imap4SUBSCRIBERate OBJECT-TYPE
    SYNTAX     Gauge32
    MAX-ACCESS read-only
    STATUS     current
    DESCRIPTION
	    "Number of SUBSCRIBE commands per sec"
    ::= { imap4Entry 84 }

imap4SUBSCRIBETotal OBJECT-TYPE
    SYNTAX     Gauge32
    MAX-ACCESS read-only
    STATUS     current
    DESCRIPTION
	    "Total number of SUBSCRIBE commands received
	    since startup"
    ::= { imap4Entry 85 }

imap4UIDFailures OBJECT-TYPE
    SYNTAX     Gauge32
    MAX-ACCESS read-only
    STATUS     current
    DESCRIPTION
	    "Total number of UID failures since startup"
    ::= { imap4Entry 86 }

imap4UIDRate OBJECT-TYPE
    SYNTAX     Gauge32
    MAX-ACCESS read-only
    STATUS     current
    DESCRIPTION
	    "Number of UID commands per sec"
    ::= { imap4Entry 87 }

imap4UIDTotal OBJECT-TYPE
    SYNTAX     Gauge32
    MAX-ACCESS read-only
    STATUS     current
    DESCRIPTION
	    "Total number of UID commands received since
	    startup"
    ::= { imap4Entry 88 }

imap4UNSUBSCRIBEFailures OBJECT-TYPE
    SYNTAX     Gauge32
    MAX-ACCESS read-only
    STATUS     current
    DESCRIPTION
	    "Total number of UNSUBSCRIBE failures since
	    startup"
    ::= { imap4Entry 89 }

imap4UNSUBSCRIBERate OBJECT-TYPE
    SYNTAX     Gauge32
    MAX-ACCESS read-only
    STATUS     current
    DESCRIPTION
	    "Number of UNSUBSCRIBE commands per sec"
    ::= { imap4Entry 90 }

imap4UNSUBSCRIBETotal OBJECT-TYPE
    SYNTAX     Gauge32
    MAX-ACCESS read-only
    STATUS     current
    DESCRIPTION
	    "Total number of UNSUBSCRIBE commands received
	    since startup"
    ::= { imap4Entry 91 }

informationStore OBJECT-IDENTITY
    STATUS     current
    DESCRIPTION
	    "Microsoft Exchange Information Store
	    performance data"
    ::= { exchange 14 }

isACLUpgradeCompletedUpgrades OBJECT-TYPE
    SYNTAX     Gauge32
    MAX-ACCESS read-only
    STATUS     current
    DESCRIPTION
	    "The total number of ACL upgrades that have
	    fully completed; a fully upgraded folder will
	    not need another ACL upgrade."
    ::= { informationStore 1 }

isACLUpgradeFailures OBJECT-TYPE
    SYNTAX     Gauge32
    MAX-ACCESS read-only
    STATUS     current
    DESCRIPTION
	    "The total number of ACL upgrades that have
	    failed; a failure to upgrade a folder leaves
	    the folder with default rights only."
    ::= { informationStore 2 }

isACLUpgradeHitsRetryList OBJECT-TYPE
    SYNTAX     Gauge32
    MAX-ACCESS read-only
    STATUS     current
    DESCRIPTION
	    "The total number of ACL upgrades that were not
	    attempted based on the retry list."
    ::= { informationStore 3 }

isACLUpgradePartialUpgrades OBJECT-TYPE
    SYNTAX     Gauge32
    MAX-ACCESS read-only
    STATUS     current
    DESCRIPTION
	    "The total number of ACL upgrades that have not
	    fully completed; a partially upgraded folder
	    will still have to go through the ACL upgrade
	    process."
    ::= { informationStore 4 }

isACLUpgradeTimesAttempted OBJECT-TYPE
    SYNTAX     Gauge32
    MAX-ACCESS read-only
    STATUS     current
    DESCRIPTION
	    "The total number of ACL upgrades attempted."
    ::= { informationStore 5 }

isActiveAnonymousUserCount OBJECT-TYPE
    SYNTAX     Gauge32
    MAX-ACCESS read-only
    STATUS     current
    DESCRIPTION
	    "Number of active users."
    ::= { informationStore 6 }

isActiveConnectionCount OBJECT-TYPE
    SYNTAX     Gauge32
    MAX-ACCESS read-only
    STATUS     current
    DESCRIPTION
	    "Number of connections that have shown some
	    activity in the last 10 minutes."
    ::= { informationStore 7 }

isActiveUserCount OBJECT-TYPE
    SYNTAX     Gauge32
    MAX-ACCESS read-only
    STATUS     current
    DESCRIPTION
	    "Number of user connections that have shown
	    some activity in the last 10 minutes."
    ::= { informationStore 8 }

isAnonymousUserCount OBJECT-TYPE
    SYNTAX     Gauge32
    MAX-ACCESS read-only
    STATUS     current
    DESCRIPTION
	    "Anonymous User Count is the number of
	    anonymous users connected to the information
	    store."
    ::= { informationStore 9 }

isAppointmentInstanceCreateRate OBJECT-TYPE
    SYNTAX     Gauge32
    MAX-ACCESS read-only
    STATUS     current
    DESCRIPTION
	    "Number of appointment instances created/sec"
    ::= { informationStore 10 }

isAppointmentInstanceDeleteRate OBJECT-TYPE
    SYNTAX     Gauge32
    MAX-ACCESS read-only
    STATUS     current
    DESCRIPTION
	    "Number of appointment instances deleted/sec"
    ::= { informationStore 11 }

isAppointmentInstancesCreated OBJECT-TYPE
    SYNTAX     Gauge32
    MAX-ACCESS read-only
    STATUS     current
    DESCRIPTION
	    "Number of appointment instances created"
    ::= { informationStore 12 }

isAppointmentInstancesDeleted OBJECT-TYPE
    SYNTAX     Gauge32
    MAX-ACCESS read-only
    STATUS     current
    DESCRIPTION
	    "Number of appointment instances deleted"
    ::= { informationStore 13 }

isBackgroundExpansionQueueLength OBJECT-TYPE
    SYNTAX     Gauge32
    MAX-ACCESS read-only
    STATUS     current
    DESCRIPTION
	    "Number of calendars that are queued for
	    background expansion"
    ::= { informationStore 14 }

isClientLatency10SecRPCs OBJECT-TYPE
    SYNTAX     Gauge32
    MAX-ACCESS read-only
    STATUS     current
    DESCRIPTION
	    "The client-reported number of successful RPCs
	    with latencies > 10 seconds."
    ::= { informationStore 15 }

isClientLatency2SecRPCs OBJECT-TYPE
    SYNTAX     Gauge32
    MAX-ACCESS read-only
    STATUS     current
    DESCRIPTION
	    "The client-reported number of successful RPCs
	    with latencies > 2 seconds."
    ::= { informationStore 16 }

isClientLatency5SecRPCs OBJECT-TYPE
    SYNTAX     Gauge32
    MAX-ACCESS read-only
    STATUS     current
    DESCRIPTION
	    "The client-reported number of successful RPCs
	    with latencies > 5 seconds."
    ::= { informationStore 17 }

isClientRPCsFail OBJECT-TYPE
    SYNTAX     Gauge32
    MAX-ACCESS read-only
    STATUS     current
    DESCRIPTION
	    "The client-reported number of failed RPCs
	    (since the store was started)."
    ::= { informationStore 18 }

isClientRPCsFailPerSec OBJECT-TYPE
    SYNTAX     Gauge32
    MAX-ACCESS read-only
    STATUS     current
    DESCRIPTION
	    "The client-reported rate of failed RPCs (since
	    the store was started)."
    ::= { informationStore 19 }

isClientRPCsFailAccessDeny OBJECT-TYPE
    SYNTAX     Gauge32
    MAX-ACCESS read-only
    STATUS     current
    DESCRIPTION
	    "The client-reported number of failed RPCs
	    (since the store was started) due to the Access
	    Denied RPC error."
    ::= { informationStore 20 }

isClientRPCsFailAccessDenyPerSec OBJECT-TYPE
    SYNTAX     Gauge32
    MAX-ACCESS read-only
    STATUS     current
    DESCRIPTION
	    "The client-reported rate of failed RPCs (since
	    the store was started) due to the Access Denied
	    RPC error."
    ::= { informationStore 21 }

isClientRPCsFailAllOtherErrs OBJECT-TYPE
    SYNTAX     Gauge32
    MAX-ACCESS read-only
    STATUS     current
    DESCRIPTION
	    "The client-reported number of failed RPCs
	    (since the store was started) due to all other
	    RPC errors."
    ::= { informationStore 22 }

isClientRPCsFailOtherErrsPerSec OBJECT-TYPE
    SYNTAX     Gauge32
    MAX-ACCESS read-only
    STATUS     current
    DESCRIPTION
	    "The client-reported rate of failed RPCs (since
	    the store was started) due to all other RPC
	    errors."
    ::= { informationStore 23 }

isClientRPCsFailCallCancel OBJECT-TYPE
    SYNTAX     Gauge32
    MAX-ACCESS read-only
    STATUS     current
    DESCRIPTION
	    "The client-reported number of failed RPCs
	    (since the store was started) due to the Call
	    Cancelled RPC error."
    ::= { informationStore 24 }

isClientRPCsFailCallCancelPerSec OBJECT-TYPE
    SYNTAX     Gauge32
    MAX-ACCESS read-only
    STATUS     current
    DESCRIPTION
	    "The client-reported rate of failed RPCs (since
	    the store was started) due to the Call
	    Cancelled RPC error."
    ::= { informationStore 25 }

isClientRPCsFailCallFail OBJECT-TYPE
    SYNTAX     Gauge32
    MAX-ACCESS read-only
    STATUS     current
    DESCRIPTION
	    "The client-reported number of failed RPCs
	    (since the store was started) due to the Call
	    Failed RPC error."
    ::= { informationStore 26 }

isClientRPCsFailCallFailPerSec OBJECT-TYPE
    SYNTAX     Gauge32
    MAX-ACCESS read-only
    STATUS     current
    DESCRIPTION
	    "The client-reported rate of failed RPCs (since
	    the store was started) due to the Call Failed
	    RPC error."
    ::= { informationStore 27 }

isClientRPCsFailSrvrBusy OBJECT-TYPE
    SYNTAX     Gauge32
    MAX-ACCESS read-only
    STATUS     current
    DESCRIPTION
	    "The client-reported number of failed RPCs
	    (since the store was started) due to the Server
	    Too Busy RPC error."
    ::= { informationStore 28 }

isClientRPCsFailSrvrBusyPerSec OBJECT-TYPE
    SYNTAX     Gauge32
    MAX-ACCESS read-only
    STATUS     current
    DESCRIPTION
	    "The client-reported rate of failed RPCs (since
	    the store was started) due to the Server Too
	    Busy RPC error."
    ::= { informationStore 29 }

isClientRPCsFailSrvrUnavail OBJECT-TYPE
    SYNTAX     Gauge32
    MAX-ACCESS read-only
    STATUS     current
    DESCRIPTION
	    "The client-reported number of failed RPCs
	    (since the store was started) due to the Server
	    Unavailable RPC error."
    ::= { informationStore 30 }

isClientRPCFailSrvrUnavailPerSec OBJECT-TYPE
    SYNTAX     Gauge32
    MAX-ACCESS read-only
    STATUS     current
    DESCRIPTION
	    "The client-reported rate of failed RPCs (since
	    the store was started) due to the Server
	    Unavailable RPC error."
    ::= { informationStore 31 }

isClientRPCsAttempted OBJECT-TYPE
    SYNTAX     Gauge32
    MAX-ACCESS read-only
    STATUS     current
    DESCRIPTION
	    "The client-reported total number of RPCs
	    attempted by the users (since the store was
	    started)."
    ::= { informationStore 32 }

isClientRPCsAttemptedPerSec OBJECT-TYPE
    SYNTAX     Gauge32
    MAX-ACCESS read-only
    STATUS     current
    DESCRIPTION
	    "Client The client-reported rate of RPCs
	    attempted by the users (since the store was
	    started)."
    ::= { informationStore 33 }

isClientRPCsSucceeded OBJECT-TYPE
    SYNTAX     Gauge32
    MAX-ACCESS read-only
    STATUS     current
    DESCRIPTION
	    "The client-reported total number of successful
	    RPCs (since the store was started)."
    ::= { informationStore 34 }

isClientRPCsSucceededPerSec OBJECT-TYPE
    SYNTAX     Gauge32
    MAX-ACCESS read-only
    STATUS     current
    DESCRIPTION
	    "The client-reported rate of successful RPCs
	    (since the store was started)."
    ::= { informationStore 35 }

isClientTotalReportedLatency OBJECT-TYPE
    SYNTAX     Gauge32
    MAX-ACCESS read-only
    STATUS     current
    DESCRIPTION
	    "The client-reported total latency (in seconds)
	    for all RPCs (since the store was started)."
    ::= { informationStore 36 }

isConnectionCount OBJECT-TYPE
    SYNTAX     Gauge32
    MAX-ACCESS read-only
    STATUS     current
    DESCRIPTION
	    "Connection Count is the number of client
	    processes connected to the information store."
    ::= { informationStore 37 }

isDLMembershipCacheEntriesCount OBJECT-TYPE
    SYNTAX     Gauge32
    MAX-ACCESS read-only
    STATUS     current
    DESCRIPTION
	    "Total number of entries stored in the DL
	    membership cache."
    ::= { informationStore 38 }

isDLMembershipCacheHits OBJECT-TYPE
    SYNTAX     Gauge32
    MAX-ACCESS read-only
    STATUS     current
    DESCRIPTION
	    "Total number of hits for the DL membership
	    cache."
    ::= { informationStore 39 }

isDLMembershipCacheMisses OBJECT-TYPE
    SYNTAX     Gauge32
    MAX-ACCESS read-only
    STATUS     current
    DESCRIPTION
	    "Total number of misses for the DL membership
	    cache."
    ::= { informationStore 40 }

isDLMembershipCacheSize OBJECT-TYPE
    SYNTAX     Gauge32
    MAX-ACCESS read-only
    STATUS     current
    DESCRIPTION
	    "Total number of memory bytes consumed by the
	    DL membership cache."
    ::= { informationStore 41 }

isDatabaseSessionHitRate OBJECT-TYPE
    SYNTAX     Gauge32
    MAX-ACCESS read-only
    STATUS     current
    DESCRIPTION
	    "Database Session Hit Rate is the percent hit
	    rate on re-using database sessions."
    ::= { informationStore 42 }

isExchmemCurrentBytesAlloc OBJECT-TYPE
    SYNTAX     Gauge32
    MAX-ACCESS read-only
    STATUS     current
    DESCRIPTION
	    "The current bytes allocated through Exchmem
	    (excluding virtual allocations)."
    ::= { informationStore 43 }

isExchmemCurrentNumVirtualAlloc OBJECT-TYPE
    SYNTAX     Gauge32
    MAX-ACCESS read-only
    STATUS     current
    DESCRIPTION
	    "The current number of Exchmem allocations that
	    were directly allocated from virtual memory."
    ::= { informationStore 44 }

isExchmemCurrentVirtualByteAlloc OBJECT-TYPE
    SYNTAX     Gauge32
    MAX-ACCESS read-only
    STATUS     current
    DESCRIPTION
	    "The current bytes virtually allocated through
	    Exchmem."
    ::= { informationStore 45 }

isExchmemMaxBytesAlloc OBJECT-TYPE
    SYNTAX     Gauge32
    MAX-ACCESS read-only
    STATUS     current
    DESCRIPTION
	    "The maximum concurrent bytes allocated through
	    Exchmem (excluding virtual allocations)."
    ::= { informationStore 46 }

isExchmemMaxVirtualBytesAlloc OBJECT-TYPE
    SYNTAX     Gauge32
    MAX-ACCESS read-only
    STATUS     current
    DESCRIPTION
	    "The maximum concurrent bytes virtually
	    allocated through Exchmem."
    ::= { informationStore 47 }

isExchmemNumOfAdditionalHeaps OBJECT-TYPE
    SYNTAX     Gauge32
    MAX-ACCESS read-only
    STATUS     current
    DESCRIPTION
	    "The number of Exchmem heaps created by
	    MSExchangeIS after startup."
    ::= { informationStore 48 }

isExchmemNumOfHeaps OBJECT-TYPE
    SYNTAX     Gauge32
    MAX-ACCESS read-only
    STATUS     current
    DESCRIPTION
	    "The total number of Exchmem heaps in use by
	    MSExchangeIS."
    ::= { informationStore 49 }

isExchmemNumOfHeapsMemoryErrors OBJECT-TYPE
    SYNTAX     Gauge32
    MAX-ACCESS read-only
    STATUS     current
    DESCRIPTION
	    "The total number of Exchmem heaps that failed
	    allocations due to insufficient available
	    memory."
    ::= { informationStore 50 }

isExchmemNumOfMemoryErrors OBJECT-TYPE
    SYNTAX     Gauge32
    MAX-ACCESS read-only
    STATUS     current
    DESCRIPTION
	    "The total number of Exchmem allocations that
	    could not be satisfied by available memory."
    ::= { informationStore 51 }

isExchmemTotalNumOfVirtualAlloc OBJECT-TYPE
    SYNTAX     Gauge32
    MAX-ACCESS read-only
    STATUS     current
    DESCRIPTION
	    "The total number of Exchmem allocations that
	    were directly allocated from virtual memory."
    ::= { informationStore 52 }

isFBPublishCount OBJECT-TYPE
    SYNTAX     Gauge32
    MAX-ACCESS read-only
    STATUS     current
    DESCRIPTION
	    "Number of free-busy publishes"
    ::= { informationStore 53 }

isFBPublishRate OBJECT-TYPE
    SYNTAX     Gauge32
    MAX-ACCESS read-only
    STATUS     current
    DESCRIPTION
	    "Number of free-busy publishes/sec"
    ::= { informationStore 54 }

isMaximumAnonymousUsers OBJECT-TYPE
    SYNTAX     Gauge32
    MAX-ACCESS read-only
    STATUS     current
    DESCRIPTION
	    "The maximum number of anonymous users since
	    startup."
    ::= { informationStore 55 }

isMaximumConnections OBJECT-TYPE
    SYNTAX     Gauge32
    MAX-ACCESS read-only
    STATUS     current
    DESCRIPTION
	    "The maximum number of concurrent connections
	    since startup."
    ::= { informationStore 56 }

isMaximumUsers OBJECT-TYPE
    SYNTAX     Gauge32
    MAX-ACCESS read-only
    STATUS     current
    DESCRIPTION
	    "Maximum Users is the maximum number of
	    concurrent users since startup."
    ::= { informationStore 57 }

isPeakPushNotificationsCacheSize OBJECT-TYPE
    SYNTAX     Gauge32
    MAX-ACCESS read-only
    STATUS     current
    DESCRIPTION
	    "The maximum size of the Push Notifications
	    Cache."
    ::= { informationStore 58 }

isPushNotificationsCacheSize OBJECT-TYPE
    SYNTAX     Gauge32
    MAX-ACCESS read-only
    STATUS     current
    DESCRIPTION
	    "The current size of the Push Notifications
	    Cache."
    ::= { informationStore 59 }

isPushNotifyGeneratedPerSec OBJECT-TYPE
    SYNTAX     Gauge32
    MAX-ACCESS read-only
    STATUS     current
    DESCRIPTION
	    "Push Notifications Generated/sec is the rate
	    at which notifications are being sent to
	    clients that have registered for notifications
	    of changes to tables in the information store."
    ::= { informationStore 60 }

isPushNotificationsSkippedPerSec OBJECT-TYPE
    SYNTAX     Gauge32
    MAX-ACCESS read-only
    STATUS     current
    DESCRIPTION
	    "Push Notifications Skipped/sec is the number
	    of push notifications that have been skipped by
	    caching at the server."
    ::= { informationStore 61 }

isRPCAveragedLatency OBJECT-TYPE
    SYNTAX     Gauge32
    MAX-ACCESS read-only
    STATUS     current
    DESCRIPTION
	    "RPC latency in milliseconds averaged for the
	    past 1024 packets."
    ::= { informationStore 62 }

isRPCClientsBytesRead OBJECT-TYPE
    SYNTAX     Gauge32
    MAX-ACCESS read-only
    STATUS     current
    DESCRIPTION
	    "RPC Clients Bytes Read is the total number of
	    bytes read from RPC clients."
    ::= { informationStore 63 }

isRPCClientsBytesWritten OBJECT-TYPE
    SYNTAX     Gauge32
    MAX-ACCESS read-only
    STATUS     current
    DESCRIPTION
	    "RPC Clients Bytes Written is the total number
	    of bytes written to RPC clients."
    ::= { informationStore 64 }

isRPCClientsUncompressBytesRead OBJECT-TYPE
    SYNTAX     Gauge32
    MAX-ACCESS read-only
    STATUS     current
    DESCRIPTION
	    "RPC Clients Uncompressed Bytes Read is the
	    total number of bytes read from RPC clients
	    after decompression."
    ::= { informationStore 65 }

isRPCClientsUncompressBytesWrite OBJECT-TYPE
    SYNTAX     Gauge32
    MAX-ACCESS read-only
    STATUS     current
    DESCRIPTION
	    "RPC Clients Uncompressed Bytes Written is the
	    total number of bytes written to RPC clients
	    before compression."
    ::= { informationStore 66 }

isRPCNumOfSlowPackets OBJECT-TYPE
    SYNTAX     Gauge32
    MAX-ACCESS read-only
    STATUS     current
    DESCRIPTION
	    "Number of RPC packets in the past 1024 that
	    have latencies longer than 2 seconds."
    ::= { informationStore 67 }

isRPCOperationsPerSec OBJECT-TYPE
    SYNTAX     Gauge32
    MAX-ACCESS read-only
    STATUS     current
    DESCRIPTION
	    "RPC Operations/sec is the rate that RPC
	    operations occur."
    ::= { informationStore 68 }

isRPCPacketsPerSec OBJECT-TYPE
    SYNTAX     Gauge32
    MAX-ACCESS read-only
    STATUS     current
    DESCRIPTION
	    "RPC Packets/sec is the rate that RPC packets
	    are processed."
    ::= { informationStore 69 }

isRPCRequests OBJECT-TYPE
    SYNTAX     Gauge32
    MAX-ACCESS read-only
    STATUS     current
    DESCRIPTION
	    "RPC Requests is the number of client requests
	    that are currently being processed by the
	    information store."
    ::= { informationStore 70 }

isRPCRequestsPeak OBJECT-TYPE
    SYNTAX     Gauge32
    MAX-ACCESS read-only
    STATUS     current
    DESCRIPTION
	    "RPC Requests Peak is the maximum number of
	    client requests that were processed
	    simultaneously by the information store since
	    it was started."
    ::= { informationStore 71 }

isReadBytesRPCClientsPerSec OBJECT-TYPE
    SYNTAX     Gauge32
    MAX-ACCESS read-only
    STATUS     current
    DESCRIPTION
	    "Read Bytes RPC Clients/sec is the rate that
	    bytes are read from RPC clients."
    ::= { informationStore 72 }

isRecurringAppointmentDeleteRate OBJECT-TYPE
    SYNTAX     Gauge32
    MAX-ACCESS read-only
    STATUS     current
    DESCRIPTION
	    "Number of recurring appoinments deleted/sec"
    ::= { informationStore 73 }

isRecurringAppointmentModifyRate OBJECT-TYPE
    SYNTAX     Gauge32
    MAX-ACCESS read-only
    STATUS     current
    DESCRIPTION
	    "Number of recurring appointments modified/sec"
    ::= { informationStore 74 }

isRecurringAppointmentsCreated OBJECT-TYPE
    SYNTAX     Gauge32
    MAX-ACCESS read-only
    STATUS     current
    DESCRIPTION
	    "Number of recurring appointments created"
    ::= { informationStore 75 }

isRecurringAppointmentsDeleted OBJECT-TYPE
    SYNTAX     Gauge32
    MAX-ACCESS read-only
    STATUS     current
    DESCRIPTION
	    "Number of recurring appointments deleted"
    ::= { informationStore 76 }

isRecurringAppointmentsModified OBJECT-TYPE
    SYNTAX     Gauge32
    MAX-ACCESS read-only
    STATUS     current
    DESCRIPTION
	    "Number of recurring appointments modified"
    ::= { informationStore 77 }

isRecurringApptCreateRate OBJECT-TYPE
    SYNTAX     Gauge32
    MAX-ACCESS read-only
    STATUS     current
    DESCRIPTION
	    "Number of recurring appointments created/sec"
    ::= { informationStore 78 }

isRecurringMasterApptsExpand OBJECT-TYPE
    SYNTAX     Gauge32
    MAX-ACCESS read-only
    STATUS     current
    DESCRIPTION
	    "Number of recurring master appointments
	    expanded"
    ::= { informationStore 79 }

isRecurringMasterExpansionRate OBJECT-TYPE
    SYNTAX     Gauge32
    MAX-ACCESS read-only
    STATUS     current
    DESCRIPTION
	    "Number of recurring master appointments
	    expanded/sec"
    ::= { informationStore 80 }

isSingleAppointmentCreationRate OBJECT-TYPE
    SYNTAX     Gauge32
    MAX-ACCESS read-only
    STATUS     current
    DESCRIPTION
	    "Number of single instance appointments
	    created/sec"
    ::= { informationStore 81 }

isSingleAppointmentDeletionRate OBJECT-TYPE
    SYNTAX     Gauge32
    MAX-ACCESS read-only
    STATUS     current
    DESCRIPTION
	    "Number of single instance appointments
	    deleted/sec"
    ::= { informationStore 82 }

isSingleAppointmentModifyRate OBJECT-TYPE
    SYNTAX     Gauge32
    MAX-ACCESS read-only
    STATUS     current
    DESCRIPTION
	    "Number of single instance appointments
	    modified/sec"
    ::= { informationStore 83 }

isSingleAppointmentsCreated OBJECT-TYPE
    SYNTAX     Gauge32
    MAX-ACCESS read-only
    STATUS     current
    DESCRIPTION
	    "Number of single instance appointments
	    created"
    ::= { informationStore 84 }

isSingleAppointmentsDeleted OBJECT-TYPE
    SYNTAX     Gauge32
    MAX-ACCESS read-only
    STATUS     current
    DESCRIPTION
	    "Number of single instance appointments
	    deleted"
    ::= { informationStore 85 }

isSingleAppointmentsModified OBJECT-TYPE
    SYNTAX     Gauge32
    MAX-ACCESS read-only
    STATUS     current
    DESCRIPTION
	    "Number of single instance appointments
	    modified"
    ::= { informationStore 86 }

isUserCount OBJECT-TYPE
    SYNTAX     Gauge32
    MAX-ACCESS read-only
    STATUS     current
    DESCRIPTION
	    "User Count is the number of users connected to
	    the information store."
    ::= { informationStore 87 }

isVMLargestBlockSize OBJECT-TYPE
    SYNTAX     Gauge32
    MAX-ACCESS read-only
    STATUS     current
    DESCRIPTION
	    "Size of the largest free virtual memory
	    block."
    ::= { informationStore 88 }

isVMTotal16MBFreeBlocks OBJECT-TYPE
    SYNTAX     Gauge32
    MAX-ACCESS read-only
    STATUS     current
    DESCRIPTION
	    "Total number of free Virtual Memory blocks
	    larger than or equal to 16MB."
    ::= { informationStore 89 }

isVMTotalFreeBlocks OBJECT-TYPE
    SYNTAX     Gauge32
    MAX-ACCESS read-only
    STATUS     current
    DESCRIPTION
	    "Total number of free Virtual Memory blocks."
    ::= { informationStore 90 }

isVMTotalLargeFreeBlockBytes OBJECT-TYPE
    SYNTAX     Gauge32
    MAX-ACCESS read-only
    STATUS     current
    DESCRIPTION
	    "Total number of bytes in free Virtual Memory
	    blocks larger than or equal to 16MB."
    ::= { informationStore 91 }

isVirusScanBytesScanned OBJECT-TYPE
    SYNTAX     Gauge32
    MAX-ACCESS read-only
    STATUS     current
    DESCRIPTION
	    "Total number of bytes in all files processed
	    by virus scanner."
    ::= { informationStore 92 }

isVirusScanFilesCleaned OBJECT-TYPE
    SYNTAX     Gauge32
    MAX-ACCESS read-only
    STATUS     current
    DESCRIPTION
	    "Total number of separate files cleaned by
	    virus scanner."
    ::= { informationStore 93 }

isVirusScanFilesCleanedPerSec OBJECT-TYPE
    SYNTAX     Gauge32
    MAX-ACCESS read-only
    STATUS     current
    DESCRIPTION
	    "The rate at which separate files are cleaned
	    by virus scanner."
    ::= { informationStore 94 }

isVirusScanFilesQuarantined OBJECT-TYPE
    SYNTAX     Gauge32
    MAX-ACCESS read-only
    STATUS     current
    DESCRIPTION
	    "Total number of separate files put into
	    quarantine by virus scanner."
    ::= { informationStore 95 }

isVirusScanFilesQuarantinePerSec OBJECT-TYPE
    SYNTAX     Gauge32
    MAX-ACCESS read-only
    STATUS     current
    DESCRIPTION
	    "The rate at which separate files are put into
	    quarantine by virus scanner."
    ::= { informationStore 96 }

isVirusScanFilesScanned OBJECT-TYPE
    SYNTAX     Gauge32
    MAX-ACCESS read-only
    STATUS     current
    DESCRIPTION
	    "Total number of separate files processed by
	    virus scanner."
    ::= { informationStore 97 }

isVirusScanFilesScannedPerSec OBJECT-TYPE
    SYNTAX     Gauge32
    MAX-ACCESS read-only
    STATUS     current
    DESCRIPTION
	    "The rate at which separate files are processed
	    by virus scanner."
    ::= { informationStore 98 }

isVirusScanFoldersScanBackground OBJECT-TYPE
    SYNTAX     Gauge32
    MAX-ACCESS read-only
    STATUS     current
    DESCRIPTION
	    "Total number of folders processed by
	    background scanning."
    ::= { informationStore 99 }

isVirusScanMessagesCleaned OBJECT-TYPE
    SYNTAX     Gauge32
    MAX-ACCESS read-only
    STATUS     current
    DESCRIPTION
	    "Total number of top-level messages cleaned by
	    virus scanner."
    ::= { informationStore 100 }

isVirusScanMessagesCleanedPerSec OBJECT-TYPE
    SYNTAX     Gauge32
    MAX-ACCESS read-only
    STATUS     current
    DESCRIPTION
	    "The rate at which top-level messages are
	    cleaned by virus scanner."
    ::= { informationStore 101 }

isVirusScanMessagesDeleted OBJECT-TYPE
    SYNTAX     Gauge32
    MAX-ACCESS read-only
    STATUS     current
    DESCRIPTION
	    "Total number of top-level messages that were
	    deleted upon request of the virus scanner."
    ::= { informationStore 102 }

isVirusScanMessagesDeletedPerSec OBJECT-TYPE
    SYNTAX     Gauge32
    MAX-ACCESS read-only
    STATUS     current
    DESCRIPTION
	    "The rate at which top-level messages are being
	    deleted upon request of the virus scanner."
    ::= { informationStore 103 }

isVirusScanMessagesProcessed OBJECT-TYPE
    SYNTAX     Gauge32
    MAX-ACCESS read-only
    STATUS     current
    DESCRIPTION
	    "Total number of top-level messages processed
	    by virus scanner."
    ::= { informationStore 104 }

isVirusScanMsgsProcessPerSec OBJECT-TYPE
    SYNTAX     Gauge32
    MAX-ACCESS read-only
    STATUS     current
    DESCRIPTION
	    "The rate at which top-level messages are
	    processed by virus scanner."
    ::= { informationStore 105 }

isVirusScanMessagesQuarantined OBJECT-TYPE
    SYNTAX     Gauge32
    MAX-ACCESS read-only
    STATUS     current
    DESCRIPTION
	    "Total number of top-level messages put into
	    quarantine by virus scanner."
    ::= { informationStore 106 }

isVirusScanMsgsQuarantinePerSec OBJECT-TYPE
    SYNTAX     Gauge32
    MAX-ACCESS read-only
    STATUS     current
    DESCRIPTION
	    "The rate at which top-level messages are put
	    into quarantine by virus scanner."
    ::= { informationStore 107 }

isVirusScanMsgsScanBackground OBJECT-TYPE
    SYNTAX     Gauge32
    MAX-ACCESS read-only
    STATUS     current
    DESCRIPTION
	    "Total number of messages processed by
	    background scanning."
    ::= { informationStore 108 }

isVirusScanQueueLength OBJECT-TYPE
    SYNTAX     Gauge32
    MAX-ACCESS read-only
    STATUS     current
    DESCRIPTION
	    "Current number of outstanding requests that
	    are queued for virus scanning."
    ::= { informationStore 109 }

isWriteBytesRPCClientsPerSec OBJECT-TYPE
    SYNTAX     Gauge32
    MAX-ACCESS read-only
    STATUS     current
    DESCRIPTION
	    "Write Bytes RPC Clients/sec is the rate that
	    bytes are written to RPC clients."
    ::= { informationStore 110 }

isClientBgRPCsFailed OBJECT-TYPE
    SYNTAX     Gauge32
    MAX-ACCESS read-only
    STATUS     current
    DESCRIPTION
	    "The client-reported number of failed
	    background RPCs (since the store was started)."
    ::= { informationStore 111 }

isClientBgRPCsFailedPerSec OBJECT-TYPE
    SYNTAX     Gauge32
    MAX-ACCESS read-only
    STATUS     current
    DESCRIPTION
	    "The client-reported rate of failed background
	    RPCs (since the store was started)."
    ::= { informationStore 112 }

isClientBgRPCsSucceeded OBJECT-TYPE
    SYNTAX     Gauge32
    MAX-ACCESS read-only
    STATUS     current
    DESCRIPTION
	    "The client-reported total number of successful
	    background RPCs (since the store was started)."
    ::= { informationStore 113 }

isClientBgRPCsSucceededPerSec OBJECT-TYPE
    SYNTAX     Gauge32
    MAX-ACCESS read-only
    STATUS     current
    DESCRIPTION
	    "The client-reported rate of successful
	    background RPCs (since the store was started)."
    ::= { informationStore 114 }

isClientFgRPCsFailed OBJECT-TYPE
    SYNTAX     Gauge32
    MAX-ACCESS read-only
    STATUS     current
    DESCRIPTION
	    "The client-reported number of failed
	    foreground RPCs (since the store was started)."
    ::= { informationStore 115 }

isClientFgRPCsFailedPerSec OBJECT-TYPE
    SYNTAX     Gauge32
    MAX-ACCESS read-only
    STATUS     current
    DESCRIPTION
	    "The client-reported rate of failed foreground
	    RPCs (since the store was started)."
    ::= { informationStore 116 }

isClientFgdRPCsSucceeded OBJECT-TYPE
    SYNTAX     Gauge32
    MAX-ACCESS read-only
    STATUS     current
    DESCRIPTION
	    "The client-reported total number of successful
	    foreground RPCs (since the store was started)."
    ::= { informationStore 117 }

isClientFgRPCsSucceededPerSec OBJECT-TYPE
    SYNTAX     Gauge32
    MAX-ACCESS read-only
    STATUS     current
    DESCRIPTION
	    "The client-reported rate of successful
	    foreground RPCs (since the store was started)."
    ::= { informationStore 118 }

isOABDiffDownloadAttempts OBJECT-TYPE
    SYNTAX     Gauge32
    MAX-ACCESS read-only
    STATUS     current
    DESCRIPTION
	    "Total number of attempts by clients to
	    download changes to the Offline Address Book."
    ::= { informationStore 119 }

isOABDiffDownloadBytes OBJECT-TYPE
    SYNTAX     Gauge32
    MAX-ACCESS read-only
    STATUS     current
    DESCRIPTION
	    "Total number of bytes sent to clients
	    performing a differential download of the
	    Offline Address Book."
    ::= { informationStore 120 }

isOABDiffDownloadBytesPerSec OBJECT-TYPE
    SYNTAX     Gauge32
    MAX-ACCESS read-only
    STATUS     current
    DESCRIPTION
	    "Rate at which bytes are being sent to clients
	    performing a differential download of the
	    Offline Address Book."
    ::= { informationStore 121 }

isOABFullDownloadAttempts OBJECT-TYPE
    SYNTAX     Gauge32
    MAX-ACCESS read-only
    STATUS     current
    DESCRIPTION
	    "Total number of attempts by clients to
	    download the full Offline Address Book."
    ::= { informationStore 122 }

isOABFullDownloadAttemptsBlocked OBJECT-TYPE
    SYNTAX     Gauge32
    MAX-ACCESS read-only
    STATUS     current
    DESCRIPTION
	    "Total number of attempts by clients to
	    download the full Offline Address Book blocked
	    due to bandwidth throttling."
    ::= { informationStore 123 }

isOABFullDownloadBytes OBJECT-TYPE
    SYNTAX     Gauge32
    MAX-ACCESS read-only
    STATUS     current
    DESCRIPTION
	    "Total number of bytes sent to clients
	    performing a full download of the Offline
	    Address Book."
    ::= { informationStore 124 }

isOABFullDownloadBytesPerSec OBJECT-TYPE
    SYNTAX     Gauge32
    MAX-ACCESS read-only
    STATUS     current
    DESCRIPTION
	    "Rate at which bytes are being sent to clients
	    performing a full download of the Offline
	    Address Book."
    ::= { informationStore 125 }

isSlowQPThreads OBJECT-TYPE
    SYNTAX     Gauge32
    MAX-ACCESS read-only
    STATUS     current
    DESCRIPTION
	    "Number of Query Processor threads currently
	    running unoptimized queries."
    ::= { informationStore 126 }

isSlowSearchThreads OBJECT-TYPE
    SYNTAX     Gauge32
    MAX-ACCESS read-only
    STATUS     current
    DESCRIPTION
	    "Number of Search threads currently running
	    unoptimized queries."
    ::= { informationStore 127 }

is55FolderUpgradeCount OBJECT-TYPE
    SYNTAX     Gauge32
    MAX-ACCESS read-only
    STATUS     current
    DESCRIPTION
	    "Total number of folders upgraded"
    ::= { informationStore 128 }

is55FolderUpgradeRate OBJECT-TYPE
    SYNTAX     Gauge32
    MAX-ACCESS read-only
    STATUS     current
    DESCRIPTION
	    "Rate of folders being upgraded"
    ::= { informationStore 129 }

is55MsgUpgradeCount OBJECT-TYPE
    SYNTAX     Gauge32
    MAX-ACCESS read-only
    STATUS     current
    DESCRIPTION
	    "Total number of messages upgraded"
    ::= { informationStore 130 }

is55MsgUpgradeRate OBJECT-TYPE
    SYNTAX     Gauge32
    MAX-ACCESS read-only
    STATUS     current
    DESCRIPTION
	    "Rate of messages being upgraded"
    ::= { informationStore 131 }

isActiveTemporaryStreams OBJECT-TYPE
    SYNTAX     Gauge32
    MAX-ACCESS read-only
    STATUS     current
    DESCRIPTION
	    "Number of existing temporary streams."
    ::= { informationStore 132 }

isHeapAllocations OBJECT-TYPE
    SYNTAX     Gauge32
    MAX-ACCESS read-only
    STATUS     current
    DESCRIPTION
	    "Current number of heap allocations"
    ::= { informationStore 133 }

isHeapAllocationsRate OBJECT-TYPE
    SYNTAX     Gauge32
    MAX-ACCESS read-only
    STATUS     current
    DESCRIPTION
	    "Number of heap allocations per second"
    ::= { informationStore 134 }

isHeapAllocationsTotal OBJECT-TYPE
    SYNTAX     Gauge32
    MAX-ACCESS read-only
    STATUS     current
    DESCRIPTION
	    "Total number of heap allocations"
    ::= { informationStore 135 }

isHeapSize OBJECT-TYPE
    SYNTAX     Gauge32
    MAX-ACCESS read-only
    STATUS     current
    DESCRIPTION
	    "Number of bytes allocated in the heap"
    ::= { informationStore 136 }

isISOwnThreadCount OBJECT-TYPE
    SYNTAX     Gauge32
    MAX-ACCESS read-only
    STATUS     current
    DESCRIPTION
	    "The number of 'own thread' tasks registered"
    ::= { informationStore 137 }

isISTASKDepth OBJECT-TYPE
    SYNTAX     Gauge32
    MAX-ACCESS read-only
    STATUS     current
    DESCRIPTION
	    "The depth (in tasks) of the IS task queue"
    ::= { informationStore 138 }

isISTASKInvokeRate OBJECT-TYPE
    SYNTAX     Gauge32
    MAX-ACCESS read-only
    STATUS     current
    DESCRIPTION
	    "The rate at which tasks are invoked by the
	    EcRegisterTask interface"
    ::= { informationStore 139 }

isISTASKInvoked OBJECT-TYPE
    SYNTAX     Gauge32
    MAX-ACCESS read-only
    STATUS     current
    DESCRIPTION
	    "The number of tasks invoked by the
	    EcRegisterTask interface"
    ::= { informationStore 140 }

isISTASKQueueRate OBJECT-TYPE
    SYNTAX     Gauge32
    MAX-ACCESS read-only
    STATUS     current
    DESCRIPTION
	    "The rate at which tasks are queued to the
	    EcRegisterTask interface"
    ::= { informationStore 141 }

isISTASKQueued OBJECT-TYPE
    SYNTAX     Gauge32
    MAX-ACCESS read-only
    STATUS     current
    DESCRIPTION
	    "The number of tasks queued by the
	    EcRegisterTask interface"
    ::= { informationStore 142 }

isMailboxCacheHitRate OBJECT-TYPE
    SYNTAX     Gauge32
    MAX-ACCESS read-only
    STATUS     current
    DESCRIPTION
	    "Rate of mailbox cache hits"
    ::= { informationStore 143 }

isMailboxCacheHitRatePercent OBJECT-TYPE
    SYNTAX     Gauge32
    MAX-ACCESS read-only
    STATUS     current
    DESCRIPTION
	    "Rate of mailbox cache hits."
    ::= { informationStore 144 }

isMailboxCacheHitRatePercentBase OBJECT-TYPE
    SYNTAX     Gauge32
    MAX-ACCESS read-only
    STATUS     current
    DESCRIPTION
	    "Rate of mailbox cache hits percent (base)"
    ::= { informationStore 145 }

isMailboxCacheHits OBJECT-TYPE
    SYNTAX     Gauge32
    MAX-ACCESS read-only
    STATUS     current
    DESCRIPTION
	    "Total number of mailbox cache hits"
    ::= { informationStore 146 }

isMailboxCacheMissRate OBJECT-TYPE
    SYNTAX     Gauge32
    MAX-ACCESS read-only
    STATUS     current
    DESCRIPTION
	    "Rate of mailbox cache misses"
    ::= { informationStore 147 }

isMailboxCacheMissRatePercent OBJECT-TYPE
    SYNTAX     Gauge32
    MAX-ACCESS read-only
    STATUS     current
    DESCRIPTION
	    "Rate of mailbox cache misses"
    ::= { informationStore 148 }

isMailboxCacheMisses OBJECT-TYPE
    SYNTAX     Gauge32
    MAX-ACCESS read-only
    STATUS     current
    DESCRIPTION
	    "Total number of mailbox cache misses"
    ::= { informationStore 149 }

isMailboxCacheQueries OBJECT-TYPE
    SYNTAX     Gauge32
    MAX-ACCESS read-only
    STATUS     current
    DESCRIPTION
	    "Total number of mailbox cache queries"
    ::= { informationStore 150 }

isMailboxCacheQueryRate OBJECT-TYPE
    SYNTAX     Gauge32
    MAX-ACCESS read-only
    STATUS     current
    DESCRIPTION
	    "Rate of mailbox cache queries"
    ::= { informationStore 151 }

isMailboxCacheSize OBJECT-TYPE
    SYNTAX     Gauge32
    MAX-ACCESS read-only
    STATUS     current
    DESCRIPTION
	    "Number of items stored in the mailbox cache"
    ::= { informationStore 152 }

isMDBTASKIdleCount OBJECT-TYPE
    SYNTAX     Gauge32
    MAX-ACCESS read-only
    STATUS     current
    DESCRIPTION
	    "The number of idle MDBTASK threads"
    ::= { informationStore 153 }

isMDBTASKInvokeRate OBJECT-TYPE
    SYNTAX     Gauge32
    MAX-ACCESS read-only
    STATUS     current
    DESCRIPTION
	    "The rate of invocation to the MDBTASK pool"
    ::= { informationStore 154 }

isMDBTASKQueueDepth OBJECT-TYPE
    SYNTAX     Gauge32
    MAX-ACCESS read-only
    STATUS     current
    DESCRIPTION
	    "The depth of the MDBTASK queue"
    ::= { informationStore 155 }

isMDBTASKQueueRate OBJECT-TYPE
    SYNTAX     Gauge32
    MAX-ACCESS read-only
    STATUS     current
    DESCRIPTION
	    "The rate of tasks queued to the MDBTASK pool"
    ::= { informationStore 156 }

isMDBTASKTasksInvoked OBJECT-TYPE
    SYNTAX     Gauge32
    MAX-ACCESS read-only
    STATUS     current
    DESCRIPTION
	    "The number of tasks that were invoked in the
	    MDBTASK module"
    ::= { informationStore 157 }

isMDBTASKTasksQueued OBJECT-TYPE
    SYNTAX     Gauge32
    MAX-ACCESS read-only
    STATUS     current
    DESCRIPTION
	    "The number of tasks queued to the MDBTASK
	    module"
    ::= { informationStore 158 }

isMDBTASKThreadCount OBJECT-TYPE
    SYNTAX     Gauge32
    MAX-ACCESS read-only
    STATUS     current
    DESCRIPTION
	    "The number of active MDBTASK threads"
    ::= { informationStore 159 }

isNumberOfAXBEvents OBJECT-TYPE
    SYNTAX     Gauge32
    MAX-ACCESS read-only
    STATUS     current
    DESCRIPTION
	    "Number of AXB events"
    ::= { informationStore 160 }

isNumberOfAXBObjects OBJECT-TYPE
    SYNTAX     Gauge32
    MAX-ACCESS read-only
    STATUS     current
    DESCRIPTION
	    "Number of AXB objects"
    ::= { informationStore 161 }

isNumberOfCRITSPOOLEntries OBJECT-TYPE
    SYNTAX     Gauge32
    MAX-ACCESS read-only
    STATUS     current
    DESCRIPTION
	    "Total number of store CRITSPOOL entries
	    allocated"
    ::= { informationStore 162 }

isNumberOfStoreCriticalSections OBJECT-TYPE
    SYNTAX     Gauge32
    MAX-ACCESS read-only
    STATUS     current
    DESCRIPTION
	    "Number of store critical sections"
    ::= { informationStore 163 }

isPeakTempStreamSize OBJECT-TYPE
    SYNTAX     Gauge32
    MAX-ACCESS read-only
    STATUS     current
    DESCRIPTION
	    "Maximum size of a temporary stream"
    ::= { informationStore 164 }

isPeakTemporaryStreams OBJECT-TYPE
    SYNTAX     Gauge32
    MAX-ACCESS read-only
    STATUS     current
    DESCRIPTION
	    "Maximum number of concurrently existing
	    temporary streams."
    ::= { informationStore 165 }

isTotalTempStreamSize OBJECT-TYPE
    SYNTAX     Gauge32
    MAX-ACCESS read-only
    STATUS     current
    DESCRIPTION
	    "Total size of all temporary streams ever
	    created"
    ::= { informationStore 166 }

isTotalTemporaryStreams OBJECT-TYPE
    SYNTAX     Gauge32
    MAX-ACCESS read-only
    STATUS     current
    DESCRIPTION
	    "Total number of temporary streams."
    ::= { informationStore 167 }

isVirusScanBytesRead OBJECT-TYPE
    SYNTAX     Gauge32
    MAX-ACCESS read-only
    STATUS     current
    DESCRIPTION
	    "Total number of bytes read by virus scanner."
    ::= { informationStore 168 }

isVirusScanBytesWritten OBJECT-TYPE
    SYNTAX     Gauge32
    MAX-ACCESS read-only
    STATUS     current
    DESCRIPTION
	    "Total number of bytes written by virus
	    scanner."
    ::= { informationStore 169 }

isVirusScanChkTimeouts OBJECT-TYPE
    SYNTAX     Gauge32
    MAX-ACCESS read-only
    STATUS     current
    DESCRIPTION
	    "The number of times operations waiting for
	    virus scan completion were timed out."
    ::= { informationStore 170 }

isVirusScanChkTimeoutsPerSec OBJECT-TYPE
    SYNTAX     Gauge32
    MAX-ACCESS read-only
    STATUS     current
    DESCRIPTION
	    "The rate at which operations waiting for virus
	    scan completion are timed out."
    ::= { informationStore 171 }

isVirusScanChksBlocked OBJECT-TYPE
    SYNTAX     Gauge32
    MAX-ACCESS read-only
    STATUS     current
    DESCRIPTION
	    "The number of times processing was blocked
	    waiting for virus scan to complete."
    ::= { informationStore 172 }

isVirusScanChksBlockedPerSec OBJECT-TYPE
    SYNTAX     Gauge32
    MAX-ACCESS read-only
    STATUS     current
    DESCRIPTION
	    "The rate at which processing is blocked
	    waiting for virus scan to complete."
    ::= { informationStore 173 }

isVirusScanChksNotSatisfied OBJECT-TYPE
    SYNTAX     Gauge32
    MAX-ACCESS read-only
    STATUS     current
    DESCRIPTION
	    "The number of times virus scan checks were not
	    satisfied by any stamp."
    ::= { informationStore 174 }

isVirusScanChksNotSatisfyPerSec OBJECT-TYPE
    SYNTAX     Gauge32
    MAX-ACCESS read-only
    STATUS     current
    DESCRIPTION
	    "The rate at which virus scan checks are not
	    satisfied by any stamp."
    ::= { informationStore 175 }

isVirusScanChksSatInstStmp OBJECT-TYPE
    SYNTAX     Gauge32
    MAX-ACCESS read-only
    STATUS     current
    DESCRIPTION
	    "The number of times virus scan checks were
	    satisfied by instance stamp."
    ::= { informationStore 176 }

isVirusScanChksSatInstStmpPerSec OBJECT-TYPE
    SYNTAX     Gauge32
    MAX-ACCESS read-only
    STATUS     current
    DESCRIPTION
	    "The rate at which virus scan checks are
	    satisfied by instance stamp."
    ::= { informationStore 177 }

isVirusScanChksSatMasterInstStmp OBJECT-TYPE
    SYNTAX     Gauge32
    MAX-ACCESS read-only
    STATUS     current
    DESCRIPTION
	    "The number of times virus scan checks were
	    satisfied by master instance stamp."
    ::= { informationStore 178 }

isVirusScanChksSatMsInstStPerSec OBJECT-TYPE
    SYNTAX     Gauge32
    MAX-ACCESS read-only
    STATUS     current
    DESCRIPTION
	    "The rate at which virus scan checks are
	    satisfied by master instance stamp."
    ::= { informationStore 179 }

isVirusScanChksSatMFTStmp OBJECT-TYPE
    SYNTAX     Gauge32
    MAX-ACCESS read-only
    STATUS     current
    DESCRIPTION
	    "The number of times virus scan checks were
	    satisfied by stamp in Message Folder Table."
    ::= { informationStore 180 }

isVirusScanChksSatMFTStmpPerSec OBJECT-TYPE
    SYNTAX     Gauge32
    MAX-ACCESS read-only
    STATUS     current
    DESCRIPTION
	    "The rate at which virus scan checks are
	    satisfied by stamp in Message Folder Table."
    ::= { informationStore 181 }

isVirusScanMsgsScannedMAPI OBJECT-TYPE
    SYNTAX     Gauge32
    MAX-ACCESS read-only
    STATUS     current
    DESCRIPTION
	    "Total number of top-level messages processed
	    as MAPI by virus scanner."
    ::= { informationStore 182 }

isVirusScanMsgsScannedMAPIPerSec OBJECT-TYPE
    SYNTAX     Gauge32
    MAX-ACCESS read-only
    STATUS     current
    DESCRIPTION
	    "The rate at which top-level messages are
	    processed as MAPI by virus scanner."
    ::= { informationStore 183 }

isVirusScanMsgsScannedMIME OBJECT-TYPE
    SYNTAX     Gauge32
    MAX-ACCESS read-only
    STATUS     current
    DESCRIPTION
	    "Total number of top-level messages processed
	    as MIME by virus scanner."
    ::= { informationStore 184 }

isVirusScanMsgsScannedMIMEPerSec OBJECT-TYPE
    SYNTAX     Gauge32
    MAX-ACCESS read-only
    STATUS     current
    DESCRIPTION
	    "The rate at which top-level messages are
	    processed as MIME by virus scanner."
    ::= { informationStore 185 }

isVirusScanQueueLenLowPriority OBJECT-TYPE
    SYNTAX     Gauge32
    MAX-ACCESS read-only
    STATUS     current
    DESCRIPTION
	    "Current number of outstanding low-priority
	    requests that are queued for virus scanning."
    ::= { informationStore 186 }

isVirusScanThreads OBJECT-TYPE
    SYNTAX     Gauge32
    MAX-ACCESS read-only
    STATUS     current
    DESCRIPTION
	    "Current number of threads in a thread pool
	    used for virus scanning. This count does not
	    include number of threads used for background
	    scanning."
    ::= { informationStore 187 }

informationStoreMailboxTable OBJECT-TYPE
    SYNTAX     SEQUENCE OF ISMailboxEntry
    MAX-ACCESS not-accessible
    STATUS     current
    DESCRIPTION
	    "Microsoft Exchange Mailbox Store performance
	    data"
    ::= { exchange 15 }

informationStoreMailboxEntry OBJECT-TYPE
    SYNTAX     ISMailboxEntry
    MAX-ACCESS not-accessible
    STATUS     current
    DESCRIPTION
	    "Performance information for one particular
	    instance of 'MSExchangeIS Mailbox' object."
    INDEX      { ismInstance }
    ::= { informationStoreMailboxTable 1 }

ISMailboxEntry ::= SEQUENCE {
    ismInstance InstanceName,
    ismActiveClientLogons Gauge32,
    ismAverageDeliveryTime Gauge32,
    ismCategorizationCount Gauge32,
    ismClientLogons Gauge32,
    ismFolderOpensPerSec Gauge32,
    ismHTTPPerDAVCurPendingNotify Gauge32,
    ismHTTPPerDAVCurSubscriptions Gauge32,
    ismHTTPPerDAVCurTransactionLocks Gauge32,
    ismHTTPPerDAVNotifyRqstsPerSec Gauge32,
    ismHTTPPerDAVTotalLocksCreated Gauge32,
    ismHTTPPerDAVTotalNotifyRequests Gauge32,
    ismHTTPPerDAVTotalSubCreate Gauge32,
    ismHTTPPerDAVTotalSubExpire Gauge32,
    ismLocalDeliveries Gauge32,
    ismLocalDeliveryRate Gauge32,
    ismLogonOperationsPerSec Gauge32,
    ismMessageOpensPerSec Gauge32,
    ismMessageRcptsDelivered Gauge32,
    ismMessageRcptsDeliveredPerMin Gauge32,
    ismMessagesDelivered Gauge32,
    ismMessagesDeliveredPerMin Gauge32,
    ismMessagesSent Gauge32,
    ismMessagesSentPerMin Gauge32,
    ismMessagesSubmitted Gauge32,
    ismMessagesSubmittedPerMin Gauge32,
    ismPeakClientLogons Gauge32,
    ismReceiveQueueSize Gauge32,
    ismSendQueueSize Gauge32,
    ismSingleInstanceRatio Gauge32,
    ismTotalCountOfRecoverableItems Gauge32,
    ismTotalSizeOfRecoverableItems Gauge32,
    ismRestrictedViewCacheHitRate Gauge32,
    ismRestrictedViewCacheMissRate Gauge32,
    ismSearchTaskRate Gauge32,
    ismSlowFindRowRate Gauge32,
    ismAbortOpRate Gauge32,
    ismAbortOpTotal Gauge32,
    ismAbortSubmitOpRate Gauge32,
    ismAbortSubmitOpTotal Gauge32,
    ismAddMsgToSendqRate Gauge32,
    ismAddMsgToSendqTotal Gauge32,
    ismAddNamedCalcPropOpRate Gauge32,
    ismAddNamedCalcPropOpTotal Gauge32,
    ismAddressTypesOpRate Gauge32,
    ismAddressTypesOpTotal Gauge32,
    ismCacheCcnReadOpRate Gauge32,
    ismCacheCcnReadOpTotal Gauge32,
    ismCheckFolderNameOpRate Gauge32,
    ismCheckFolderNameOpTotal Gauge32,
    ismCheckRightsOnFolderRate Gauge32,
    ismCheckRightsOnFolderTotal Gauge32,
    ismCloneStreamOpRate Gauge32,
    ismCloneStreamOpTotal Gauge32,
    ismCollapseRowOpRate Gauge32,
    ismCollapseRowOpTotal Gauge32,
    ismCommitStreamOpRate Gauge32,
    ismCommitStreamOpTotal Gauge32,
    ismCopyPropsOpRate Gauge32,
    ismCopyPropsOpTotal Gauge32,
    ismCopyToOpRate Gauge32,
    ismCopyToOpTotal Gauge32,
    ismCopyToStreamOpRate Gauge32,
    ismCopyToStreamOpTotal Gauge32,
    ismCreateAttachOpRate Gauge32,
    ismCreateAttachOpTotal Gauge32,
    ismCreateBookMarkOperationPerSec Gauge32,
    ismCreateFolderOpRate Gauge32,
    ismCreateFolderOpTotal Gauge32,
    ismDatabaseSessionActiveCount Gauge32,
    ismDatabaseSessionCount Gauge32,
    ismDeleteAttachOpRate Gauge32,
    ismDeleteAttachOpTotal Gauge32,
    ismDeleteFolderOpRate Gauge32,
    ismDeleteFolderOpTotal Gauge32,
    ismDeleteMessagesOpRate Gauge32,
    ismDeleteMessagesOpTotal Gauge32,
    ismDelMsgFromSendqRate Gauge32,
    ismDelMsgFromSendqTotal Gauge32,
    ismDelPropertyOperationsPerSec Gauge32,
    ismDeregisterTableNotificOpRate Gauge32,
    ismDeregisterTableNotificOpTotal Gauge32,
    ismDoCrossPostOpRate Gauge32,
    ismDoCrossPostOpTotal Gauge32,
    ismEmptyFolderOpRate Gauge32,
    ismEmptyFolderOpTotal Gauge32,
    ismExpandRowOpRate Gauge32,
    ismExpandRowOpTotal Gauge32,
    ismFghostedOpRate Gauge32,
    ismFghostedOpTotal Gauge32,
    ismFindRowOperationsPerSec Gauge32,
    ismFlushPerUserOpRate Gauge32,
    ismFlushPerUserOpTotal Gauge32,
    ismFolderCount Gauge32,
    ismFreeBookmarkOpRate Gauge32,
    ismFreeBookmarkOpTotal Gauge32,
    ismFXDstCopyFolderOpRate Gauge32,
    ismFXDstCopyFolderOpTotal Gauge32,
    ismFXDstCopyMessagesOpRate Gauge32,
    ismFXDstCopyMessagesOpTotal Gauge32,
    ismFXDstCopyPropsOpRate Gauge32,
    ismFXDstCopyPropsOpTotal Gauge32,
    ismFXDstCopyToOpRate Gauge32,
    ismFXDstCopyToOpTotal Gauge32,
    ismFXDstPutBufferOpRate Gauge32,
    ismFXDstPutBufferOpTotal Gauge32,
    ismFXGetBufferCurrentCallerCount Gauge32,
    ismFXGetBufferCurrentUsersExec Gauge32,
    ismFXGetBufferRopsAccepted Gauge32,
    ismFXGetBufferRopsAcceptedPerSec Gauge32,
    ismFXGetBufferRopsCalled Gauge32,
    ismFXGetBufferRopsCalledPerSec Gauge32,
    ismFXGetBufferRopsDenied Gauge32,
    ismFXGetBufferRopsDeniedPerSec Gauge32,
    ismFXGetIncrStateOpRate Gauge32,
    ismFXGetIncrStateOpTotal Gauge32,
    ismFXSrcCopyFolderOpRate Gauge32,
    ismFXSrcCopyFolderOpTotal Gauge32,
    ismFXSrcCopyMessagesOpRate Gauge32,
    ismFXSrcCopyMessagesOpTotal Gauge32,
    ismFXSrcCopyPropsOpRate Gauge32,
    ismFXSrcCopyPropsOpTotal Gauge32,
    ismFXSrcCopyToOpRate Gauge32,
    ismFXSrcCopyToOpTotal Gauge32,
    ismFXSrcGetBufferOpRate Gauge32,
    ismFXSrcGetBufferOpTotal Gauge32,
    ismGetAdrListOpRate Gauge32,
    ismGetAdrListOpTotal Gauge32,
    ismGetAllPerUserLtidsOpRate Gauge32,
    ismGetAllPerUserLtidsOpTotal Gauge32,
    ismGetCollapseStateOpRate Gauge32,
    ismGetCollapseStateOpTotal Gauge32,
    ismGetFileHandlePropOpRate Gauge32,
    ismGetFileHandlePropOpTotal Gauge32,
    ismGetFoldersTableRpcIntfRate Gauge32,
    ismGetFoldersTableRpcIntfTotal Gauge32,
    ismGetIDsFromNamesOpRate Gauge32,
    ismGetIDsFromNamesOpTotal Gauge32,
    ismGetLocalRepIdsOpRate Gauge32,
    ismGetLocalRepIdsOpTotal Gauge32,
    ismGetMailboxTableRpcIntfRate Gauge32,
    ismGetMailboxTableRpcIntfTotal Gauge32,
    ismGetMessagePropOpRate Gauge32,
    ismGetMessagePropOpTotal Gauge32,
    ismGetMessageStatusOpRate Gauge32,
    ismGetMessageStatusOpTotal Gauge32,
    ismGetNamesFromIDsOpRate Gauge32,
    ismGetNamesFromIDsOpTotal Gauge32,
    ismGetOwningMDBsOpRate Gauge32,
    ismGetOwningMDBsOpTotal Gauge32,
    ismGetPerUserGuidOpRate Gauge32,
    ismGetPerUserGuidOpTotal Gauge32,
    ismGetPerUserLtidsOpRate Gauge32,
    ismGetPerUserLtidsOpTotal Gauge32,
    ismGetPerUserOpRate Gauge32,
    ismGetPerUserOpTotal Gauge32,
    ismGetPropertyOperationsPerSec Gauge32,
    ismGetPropListOpRate Gauge32,
    ismGetPropListOpTotal Gauge32,
    ismGetReceiveFolderOpRate Gauge32,
    ismGetReceiveFolderOpTotal Gauge32,
    ismGetReceiveFolderTableOpRate Gauge32,
    ismGetReceiveFolderTableOpTotal Gauge32,
    ismGetRecipColumnsOpRate Gauge32,
    ismGetRecipColumnsOpTotal Gauge32,
    ismGetRecipCountOpRate Gauge32,
    ismGetRecipCountOpTotal Gauge32,
    ismGetRecipOpRate Gauge32,
    ismGetRecipOpTotal Gauge32,
    ismGetRightsOpRate Gauge32,
    ismGetRightsOpTotal Gauge32,
    ismGetSearchCriteriaOpRate Gauge32,
    ismGetSearchCriteriaOpTotal Gauge32,
    ismGetStatusOpRate Gauge32,
    ismGetStatusOpTotal Gauge32,
    ismGetStreamSizeOpRate Gauge32,
    ismGetStreamSizeOpTotal Gauge32,
    ismGetTableOpRate Gauge32,
    ismGetTableOpTotal Gauge32,
    ismGetXhdrListOpRate Gauge32,
    ismGetXhdrListOpTotal Gauge32,
    ismIdFromLtidOpRate Gauge32,
    ismIdFromLtidOpTotal Gauge32,
    ismImportDeleteOpRate Gauge32,
    ismImportDeleteOpTotal Gauge32,
    ismImportHierChgOpRate Gauge32,
    ismImportHierChgOpTotal Gauge32,
    ismImportHierDelOpRate Gauge32,
    ismImportHierDelOpTotal Gauge32,
    ismImportMsgChgOpRate Gauge32,
    ismImportMsgChgOpTotal Gauge32,
    ismImportMsgMoveOpRate Gauge32,
    ismImportMsgMoveOpTotal Gauge32,
    ismImportReadsOpRate Gauge32,
    ismImportReadsOpTotal Gauge32,
    ismIncrCfgOpRate Gauge32,
    ismIncrCfgOpTotal Gauge32,
    ismLocalDeliveryOpRate Gauge32,
    ismLocalDeliveryOpTotal Gauge32,
    ismLockRegionStreamOpRate Gauge32,
    ismLockRegionStreamOpTotal Gauge32,
    ismLtidFromIdOpRate Gauge32,
    ismLtidFromIdOpTotal Gauge32,
    ismMessageRcpntsDeliveredPerSec Gauge32,
    ismMessagesDeliveredPerSec Gauge32,
    ismModifyACLOpRate Gauge32,
    ismModifyACLOpTotal Gauge32,
    ismModifyMvPropOpRate Gauge32,
    ismModifyMvPropOpTotal Gauge32,
    ismModifyRcpntsOperationsPerSec Gauge32,
    ismModifyRulesOpRate Gauge32,
    ismModifyRulesOpTotal Gauge32,
    ismModifyRulesRate Gauge32,
    ismModifyRulesTotal Gauge32,
    ismMoveCopyFolderOpRate Gauge32,
    ismMoveCopyFolderOpTotal Gauge32,
    ismMoveCopyMessagesOpRate Gauge32,
    ismMoveCopyMessagesOpTotal Gauge32,
    ismNextNewsgroupOpRate Gauge32,
    ismNextNewsgroupOpTotal Gauge32,
    ismNukeRecipientsOpRate Gauge32,
    ismNukeRecipientsOpTotal Gauge32,
    ismOpenAdvisorOpRate Gauge32,
    ismOpenAdvisorOpTotal Gauge32,
    ismOpenAttachOpRate Gauge32,
    ismOpenAttachOpTotal Gauge32,
    ismOpenCollectOpRate Gauge32,
    ismOpenCollectOpTotal Gauge32,
    ismOpenFolderByNntpNameOpRate Gauge32,
    ismOpenFolderByNntpNameOpTotal Gauge32,
    ismOpenImailConversionObjOpRate Gauge32,
    ismOpenImailConversionObjOpTotal Gauge32,
    ismOpenImailConversionStrOpRate Gauge32,
    ismOpenImailConversionStrOpTotal Gauge32,
    ismOpenMessageByArticleNumOpRate Gauge32,
    ismOpenMessageByArticleNmOpTotal Gauge32,
    ismOpenMessageByMsgIdOpRate Gauge32,
    ismOpenMessageByMsgIdOpTotal Gauge32,
    ismOpenMessagePropOpRate Gauge32,
    ismOpenMessagePropOpTotal Gauge32,
    ismOpenStreamOperationsPerSec Gauge32,
    ismPrepareReadRecipientsRate Gauge32,
    ismPrepareReadRecipientsTotal Gauge32,
    ismQryNamedPropsOpRate Gauge32,
    ismQryNamedPropsOpTotal Gauge32,
    ismQueryColumnsAllOpRate Gauge32,
    ismQueryColumnsAllOpTotal Gauge32,
    ismQueryPositionOperationsPerSec Gauge32,
    ismQueryRowsOpRate Gauge32,
    ismQueryRowsOpTotal Gauge32,
    ismReadStreamOpRate Gauge32,
    ismReadStreamOpTotal Gauge32,
    ismRegICSNotifsOpRate Gauge32,
    ismRegICSNotifsOpTotal Gauge32,
    ismRegisterNotifyOperationPerSec Gauge32,
    ismRegisterTableNotifyOpRate Gauge32,
    ismRegisterTableNotifyOpTotal Gauge32,
    ismRenderMessageOpRate Gauge32,
    ismRenderMessageOpTotal Gauge32,
    ismResetTableOpRate Gauge32,
    ismResetTableOpTotal Gauge32,
    ismRestrictOperationsPerSec Gauge32,
    ismRowsInACLListTable Gauge32,
    ismRowsInACLMemberTable Gauge32,
    ismRowsInCategTables Gauge32,
    ismRowsInDeletedAttachmentsTable Gauge32,
    ismRowsInDeletedFoldersTable Gauge32,
    ismRowsInDeletedMessagesTable Gauge32,
    ismRowsInDeliveredToTable Gauge32,
    ismRowsInFolderTombstoneTable Gauge32,
    ismRowsInIdxAgeTable Gauge32,
    ismRowsInMailboxTable Gauge32,
    ismRowsInMessageTable Gauge32,
    ismRowsInMessageTombstoneTable Gauge32,
    ismRowsInMsgFolderTables Gauge32,
    ismRowsInNamedPropsTable Gauge32,
    ismRowsInNeedRNTable Gauge32,
    ismRowsInPerUserReadTable Gauge32,
    ismRowsInReceiveFoldersTable Gauge32,
    ismRowsInReplicationTable Gauge32,
    ismRowsInReplidMapTable Gauge32,
    ismRowsInRulesTable Gauge32,
    ismRowsInSearchQueueTable Gauge32,
    ismRowsInTimedEventsTable Gauge32,
    ismSaveChangesAttachOpRate Gauge32,
    ismSaveChangesAttachOpTotal Gauge32,
    ismSaveChangesMessageOpRate Gauge32,
    ismSaveChangesMessageOpTotal Gauge32,
    ismSeekRowOperationsPerSec Gauge32,
    ismSeekRowApproxOperationsPerSec Gauge32,
    ismSeekRowBookMarkOpPerSec Gauge32,
    ismSeekStreamOpRate Gauge32,
    ismSeekStreamOpTotal Gauge32,
    ismSendqTasksRate Gauge32,
    ismSendqTasksTotal Gauge32,
    ismSetCollapseStateOpRate Gauge32,
    ismSetCollapseStateOpTotal Gauge32,
    ismSetColumnsOpRate Gauge32,
    ismSetColumnsOpTotal Gauge32,
    ismSetFileHandlePropOpRate Gauge32,
    ismSetFileHandlePropOpTotal Gauge32,
    ismSetfLocalizedOpRate Gauge32,
    ismSetfLocalizedOpTotal Gauge32,
    ismSetICSNotifGUIDOpRate Gauge32,
    ismSetICSNotifGUIDOpTotal Gauge32,
    ismSetLocalRepMidsetDelOpRate Gauge32,
    ismSetLocalRepMidsetDelOpTotal Gauge32,
    ismSetMessageFolderFlagsOpRate Gauge32,
    ismSetMessageFolderFlagsOpTotal Gauge32,
    ismSetMessagePropOpRate Gauge32,
    ismSetMessagePropOpTotal Gauge32,
    ismSetMessageStatusOpRate Gauge32,
    ismSetMessageStatusOpTotal Gauge32,
    ismSetPerUserOpRate Gauge32,
    ismSetPerUserOpTotal Gauge32,
    ismSetPropertyOperationsPerSec Gauge32,
    ismSetReadFlagOpRate Gauge32,
    ismSetReadFlagOpTotal Gauge32,
    ismSetReadFlagsOpRate Gauge32,
    ismSetReadFlagsOpTotal Gauge32,
    ismSetReceiveFolderOpRate Gauge32,
    ismSetReceiveFolderOpTotal Gauge32,
    ismSetRecipOpRate Gauge32,
    ismSetRecipOpTotal Gauge32,
    ismSetSearchCriteriaOpRate Gauge32,
    ismSetSearchCriteriaOpTotal Gauge32,
    ismSetSizeStreamOpRate Gauge32,
    ismSetSizeStreamOpTotal Gauge32,
    ismSetSpoolerOpRate Gauge32,
    ismSetSpoolerOpTotal Gauge32,
    ismSetXportOpRate Gauge32,
    ismSetXportOpTotal Gauge32,
    ismSortTableOpRate Gauge32,
    ismSortTableOpTotal Gauge32,
    ismSpoolerLockMsgOpRate Gauge32,
    ismSpoolerLockMsgOpTotal Gauge32,
    ismSpoolerRulesOpRate Gauge32,
    ismSpoolerRulesOpTotal Gauge32,
    ismTellVersionOpRate Gauge32,
    ismTellVersionOpTotal Gauge32,
    ismTranRateFromMimeToMapi Gauge32,
    ismTranRateFromMimeToMimebyref Gauge32,
    ismTranRateFromMimebyrefToMapi Gauge32,
    ismTranRateFromNewToMime Gauge32,
    ismTransFromMimeToMapi Gauge32,
    ismTransFromMimeToMimebyref Gauge32,
    ismTransFromMimebyrefToMapi Gauge32,
    ismTransFromNewToMime Gauge32,
    ismTransportSendOpRate Gauge32,
    ismTransportSendOpTotal Gauge32,
    ismUpdateDAMsOpRate Gauge32,
    ismUpdateDAMsOpTotal Gauge32,
    ismUpdateFolderInternetIdOpRate Gauge32,
    ismUpdateFolderInternetIdOpTotal Gauge32,
    ismUpdateRecipPtagsOpRate Gauge32,
    ismUpdateRecipPtagsOpTotal Gauge32,
    ismUpldStStrmBeginOpRate Gauge32,
    ismUpldStStrmBeginOpTotal Gauge32,
    ismUpldStStrmContinueOpRate Gauge32,
    ismUpldStStrmContinueOpTotal Gauge32,
    ismUpldStStrmEndOpRate Gauge32,
    ismUpldStStrmEndOpTotal Gauge32,
    ismValidAttachsOpRate Gauge32,
    ismValidAttachsOpTotal Gauge32,
    ismWriteStreamOpRate Gauge32,
    ismWriteStreamOpTotal Gauge32,
    ismXportNewMailOpRate Gauge32,
    ismXportNewMailOpTotal Gauge32
}

ismInstance OBJECT-TYPE
    SYNTAX     InstanceName
    MAX-ACCESS read-only
    STATUS     current
    DESCRIPTION
	    "Instance name."
    ::= { informationStoreMailboxEntry 1 }

ismActiveClientLogons OBJECT-TYPE
    SYNTAX     Gauge32
    MAX-ACCESS read-only
    STATUS     current
    DESCRIPTION
	    "Active Client Logons is the number of clients
	    that performed any action within the last ten
	    minute time interval."
    ::= { informationStoreMailboxEntry 2 }

ismAverageDeliveryTime OBJECT-TYPE
    SYNTAX     Gauge32
    MAX-ACCESS read-only
    STATUS     current
    DESCRIPTION
	    "Average Delivery Time is the average time in
	    miliseconds between the submission of a message
	    to the mailbox store and the delivery to all
	    local recipients (recipients on the same
	    server) for the last 10 messages."
    ::= { informationStoreMailboxEntry 3 }

ismCategorizationCount OBJECT-TYPE
    SYNTAX     Gauge32
    MAX-ACCESS read-only
    STATUS     current
    DESCRIPTION
	    "Categorization Count is the number of
	    categorizations that exist in the mailbox
	    store. Categorizations are created when a user
	    creates a filtered view or performs a search.
	    When the information store must maintain an
	    excessive number of categorizations, p"
    ::= { informationStoreMailboxEntry 4 }

ismClientLogons OBJECT-TYPE
    SYNTAX     Gauge32
    MAX-ACCESS read-only
    STATUS     current
    DESCRIPTION
	    "Client Logons is the number of clients
	    (including system processes) currently logged
	    on."
    ::= { informationStoreMailboxEntry 5 }

ismFolderOpensPerSec OBJECT-TYPE
    SYNTAX     Gauge32
    MAX-ACCESS read-only
    STATUS     current
    DESCRIPTION
	    "Folder opens/sec is the rate that requests to
	    open folders are submitted to the information
	    store."
    ::= { informationStoreMailboxEntry 6 }

ismHTTPPerDAVCurPendingNotify OBJECT-TYPE
    SYNTAX     Gauge32
    MAX-ACCESS read-only
    STATUS     current
    DESCRIPTION
	    "Number of notifications happened that are
	    pending (i.e. to be polled)."
    ::= { informationStoreMailboxEntry 7 }

ismHTTPPerDAVCurSubscriptions OBJECT-TYPE
    SYNTAX     Gauge32
    MAX-ACCESS read-only
    STATUS     current
    DESCRIPTION
	    "The number of subscriptions currently active
	    in response to HTTP SUBSCRIBE requests."
    ::= { informationStoreMailboxEntry 8 }

ismHTTPPerDAVCurTransactionLocks OBJECT-TYPE
    SYNTAX     Gauge32
    MAX-ACCESS read-only
    STATUS     current
    DESCRIPTION
	    "The number of DAV transaction locks currently
	    active."
    ::= { informationStoreMailboxEntry 9 }

ismHTTPPerDAVNotifyRqstsPerSec OBJECT-TYPE
    SYNTAX     Gauge32
    MAX-ACCESS read-only
    STATUS     current
    DESCRIPTION
	    "The rate at which the server sends HTTP NOTIFY
	    requests."
    ::= { informationStoreMailboxEntry 10 }

ismHTTPPerDAVTotalLocksCreated OBJECT-TYPE
    SYNTAX     Gauge32
    MAX-ACCESS read-only
    STATUS     current
    DESCRIPTION
	    "The number locks granted by the server in
	    response to HTTP LOCK requests since service
	    startup."
    ::= { informationStoreMailboxEntry 11 }

ismHTTPPerDAVTotalNotifyRequests OBJECT-TYPE
    SYNTAX     Gauge32
    MAX-ACCESS read-only
    STATUS     current
    DESCRIPTION
	    "The number of HTTP NOTIFY requests sent by the
	    server since service startup."
    ::= { informationStoreMailboxEntry 12 }

ismHTTPPerDAVTotalSubCreate OBJECT-TYPE
    SYNTAX     Gauge32
    MAX-ACCESS read-only
    STATUS     current
    DESCRIPTION
	    "The number of subscriptions granted by the
	    server in response to HTTP SUBSCRIBE requests
	    since service startup."
    ::= { informationStoreMailboxEntry 13 }

ismHTTPPerDAVTotalSubExpire OBJECT-TYPE
    SYNTAX     Gauge32
    MAX-ACCESS read-only
    STATUS     current
    DESCRIPTION
	    "The number of subscriptions granted by the
	    server in response to HTTP SUBSCRIBE requests
	    that have expired since service startup."
    ::= { informationStoreMailboxEntry 14 }

ismLocalDeliveries OBJECT-TYPE
    SYNTAX     Gauge32
    MAX-ACCESS read-only
    STATUS     current
    DESCRIPTION
	    "Total number of messages delivered locally"
    ::= { informationStoreMailboxEntry 15 }

ismLocalDeliveryRate OBJECT-TYPE
    SYNTAX     Gauge32
    MAX-ACCESS read-only
    STATUS     current
    DESCRIPTION
	    "Rate at which messages are delivered locally"
    ::= { informationStoreMailboxEntry 16 }

ismLogonOperationsPerSec OBJECT-TYPE
    SYNTAX     Gauge32
    MAX-ACCESS read-only
    STATUS     current
    DESCRIPTION
	    "Logon Operations/sec is the rate of Logon
	    requests in the mailbox store."
    ::= { informationStoreMailboxEntry 17 }

ismMessageOpensPerSec OBJECT-TYPE
    SYNTAX     Gauge32
    MAX-ACCESS read-only
    STATUS     current
    DESCRIPTION
	    "Message Opens/sec is the rate that requests to
	    open messages are submitted to the information
	    store."
    ::= { informationStoreMailboxEntry 18 }

ismMessageRcptsDelivered OBJECT-TYPE
    SYNTAX     Gauge32
    MAX-ACCESS read-only
    STATUS     current
    DESCRIPTION
	    "Message Recipients Delivered is the total
	    number of recipients that have received a
	    message since startup."
    ::= { informationStoreMailboxEntry 19 }

ismMessageRcptsDeliveredPerMin OBJECT-TYPE
    SYNTAX     Gauge32
    MAX-ACCESS read-only
    STATUS     current
    DESCRIPTION
	    "Message Recipients Delivered/min is the rate
	    that recipients receive messages."
    ::= { informationStoreMailboxEntry 20 }

ismMessagesDelivered OBJECT-TYPE
    SYNTAX     Gauge32
    MAX-ACCESS read-only
    STATUS     current
    DESCRIPTION
	    "Messages Delivered is the total number of
	    messages delivered to all recipients since
	    startup."
    ::= { informationStoreMailboxEntry 21 }

ismMessagesDeliveredPerMin OBJECT-TYPE
    SYNTAX     Gauge32
    MAX-ACCESS read-only
    STATUS     current
    DESCRIPTION
	    "Messages Delivered/min is the rate that
	    messages are delivered to all recipients."
    ::= { informationStoreMailboxEntry 22 }

ismMessagesSent OBJECT-TYPE
    SYNTAX     Gauge32
    MAX-ACCESS read-only
    STATUS     current
    DESCRIPTION
	    "Messages Sent is the total number of messages
	    sent to the transport since startup."
    ::= { informationStoreMailboxEntry 23 }

ismMessagesSentPerMin OBJECT-TYPE
    SYNTAX     Gauge32
    MAX-ACCESS read-only
    STATUS     current
    DESCRIPTION
	    "Messages Sent/min is the rate that messages
	    are sent to the transport."
    ::= { informationStoreMailboxEntry 24 }

ismMessagesSubmitted OBJECT-TYPE
    SYNTAX     Gauge32
    MAX-ACCESS read-only
    STATUS     current
    DESCRIPTION
	    "Messages Submitted is the total number of
	    messages submitted by clients since service
	    startup."
    ::= { informationStoreMailboxEntry 25 }

ismMessagesSubmittedPerMin OBJECT-TYPE
    SYNTAX     Gauge32
    MAX-ACCESS read-only
    STATUS     current
    DESCRIPTION
	    "Messages Submitted/min is the rate that
	    messages are submitted by clients."
    ::= { informationStoreMailboxEntry 26 }

ismPeakClientLogons OBJECT-TYPE
    SYNTAX     Gauge32
    MAX-ACCESS read-only
    STATUS     current
    DESCRIPTION
	    "Peak Client Logons is the maximum number of
	    concurrent client logons since the service
	    started."
    ::= { informationStoreMailboxEntry 27 }

ismReceiveQueueSize OBJECT-TYPE
    SYNTAX     Gauge32
    MAX-ACCESS read-only
    STATUS     current
    DESCRIPTION
	    "Receive Queue Size is the number of messages
	    in the mailbox store's receive queue."
    ::= { informationStoreMailboxEntry 28 }

ismSendQueueSize OBJECT-TYPE
    SYNTAX     Gauge32
    MAX-ACCESS read-only
    STATUS     current
    DESCRIPTION
	    "Send Queue Size is the number of messages in
	    the mailbox store's send queue."
    ::= { informationStoreMailboxEntry 29 }

ismSingleInstanceRatio OBJECT-TYPE
    SYNTAX     Gauge32
    MAX-ACCESS read-only
    STATUS     current
    DESCRIPTION
	    "Single Instance Ratio is the average number of
	    references to each message in the mailbox
	    store."
    ::= { informationStoreMailboxEntry 30 }

ismTotalCountOfRecoverableItems OBJECT-TYPE
    SYNTAX     Gauge32
    MAX-ACCESS read-only
    STATUS     current
    DESCRIPTION
	    "Total Count of Recoverable Items is the total
	    number of items retained for Item Recovery"
    ::= { informationStoreMailboxEntry 31 }

ismTotalSizeOfRecoverableItems OBJECT-TYPE
    SYNTAX     Gauge32
    MAX-ACCESS read-only
    STATUS     current
    DESCRIPTION
	    "Total Size of Recoverable Items is the total
	    size in kilobytes of items retained for Item
	    Recovery"
    ::= { informationStoreMailboxEntry 32 }

ismRestrictedViewCacheHitRate OBJECT-TYPE
    SYNTAX     Gauge32
    MAX-ACCESS read-only
    STATUS     current
    DESCRIPTION
	    "Restricted View Cache Hit Rate is the rate at
	    which restricted views are reused in the
	    mailbox store."
    ::= { informationStoreMailboxEntry 33 }

ismRestrictedViewCacheMissRate OBJECT-TYPE
    SYNTAX     Gauge32
    MAX-ACCESS read-only
    STATUS     current
    DESCRIPTION
	    "Restricted View Cache Miss Rate is the rate at
	    which restricted views are created in the
	    mailbox store."
    ::= { informationStoreMailboxEntry 34 }

ismSearchTaskRate OBJECT-TYPE
    SYNTAX     Gauge32
    MAX-ACCESS read-only
    STATUS     current
    DESCRIPTION
	    "Number of search tasks created per second."
    ::= { informationStoreMailboxEntry 35 }

ismSlowFindRowRate OBJECT-TYPE
    SYNTAX     Gauge32
    MAX-ACCESS read-only
    STATUS     current
    DESCRIPTION
	    "Slow FindRow Rate is the rate at which the
	    slower FindRow needs to be used in the mailbox
	    store."
    ::= { informationStoreMailboxEntry 36 }

ismAbortOpRate OBJECT-TYPE
    SYNTAX     Gauge32
    MAX-ACCESS read-only
    STATUS     current
    DESCRIPTION
	    "AbortOpRate."
    ::= { informationStoreMailboxEntry 37 }

ismAbortOpTotal OBJECT-TYPE
    SYNTAX     Gauge32
    MAX-ACCESS read-only
    STATUS     current
    DESCRIPTION
	    "AbortOpTotal."
    ::= { informationStoreMailboxEntry 38 }

ismAbortSubmitOpRate OBJECT-TYPE
    SYNTAX     Gauge32
    MAX-ACCESS read-only
    STATUS     current
    DESCRIPTION
	    "AbortSubmitOpRate."
    ::= { informationStoreMailboxEntry 39 }

ismAbortSubmitOpTotal OBJECT-TYPE
    SYNTAX     Gauge32
    MAX-ACCESS read-only
    STATUS     current
    DESCRIPTION
	    "AbortSubmitOpTotal."
    ::= { informationStoreMailboxEntry 40 }

ismAddMsgToSendqRate OBJECT-TYPE
    SYNTAX     Gauge32
    MAX-ACCESS read-only
    STATUS     current
    DESCRIPTION
	    "Messages added to the send queue."
    ::= { informationStoreMailboxEntry 41 }

ismAddMsgToSendqTotal OBJECT-TYPE
    SYNTAX     Gauge32
    MAX-ACCESS read-only
    STATUS     current
    DESCRIPTION
	    "Messages added to the send queue."
    ::= { informationStoreMailboxEntry 42 }

ismAddNamedCalcPropOpRate OBJECT-TYPE
    SYNTAX     Gauge32
    MAX-ACCESS read-only
    STATUS     current
    DESCRIPTION
	    "AddNamedCalcPropOpRate."
    ::= { informationStoreMailboxEntry 43 }

ismAddNamedCalcPropOpTotal OBJECT-TYPE
    SYNTAX     Gauge32
    MAX-ACCESS read-only
    STATUS     current
    DESCRIPTION
	    "AddNamedCalcPropOpTotal."
    ::= { informationStoreMailboxEntry 44 }

ismAddressTypesOpRate OBJECT-TYPE
    SYNTAX     Gauge32
    MAX-ACCESS read-only
    STATUS     current
    DESCRIPTION
	    "AddressTypesOpRate."
    ::= { informationStoreMailboxEntry 45 }

ismAddressTypesOpTotal OBJECT-TYPE
    SYNTAX     Gauge32
    MAX-ACCESS read-only
    STATUS     current
    DESCRIPTION
	    "AddressTypesOpTotal."
    ::= { informationStoreMailboxEntry 46 }

ismCacheCcnReadOpRate OBJECT-TYPE
    SYNTAX     Gauge32
    MAX-ACCESS read-only
    STATUS     current
    DESCRIPTION
	    "CacheCcnReadOpRate."
    ::= { informationStoreMailboxEntry 47 }

ismCacheCcnReadOpTotal OBJECT-TYPE
    SYNTAX     Gauge32
    MAX-ACCESS read-only
    STATUS     current
    DESCRIPTION
	    "CacheCcnReadOpTotal."
    ::= { informationStoreMailboxEntry 48 }

ismCheckFolderNameOpRate OBJECT-TYPE
    SYNTAX     Gauge32
    MAX-ACCESS read-only
    STATUS     current
    DESCRIPTION
	    "CheckFolderNameOpRate."
    ::= { informationStoreMailboxEntry 49 }

ismCheckFolderNameOpTotal OBJECT-TYPE
    SYNTAX     Gauge32
    MAX-ACCESS read-only
    STATUS     current
    DESCRIPTION
	    "CheckFolderNameOpTotal."
    ::= { informationStoreMailboxEntry 50 }

ismCheckRightsOnFolderRate OBJECT-TYPE
    SYNTAX     Gauge32
    MAX-ACCESS read-only
    STATUS     current
    DESCRIPTION
	    "CheckRightsOnFolderRate."
    ::= { informationStoreMailboxEntry 51 }

ismCheckRightsOnFolderTotal OBJECT-TYPE
    SYNTAX     Gauge32
    MAX-ACCESS read-only
    STATUS     current
    DESCRIPTION
	    "CheckRightsOnFolderTotal."
    ::= { informationStoreMailboxEntry 52 }

ismCloneStreamOpRate OBJECT-TYPE
    SYNTAX     Gauge32
    MAX-ACCESS read-only
    STATUS     current
    DESCRIPTION
	    "CloneStreamOpRate."
    ::= { informationStoreMailboxEntry 53 }

ismCloneStreamOpTotal OBJECT-TYPE
    SYNTAX     Gauge32
    MAX-ACCESS read-only
    STATUS     current
    DESCRIPTION
	    "CloneStreamOpTotal."
    ::= { informationStoreMailboxEntry 54 }

ismCollapseRowOpRate OBJECT-TYPE
    SYNTAX     Gauge32
    MAX-ACCESS read-only
    STATUS     current
    DESCRIPTION
	    "CollapseRowOpRate."
    ::= { informationStoreMailboxEntry 55 }

ismCollapseRowOpTotal OBJECT-TYPE
    SYNTAX     Gauge32
    MAX-ACCESS read-only
    STATUS     current
    DESCRIPTION
	    "CollapseRowOpTotal."
    ::= { informationStoreMailboxEntry 56 }

ismCommitStreamOpRate OBJECT-TYPE
    SYNTAX     Gauge32
    MAX-ACCESS read-only
    STATUS     current
    DESCRIPTION
	    "CommitStreamOpRate."
    ::= { informationStoreMailboxEntry 57 }

ismCommitStreamOpTotal OBJECT-TYPE
    SYNTAX     Gauge32
    MAX-ACCESS read-only
    STATUS     current
    DESCRIPTION
	    "CommitStreamOpTotal."
    ::= { informationStoreMailboxEntry 58 }

ismCopyPropsOpRate OBJECT-TYPE
    SYNTAX     Gauge32
    MAX-ACCESS read-only
    STATUS     current
    DESCRIPTION
	    "CopyPropsOpRate."
    ::= { informationStoreMailboxEntry 59 }

ismCopyPropsOpTotal OBJECT-TYPE
    SYNTAX     Gauge32
    MAX-ACCESS read-only
    STATUS     current
    DESCRIPTION
	    "CopyPropsOpTotal."
    ::= { informationStoreMailboxEntry 60 }

ismCopyToOpRate OBJECT-TYPE
    SYNTAX     Gauge32
    MAX-ACCESS read-only
    STATUS     current
    DESCRIPTION
	    "CopyToOpRate."
    ::= { informationStoreMailboxEntry 61 }

ismCopyToOpTotal OBJECT-TYPE
    SYNTAX     Gauge32
    MAX-ACCESS read-only
    STATUS     current
    DESCRIPTION
	    "CopyToOpTotal."
    ::= { informationStoreMailboxEntry 62 }

ismCopyToStreamOpRate OBJECT-TYPE
    SYNTAX     Gauge32
    MAX-ACCESS read-only
    STATUS     current
    DESCRIPTION
	    "CopyToStreamOpRate."
    ::= { informationStoreMailboxEntry 63 }

ismCopyToStreamOpTotal OBJECT-TYPE
    SYNTAX     Gauge32
    MAX-ACCESS read-only
    STATUS     current
    DESCRIPTION
	    "CopyToStreamOpTotal."
    ::= { informationStoreMailboxEntry 64 }

ismCreateAttachOpRate OBJECT-TYPE
    SYNTAX     Gauge32
    MAX-ACCESS read-only
    STATUS     current
    DESCRIPTION
	    "CreateAttachOpRate."
    ::= { informationStoreMailboxEntry 65 }

ismCreateAttachOpTotal OBJECT-TYPE
    SYNTAX     Gauge32
    MAX-ACCESS read-only
    STATUS     current
    DESCRIPTION
	    "CreateAttachOpTotal."
    ::= { informationStoreMailboxEntry 66 }

ismCreateBookMarkOperationPerSec OBJECT-TYPE
    SYNTAX     Gauge32
    MAX-ACCESS read-only
    STATUS     current
    DESCRIPTION
	    "CreateBookMark Operations/sec is the rate of
	    CreateBookMark requests in the mailbox store."
    ::= { informationStoreMailboxEntry 67 }

ismCreateFolderOpRate OBJECT-TYPE
    SYNTAX     Gauge32
    MAX-ACCESS read-only
    STATUS     current
    DESCRIPTION
	    "CreateFolderOpRate."
    ::= { informationStoreMailboxEntry 68 }

ismCreateFolderOpTotal OBJECT-TYPE
    SYNTAX     Gauge32
    MAX-ACCESS read-only
    STATUS     current
    DESCRIPTION
	    "CreateFolderOpTotal."
    ::= { informationStoreMailboxEntry 69 }

ismDatabaseSessionActiveCount OBJECT-TYPE
    SYNTAX     Gauge32
    MAX-ACCESS read-only
    STATUS     current
    DESCRIPTION
	    "Number of database sessions in use at the
	    current time"
    ::= { informationStoreMailboxEntry 70 }

ismDatabaseSessionCount OBJECT-TYPE
    SYNTAX     Gauge32
    MAX-ACCESS read-only
    STATUS     current
    DESCRIPTION
	    "Number of database sessions allocated"
    ::= { informationStoreMailboxEntry 71 }

ismDeleteAttachOpRate OBJECT-TYPE
    SYNTAX     Gauge32
    MAX-ACCESS read-only
    STATUS     current
    DESCRIPTION
	    "DeleteAttachOpRate."
    ::= { informationStoreMailboxEntry 72 }

ismDeleteAttachOpTotal OBJECT-TYPE
    SYNTAX     Gauge32
    MAX-ACCESS read-only
    STATUS     current
    DESCRIPTION
	    "DeleteAttachOpTotal."
    ::= { informationStoreMailboxEntry 73 }

ismDeleteFolderOpRate OBJECT-TYPE
    SYNTAX     Gauge32
    MAX-ACCESS read-only
    STATUS     current
    DESCRIPTION
	    "DeleteFolderOpRate."
    ::= { informationStoreMailboxEntry 74 }

ismDeleteFolderOpTotal OBJECT-TYPE
    SYNTAX     Gauge32
    MAX-ACCESS read-only
    STATUS     current
    DESCRIPTION
	    "DeleteFolderOpTotal."
    ::= { informationStoreMailboxEntry 75 }

ismDeleteMessagesOpRate OBJECT-TYPE
    SYNTAX     Gauge32
    MAX-ACCESS read-only
    STATUS     current
    DESCRIPTION
	    "DeleteMessagesOpRate."
    ::= { informationStoreMailboxEntry 76 }

ismDeleteMessagesOpTotal OBJECT-TYPE
    SYNTAX     Gauge32
    MAX-ACCESS read-only
    STATUS     current
    DESCRIPTION
	    "DeleteMessagesOpTotal."
    ::= { informationStoreMailboxEntry 77 }

ismDelMsgFromSendqRate OBJECT-TYPE
    SYNTAX     Gauge32
    MAX-ACCESS read-only
    STATUS     current
    DESCRIPTION
	    "Messages deleted from the send queue."
    ::= { informationStoreMailboxEntry 78 }

ismDelMsgFromSendqTotal OBJECT-TYPE
    SYNTAX     Gauge32
    MAX-ACCESS read-only
    STATUS     current
    DESCRIPTION
	    "Messages deleted from the send queue."
    ::= { informationStoreMailboxEntry 79 }

ismDelPropertyOperationsPerSec OBJECT-TYPE
    SYNTAX     Gauge32
    MAX-ACCESS read-only
    STATUS     current
    DESCRIPTION
	    "DelProperty Operations/sec is the rate of
	    DelProperty requests in the mailbox store."
    ::= { informationStoreMailboxEntry 80 }

ismDeregisterTableNotificOpRate OBJECT-TYPE
    SYNTAX     Gauge32
    MAX-ACCESS read-only
    STATUS     current
    DESCRIPTION
	    "DeregisterTableNotificationOpRate."
    ::= { informationStoreMailboxEntry 81 }

ismDeregisterTableNotificOpTotal OBJECT-TYPE
    SYNTAX     Gauge32
    MAX-ACCESS read-only
    STATUS     current
    DESCRIPTION
	    "DeregisterTableNotificationOpTotal."
    ::= { informationStoreMailboxEntry 82 }

ismDoCrossPostOpRate OBJECT-TYPE
    SYNTAX     Gauge32
    MAX-ACCESS read-only
    STATUS     current
    DESCRIPTION
	    "DoCrossPostOpRate."
    ::= { informationStoreMailboxEntry 83 }

ismDoCrossPostOpTotal OBJECT-TYPE
    SYNTAX     Gauge32
    MAX-ACCESS read-only
    STATUS     current
    DESCRIPTION
	    "DoCrossPostOpTotal."
    ::= { informationStoreMailboxEntry 84 }

ismEmptyFolderOpRate OBJECT-TYPE
    SYNTAX     Gauge32
    MAX-ACCESS read-only
    STATUS     current
    DESCRIPTION
	    "EmptyFolderOpRate."
    ::= { informationStoreMailboxEntry 85 }

ismEmptyFolderOpTotal OBJECT-TYPE
    SYNTAX     Gauge32
    MAX-ACCESS read-only
    STATUS     current
    DESCRIPTION
	    "EmptyFolderOpTotal."
    ::= { informationStoreMailboxEntry 86 }

ismExpandRowOpRate OBJECT-TYPE
    SYNTAX     Gauge32
    MAX-ACCESS read-only
    STATUS     current
    DESCRIPTION
	    "ExpandRowOpRate."
    ::= { informationStoreMailboxEntry 87 }

ismExpandRowOpTotal OBJECT-TYPE
    SYNTAX     Gauge32
    MAX-ACCESS read-only
    STATUS     current
    DESCRIPTION
	    "ExpandRowOpTotal."
    ::= { informationStoreMailboxEntry 88 }

ismFghostedOpRate OBJECT-TYPE
    SYNTAX     Gauge32
    MAX-ACCESS read-only
    STATUS     current
    DESCRIPTION
	    "FghostedOpRate."
    ::= { informationStoreMailboxEntry 89 }

ismFghostedOpTotal OBJECT-TYPE
    SYNTAX     Gauge32
    MAX-ACCESS read-only
    STATUS     current
    DESCRIPTION
	    "FghostedOpTotal."
    ::= { informationStoreMailboxEntry 90 }

ismFindRowOperationsPerSec OBJECT-TYPE
    SYNTAX     Gauge32
    MAX-ACCESS read-only
    STATUS     current
    DESCRIPTION
	    "FindRow operations/sec is the rate of FindRow
	    requests in the mailbox store."
    ::= { informationStoreMailboxEntry 91 }

ismFlushPerUserOpRate OBJECT-TYPE
    SYNTAX     Gauge32
    MAX-ACCESS read-only
    STATUS     current
    DESCRIPTION
	    "FlushPerUserOpRate."
    ::= { informationStoreMailboxEntry 92 }

ismFlushPerUserOpTotal OBJECT-TYPE
    SYNTAX     Gauge32
    MAX-ACCESS read-only
    STATUS     current
    DESCRIPTION
	    "FlushPerUserOpTotal."
    ::= { informationStoreMailboxEntry 93 }

ismFolderCount OBJECT-TYPE
    SYNTAX     Gauge32
    MAX-ACCESS read-only
    STATUS     current
    DESCRIPTION
	    "Folder Count is the number of separate folders
	    (including top-level folders and subfolders)
	    that exist in the mailbox store."
    ::= { informationStoreMailboxEntry 94 }

ismFreeBookmarkOpRate OBJECT-TYPE
    SYNTAX     Gauge32
    MAX-ACCESS read-only
    STATUS     current
    DESCRIPTION
	    "FreeBookmarkOpRate."
    ::= { informationStoreMailboxEntry 95 }

ismFreeBookmarkOpTotal OBJECT-TYPE
    SYNTAX     Gauge32
    MAX-ACCESS read-only
    STATUS     current
    DESCRIPTION
	    "FreeBookmarkOpTotal."
    ::= { informationStoreMailboxEntry 96 }

ismFXDstCopyFolderOpRate OBJECT-TYPE
    SYNTAX     Gauge32
    MAX-ACCESS read-only
    STATUS     current
    DESCRIPTION
	    "FXDstCopyFolderOpRate."
    ::= { informationStoreMailboxEntry 97 }

ismFXDstCopyFolderOpTotal OBJECT-TYPE
    SYNTAX     Gauge32
    MAX-ACCESS read-only
    STATUS     current
    DESCRIPTION
	    "FXDstCopyFolderOpTotal."
    ::= { informationStoreMailboxEntry 98 }

ismFXDstCopyMessagesOpRate OBJECT-TYPE
    SYNTAX     Gauge32
    MAX-ACCESS read-only
    STATUS     current
    DESCRIPTION
	    "FXDstCopyMessagesOpRate."
    ::= { informationStoreMailboxEntry 99 }

ismFXDstCopyMessagesOpTotal OBJECT-TYPE
    SYNTAX     Gauge32
    MAX-ACCESS read-only
    STATUS     current
    DESCRIPTION
	    "FXDstCopyMessagesOpTotal."
    ::= { informationStoreMailboxEntry 100 }

ismFXDstCopyPropsOpRate OBJECT-TYPE
    SYNTAX     Gauge32
    MAX-ACCESS read-only
    STATUS     current
    DESCRIPTION
	    "FXDstCopyPropsOpRate."
    ::= { informationStoreMailboxEntry 101 }

ismFXDstCopyPropsOpTotal OBJECT-TYPE
    SYNTAX     Gauge32
    MAX-ACCESS read-only
    STATUS     current
    DESCRIPTION
	    "FXDstCopyPropsOpTotal."
    ::= { informationStoreMailboxEntry 102 }

ismFXDstCopyToOpRate OBJECT-TYPE
    SYNTAX     Gauge32
    MAX-ACCESS read-only
    STATUS     current
    DESCRIPTION
	    "FXDstCopyToOpRate."
    ::= { informationStoreMailboxEntry 103 }

ismFXDstCopyToOpTotal OBJECT-TYPE
    SYNTAX     Gauge32
    MAX-ACCESS read-only
    STATUS     current
    DESCRIPTION
	    "FXDstCopyToOpTotal."
    ::= { informationStoreMailboxEntry 104 }

ismFXDstPutBufferOpRate OBJECT-TYPE
    SYNTAX     Gauge32
    MAX-ACCESS read-only
    STATUS     current
    DESCRIPTION
	    "FXDstPutBufferOpRate."
    ::= { informationStoreMailboxEntry 105 }

ismFXDstPutBufferOpTotal OBJECT-TYPE
    SYNTAX     Gauge32
    MAX-ACCESS read-only
    STATUS     current
    DESCRIPTION
	    "FXDstPutBufferOpTotal."
    ::= { informationStoreMailboxEntry 106 }

ismFXGetBufferCurrentCallerCount OBJECT-TYPE
    SYNTAX     Gauge32
    MAX-ACCESS read-only
    STATUS     current
    DESCRIPTION
	    "Simultaneous FXGetBuffer rops being called."
    ::= { informationStoreMailboxEntry 107 }

ismFXGetBufferCurrentUsersExec OBJECT-TYPE
    SYNTAX     Gauge32
    MAX-ACCESS read-only
    STATUS     current
    DESCRIPTION
	    "Simultaneous FXGetBuffer rops being executed."
    ::= { informationStoreMailboxEntry 108 }

ismFXGetBufferRopsAccepted OBJECT-TYPE
    SYNTAX     Gauge32
    MAX-ACCESS read-only
    STATUS     current
    DESCRIPTION
	    "The total number of FXGetBuffer rops
	    accepted."
    ::= { informationStoreMailboxEntry 109 }

ismFXGetBufferRopsAcceptedPerSec OBJECT-TYPE
    SYNTAX     Gauge32
    MAX-ACCESS read-only
    STATUS     current
    DESCRIPTION
	    "FXGetBuffer rops calls accepted per sec."
    ::= { informationStoreMailboxEntry 110 }

ismFXGetBufferRopsCalled OBJECT-TYPE
    SYNTAX     Gauge32
    MAX-ACCESS read-only
    STATUS     current
    DESCRIPTION
	    "The total number of FXGetBuffer rops."
    ::= { informationStoreMailboxEntry 111 }

ismFXGetBufferRopsCalledPerSec OBJECT-TYPE
    SYNTAX     Gauge32
    MAX-ACCESS read-only
    STATUS     current
    DESCRIPTION
	    "Number of FXGetBuffer rops per sec."
    ::= { informationStoreMailboxEntry 112 }

ismFXGetBufferRopsDenied OBJECT-TYPE
    SYNTAX     Gauge32
    MAX-ACCESS read-only
    STATUS     current
    DESCRIPTION
	    "The total number of FXGetBuffer rops denied."
    ::= { informationStoreMailboxEntry 113 }

ismFXGetBufferRopsDeniedPerSec OBJECT-TYPE
    SYNTAX     Gauge32
    MAX-ACCESS read-only
    STATUS     current
    DESCRIPTION
	    "FXGetBuffer rops denied per sec."
    ::= { informationStoreMailboxEntry 114 }

ismFXGetIncrStateOpRate OBJECT-TYPE
    SYNTAX     Gauge32
    MAX-ACCESS read-only
    STATUS     current
    DESCRIPTION
	    "FXGetIncrStateOpRate."
    ::= { informationStoreMailboxEntry 115 }

ismFXGetIncrStateOpTotal OBJECT-TYPE
    SYNTAX     Gauge32
    MAX-ACCESS read-only
    STATUS     current
    DESCRIPTION
	    "FXGetIncrStateOpTotal."
    ::= { informationStoreMailboxEntry 116 }

ismFXSrcCopyFolderOpRate OBJECT-TYPE
    SYNTAX     Gauge32
    MAX-ACCESS read-only
    STATUS     current
    DESCRIPTION
	    "FXSrcCopyFolderOpRate."
    ::= { informationStoreMailboxEntry 117 }

ismFXSrcCopyFolderOpTotal OBJECT-TYPE
    SYNTAX     Gauge32
    MAX-ACCESS read-only
    STATUS     current
    DESCRIPTION
	    "FXSrcCopyFolderOpTotal."
    ::= { informationStoreMailboxEntry 118 }

ismFXSrcCopyMessagesOpRate OBJECT-TYPE
    SYNTAX     Gauge32
    MAX-ACCESS read-only
    STATUS     current
    DESCRIPTION
	    "FXSrcCopyMessagesOpRate."
    ::= { informationStoreMailboxEntry 119 }

ismFXSrcCopyMessagesOpTotal OBJECT-TYPE
    SYNTAX     Gauge32
    MAX-ACCESS read-only
    STATUS     current
    DESCRIPTION
	    "FXSrcCopyMessagesOpTotal."
    ::= { informationStoreMailboxEntry 120 }

ismFXSrcCopyPropsOpRate OBJECT-TYPE
    SYNTAX     Gauge32
    MAX-ACCESS read-only
    STATUS     current
    DESCRIPTION
	    "FXSrcCopyPropsOpRate."
    ::= { informationStoreMailboxEntry 121 }

ismFXSrcCopyPropsOpTotal OBJECT-TYPE
    SYNTAX     Gauge32
    MAX-ACCESS read-only
    STATUS     current
    DESCRIPTION
	    "FXSrcCopyPropsOpTotal."
    ::= { informationStoreMailboxEntry 122 }

ismFXSrcCopyToOpRate OBJECT-TYPE
    SYNTAX     Gauge32
    MAX-ACCESS read-only
    STATUS     current
    DESCRIPTION
	    "FXSrcCopyToOpRate."
    ::= { informationStoreMailboxEntry 123 }

ismFXSrcCopyToOpTotal OBJECT-TYPE
    SYNTAX     Gauge32
    MAX-ACCESS read-only
    STATUS     current
    DESCRIPTION
	    "FXSrcCopyToOpTotal."
    ::= { informationStoreMailboxEntry 124 }

ismFXSrcGetBufferOpRate OBJECT-TYPE
    SYNTAX     Gauge32
    MAX-ACCESS read-only
    STATUS     current
    DESCRIPTION
	    "FXSrcGetBufferOpRate."
    ::= { informationStoreMailboxEntry 125 }

ismFXSrcGetBufferOpTotal OBJECT-TYPE
    SYNTAX     Gauge32
    MAX-ACCESS read-only
    STATUS     current
    DESCRIPTION
	    "FXSrcGetBufferOpTotal."
    ::= { informationStoreMailboxEntry 126 }

ismGetAdrListOpRate OBJECT-TYPE
    SYNTAX     Gauge32
    MAX-ACCESS read-only
    STATUS     current
    DESCRIPTION
	    "GetAdrListOpRate."
    ::= { informationStoreMailboxEntry 127 }

ismGetAdrListOpTotal OBJECT-TYPE
    SYNTAX     Gauge32
    MAX-ACCESS read-only
    STATUS     current
    DESCRIPTION
	    "GetAdrListOpTotal."
    ::= { informationStoreMailboxEntry 128 }

ismGetAllPerUserLtidsOpRate OBJECT-TYPE
    SYNTAX     Gauge32
    MAX-ACCESS read-only
    STATUS     current
    DESCRIPTION
	    "GetAllPerUserLtidsOpRate."
    ::= { informationStoreMailboxEntry 129 }

ismGetAllPerUserLtidsOpTotal OBJECT-TYPE
    SYNTAX     Gauge32
    MAX-ACCESS read-only
    STATUS     current
    DESCRIPTION
	    "GetAllPerUserLtidsOpTotal."
    ::= { informationStoreMailboxEntry 130 }

ismGetCollapseStateOpRate OBJECT-TYPE
    SYNTAX     Gauge32
    MAX-ACCESS read-only
    STATUS     current
    DESCRIPTION
	    "GetCollapseStateOpRate."
    ::= { informationStoreMailboxEntry 131 }

ismGetCollapseStateOpTotal OBJECT-TYPE
    SYNTAX     Gauge32
    MAX-ACCESS read-only
    STATUS     current
    DESCRIPTION
	    "GetCollapseStateOpTotal."
    ::= { informationStoreMailboxEntry 132 }

ismGetFileHandlePropOpRate OBJECT-TYPE
    SYNTAX     Gauge32
    MAX-ACCESS read-only
    STATUS     current
    DESCRIPTION
	    "GetFileHandlePropOpRate"
    ::= { informationStoreMailboxEntry 133 }

ismGetFileHandlePropOpTotal OBJECT-TYPE
    SYNTAX     Gauge32
    MAX-ACCESS read-only
    STATUS     current
    DESCRIPTION
	    "GetFileHandlePropOpTotal"
    ::= { informationStoreMailboxEntry 134 }

ismGetFoldersTableRpcIntfRate OBJECT-TYPE
    SYNTAX     Gauge32
    MAX-ACCESS read-only
    STATUS     current
    DESCRIPTION
	    "GetFoldersTableRpcIntfRate."
    ::= { informationStoreMailboxEntry 135 }

ismGetFoldersTableRpcIntfTotal OBJECT-TYPE
    SYNTAX     Gauge32
    MAX-ACCESS read-only
    STATUS     current
    DESCRIPTION
	    "GetFoldersTableRpcIntfTotal."
    ::= { informationStoreMailboxEntry 136 }

ismGetIDsFromNamesOpRate OBJECT-TYPE
    SYNTAX     Gauge32
    MAX-ACCESS read-only
    STATUS     current
    DESCRIPTION
	    "GetIDsFromNamesOpRate."
    ::= { informationStoreMailboxEntry 137 }

ismGetIDsFromNamesOpTotal OBJECT-TYPE
    SYNTAX     Gauge32
    MAX-ACCESS read-only
    STATUS     current
    DESCRIPTION
	    "GetIDsFromNamesOpTotal."
    ::= { informationStoreMailboxEntry 138 }

ismGetLocalRepIdsOpRate OBJECT-TYPE
    SYNTAX     Gauge32
    MAX-ACCESS read-only
    STATUS     current
    DESCRIPTION
	    "GetLocalRepIdsOpRate."
    ::= { informationStoreMailboxEntry 139 }

ismGetLocalRepIdsOpTotal OBJECT-TYPE
    SYNTAX     Gauge32
    MAX-ACCESS read-only
    STATUS     current
    DESCRIPTION
	    "GetLocalRepIdsOpTotal."
    ::= { informationStoreMailboxEntry 140 }

ismGetMailboxTableRpcIntfRate OBJECT-TYPE
    SYNTAX     Gauge32
    MAX-ACCESS read-only
    STATUS     current
    DESCRIPTION
	    "GetMailboxTableRpcIntfRate."
    ::= { informationStoreMailboxEntry 141 }

ismGetMailboxTableRpcIntfTotal OBJECT-TYPE
    SYNTAX     Gauge32
    MAX-ACCESS read-only
    STATUS     current
    DESCRIPTION
	    "GetMailboxTableRpcIntfTotal."
    ::= { informationStoreMailboxEntry 142 }

ismGetMessagePropOpRate OBJECT-TYPE
    SYNTAX     Gauge32
    MAX-ACCESS read-only
    STATUS     current
    DESCRIPTION
	    "GetMessagePropOpRate."
    ::= { informationStoreMailboxEntry 143 }

ismGetMessagePropOpTotal OBJECT-TYPE
    SYNTAX     Gauge32
    MAX-ACCESS read-only
    STATUS     current
    DESCRIPTION
	    "GetMessagePropOpTotal."
    ::= { informationStoreMailboxEntry 144 }

ismGetMessageStatusOpRate OBJECT-TYPE
    SYNTAX     Gauge32
    MAX-ACCESS read-only
    STATUS     current
    DESCRIPTION
	    "GetMessageStatusOpRate."
    ::= { informationStoreMailboxEntry 145 }

ismGetMessageStatusOpTotal OBJECT-TYPE
    SYNTAX     Gauge32
    MAX-ACCESS read-only
    STATUS     current
    DESCRIPTION
	    "GetMessageStatusOpTotal."
    ::= { informationStoreMailboxEntry 146 }

ismGetNamesFromIDsOpRate OBJECT-TYPE
    SYNTAX     Gauge32
    MAX-ACCESS read-only
    STATUS     current
    DESCRIPTION
	    "GetNamesFromIDsOpRate."
    ::= { informationStoreMailboxEntry 147 }

ismGetNamesFromIDsOpTotal OBJECT-TYPE
    SYNTAX     Gauge32
    MAX-ACCESS read-only
    STATUS     current
    DESCRIPTION
	    "GetNamesFromIDsOpTotal."
    ::= { informationStoreMailboxEntry 148 }

ismGetOwningMDBsOpRate OBJECT-TYPE
    SYNTAX     Gauge32
    MAX-ACCESS read-only
    STATUS     current
    DESCRIPTION
	    "GetOwningMDBsOpRate."
    ::= { informationStoreMailboxEntry 149 }

ismGetOwningMDBsOpTotal OBJECT-TYPE
    SYNTAX     Gauge32
    MAX-ACCESS read-only
    STATUS     current
    DESCRIPTION
	    "GetOwningMDBsOpTotal."
    ::= { informationStoreMailboxEntry 150 }

ismGetPerUserGuidOpRate OBJECT-TYPE
    SYNTAX     Gauge32
    MAX-ACCESS read-only
    STATUS     current
    DESCRIPTION
	    "GetPerUserGuidOpRate."
    ::= { informationStoreMailboxEntry 151 }

ismGetPerUserGuidOpTotal OBJECT-TYPE
    SYNTAX     Gauge32
    MAX-ACCESS read-only
    STATUS     current
    DESCRIPTION
	    "GetPerUserGuidOpTotal."
    ::= { informationStoreMailboxEntry 152 }

ismGetPerUserLtidsOpRate OBJECT-TYPE
    SYNTAX     Gauge32
    MAX-ACCESS read-only
    STATUS     current
    DESCRIPTION
	    "GetPerUserLtidsOpRate."
    ::= { informationStoreMailboxEntry 153 }

ismGetPerUserLtidsOpTotal OBJECT-TYPE
    SYNTAX     Gauge32
    MAX-ACCESS read-only
    STATUS     current
    DESCRIPTION
	    "GetPerUserLtidsOpTotal."
    ::= { informationStoreMailboxEntry 154 }

ismGetPerUserOpRate OBJECT-TYPE
    SYNTAX     Gauge32
    MAX-ACCESS read-only
    STATUS     current
    DESCRIPTION
	    "GetPerUserOpRate."
    ::= { informationStoreMailboxEntry 155 }

ismGetPerUserOpTotal OBJECT-TYPE
    SYNTAX     Gauge32
    MAX-ACCESS read-only
    STATUS     current
    DESCRIPTION
	    "GetPerUserOpTotal."
    ::= { informationStoreMailboxEntry 156 }

ismGetPropertyOperationsPerSec OBJECT-TYPE
    SYNTAX     Gauge32
    MAX-ACCESS read-only
    STATUS     current
    DESCRIPTION
	    "GetProperty Operations/sec is the rate of
	    GetProperty requests in the mailbox store."
    ::= { informationStoreMailboxEntry 157 }

ismGetPropListOpRate OBJECT-TYPE
    SYNTAX     Gauge32
    MAX-ACCESS read-only
    STATUS     current
    DESCRIPTION
	    "GetPropListOpRate."
    ::= { informationStoreMailboxEntry 158 }

ismGetPropListOpTotal OBJECT-TYPE
    SYNTAX     Gauge32
    MAX-ACCESS read-only
    STATUS     current
    DESCRIPTION
	    "GetPropListOpTotal."
    ::= { informationStoreMailboxEntry 159 }

ismGetReceiveFolderOpRate OBJECT-TYPE
    SYNTAX     Gauge32
    MAX-ACCESS read-only
    STATUS     current
    DESCRIPTION
	    "GetReceiveFolderOpRate."
    ::= { informationStoreMailboxEntry 160 }

ismGetReceiveFolderOpTotal OBJECT-TYPE
    SYNTAX     Gauge32
    MAX-ACCESS read-only
    STATUS     current
    DESCRIPTION
	    "GetReceiveFolderOpTotal."
    ::= { informationStoreMailboxEntry 161 }

ismGetReceiveFolderTableOpRate OBJECT-TYPE
    SYNTAX     Gauge32
    MAX-ACCESS read-only
    STATUS     current
    DESCRIPTION
	    "GetReceiveFolderTableOpRate."
    ::= { informationStoreMailboxEntry 162 }

ismGetReceiveFolderTableOpTotal OBJECT-TYPE
    SYNTAX     Gauge32
    MAX-ACCESS read-only
    STATUS     current
    DESCRIPTION
	    "GetReceiveFolderTableOpTotal."
    ::= { informationStoreMailboxEntry 163 }

ismGetRecipColumnsOpRate OBJECT-TYPE
    SYNTAX     Gauge32
    MAX-ACCESS read-only
    STATUS     current
    DESCRIPTION
	    "Get the available columns in a recipient
	    table."
    ::= { informationStoreMailboxEntry 164 }

ismGetRecipColumnsOpTotal OBJECT-TYPE
    SYNTAX     Gauge32
    MAX-ACCESS read-only
    STATUS     current
    DESCRIPTION
	    "Get the available columns in a recipient
	    table."
    ::= { informationStoreMailboxEntry 165 }

ismGetRecipCountOpRate OBJECT-TYPE
    SYNTAX     Gauge32
    MAX-ACCESS read-only
    STATUS     current
    DESCRIPTION
	    "GetRecipCountOpRate."
    ::= { informationStoreMailboxEntry 166 }

ismGetRecipCountOpTotal OBJECT-TYPE
    SYNTAX     Gauge32
    MAX-ACCESS read-only
    STATUS     current
    DESCRIPTION
	    "GetRecipCountOpTotal."
    ::= { informationStoreMailboxEntry 167 }

ismGetRecipOpRate OBJECT-TYPE
    SYNTAX     Gauge32
    MAX-ACCESS read-only
    STATUS     current
    DESCRIPTION
	    "GetRecipOpRate."
    ::= { informationStoreMailboxEntry 168 }

ismGetRecipOpTotal OBJECT-TYPE
    SYNTAX     Gauge32
    MAX-ACCESS read-only
    STATUS     current
    DESCRIPTION
	    "GetRecipOpTotal."
    ::= { informationStoreMailboxEntry 169 }

ismGetRightsOpRate OBJECT-TYPE
    SYNTAX     Gauge32
    MAX-ACCESS read-only
    STATUS     current
    DESCRIPTION
	    "GetRightsOpRate."
    ::= { informationStoreMailboxEntry 170 }

ismGetRightsOpTotal OBJECT-TYPE
    SYNTAX     Gauge32
    MAX-ACCESS read-only
    STATUS     current
    DESCRIPTION
	    "GetRightsOpTotal."
    ::= { informationStoreMailboxEntry 171 }

ismGetSearchCriteriaOpRate OBJECT-TYPE
    SYNTAX     Gauge32
    MAX-ACCESS read-only
    STATUS     current
    DESCRIPTION
	    "GetSearchCriteriaOpRate."
    ::= { informationStoreMailboxEntry 172 }

ismGetSearchCriteriaOpTotal OBJECT-TYPE
    SYNTAX     Gauge32
    MAX-ACCESS read-only
    STATUS     current
    DESCRIPTION
	    "GetSearchCriteriaOpTotal."
    ::= { informationStoreMailboxEntry 173 }

ismGetStatusOpRate OBJECT-TYPE
    SYNTAX     Gauge32
    MAX-ACCESS read-only
    STATUS     current
    DESCRIPTION
	    "GetStatusOpRate."
    ::= { informationStoreMailboxEntry 174 }

ismGetStatusOpTotal OBJECT-TYPE
    SYNTAX     Gauge32
    MAX-ACCESS read-only
    STATUS     current
    DESCRIPTION
	    "GetStatusOpTotal."
    ::= { informationStoreMailboxEntry 175 }

ismGetStreamSizeOpRate OBJECT-TYPE
    SYNTAX     Gauge32
    MAX-ACCESS read-only
    STATUS     current
    DESCRIPTION
	    "GetStreamSizeOpRate."
    ::= { informationStoreMailboxEntry 176 }

ismGetStreamSizeOpTotal OBJECT-TYPE
    SYNTAX     Gauge32
    MAX-ACCESS read-only
    STATUS     current
    DESCRIPTION
	    "GetStreamSizeOpTotal."
    ::= { informationStoreMailboxEntry 177 }

ismGetTableOpRate OBJECT-TYPE
    SYNTAX     Gauge32
    MAX-ACCESS read-only
    STATUS     current
    DESCRIPTION
	    "GetTableOpRate."
    ::= { informationStoreMailboxEntry 178 }

ismGetTableOpTotal OBJECT-TYPE
    SYNTAX     Gauge32
    MAX-ACCESS read-only
    STATUS     current
    DESCRIPTION
	    "GetTableOpTotal."
    ::= { informationStoreMailboxEntry 179 }

ismGetXhdrListOpRate OBJECT-TYPE
    SYNTAX     Gauge32
    MAX-ACCESS read-only
    STATUS     current
    DESCRIPTION
	    "GetXhdrListOpRate."
    ::= { informationStoreMailboxEntry 180 }

ismGetXhdrListOpTotal OBJECT-TYPE
    SYNTAX     Gauge32
    MAX-ACCESS read-only
    STATUS     current
    DESCRIPTION
	    "GetXhdrListOpTotal."
    ::= { informationStoreMailboxEntry 181 }

ismIdFromLtidOpRate OBJECT-TYPE
    SYNTAX     Gauge32
    MAX-ACCESS read-only
    STATUS     current
    DESCRIPTION
	    "IdFromLtidOpRate."
    ::= { informationStoreMailboxEntry 182 }

ismIdFromLtidOpTotal OBJECT-TYPE
    SYNTAX     Gauge32
    MAX-ACCESS read-only
    STATUS     current
    DESCRIPTION
	    "IdFromLtidOpTotal."
    ::= { informationStoreMailboxEntry 183 }

ismImportDeleteOpRate OBJECT-TYPE
    SYNTAX     Gauge32
    MAX-ACCESS read-only
    STATUS     current
    DESCRIPTION
	    "ImportDeleteOpRate."
    ::= { informationStoreMailboxEntry 184 }

ismImportDeleteOpTotal OBJECT-TYPE
    SYNTAX     Gauge32
    MAX-ACCESS read-only
    STATUS     current
    DESCRIPTION
	    "ImportDeleteOpTotal."
    ::= { informationStoreMailboxEntry 185 }

ismImportHierChgOpRate OBJECT-TYPE
    SYNTAX     Gauge32
    MAX-ACCESS read-only
    STATUS     current
    DESCRIPTION
	    "ImportHierChgOpRate."
    ::= { informationStoreMailboxEntry 186 }

ismImportHierChgOpTotal OBJECT-TYPE
    SYNTAX     Gauge32
    MAX-ACCESS read-only
    STATUS     current
    DESCRIPTION
	    "ImportHierChgOpTotal."
    ::= { informationStoreMailboxEntry 187 }

ismImportHierDelOpRate OBJECT-TYPE
    SYNTAX     Gauge32
    MAX-ACCESS read-only
    STATUS     current
    DESCRIPTION
	    "ImportHierDelOpRate."
    ::= { informationStoreMailboxEntry 188 }

ismImportHierDelOpTotal OBJECT-TYPE
    SYNTAX     Gauge32
    MAX-ACCESS read-only
    STATUS     current
    DESCRIPTION
	    "ImportHierDelOpTotal."
    ::= { informationStoreMailboxEntry 189 }

ismImportMsgChgOpRate OBJECT-TYPE
    SYNTAX     Gauge32
    MAX-ACCESS read-only
    STATUS     current
    DESCRIPTION
	    "ImportMsgChgOpRate."
    ::= { informationStoreMailboxEntry 190 }

ismImportMsgChgOpTotal OBJECT-TYPE
    SYNTAX     Gauge32
    MAX-ACCESS read-only
    STATUS     current
    DESCRIPTION
	    "ImportMsgChgOpTotal."
    ::= { informationStoreMailboxEntry 191 }

ismImportMsgMoveOpRate OBJECT-TYPE
    SYNTAX     Gauge32
    MAX-ACCESS read-only
    STATUS     current
    DESCRIPTION
	    "ImportMsgMoveOpRate."
    ::= { informationStoreMailboxEntry 192 }

ismImportMsgMoveOpTotal OBJECT-TYPE
    SYNTAX     Gauge32
    MAX-ACCESS read-only
    STATUS     current
    DESCRIPTION
	    "ImportMsgMoveOpTotal."
    ::= { informationStoreMailboxEntry 193 }

ismImportReadsOpRate OBJECT-TYPE
    SYNTAX     Gauge32
    MAX-ACCESS read-only
    STATUS     current
    DESCRIPTION
	    "ImportReadsOpRate."
    ::= { informationStoreMailboxEntry 194 }

ismImportReadsOpTotal OBJECT-TYPE
    SYNTAX     Gauge32
    MAX-ACCESS read-only
    STATUS     current
    DESCRIPTION
	    "ImportReadsOpTotal."
    ::= { informationStoreMailboxEntry 195 }

ismIncrCfgOpRate OBJECT-TYPE
    SYNTAX     Gauge32
    MAX-ACCESS read-only
    STATUS     current
    DESCRIPTION
	    "IncrCfgOpRate."
    ::= { informationStoreMailboxEntry 196 }

ismIncrCfgOpTotal OBJECT-TYPE
    SYNTAX     Gauge32
    MAX-ACCESS read-only
    STATUS     current
    DESCRIPTION
	    "IncrCfgOpTotal."
    ::= { informationStoreMailboxEntry 197 }

ismLocalDeliveryOpRate OBJECT-TYPE
    SYNTAX     Gauge32
    MAX-ACCESS read-only
    STATUS     current
    DESCRIPTION
	    "LocalDeliveryOpRate."
    ::= { informationStoreMailboxEntry 198 }

ismLocalDeliveryOpTotal OBJECT-TYPE
    SYNTAX     Gauge32
    MAX-ACCESS read-only
    STATUS     current
    DESCRIPTION
	    "Number of messages delivered locally through
	    the Local Delivery RPCINTF API."
    ::= { informationStoreMailboxEntry 199 }

ismLockRegionStreamOpRate OBJECT-TYPE
    SYNTAX     Gauge32
    MAX-ACCESS read-only
    STATUS     current
    DESCRIPTION
	    "LockRegionStreamOpRate."
    ::= { informationStoreMailboxEntry 200 }

ismLockRegionStreamOpTotal OBJECT-TYPE
    SYNTAX     Gauge32
    MAX-ACCESS read-only
    STATUS     current
    DESCRIPTION
	    "LockRegionStreamOpTotal."
    ::= { informationStoreMailboxEntry 201 }

ismLtidFromIdOpRate OBJECT-TYPE
    SYNTAX     Gauge32
    MAX-ACCESS read-only
    STATUS     current
    DESCRIPTION
	    "LtidFromIdOpRate."
    ::= { informationStoreMailboxEntry 202 }

ismLtidFromIdOpTotal OBJECT-TYPE
    SYNTAX     Gauge32
    MAX-ACCESS read-only
    STATUS     current
    DESCRIPTION
	    "LtidFromIdOpTotal."
    ::= { informationStoreMailboxEntry 203 }

ismMessageRcpntsDeliveredPerSec OBJECT-TYPE
    SYNTAX     Gauge32
    MAX-ACCESS read-only
    STATUS     current
    DESCRIPTION
	    "Message Recipients Delivered/sec is the rate
	    at which the message recipients receive a
	    message in the mailbox store."
    ::= { informationStoreMailboxEntry 204 }

ismMessagesDeliveredPerSec OBJECT-TYPE
    SYNTAX     Gauge32
    MAX-ACCESS read-only
    STATUS     current
    DESCRIPTION
	    "Messages Delivered/sec is the rate at which
	    messages are delivered to the the mailbox
	    store."
    ::= { informationStoreMailboxEntry 205 }

ismModifyACLOpRate OBJECT-TYPE
    SYNTAX     Gauge32
    MAX-ACCESS read-only
    STATUS     current
    DESCRIPTION
	    "ModifyACLOpRate."
    ::= { informationStoreMailboxEntry 206 }

ismModifyACLOpTotal OBJECT-TYPE
    SYNTAX     Gauge32
    MAX-ACCESS read-only
    STATUS     current
    DESCRIPTION
	    "ModifyACLOpTotal."
    ::= { informationStoreMailboxEntry 207 }

ismModifyMvPropOpRate OBJECT-TYPE
    SYNTAX     Gauge32
    MAX-ACCESS read-only
    STATUS     current
    DESCRIPTION
	    "ModifyMvPropOpRate."
    ::= { informationStoreMailboxEntry 208 }

ismModifyMvPropOpTotal OBJECT-TYPE
    SYNTAX     Gauge32
    MAX-ACCESS read-only
    STATUS     current
    DESCRIPTION
	    "ModifyMvPropOpTotal."
    ::= { informationStoreMailboxEntry 209 }

ismModifyRcpntsOperationsPerSec OBJECT-TYPE
    SYNTAX     Gauge32
    MAX-ACCESS read-only
    STATUS     current
    DESCRIPTION
	    "ModifyRecipients Operations/sec is the rate of
	    ModifyRecipients requests in the mailbox
	    store."
    ::= { informationStoreMailboxEntry 210 }

ismModifyRulesOpRate OBJECT-TYPE
    SYNTAX     Gauge32
    MAX-ACCESS read-only
    STATUS     current
    DESCRIPTION
	    "ModifyRulesOpRate."
    ::= { informationStoreMailboxEntry 211 }

ismModifyRulesOpTotal OBJECT-TYPE
    SYNTAX     Gauge32
    MAX-ACCESS read-only
    STATUS     current
    DESCRIPTION
	    "ModifyRulesOpTotal."
    ::= { informationStoreMailboxEntry 212 }

ismModifyRulesRate OBJECT-TYPE
    SYNTAX     Gauge32
    MAX-ACCESS read-only
    STATUS     current
    DESCRIPTION
	    "ModifyRulesRate."
    ::= { informationStoreMailboxEntry 213 }

ismModifyRulesTotal OBJECT-TYPE
    SYNTAX     Gauge32
    MAX-ACCESS read-only
    STATUS     current
    DESCRIPTION
	    "ModifyRulesTotal."
    ::= { informationStoreMailboxEntry 214 }

ismMoveCopyFolderOpRate OBJECT-TYPE
    SYNTAX     Gauge32
    MAX-ACCESS read-only
    STATUS     current
    DESCRIPTION
	    "MoveCopyFolderOpRate."
    ::= { informationStoreMailboxEntry 215 }

ismMoveCopyFolderOpTotal OBJECT-TYPE
    SYNTAX     Gauge32
    MAX-ACCESS read-only
    STATUS     current
    DESCRIPTION
	    "MoveCopyFolderOpTotal."
    ::= { informationStoreMailboxEntry 216 }

ismMoveCopyMessagesOpRate OBJECT-TYPE
    SYNTAX     Gauge32
    MAX-ACCESS read-only
    STATUS     current
    DESCRIPTION
	    "MoveCopyMessagesOpRate."
    ::= { informationStoreMailboxEntry 217 }

ismMoveCopyMessagesOpTotal OBJECT-TYPE
    SYNTAX     Gauge32
    MAX-ACCESS read-only
    STATUS     current
    DESCRIPTION
	    "MoveCopyMessagesOpTotal."
    ::= { informationStoreMailboxEntry 218 }

ismNextNewsgroupOpRate OBJECT-TYPE
    SYNTAX     Gauge32
    MAX-ACCESS read-only
    STATUS     current
    DESCRIPTION
	    "NextNewsgroupOpRate."
    ::= { informationStoreMailboxEntry 219 }

ismNextNewsgroupOpTotal OBJECT-TYPE
    SYNTAX     Gauge32
    MAX-ACCESS read-only
    STATUS     current
    DESCRIPTION
	    "NextNewsgroupOpTotal."
    ::= { informationStoreMailboxEntry 220 }

ismNukeRecipientsOpRate OBJECT-TYPE
    SYNTAX     Gauge32
    MAX-ACCESS read-only
    STATUS     current
    DESCRIPTION
	    "NukeRecipientsOpRate."
    ::= { informationStoreMailboxEntry 221 }

ismNukeRecipientsOpTotal OBJECT-TYPE
    SYNTAX     Gauge32
    MAX-ACCESS read-only
    STATUS     current
    DESCRIPTION
	    "NukeRecipientsOpTotal."
    ::= { informationStoreMailboxEntry 222 }

ismOpenAdvisorOpRate OBJECT-TYPE
    SYNTAX     Gauge32
    MAX-ACCESS read-only
    STATUS     current
    DESCRIPTION
	    "OpenAdvisorOpRate."
    ::= { informationStoreMailboxEntry 223 }

ismOpenAdvisorOpTotal OBJECT-TYPE
    SYNTAX     Gauge32
    MAX-ACCESS read-only
    STATUS     current
    DESCRIPTION
	    "OpenAdvisorOpTotal."
    ::= { informationStoreMailboxEntry 224 }

ismOpenAttachOpRate OBJECT-TYPE
    SYNTAX     Gauge32
    MAX-ACCESS read-only
    STATUS     current
    DESCRIPTION
	    "OpenAttachOpRate."
    ::= { informationStoreMailboxEntry 225 }

ismOpenAttachOpTotal OBJECT-TYPE
    SYNTAX     Gauge32
    MAX-ACCESS read-only
    STATUS     current
    DESCRIPTION
	    "OpenAttachOpTotal."
    ::= { informationStoreMailboxEntry 226 }

ismOpenCollectOpRate OBJECT-TYPE
    SYNTAX     Gauge32
    MAX-ACCESS read-only
    STATUS     current
    DESCRIPTION
	    "OpenCollectOpRate."
    ::= { informationStoreMailboxEntry 227 }

ismOpenCollectOpTotal OBJECT-TYPE
    SYNTAX     Gauge32
    MAX-ACCESS read-only
    STATUS     current
    DESCRIPTION
	    "OpenCollectOpTotal."
    ::= { informationStoreMailboxEntry 228 }

ismOpenFolderByNntpNameOpRate OBJECT-TYPE
    SYNTAX     Gauge32
    MAX-ACCESS read-only
    STATUS     current
    DESCRIPTION
	    "OpenFolderByNntpNameOpRate."
    ::= { informationStoreMailboxEntry 229 }

ismOpenFolderByNntpNameOpTotal OBJECT-TYPE
    SYNTAX     Gauge32
    MAX-ACCESS read-only
    STATUS     current
    DESCRIPTION
	    "OpenFolderByNntpNameOpTotal."
    ::= { informationStoreMailboxEntry 230 }

ismOpenImailConversionObjOpRate OBJECT-TYPE
    SYNTAX     Gauge32
    MAX-ACCESS read-only
    STATUS     current
    DESCRIPTION
	    "OpenImailConversionObjectOpRate."
    ::= { informationStoreMailboxEntry 231 }

ismOpenImailConversionObjOpTotal OBJECT-TYPE
    SYNTAX     Gauge32
    MAX-ACCESS read-only
    STATUS     current
    DESCRIPTION
	    "OpenImailConversionObjectOpTotal."
    ::= { informationStoreMailboxEntry 232 }

ismOpenImailConversionStrOpRate OBJECT-TYPE
    SYNTAX     Gauge32
    MAX-ACCESS read-only
    STATUS     current
    DESCRIPTION
	    "OpenImailConversionStreamOpRate."
    ::= { informationStoreMailboxEntry 233 }

ismOpenImailConversionStrOpTotal OBJECT-TYPE
    SYNTAX     Gauge32
    MAX-ACCESS read-only
    STATUS     current
    DESCRIPTION
	    "OpenImailConversionStreamOpTotal."
    ::= { informationStoreMailboxEntry 234 }

ismOpenMessageByArticleNumOpRate OBJECT-TYPE
    SYNTAX     Gauge32
    MAX-ACCESS read-only
    STATUS     current
    DESCRIPTION
	    "OpenMessageByArticleNumberOpRate."
    ::= { informationStoreMailboxEntry 235 }

ismOpenMessageByArticleNmOpTotal OBJECT-TYPE
    SYNTAX     Gauge32
    MAX-ACCESS read-only
    STATUS     current
    DESCRIPTION
	    "OpenMessageByArticleNumberOpTotal."
    ::= { informationStoreMailboxEntry 236 }

ismOpenMessageByMsgIdOpRate OBJECT-TYPE
    SYNTAX     Gauge32
    MAX-ACCESS read-only
    STATUS     current
    DESCRIPTION
	    "OpenMessageByMsgIdOpRate."
    ::= { informationStoreMailboxEntry 237 }

ismOpenMessageByMsgIdOpTotal OBJECT-TYPE
    SYNTAX     Gauge32
    MAX-ACCESS read-only
    STATUS     current
    DESCRIPTION
	    "OpenMessageByMsgIdOpTotal."
    ::= { informationStoreMailboxEntry 238 }

ismOpenMessagePropOpRate OBJECT-TYPE
    SYNTAX     Gauge32
    MAX-ACCESS read-only
    STATUS     current
    DESCRIPTION
	    "OpenMessagePropOpRate."
    ::= { informationStoreMailboxEntry 239 }

ismOpenMessagePropOpTotal OBJECT-TYPE
    SYNTAX     Gauge32
    MAX-ACCESS read-only
    STATUS     current
    DESCRIPTION
	    "OpenMessagePropOpTotal."
    ::= { informationStoreMailboxEntry 240 }

ismOpenStreamOperationsPerSec OBJECT-TYPE
    SYNTAX     Gauge32
    MAX-ACCESS read-only
    STATUS     current
    DESCRIPTION
	    "OpenStream Operations/sec is the rate of
	    OpenStream requests in the mailbox store."
    ::= { informationStoreMailboxEntry 241 }

ismPrepareReadRecipientsRate OBJECT-TYPE
    SYNTAX     Gauge32
    MAX-ACCESS read-only
    STATUS     current
    DESCRIPTION
	    "PrepareReadRecipientsRate."
    ::= { informationStoreMailboxEntry 242 }

ismPrepareReadRecipientsTotal OBJECT-TYPE
    SYNTAX     Gauge32
    MAX-ACCESS read-only
    STATUS     current
    DESCRIPTION
	    "PrepareReadRecipientsTotal."
    ::= { informationStoreMailboxEntry 243 }

ismQryNamedPropsOpRate OBJECT-TYPE
    SYNTAX     Gauge32
    MAX-ACCESS read-only
    STATUS     current
    DESCRIPTION
	    "QryNamedPropsOpRate."
    ::= { informationStoreMailboxEntry 244 }

ismQryNamedPropsOpTotal OBJECT-TYPE
    SYNTAX     Gauge32
    MAX-ACCESS read-only
    STATUS     current
    DESCRIPTION
	    "QryNamedPropsOpTotal."
    ::= { informationStoreMailboxEntry 245 }

ismQueryColumnsAllOpRate OBJECT-TYPE
    SYNTAX     Gauge32
    MAX-ACCESS read-only
    STATUS     current
    DESCRIPTION
	    "QueryColumnsAllOpRate."
    ::= { informationStoreMailboxEntry 246 }

ismQueryColumnsAllOpTotal OBJECT-TYPE
    SYNTAX     Gauge32
    MAX-ACCESS read-only
    STATUS     current
    DESCRIPTION
	    "QueryColumnsAllOpTotal."
    ::= { informationStoreMailboxEntry 247 }

ismQueryPositionOperationsPerSec OBJECT-TYPE
    SYNTAX     Gauge32
    MAX-ACCESS read-only
    STATUS     current
    DESCRIPTION
	    "QueryPosition Operations/sec is the rate of
	    QueryPosition requests in the mailbox store."
    ::= { informationStoreMailboxEntry 248 }

ismQueryRowsOpRate OBJECT-TYPE
    SYNTAX     Gauge32
    MAX-ACCESS read-only
    STATUS     current
    DESCRIPTION
	    "QueryRowsOpRate."
    ::= { informationStoreMailboxEntry 249 }

ismQueryRowsOpTotal OBJECT-TYPE
    SYNTAX     Gauge32
    MAX-ACCESS read-only
    STATUS     current
    DESCRIPTION
	    "QueryRowsOpTotal."
    ::= { informationStoreMailboxEntry 250 }

ismReadStreamOpRate OBJECT-TYPE
    SYNTAX     Gauge32
    MAX-ACCESS read-only
    STATUS     current
    DESCRIPTION
	    "ReadStreamOpRate."
    ::= { informationStoreMailboxEntry 251 }

ismReadStreamOpTotal OBJECT-TYPE
    SYNTAX     Gauge32
    MAX-ACCESS read-only
    STATUS     current
    DESCRIPTION
	    "ReadStreamOpTotal."
    ::= { informationStoreMailboxEntry 252 }

ismRegICSNotifsOpRate OBJECT-TYPE
    SYNTAX     Gauge32
    MAX-ACCESS read-only
    STATUS     current
    DESCRIPTION
	    "RegICSNotifsOpRate."
    ::= { informationStoreMailboxEntry 253 }

ismRegICSNotifsOpTotal OBJECT-TYPE
    SYNTAX     Gauge32
    MAX-ACCESS read-only
    STATUS     current
    DESCRIPTION
	    "RegICSNotifsOpTotal."
    ::= { informationStoreMailboxEntry 254 }

ismRegisterNotifyOperationPerSec OBJECT-TYPE
    SYNTAX     Gauge32
    MAX-ACCESS read-only
    STATUS     current
    DESCRIPTION
	    "RegisterNotification Operations/sec is the
	    rate of RegisterNotification requests in the
	    mailbox store."
    ::= { informationStoreMailboxEntry 255 }

ismRegisterTableNotifyOpRate OBJECT-TYPE
    SYNTAX     Gauge32
    MAX-ACCESS read-only
    STATUS     current
    DESCRIPTION
	    "RegisterTableNotificationOpRate."
    ::= { informationStoreMailboxEntry 256 }

ismRegisterTableNotifyOpTotal OBJECT-TYPE
    SYNTAX     Gauge32
    MAX-ACCESS read-only
    STATUS     current
    DESCRIPTION
	    "RegisterTableNotificationOpTotal."
    ::= { informationStoreMailboxEntry 257 }

ismRenderMessageOpRate OBJECT-TYPE
    SYNTAX     Gauge32
    MAX-ACCESS read-only
    STATUS     current
    DESCRIPTION
	    "RenderMessageOpRate."
    ::= { informationStoreMailboxEntry 258 }

ismRenderMessageOpTotal OBJECT-TYPE
    SYNTAX     Gauge32
    MAX-ACCESS read-only
    STATUS     current
    DESCRIPTION
	    "RenderMessageOpTotal."
    ::= { informationStoreMailboxEntry 259 }

ismResetTableOpRate OBJECT-TYPE
    SYNTAX     Gauge32
    MAX-ACCESS read-only
    STATUS     current
    DESCRIPTION
	    "ResetTableOpRate."
    ::= { informationStoreMailboxEntry 260 }

ismResetTableOpTotal OBJECT-TYPE
    SYNTAX     Gauge32
    MAX-ACCESS read-only
    STATUS     current
    DESCRIPTION
	    "ResetTableOpTotal."
    ::= { informationStoreMailboxEntry 261 }

ismRestrictOperationsPerSec OBJECT-TYPE
    SYNTAX     Gauge32
    MAX-ACCESS read-only
    STATUS     current
    DESCRIPTION
	    "Restrict Operations/sec is the rate of
	    Restrict requests in the mailbox store."
    ::= { informationStoreMailboxEntry 262 }

ismRowsInACLListTable OBJECT-TYPE
    SYNTAX     Gauge32
    MAX-ACCESS read-only
    STATUS     current
    DESCRIPTION
	    "Total number of rows in the ACLList Table."
    ::= { informationStoreMailboxEntry 263 }

ismRowsInACLMemberTable OBJECT-TYPE
    SYNTAX     Gauge32
    MAX-ACCESS read-only
    STATUS     current
    DESCRIPTION
	    "Total number of rows in the ACLMember Table."
    ::= { informationStoreMailboxEntry 264 }

ismRowsInCategTables OBJECT-TYPE
    SYNTAX     Gauge32
    MAX-ACCESS read-only
    STATUS     current
    DESCRIPTION
	    "Total number of rows in the Categ Tables."
    ::= { informationStoreMailboxEntry 265 }

ismRowsInDeletedAttachmentsTable OBJECT-TYPE
    SYNTAX     Gauge32
    MAX-ACCESS read-only
    STATUS     current
    DESCRIPTION
	    "Total number of rows in the DeletedAttachments
	    Table."
    ::= { informationStoreMailboxEntry 266 }

ismRowsInDeletedFoldersTable OBJECT-TYPE
    SYNTAX     Gauge32
    MAX-ACCESS read-only
    STATUS     current
    DESCRIPTION
	    "Total number of rows in the DeletedFolders
	    Table."
    ::= { informationStoreMailboxEntry 267 }

ismRowsInDeletedMessagesTable OBJECT-TYPE
    SYNTAX     Gauge32
    MAX-ACCESS read-only
    STATUS     current
    DESCRIPTION
	    "Total number of rows in the DeletedMessages
	    Table."
    ::= { informationStoreMailboxEntry 268 }

ismRowsInDeliveredToTable OBJECT-TYPE
    SYNTAX     Gauge32
    MAX-ACCESS read-only
    STATUS     current
    DESCRIPTION
	    "Total number of rows in the DeliveredTo
	    Table."
    ::= { informationStoreMailboxEntry 269 }

ismRowsInFolderTombstoneTable OBJECT-TYPE
    SYNTAX     Gauge32
    MAX-ACCESS read-only
    STATUS     current
    DESCRIPTION
	    "Total number of rows in the Folder Tombstone
	    Table."
    ::= { informationStoreMailboxEntry 270 }

ismRowsInIdxAgeTable OBJECT-TYPE
    SYNTAX     Gauge32
    MAX-ACCESS read-only
    STATUS     current
    DESCRIPTION
	    "Total number of rows in the IdxAge Table."
    ::= { informationStoreMailboxEntry 271 }

ismRowsInMailboxTable OBJECT-TYPE
    SYNTAX     Gauge32
    MAX-ACCESS read-only
    STATUS     current
    DESCRIPTION
	    "Total number of rows in the Mailbox Table."
    ::= { informationStoreMailboxEntry 272 }

ismRowsInMessageTable OBJECT-TYPE
    SYNTAX     Gauge32
    MAX-ACCESS read-only
    STATUS     current
    DESCRIPTION
	    "Total number of rows in the Message Table."
    ::= { informationStoreMailboxEntry 273 }

ismRowsInMessageTombstoneTable OBJECT-TYPE
    SYNTAX     Gauge32
    MAX-ACCESS read-only
    STATUS     current
    DESCRIPTION
	    "Total number of rows in the Message Tombstone
	    Table."
    ::= { informationStoreMailboxEntry 274 }

ismRowsInMsgFolderTables OBJECT-TYPE
    SYNTAX     Gauge32
    MAX-ACCESS read-only
    STATUS     current
    DESCRIPTION
	    "Total number of rows in the MsgFolder Tables."
    ::= { informationStoreMailboxEntry 275 }

ismRowsInNamedPropsTable OBJECT-TYPE
    SYNTAX     Gauge32
    MAX-ACCESS read-only
    STATUS     current
    DESCRIPTION
	    "Total number of rows in the NamedProps Table."
    ::= { informationStoreMailboxEntry 276 }

ismRowsInNeedRNTable OBJECT-TYPE
    SYNTAX     Gauge32
    MAX-ACCESS read-only
    STATUS     current
    DESCRIPTION
	    "Total number of rows in the NeedRN Table."
    ::= { informationStoreMailboxEntry 277 }

ismRowsInPerUserReadTable OBJECT-TYPE
    SYNTAX     Gauge32
    MAX-ACCESS read-only
    STATUS     current
    DESCRIPTION
	    "Total number of rows in the PerUserRead
	    Table."
    ::= { informationStoreMailboxEntry 278 }

ismRowsInReceiveFoldersTable OBJECT-TYPE
    SYNTAX     Gauge32
    MAX-ACCESS read-only
    STATUS     current
    DESCRIPTION
	    "Total number of rows in the ReceiveFolders
	    Table."
    ::= { informationStoreMailboxEntry 279 }

ismRowsInReplicationTable OBJECT-TYPE
    SYNTAX     Gauge32
    MAX-ACCESS read-only
    STATUS     current
    DESCRIPTION
	    "Total number of rows in the Replication
	    Table."
    ::= { informationStoreMailboxEntry 280 }

ismRowsInReplidMapTable OBJECT-TYPE
    SYNTAX     Gauge32
    MAX-ACCESS read-only
    STATUS     current
    DESCRIPTION
	    "Total number of rows in the ReplidMap Table."
    ::= { informationStoreMailboxEntry 281 }

ismRowsInRulesTable OBJECT-TYPE
    SYNTAX     Gauge32
    MAX-ACCESS read-only
    STATUS     current
    DESCRIPTION
	    "Total number of rows in the Rules Table."
    ::= { informationStoreMailboxEntry 282 }

ismRowsInSearchQueueTable OBJECT-TYPE
    SYNTAX     Gauge32
    MAX-ACCESS read-only
    STATUS     current
    DESCRIPTION
	    "Total number of rows in the SearchQueue
	    Table."
    ::= { informationStoreMailboxEntry 283 }

ismRowsInTimedEventsTable OBJECT-TYPE
    SYNTAX     Gauge32
    MAX-ACCESS read-only
    STATUS     current
    DESCRIPTION
	    "Total number of rows in the TimedEvents
	    Table."
    ::= { informationStoreMailboxEntry 284 }

ismSaveChangesAttachOpRate OBJECT-TYPE
    SYNTAX     Gauge32
    MAX-ACCESS read-only
    STATUS     current
    DESCRIPTION
	    "SaveChangesAttachOpRate."
    ::= { informationStoreMailboxEntry 285 }

ismSaveChangesAttachOpTotal OBJECT-TYPE
    SYNTAX     Gauge32
    MAX-ACCESS read-only
    STATUS     current
    DESCRIPTION
	    "SaveChangesAttachOpTotal."
    ::= { informationStoreMailboxEntry 286 }

ismSaveChangesMessageOpRate OBJECT-TYPE
    SYNTAX     Gauge32
    MAX-ACCESS read-only
    STATUS     current
    DESCRIPTION
	    "SaveChangesMessageOpRate."
    ::= { informationStoreMailboxEntry 287 }

ismSaveChangesMessageOpTotal OBJECT-TYPE
    SYNTAX     Gauge32
    MAX-ACCESS read-only
    STATUS     current
    DESCRIPTION
	    "SaveChangesMessageOpTotal."
    ::= { informationStoreMailboxEntry 288 }

ismSeekRowOperationsPerSec OBJECT-TYPE
    SYNTAX     Gauge32
    MAX-ACCESS read-only
    STATUS     current
    DESCRIPTION
	    "SeekRow Operations/sec is the rate of SeekRow
	    requests in the mailbox store."
    ::= { informationStoreMailboxEntry 289 }

ismSeekRowApproxOperationsPerSec OBJECT-TYPE
    SYNTAX     Gauge32
    MAX-ACCESS read-only
    STATUS     current
    DESCRIPTION
	    "SeekRowApproximate Operations/sec is the rate
	    of SeekRowApproximate requests in the mailbox
	    store."
    ::= { informationStoreMailboxEntry 290 }

ismSeekRowBookMarkOpPerSec OBJECT-TYPE
    SYNTAX     Gauge32
    MAX-ACCESS read-only
    STATUS     current
    DESCRIPTION
	    "SeekRowBookMark Operations/sec is the rate of
	    SeekRowBookMark requests in the mailbox store."
    ::= { informationStoreMailboxEntry 291 }

ismSeekStreamOpRate OBJECT-TYPE
    SYNTAX     Gauge32
    MAX-ACCESS read-only
    STATUS     current
    DESCRIPTION
	    "SeekStreamOpRate."
    ::= { informationStoreMailboxEntry 292 }

ismSeekStreamOpTotal OBJECT-TYPE
    SYNTAX     Gauge32
    MAX-ACCESS read-only
    STATUS     current
    DESCRIPTION
	    "SeekStreamOpTotal."
    ::= { informationStoreMailboxEntry 293 }

ismSendqTasksRate OBJECT-TYPE
    SYNTAX     Gauge32
    MAX-ACCESS read-only
    STATUS     current
    DESCRIPTION
	    "Send queue tasks to process messages on the
	    send queue."
    ::= { informationStoreMailboxEntry 294 }

ismSendqTasksTotal OBJECT-TYPE
    SYNTAX     Gauge32
    MAX-ACCESS read-only
    STATUS     current
    DESCRIPTION
	    "Send queue tasks to process messages on the
	    send queue."
    ::= { informationStoreMailboxEntry 295 }

ismSetCollapseStateOpRate OBJECT-TYPE
    SYNTAX     Gauge32
    MAX-ACCESS read-only
    STATUS     current
    DESCRIPTION
	    "SetCollapseStateOpRate."
    ::= { informationStoreMailboxEntry 296 }

ismSetCollapseStateOpTotal OBJECT-TYPE
    SYNTAX     Gauge32
    MAX-ACCESS read-only
    STATUS     current
    DESCRIPTION
	    "SetCollapseStateOpTotal."
    ::= { informationStoreMailboxEntry 297 }

ismSetColumnsOpRate OBJECT-TYPE
    SYNTAX     Gauge32
    MAX-ACCESS read-only
    STATUS     current
    DESCRIPTION
	    "SetColumnsOpRate."
    ::= { informationStoreMailboxEntry 298 }

ismSetColumnsOpTotal OBJECT-TYPE
    SYNTAX     Gauge32
    MAX-ACCESS read-only
    STATUS     current
    DESCRIPTION
	    "SetColumnsOpTotal."
    ::= { informationStoreMailboxEntry 299 }

ismSetFileHandlePropOpRate OBJECT-TYPE
    SYNTAX     Gauge32
    MAX-ACCESS read-only
    STATUS     current
    DESCRIPTION
	    "SetFileHandlePropOpRate"
    ::= { informationStoreMailboxEntry 300 }

ismSetFileHandlePropOpTotal OBJECT-TYPE
    SYNTAX     Gauge32
    MAX-ACCESS read-only
    STATUS     current
    DESCRIPTION
	    "SetFileHandlePropOpTotal"
    ::= { informationStoreMailboxEntry 301 }

ismSetfLocalizedOpRate OBJECT-TYPE
    SYNTAX     Gauge32
    MAX-ACCESS read-only
    STATUS     current
    DESCRIPTION
	    "SetfLocalizedOpRate."
    ::= { informationStoreMailboxEntry 302 }

ismSetfLocalizedOpTotal OBJECT-TYPE
    SYNTAX     Gauge32
    MAX-ACCESS read-only
    STATUS     current
    DESCRIPTION
	    "SetfLocalizedOpTotal."
    ::= { informationStoreMailboxEntry 303 }

ismSetICSNotifGUIDOpRate OBJECT-TYPE
    SYNTAX     Gauge32
    MAX-ACCESS read-only
    STATUS     current
    DESCRIPTION
	    "SetICSNotifGUIDOpRate."
    ::= { informationStoreMailboxEntry 304 }

ismSetICSNotifGUIDOpTotal OBJECT-TYPE
    SYNTAX     Gauge32
    MAX-ACCESS read-only
    STATUS     current
    DESCRIPTION
	    "SetICSNotifGUIDOpTotal."
    ::= { informationStoreMailboxEntry 305 }

ismSetLocalRepMidsetDelOpRate OBJECT-TYPE
    SYNTAX     Gauge32
    MAX-ACCESS read-only
    STATUS     current
    DESCRIPTION
	    "SetLocalRepMidsetDeletedOpRate."
    ::= { informationStoreMailboxEntry 306 }

ismSetLocalRepMidsetDelOpTotal OBJECT-TYPE
    SYNTAX     Gauge32
    MAX-ACCESS read-only
    STATUS     current
    DESCRIPTION
	    "SetLocalRepMidsetDeletedOpTotal."
    ::= { informationStoreMailboxEntry 307 }

ismSetMessageFolderFlagsOpRate OBJECT-TYPE
    SYNTAX     Gauge32
    MAX-ACCESS read-only
    STATUS     current
    DESCRIPTION
	    "SetMessageFolderFlagsOpRate."
    ::= { informationStoreMailboxEntry 308 }

ismSetMessageFolderFlagsOpTotal OBJECT-TYPE
    SYNTAX     Gauge32
    MAX-ACCESS read-only
    STATUS     current
    DESCRIPTION
	    "SetMessageFolderFlagsOpTotal."
    ::= { informationStoreMailboxEntry 309 }

ismSetMessagePropOpRate OBJECT-TYPE
    SYNTAX     Gauge32
    MAX-ACCESS read-only
    STATUS     current
    DESCRIPTION
	    "SetMessagePropOpRate."
    ::= { informationStoreMailboxEntry 310 }

ismSetMessagePropOpTotal OBJECT-TYPE
    SYNTAX     Gauge32
    MAX-ACCESS read-only
    STATUS     current
    DESCRIPTION
	    "SetMessagePropOpTotal."
    ::= { informationStoreMailboxEntry 311 }

ismSetMessageStatusOpRate OBJECT-TYPE
    SYNTAX     Gauge32
    MAX-ACCESS read-only
    STATUS     current
    DESCRIPTION
	    "SetMessageStatusOpRate."
    ::= { informationStoreMailboxEntry 312 }

ismSetMessageStatusOpTotal OBJECT-TYPE
    SYNTAX     Gauge32
    MAX-ACCESS read-only
    STATUS     current
    DESCRIPTION
	    "SetMessageStatusOpTotal."
    ::= { informationStoreMailboxEntry 313 }

ismSetPerUserOpRate OBJECT-TYPE
    SYNTAX     Gauge32
    MAX-ACCESS read-only
    STATUS     current
    DESCRIPTION
	    "SetPerUserOpRate."
    ::= { informationStoreMailboxEntry 314 }

ismSetPerUserOpTotal OBJECT-TYPE
    SYNTAX     Gauge32
    MAX-ACCESS read-only
    STATUS     current
    DESCRIPTION
	    "SetPerUserOpTotal."
    ::= { informationStoreMailboxEntry 315 }

ismSetPropertyOperationsPerSec OBJECT-TYPE
    SYNTAX     Gauge32
    MAX-ACCESS read-only
    STATUS     current
    DESCRIPTION
	    "SetProperty Operations/sec is the rate of
	    SetProperty requests in the mailbox store."
    ::= { informationStoreMailboxEntry 316 }

ismSetReadFlagOpRate OBJECT-TYPE
    SYNTAX     Gauge32
    MAX-ACCESS read-only
    STATUS     current
    DESCRIPTION
	    "SetReadFlagOpRate."
    ::= { informationStoreMailboxEntry 317 }

ismSetReadFlagOpTotal OBJECT-TYPE
    SYNTAX     Gauge32
    MAX-ACCESS read-only
    STATUS     current
    DESCRIPTION
	    "SetReadFlagOpTotal."
    ::= { informationStoreMailboxEntry 318 }

ismSetReadFlagsOpRate OBJECT-TYPE
    SYNTAX     Gauge32
    MAX-ACCESS read-only
    STATUS     current
    DESCRIPTION
	    "SetReadFlagsOpRate."
    ::= { informationStoreMailboxEntry 319 }

ismSetReadFlagsOpTotal OBJECT-TYPE
    SYNTAX     Gauge32
    MAX-ACCESS read-only
    STATUS     current
    DESCRIPTION
	    "SetReadFlagsOpTotal."
    ::= { informationStoreMailboxEntry 320 }

ismSetReceiveFolderOpRate OBJECT-TYPE
    SYNTAX     Gauge32
    MAX-ACCESS read-only
    STATUS     current
    DESCRIPTION
	    "SetReceiveFolderOpRate."
    ::= { informationStoreMailboxEntry 321 }

ismSetReceiveFolderOpTotal OBJECT-TYPE
    SYNTAX     Gauge32
    MAX-ACCESS read-only
    STATUS     current
    DESCRIPTION
	    "SetReceiveFolderOpTotal."
    ::= { informationStoreMailboxEntry 322 }

ismSetRecipOpRate OBJECT-TYPE
    SYNTAX     Gauge32
    MAX-ACCESS read-only
    STATUS     current
    DESCRIPTION
	    "SetRecipOpRate."
    ::= { informationStoreMailboxEntry 323 }

ismSetRecipOpTotal OBJECT-TYPE
    SYNTAX     Gauge32
    MAX-ACCESS read-only
    STATUS     current
    DESCRIPTION
	    "SetRecipOpTotal."
    ::= { informationStoreMailboxEntry 324 }

ismSetSearchCriteriaOpRate OBJECT-TYPE
    SYNTAX     Gauge32
    MAX-ACCESS read-only
    STATUS     current
    DESCRIPTION
	    "SetSearchCriteriaOpRate."
    ::= { informationStoreMailboxEntry 325 }

ismSetSearchCriteriaOpTotal OBJECT-TYPE
    SYNTAX     Gauge32
    MAX-ACCESS read-only
    STATUS     current
    DESCRIPTION
	    "SetSearchCriteriaOpTotal."
    ::= { informationStoreMailboxEntry 326 }

ismSetSizeStreamOpRate OBJECT-TYPE
    SYNTAX     Gauge32
    MAX-ACCESS read-only
    STATUS     current
    DESCRIPTION
	    "SetSizeStreamOpRate."
    ::= { informationStoreMailboxEntry 327 }

ismSetSizeStreamOpTotal OBJECT-TYPE
    SYNTAX     Gauge32
    MAX-ACCESS read-only
    STATUS     current
    DESCRIPTION
	    "SetSizeStreamOpTotal."
    ::= { informationStoreMailboxEntry 328 }

ismSetSpoolerOpRate OBJECT-TYPE
    SYNTAX     Gauge32
    MAX-ACCESS read-only
    STATUS     current
    DESCRIPTION
	    "SetSpoolerOpRate."
    ::= { informationStoreMailboxEntry 329 }

ismSetSpoolerOpTotal OBJECT-TYPE
    SYNTAX     Gauge32
    MAX-ACCESS read-only
    STATUS     current
    DESCRIPTION
	    "SetSpoolerOpTotal."
    ::= { informationStoreMailboxEntry 330 }

ismSetXportOpRate OBJECT-TYPE
    SYNTAX     Gauge32
    MAX-ACCESS read-only
    STATUS     current
    DESCRIPTION
	    "SetXportOpRate."
    ::= { informationStoreMailboxEntry 331 }

ismSetXportOpTotal OBJECT-TYPE
    SYNTAX     Gauge32
    MAX-ACCESS read-only
    STATUS     current
    DESCRIPTION
	    "SetXportOpTotal."
    ::= { informationStoreMailboxEntry 332 }

ismSortTableOpRate OBJECT-TYPE
    SYNTAX     Gauge32
    MAX-ACCESS read-only
    STATUS     current
    DESCRIPTION
	    "SortTableOpRate."
    ::= { informationStoreMailboxEntry 333 }

ismSortTableOpTotal OBJECT-TYPE
    SYNTAX     Gauge32
    MAX-ACCESS read-only
    STATUS     current
    DESCRIPTION
	    "SortTableOpTotal."
    ::= { informationStoreMailboxEntry 334 }

ismSpoolerLockMsgOpRate OBJECT-TYPE
    SYNTAX     Gauge32
    MAX-ACCESS read-only
    STATUS     current
    DESCRIPTION
	    "SpoolerLockMsgOpRate."
    ::= { informationStoreMailboxEntry 335 }

ismSpoolerLockMsgOpTotal OBJECT-TYPE
    SYNTAX     Gauge32
    MAX-ACCESS read-only
    STATUS     current
    DESCRIPTION
	    "SpoolerLockMsgOpTotal."
    ::= { informationStoreMailboxEntry 336 }

ismSpoolerRulesOpRate OBJECT-TYPE
    SYNTAX     Gauge32
    MAX-ACCESS read-only
    STATUS     current
    DESCRIPTION
	    "SpoolerRulesOpRate."
    ::= { informationStoreMailboxEntry 337 }

ismSpoolerRulesOpTotal OBJECT-TYPE
    SYNTAX     Gauge32
    MAX-ACCESS read-only
    STATUS     current
    DESCRIPTION
	    "SpoolerRulesOpTotal."
    ::= { informationStoreMailboxEntry 338 }

ismTellVersionOpRate OBJECT-TYPE
    SYNTAX     Gauge32
    MAX-ACCESS read-only
    STATUS     current
    DESCRIPTION
	    "TellVersionOpRate."
    ::= { informationStoreMailboxEntry 339 }

ismTellVersionOpTotal OBJECT-TYPE
    SYNTAX     Gauge32
    MAX-ACCESS read-only
    STATUS     current
    DESCRIPTION
	    "TellVersionOpTotal."
    ::= { informationStoreMailboxEntry 340 }

ismTranRateFromMimeToMapi OBJECT-TYPE
    SYNTAX     Gauge32
    MAX-ACCESS read-only
    STATUS     current
    DESCRIPTION
	    "Rate of transitions from mime to mapi (per
	    sec)."
    ::= { informationStoreMailboxEntry 341 }

ismTranRateFromMimeToMimebyref OBJECT-TYPE
    SYNTAX     Gauge32
    MAX-ACCESS read-only
    STATUS     current
    DESCRIPTION
	    "Rate of transitions from mime to mimebyref
	    (per sec)."
    ::= { informationStoreMailboxEntry 342 }

ismTranRateFromMimebyrefToMapi OBJECT-TYPE
    SYNTAX     Gauge32
    MAX-ACCESS read-only
    STATUS     current
    DESCRIPTION
	    "Rate of transitions from mimebyref to mapi
	    (per sec)."
    ::= { informationStoreMailboxEntry 343 }

ismTranRateFromNewToMime OBJECT-TYPE
    SYNTAX     Gauge32
    MAX-ACCESS read-only
    STATUS     current
    DESCRIPTION
	    "Rate of new messages created with mime."
    ::= { informationStoreMailboxEntry 344 }

ismTransFromMimeToMapi OBJECT-TYPE
    SYNTAX     Gauge32
    MAX-ACCESS read-only
    STATUS     current
    DESCRIPTION
	    "Total number of transitions from mime to
	    mapi."
    ::= { informationStoreMailboxEntry 345 }

ismTransFromMimeToMimebyref OBJECT-TYPE
    SYNTAX     Gauge32
    MAX-ACCESS read-only
    STATUS     current
    DESCRIPTION
	    "Total number of transitions from mime to
	    mimebyref."
    ::= { informationStoreMailboxEntry 346 }

ismTransFromMimebyrefToMapi OBJECT-TYPE
    SYNTAX     Gauge32
    MAX-ACCESS read-only
    STATUS     current
    DESCRIPTION
	    "Total number of transitions from mimebyref to
	    mapi."
    ::= { informationStoreMailboxEntry 347 }

ismTransFromNewToMime OBJECT-TYPE
    SYNTAX     Gauge32
    MAX-ACCESS read-only
    STATUS     current
    DESCRIPTION
	    "Total number of new messages created with
	    mime."
    ::= { informationStoreMailboxEntry 348 }

ismTransportSendOpRate OBJECT-TYPE
    SYNTAX     Gauge32
    MAX-ACCESS read-only
    STATUS     current
    DESCRIPTION
	    "TransportSendOpRate."
    ::= { informationStoreMailboxEntry 349 }

ismTransportSendOpTotal OBJECT-TYPE
    SYNTAX     Gauge32
    MAX-ACCESS read-only
    STATUS     current
    DESCRIPTION
	    "TransportSendOpTotal."
    ::= { informationStoreMailboxEntry 350 }

ismUpdateDAMsOpRate OBJECT-TYPE
    SYNTAX     Gauge32
    MAX-ACCESS read-only
    STATUS     current
    DESCRIPTION
	    "UpdateDAMsOpRate."
    ::= { informationStoreMailboxEntry 351 }

ismUpdateDAMsOpTotal OBJECT-TYPE
    SYNTAX     Gauge32
    MAX-ACCESS read-only
    STATUS     current
    DESCRIPTION
	    "UpdateDAMsOpTotal."
    ::= { informationStoreMailboxEntry 352 }

ismUpdateFolderInternetIdOpRate OBJECT-TYPE
    SYNTAX     Gauge32
    MAX-ACCESS read-only
    STATUS     current
    DESCRIPTION
	    "UpdateFolderInternetIdOpRate."
    ::= { informationStoreMailboxEntry 353 }

ismUpdateFolderInternetIdOpTotal OBJECT-TYPE
    SYNTAX     Gauge32
    MAX-ACCESS read-only
    STATUS     current
    DESCRIPTION
	    "UpdateFolderInternetIdOpTotal."
    ::= { informationStoreMailboxEntry 354 }

ismUpdateRecipPtagsOpRate OBJECT-TYPE
    SYNTAX     Gauge32
    MAX-ACCESS read-only
    STATUS     current
    DESCRIPTION
	    "UpdateRecipPtagsOpRate."
    ::= { informationStoreMailboxEntry 355 }

ismUpdateRecipPtagsOpTotal OBJECT-TYPE
    SYNTAX     Gauge32
    MAX-ACCESS read-only
    STATUS     current
    DESCRIPTION
	    "UpdateRecipPtagsOpTotal."
    ::= { informationStoreMailboxEntry 356 }

ismUpldStStrmBeginOpRate OBJECT-TYPE
    SYNTAX     Gauge32
    MAX-ACCESS read-only
    STATUS     current
    DESCRIPTION
	    "UpldStStrmBeginOpRate."
    ::= { informationStoreMailboxEntry 357 }

ismUpldStStrmBeginOpTotal OBJECT-TYPE
    SYNTAX     Gauge32
    MAX-ACCESS read-only
    STATUS     current
    DESCRIPTION
	    "UpldStStrmBeginOpTotal."
    ::= { informationStoreMailboxEntry 358 }

ismUpldStStrmContinueOpRate OBJECT-TYPE
    SYNTAX     Gauge32
    MAX-ACCESS read-only
    STATUS     current
    DESCRIPTION
	    "UpldStStrmContinueOpRate."
    ::= { informationStoreMailboxEntry 359 }

ismUpldStStrmContinueOpTotal OBJECT-TYPE
    SYNTAX     Gauge32
    MAX-ACCESS read-only
    STATUS     current
    DESCRIPTION
	    "UpldStStrmContinueOpTotal."
    ::= { informationStoreMailboxEntry 360 }

ismUpldStStrmEndOpRate OBJECT-TYPE
    SYNTAX     Gauge32
    MAX-ACCESS read-only
    STATUS     current
    DESCRIPTION
	    "UpldStStrmEndOpRate."
    ::= { informationStoreMailboxEntry 361 }

ismUpldStStrmEndOpTotal OBJECT-TYPE
    SYNTAX     Gauge32
    MAX-ACCESS read-only
    STATUS     current
    DESCRIPTION
	    "UpldStStrmEndOpTotal."
    ::= { informationStoreMailboxEntry 362 }

ismValidAttachsOpRate OBJECT-TYPE
    SYNTAX     Gauge32
    MAX-ACCESS read-only
    STATUS     current
    DESCRIPTION
	    "ValidAttachsOpRate."
    ::= { informationStoreMailboxEntry 363 }

ismValidAttachsOpTotal OBJECT-TYPE
    SYNTAX     Gauge32
    MAX-ACCESS read-only
    STATUS     current
    DESCRIPTION
	    "ValidAttachsOpTotal."
    ::= { informationStoreMailboxEntry 364 }

ismWriteStreamOpRate OBJECT-TYPE
    SYNTAX     Gauge32
    MAX-ACCESS read-only
    STATUS     current
    DESCRIPTION
	    "WriteStreamOpRate."
    ::= { informationStoreMailboxEntry 365 }

ismWriteStreamOpTotal OBJECT-TYPE
    SYNTAX     Gauge32
    MAX-ACCESS read-only
    STATUS     current
    DESCRIPTION
	    "WriteStreamOpTotal."
    ::= { informationStoreMailboxEntry 366 }

ismXportNewMailOpRate OBJECT-TYPE
    SYNTAX     Gauge32
    MAX-ACCESS read-only
    STATUS     current
    DESCRIPTION
	    "XportNewMailOpRate."
    ::= { informationStoreMailboxEntry 367 }

ismXportNewMailOpTotal OBJECT-TYPE
    SYNTAX     Gauge32
    MAX-ACCESS read-only
    STATUS     current
    DESCRIPTION
	    "XportNewMailOpTotal."
    ::= { informationStoreMailboxEntry 368 }

informationStorePublicTable OBJECT-TYPE
    SYNTAX     SEQUENCE OF ISPublicEntry
    MAX-ACCESS not-accessible
    STATUS     current
    DESCRIPTION
	    "Microsoft Exchange Public Folder Store
	    performance data"
    ::= { exchange 16 }

informationStorePublicEntry OBJECT-TYPE
    SYNTAX     ISPublicEntry
    MAX-ACCESS not-accessible
    STATUS     current
    DESCRIPTION
	    "Performance information for one particular
	    instance of 'MSExchangeIS Public' object."
    INDEX      { ispInstance }
    ::= { informationStorePublicTable 1 }

ISPublicEntry ::= SEQUENCE {
    ispInstance InstanceName,
    ispActiveClientLogons Gauge32,
    ispAverageDeliveryTime Gauge32,
    ispCategorizationCount Gauge32,
    ispClientLogons Gauge32,
    ispFolderOpensPerSec Gauge32,
    ispHTTPDAVCurrentPendingNotify Gauge32,
    ispHTTPDAVCurrentSubscriptions Gauge32,
    ispHTTPDAVCurrentTransactionLock Gauge32,
    ispHTTPDAVNotifyRequestsSec Gauge32,
    ispHTTPDAVTotalLocksCreate Gauge32,
    ispHTTPDAVTotalNotifyRequests Gauge32,
    ispHTTPDAVTotalSubscribeCreate Gauge32,
    ispHTTPDAVTotalSubscribeExpire Gauge32,
    ispLogonOperationsPerSec Gauge32,
    ispMessageOpensPerSec Gauge32,
    ispMessageRcpntsDelivered Gauge32,
    ispMessageRcpntsDeliveredPerMin Gauge32,
    ispMessagesDelivered Gauge32,
    ispMessagesDeliveredPerMin Gauge32,
    ispMessagesSent Gauge32,
    ispMessagesSentPerMin Gauge32,
    ispMessagesSubmitted Gauge32,
    ispMessagesSubmittedPerMin Gauge32,
    ispNumMsgsExpirePublicFolders Gauge32,
    ispPeakClientLogons Gauge32,
    ispRcvQueueSize Gauge32,
    ispReplicationBackfillDtMsgsRcvd Gauge32,
    ispReplicationBackfillDtMsgsSent Gauge32,
    ispReplicationBackfillRqstsRcvd Gauge32,
    ispReplicationBackfillRqstsSent Gauge32,
    ispReplicationFolderChangesRcvd Gauge32,
    ispReplicationFolderChangesSent Gauge32,
    ispReplicationFolderDataMsgsRcvd Gauge32,
    ispReplicationFolderDataMsgsSent Gauge32,
    ispReplicationFolderTreeMsgsRcvd Gauge32,
    ispReplicationFolderTreeMsgsSent Gauge32,
    ispReplicationMsgChangesRcvd Gauge32,
    ispReplicationMsgChangesSent Gauge32,
    ispReplicationMsgsRcvd Gauge32,
    ispReplicationMsgsSent Gauge32,
    ispReplicationRcvQueueSize Gauge32,
    ispReplicationStatusMsgsRcvd Gauge32,
    ispReplicationStatusMsgsSent Gauge32,
    ispSendQueueSize Gauge32,
    ispSingleInstanceRatio Gauge32,
    ispTotalCountOfRecoverableItems Gauge32,
    ispTotalSizeOfRecoverableItems Gauge32,
    ispRestrictedViewCacheHitRate Gauge32,
    ispRestrictedViewCacheMissRate Gauge32,
    ispSearchTaskRate Gauge32,
    ispSlowFindRowRate Gauge32,
    ispAbortOpRate Gauge32,
    ispAbortOpTotal Gauge32,
    ispAbortSubmitOpRate Gauge32,
    ispAbortSubmitOpTotal Gauge32,
    ispAddMsgToSendqRate Gauge32,
    ispAddMsgToSendqTotal Gauge32,
    ispAddNamedCalcPropOpRate Gauge32,
    ispAddNamedCalcPropOpTotal Gauge32,
    ispAddressTypesOpRate Gauge32,
    ispAddressTypesOpTotal Gauge32,
    ispCacheCcnReadOpRate Gauge32,
    ispCacheCcnReadOpTotal Gauge32,
    ispCheckFolderNameOpRate Gauge32,
    ispCheckFolderNameOpTotal Gauge32,
    ispCheckRightsOnFolderRate Gauge32,
    ispCheckRightsOnFolderTotal Gauge32,
    ispCloneStreamOpRate Gauge32,
    ispCloneStreamOpTotal Gauge32,
    ispCollapseRowOpRate Gauge32,
    ispCollapseRowOpTotal Gauge32,
    ispCommitStreamOpRate Gauge32,
    ispCommitStreamOpTotal Gauge32,
    ispCopyPropsOpRate Gauge32,
    ispCopyPropsOpTotal Gauge32,
    ispCopyToOpRate Gauge32,
    ispCopyToOpTotal Gauge32,
    ispCopyToStreamOpRate Gauge32,
    ispCopyToStreamOpTotal Gauge32,
    ispCreateAttachOpRate Gauge32,
    ispCreateAttachOpTotal Gauge32,
    ispCreateBookMarkOperationPerSec Gauge32,
    ispCreateFolderOpRate Gauge32,
    ispCreateFolderOpTotal Gauge32,
    ispDatabaseSessionActiveCount Gauge32,
    ispDatabaseSessionCount Gauge32,
    ispDeleteAttachOpRate Gauge32,
    ispDeleteAttachOpTotal Gauge32,
    ispDeleteFolderOpRate Gauge32,
    ispDeleteFolderOpTotal Gauge32,
    ispDeleteMessagesOpRate Gauge32,
    ispDeleteMessagesOpTotal Gauge32,
    ispDelMsgFromSendqRate Gauge32,
    ispDelMsgFromSendqTotal Gauge32,
    ispDelPropertyOperationsPerSec Gauge32,
    ispDeregisterTableNotifyOpRate Gauge32,
    ispDeregisterTableNotifyOpTotal Gauge32,
    ispDoCrossPostOpRate Gauge32,
    ispDoCrossPostOpTotal Gauge32,
    ispEmptyFolderOpRate Gauge32,
    ispEmptyFolderOpTotal Gauge32,
    ispExpandRowOpRate Gauge32,
    ispExpandRowOpTotal Gauge32,
    ispFghostedOpRate Gauge32,
    ispFghostedOpTotal Gauge32,
    ispFindRowOperationsPerSec Gauge32,
    ispFlushPerUserOpRate Gauge32,
    ispFlushPerUserOpTotal Gauge32,
    ispFolderCount Gauge32,
    ispFreeBookmarkOpRate Gauge32,
    ispFreeBookmarkOpTotal Gauge32,
    ispFXDstCopyFolderOpRate Gauge32,
    ispFXDstCopyFolderOpTotal Gauge32,
    ispFXDstCopyMessagesOpRate Gauge32,
    ispFXDstCopyMessagesOpTotal Gauge32,
    ispFXDstCopyPropsOpRate Gauge32,
    ispFXDstCopyPropsOpTotal Gauge32,
    ispFXDstCopyToOpRate Gauge32,
    ispFXDstCopyToOpTotal Gauge32,
    ispFXDstPutBufferOpRate Gauge32,
    ispFXDstPutBufferOpTotal Gauge32,
    ispFXGetBufferCurrentCallerCount Gauge32,
    ispFXGetBufferCurrentUsersExec Gauge32,
    ispFXGetBufferRopsAccepted Gauge32,
    ispFXGetBufferRopsAcceptedPerSec Gauge32,
    ispFXGetBufferRopsCalled Gauge32,
    ispFXGetBufferRopsCalledPerSec Gauge32,
    ispFXGetBufferRopsDenied Gauge32,
    ispFXGetBufferRopsDeniedPerSec Gauge32,
    ispFXGetIncrStateOpRate Gauge32,
    ispFXGetIncrStateOpTotal Gauge32,
    ispFXSrcCopyFolderOpRate Gauge32,
    ispFXSrcCopyFolderOpTotal Gauge32,
    ispFXSrcCopyMessagesOpRate Gauge32,
    ispFXSrcCopyMessagesOpTotal Gauge32,
    ispFXSrcCopyPropsOpRate Gauge32,
    ispFXSrcCopyPropsOpTotal Gauge32,
    ispFXSrcCopyToOpRate Gauge32,
    ispFXSrcCopyToOpTotal Gauge32,
    ispFXSrcGetBufferOpRate Gauge32,
    ispFXSrcGetBufferOpTotal Gauge32,
    ispGetAdrListOpRate Gauge32,
    ispGetAdrListOpTotal Gauge32,
    ispGetAllPerUserLtidsOpRate Gauge32,
    ispGetAllPerUserLtidsOpTotal Gauge32,
    ispGetCollapseStateOpRate Gauge32,
    ispGetCollapseStateOpTotal Gauge32,
    ispGetFileHandlePropOpRate Gauge32,
    ispGetFileHandlePropOpTotal Gauge32,
    ispGetFoldersTableRpcIntfRate Gauge32,
    ispGetFoldersTableRpcIntfTotal Gauge32,
    ispGetIDsFromNamesOpRate Gauge32,
    ispGetIDsFromNamesOpTotal Gauge32,
    ispGetLocalRepIdsOpRate Gauge32,
    ispGetLocalRepIdsOpTotal Gauge32,
    ispGetMailboxTableRpcIntfRate Gauge32,
    ispGetMailboxTableRpcIntfTotal Gauge32,
    ispGetMessagePropOpRate Gauge32,
    ispGetMessagePropOpTotal Gauge32,
    ispGetMessageStatusOpRate Gauge32,
    ispGetMessageStatusOpTotal Gauge32,
    ispGetNamesFromIDsOpRate Gauge32,
    ispGetNamesFromIDsOpTotal Gauge32,
    ispGetOwningMDBsOpRate Gauge32,
    ispGetOwningMDBsOpTotal Gauge32,
    ispGetPerUserGuidOpRate Gauge32,
    ispGetPerUserGuidOpTotal Gauge32,
    ispGetPerUserLtidsOpRate Gauge32,
    ispGetPerUserLtidsOpTotal Gauge32,
    ispGetPerUserOpRate Gauge32,
    ispGetPerUserOpTotal Gauge32,
    ispGetPropertyOperationsPerSec Gauge32,
    ispGetPropListOpRate Gauge32,
    ispGetPropListOpTotal Gauge32,
    ispGetReceiveFolderOpRate Gauge32,
    ispGetReceiveFolderOpTotal Gauge32,
    ispGetReceiveFolderTableOpRate Gauge32,
    ispGetReceiveFolderTableOpTotal Gauge32,
    ispGetRecipColumnsOpRate Gauge32,
    ispGetRecipColumnsOpTotal Gauge32,
    ispGetRecipCountOpRate Gauge32,
    ispGetRecipCountOpTotal Gauge32,
    ispGetRecipOpRate Gauge32,
    ispGetRecipOpTotal Gauge32,
    ispGetRightsOpRate Gauge32,
    ispGetRightsOpTotal Gauge32,
    ispGetSearchCriteriaOpRate Gauge32,
    ispGetSearchCriteriaOpTotal Gauge32,
    ispGetStatusOpRate Gauge32,
    ispGetStatusOpTotal Gauge32,
    ispGetStreamSizeOpRate Gauge32,
    ispGetStreamSizeOpTotal Gauge32,
    ispGetTableOpRate Gauge32,
    ispGetTableOpTotal Gauge32,
    ispGetXhdrListOpRate Gauge32,
    ispGetXhdrListOpTotal Gauge32,
    ispIdFromLtidOpRate Gauge32,
    ispIdFromLtidOpTotal Gauge32,
    ispImportDeleteOpRate Gauge32,
    ispImportDeleteOpTotal Gauge32,
    ispImportHierChgOpRate Gauge32,
    ispImportHierChgOpTotal Gauge32,
    ispImportHierDelOpRate Gauge32,
    ispImportHierDelOpTotal Gauge32,
    ispImportMsgChgOpRate Gauge32,
    ispImportMsgChgOpTotal Gauge32,
    ispImportMsgMoveOpRate Gauge32,
    ispImportMsgMoveOpTotal Gauge32,
    ispImportReadsOpRate Gauge32,
    ispImportReadsOpTotal Gauge32,
    ispIncrCfgOpRate Gauge32,
    ispIncrCfgOpTotal Gauge32,
    ispLocalDeliveryOpRate Gauge32,
    ispLocalDeliveryOpTotal Gauge32,
    ispLockRegionStreamOpRate Gauge32,
    ispLockRegionStreamOpTotal Gauge32,
    ispLtidFromIdOpRate Gauge32,
    ispLtidFromIdOpTotal Gauge32,
    ispModifyACLOpRate Gauge32,
    ispModifyACLOpTotal Gauge32,
    ispModifyMvPropOpRate Gauge32,
    ispModifyMvPropOpTotal Gauge32,
    ispModifyRcpntsOperationsPerSec Gauge32,
    ispModifyRulesOpRate Gauge32,
    ispModifyRulesOpTotal Gauge32,
    ispModifyRulesRate Gauge32,
    ispModifyRulesTotal Gauge32,
    ispMoveCopyFolderOpRate Gauge32,
    ispMoveCopyFolderOpTotal Gauge32,
    ispMoveCopyMessagesOpRate Gauge32,
    ispMoveCopyMessagesOpTotal Gauge32,
    ispNextNewsgroupOpRate Gauge32,
    ispNextNewsgroupOpTotal Gauge32,
    ispNukeRecipientsOpRate Gauge32,
    ispNukeRecipientsOpTotal Gauge32,
    ispOpenAdvisorOpRate Gauge32,
    ispOpenAdvisorOpTotal Gauge32,
    ispOpenAttachOpRate Gauge32,
    ispOpenAttachOpTotal Gauge32,
    ispOpenCollectOpRate Gauge32,
    ispOpenCollectOpTotal Gauge32,
    ispOpenFolderByNntpNameOpRate Gauge32,
    ispOpenFolderByNntpNameOpTotal Gauge32,
    ispOpenImailConvObjectOpRate Gauge32,
    ispOpenImailConvObjectOpTotal Gauge32,
    ispOpenImailConvStreamOpRate Gauge32,
    ispOpenImailConvStreamOpTotal Gauge32,
    ispOpenMessageByArticleNumOpRate Gauge32,
    ispOpenMessageByArticleNmOpTotal Gauge32,
    ispOpenMessageByMsgIdOpRate Gauge32,
    ispOpenMessageByMsgIdOpTotal Gauge32,
    ispOpenMessagePropOpRate Gauge32,
    ispOpenMessagePropOpTotal Gauge32,
    ispOpenStreamOperationsPerSec Gauge32,
    ispUserReadCacheConsumed Gauge32,
    ispUserReadCacheDirty Gauge32,
    ispUserReadCacheEntriesReUsedSec Gauge32,
    ispUserReadCacheEntriesScanSec Gauge32,
    ispUserReadCacheInUse Gauge32,
    ispUserReadCacheInsertsSec Gauge32,
    ispUserReadCacheLookupHitRatio Gauge32,
    ispUserReadCacheLookHitRatioBase Gauge32,
    ispUserReadCacheLookupsSec Gauge32,
    ispUserReadCacheScansSec Gauge32,
    ispUserReadCacheSize Gauge32,
    ispPrepareReadRecipientsRate Gauge32,
    ispPrepareReadRecipientsTotal Gauge32,
    ispQryNamedPropsOpRate Gauge32,
    ispQryNamedPropsOpTotal Gauge32,
    ispQueryColumnsAllOpRate Gauge32,
    ispQueryColumnsAllOpTotal Gauge32,
    ispQueryPositionOperationsPerSec Gauge32,
    ispQueryRowsOpRate Gauge32,
    ispQueryRowsOpTotal Gauge32,
    ispReadStreamOpRate Gauge32,
    ispReadStreamOpTotal Gauge32,
    ispRegICSNotifsOpRate Gauge32,
    ispRegICSNotifsOpTotal Gauge32,
    ispRegisterNotifyOperationPerSec Gauge32,
    ispRegisterTableNotifyOpRate Gauge32,
    ispRegisterTableNotifyOpTotal Gauge32,
    ispRenderMessageOpRate Gauge32,
    ispRenderMessageOpTotal Gauge32,
    ispResetTableOpRate Gauge32,
    ispResetTableOpTotal Gauge32,
    ispRestrictOperationsPerSec Gauge32,
    ispRowsInACLListTable Gauge32,
    ispRowsInACLMemberTable Gauge32,
    ispRowsInCategTables Gauge32,
    ispRowsInDeletedAttachmentsTable Gauge32,
    ispRowsInDeletedFoldersTable Gauge32,
    ispRowsInDeletedMessagesTable Gauge32,
    ispRowsInDeliveredToTable Gauge32,
    ispRowsInFolderTombstoneTable Gauge32,
    ispRowsInIdxAgeTable Gauge32,
    ispRowsInMailboxTable Gauge32,
    ispRowsInMessageTable Gauge32,
    ispRowsInMessageTombstoneTable Gauge32,
    ispRowsInMsgFolderTables Gauge32,
    ispRowsInNamedPropsTable Gauge32,
    ispRowsInNeedRNTable Gauge32,
    ispRowsInPerUserReadTable Gauge32,
    ispRowsInReceiveFoldersTable Gauge32,
    ispRowsInReplicationTable Gauge32,
    ispRowsInReplidMapTable Gauge32,
    ispRowsInRulesTable Gauge32,
    ispRowsInSearchQueueTable Gauge32,
    ispRowsInTimedEventsTable Gauge32,
    ispSaveChangesAttachOpRate Gauge32,
    ispSaveChangesAttachOpTotal Gauge32,
    ispSaveChangesMessageOpRate Gauge32,
    ispSaveChangesMessageOpTotal Gauge32,
    ispSeekRowOperationsPerSec Gauge32,
    ispSeekRowApproxOperationsPerSec Gauge32,
    ispSeekRowBookMarkOpPerSec Gauge32,
    ispSeekStreamOpRate Gauge32,
    ispSeekStreamOpTotal Gauge32,
    ispSendqTasksRate Gauge32,
    ispSendqTasksTotal Gauge32,
    ispSetCollapseStateOpRate Gauge32,
    ispSetCollapseStateOpTotal Gauge32,
    ispSetColumnsOpRate Gauge32,
    ispSetColumnsOpTotal Gauge32,
    ispSetFileHandlePropOpRate Gauge32,
    ispSetFileHandlePropOpTotal Gauge32,
    ispSetfLocalizedOpRate Gauge32,
    ispSetfLocalizedOpTotal Gauge32,
    ispSetICSNotifGUIDOpRate Gauge32,
    ispSetICSNotifGUIDOpTotal Gauge32,
    ispSetLocalRepMidsetDeleteOpRate Gauge32,
    ispSetLocalRepMidsetDelOpTotal Gauge32,
    ispSetMessageFolderFlagsOpRate Gauge32,
    ispSetMessageFolderFlagsOpTotal Gauge32,
    ispSetMessagePropOpRate Gauge32,
    ispSetMessagePropOpTotal Gauge32,
    ispSetMessageStatusOpRate Gauge32,
    ispSetMessageStatusOpTotal Gauge32,
    ispSetPerUserOpRate Gauge32,
    ispSetPerUserOpTotal Gauge32,
    ispSetPropertyOperationsPerSec Gauge32,
    ispSetReadFlagOpRate Gauge32,
    ispSetReadFlagOpTotal Gauge32,
    ispSetReadFlagsOpRate Gauge32,
    ispSetReadFlagsOpTotal Gauge32,
    ispSetReceiveFolderOpRate Gauge32,
    ispSetReceiveFolderOpTotal Gauge32,
    ispSetRecipOpRate Gauge32,
    ispSetRecipOpTotal Gauge32,
    ispSetSearchCriteriaOpRate Gauge32,
    ispSetSearchCriteriaOpTotal Gauge32,
    ispSetSizeStreamOpRate Gauge32,
    ispSetSizeStreamOpTotal Gauge32,
    ispSetSpoolerOpRate Gauge32,
    ispSetSpoolerOpTotal Gauge32,
    ispSetXportOpRate Gauge32,
    ispSetXportOpTotal Gauge32,
    ispSortTableOpRate Gauge32,
    ispSortTableOpTotal Gauge32,
    ispSpoolerLockMsgOpRate Gauge32,
    ispSpoolerLockMsgOpTotal Gauge32,
    ispSpoolerRulesOpRate Gauge32,
    ispSpoolerRulesOpTotal Gauge32,
    ispTellVersionOpRate Gauge32,
    ispTellVersionOpTotal Gauge32,
    ispTranRateFromMimeToMapi Gauge32,
    ispTranRateFromMimeToMimebyref Gauge32,
    ispTranRateFromMimebyrefToMapi Gauge32,
    ispTranRateFromNewToMime Gauge32,
    ispTransFromMimeToMapi Gauge32,
    ispTransFromMimeToMimebyref Gauge32,
    ispTransFromMimebyrefToMapi Gauge32,
    ispTransFromNewToMime Gauge32,
    ispTransportSendOpRate Gauge32,
    ispTransportSendOpTotal Gauge32,
    ispUpdateDAMsOpRate Gauge32,
    ispUpdateDAMsOpTotal Gauge32,
    ispUpdateFolderInternetIdOpRate Gauge32,
    ispUpdateFolderInternetIdOpTotal Gauge32,
    ispUpdateRecipPtagsOpRate Gauge32,
    ispUpdateRecipPtagsOpTotal Gauge32,
    ispUpldStStrmBeginOpRate Gauge32,
    ispUpldStStrmBeginOpTotal Gauge32,
    ispUpldStStrmContinueOpRate Gauge32,
    ispUpldStStrmContinueOpTotal Gauge32,
    ispUpldStStrmEndOpRate Gauge32,
    ispUpldStStrmEndOpTotal Gauge32,
    ispValidAttachsOpRate Gauge32,
    ispValidAttachsOpTotal Gauge32,
    ispWriteStreamOpRate Gauge32,
    ispWriteStreamOpTotal Gauge32,
    ispXportNewMailOpRate Gauge32,
    ispXportNewMailOpTotal Gauge32
}

ispInstance OBJECT-TYPE
    SYNTAX     InstanceName
    MAX-ACCESS read-only
    STATUS     current
    DESCRIPTION
	    "Instance name."
    ::= { informationStorePublicEntry 1 }

ispActiveClientLogons OBJECT-TYPE
    SYNTAX     Gauge32
    MAX-ACCESS read-only
    STATUS     current
    DESCRIPTION
	    "Active Client Logons is the number of clients
	    that performed any action within the last ten
	    minute time interval."
    ::= { informationStorePublicEntry 2 }

ispAverageDeliveryTime OBJECT-TYPE
    SYNTAX     Gauge32
    MAX-ACCESS read-only
    STATUS     current
    DESCRIPTION
	    "Average Delivery Time is the average time in
	    miliseconds between the submission of a message
	    to the public store and the delivery to all
	    local recipients (recipients on the same
	    server) for the last 10 messages."
    ::= { informationStorePublicEntry 3 }

ispCategorizationCount OBJECT-TYPE
    SYNTAX     Gauge32
    MAX-ACCESS read-only
    STATUS     current
    DESCRIPTION
	    "Categorization Count is the number of
	    categorizations that exist in the public store.
	    Categorizations are created when a user creates
	    a filtered view or performs a search. When the
	    information store must maintain an excessive
	    number of categorizations, pe"
    ::= { informationStorePublicEntry 4 }

ispClientLogons OBJECT-TYPE
    SYNTAX     Gauge32
    MAX-ACCESS read-only
    STATUS     current
    DESCRIPTION
	    "Client Logons is the number of clients
	    (including system processes) currently logged
	    on."
    ::= { informationStorePublicEntry 5 }

ispFolderOpensPerSec OBJECT-TYPE
    SYNTAX     Gauge32
    MAX-ACCESS read-only
    STATUS     current
    DESCRIPTION
	    "Folder opens/sec is the rate that requests to
	    open folders are submitted to the information
	    store."
    ::= { informationStorePublicEntry 6 }

ispHTTPDAVCurrentPendingNotify OBJECT-TYPE
    SYNTAX     Gauge32
    MAX-ACCESS read-only
    STATUS     current
    DESCRIPTION
	    "Number of notifications happened that are
	    pending (i.e. to be polled)."
    ::= { informationStorePublicEntry 7 }

ispHTTPDAVCurrentSubscriptions OBJECT-TYPE
    SYNTAX     Gauge32
    MAX-ACCESS read-only
    STATUS     current
    DESCRIPTION
	    "The number of subscriptions currently active
	    in response to HTTP SUBSCRIBE requests."
    ::= { informationStorePublicEntry 8 }

ispHTTPDAVCurrentTransactionLock OBJECT-TYPE
    SYNTAX     Gauge32
    MAX-ACCESS read-only
    STATUS     current
    DESCRIPTION
	    "The number of DAV transaction locks currently
	    active."
    ::= { informationStorePublicEntry 9 }

ispHTTPDAVNotifyRequestsSec OBJECT-TYPE
    SYNTAX     Gauge32
    MAX-ACCESS read-only
    STATUS     current
    DESCRIPTION
	    "The rate at which the server sends HTTP NOTIFY
	    requests."
    ::= { informationStorePublicEntry 10 }

ispHTTPDAVTotalLocksCreate OBJECT-TYPE
    SYNTAX     Gauge32
    MAX-ACCESS read-only
    STATUS     current
    DESCRIPTION
	    "The number locks granted by the server in
	    response to HTTP LOCK requests since service
	    startup."
    ::= { informationStorePublicEntry 11 }

ispHTTPDAVTotalNotifyRequests OBJECT-TYPE
    SYNTAX     Gauge32
    MAX-ACCESS read-only
    STATUS     current
    DESCRIPTION
	    "The number of HTTP NOTIFY requests sent by the
	    server since service startup."
    ::= { informationStorePublicEntry 12 }

ispHTTPDAVTotalSubscribeCreate OBJECT-TYPE
    SYNTAX     Gauge32
    MAX-ACCESS read-only
    STATUS     current
    DESCRIPTION
	    "The number of subscriptions granted by the
	    server in response to HTTP SUBSCRIBE requests
	    since service startup."
    ::= { informationStorePublicEntry 13 }

ispHTTPDAVTotalSubscribeExpire OBJECT-TYPE
    SYNTAX     Gauge32
    MAX-ACCESS read-only
    STATUS     current
    DESCRIPTION
	    "The number of subscriptions granted by the
	    server in response to HTTP SUBSCRIBE requests
	    that have expired since service startup."
    ::= { informationStorePublicEntry 14 }

ispLogonOperationsPerSec OBJECT-TYPE
    SYNTAX     Gauge32
    MAX-ACCESS read-only
    STATUS     current
    DESCRIPTION
	    "Logon Operations/sec is the rate of Logon
	    requests in the public store."
    ::= { informationStorePublicEntry 15 }

ispMessageOpensPerSec OBJECT-TYPE
    SYNTAX     Gauge32
    MAX-ACCESS read-only
    STATUS     current
    DESCRIPTION
	    "Message Opens/sec is the rate that requests to
	    open messages are submitted to the information
	    store."
    ::= { informationStorePublicEntry 16 }

ispMessageRcpntsDelivered OBJECT-TYPE
    SYNTAX     Gauge32
    MAX-ACCESS read-only
    STATUS     current
    DESCRIPTION
	    "Message Recipients Delivered is the total
	    number of recipients that have received a
	    message since startup."
    ::= { informationStorePublicEntry 17 }

ispMessageRcpntsDeliveredPerMin OBJECT-TYPE
    SYNTAX     Gauge32
    MAX-ACCESS read-only
    STATUS     current
    DESCRIPTION
	    "Message Recipients Delivered/min is the rate
	    that recipients receive messages."
    ::= { informationStorePublicEntry 18 }

ispMessagesDelivered OBJECT-TYPE
    SYNTAX     Gauge32
    MAX-ACCESS read-only
    STATUS     current
    DESCRIPTION
	    "Messages Delivered is the total number of
	    messages delivered to all recipients since
	    startup."
    ::= { informationStorePublicEntry 19 }

ispMessagesDeliveredPerMin OBJECT-TYPE
    SYNTAX     Gauge32
    MAX-ACCESS read-only
    STATUS     current
    DESCRIPTION
	    "Messages Delivered/min is the rate that
	    messages are delivered to all recipients."
    ::= { informationStorePublicEntry 20 }

ispMessagesSent OBJECT-TYPE
    SYNTAX     Gauge32
    MAX-ACCESS read-only
    STATUS     current
    DESCRIPTION
	    "Messages Sent is the total number of messages
	    sent to the transport since startup."
    ::= { informationStorePublicEntry 21 }

ispMessagesSentPerMin OBJECT-TYPE
    SYNTAX     Gauge32
    MAX-ACCESS read-only
    STATUS     current
    DESCRIPTION
	    "Messages Sent/min is the rate that messages
	    are sent to the transport."
    ::= { informationStorePublicEntry 22 }

ispMessagesSubmitted OBJECT-TYPE
    SYNTAX     Gauge32
    MAX-ACCESS read-only
    STATUS     current
    DESCRIPTION
	    "Messages Submitted is the total number of
	    messages submitted by clients since service
	    startup."
    ::= { informationStorePublicEntry 23 }

ispMessagesSubmittedPerMin OBJECT-TYPE
    SYNTAX     Gauge32
    MAX-ACCESS read-only
    STATUS     current
    DESCRIPTION
	    "Messages Submitted/min is the rate that
	    messages are submitted by clients."
    ::= { informationStorePublicEntry 24 }

ispNumMsgsExpirePublicFolders OBJECT-TYPE
    SYNTAX     Gauge32
    MAX-ACCESS read-only
    STATUS     current
    DESCRIPTION
	    "Number of messages expired from public
	    folders"
    ::= { informationStorePublicEntry 25 }

ispPeakClientLogons OBJECT-TYPE
    SYNTAX     Gauge32
    MAX-ACCESS read-only
    STATUS     current
    DESCRIPTION
	    "Peak Client Logons is the maximum number of
	    concurrent client logons since the service
	    started."
    ::= { informationStorePublicEntry 26 }

ispRcvQueueSize OBJECT-TYPE
    SYNTAX     Gauge32
    MAX-ACCESS read-only
    STATUS     current
    DESCRIPTION
	    "Receive Queue Size is the number of messages
	    in the public store's receive queue."
    ::= { informationStorePublicEntry 27 }

ispReplicationBackfillDtMsgsRcvd OBJECT-TYPE
    SYNTAX     Gauge32
    MAX-ACCESS read-only
    STATUS     current
    DESCRIPTION
	    "Replication Backfill Data Messages Received is
	    the number of replication messages received
	    from other servers in response to backfill
	    requests since service startup."
    ::= { informationStorePublicEntry 28 }

ispReplicationBackfillDtMsgsSent OBJECT-TYPE
    SYNTAX     Gauge32
    MAX-ACCESS read-only
    STATUS     current
    DESCRIPTION
	    "Replication Backfill Data Messages Sent is the
	    number of replication messages sent in response
	    to backfill requests from other servers since
	    service startup."
    ::= { informationStorePublicEntry 29 }

ispReplicationBackfillRqstsRcvd OBJECT-TYPE
    SYNTAX     Gauge32
    MAX-ACCESS read-only
    STATUS     current
    DESCRIPTION
	    "Replication Backfill Requests Received is the
	    number of backfill request replication messages
	    that have been received from other servers
	    since service startup."
    ::= { informationStorePublicEntry 30 }

ispReplicationBackfillRqstsSent OBJECT-TYPE
    SYNTAX     Gauge32
    MAX-ACCESS read-only
    STATUS     current
    DESCRIPTION
	    "Replication Backfill Requests Sent is the
	    number of backfill request replication messages
	    that have been sent to other servers since
	    service startup."
    ::= { informationStorePublicEntry 31 }

ispReplicationFolderChangesRcvd OBJECT-TYPE
    SYNTAX     Gauge32
    MAX-ACCESS read-only
    STATUS     current
    DESCRIPTION
	    "Replication Folder Changes Received is the
	    number of folder changes that have been
	    replicated from other servers since service
	    startup."
    ::= { informationStorePublicEntry 32 }

ispReplicationFolderChangesSent OBJECT-TYPE
    SYNTAX     Gauge32
    MAX-ACCESS read-only
    STATUS     current
    DESCRIPTION
	    "Replication Folder Tree Messages Sent is the
	    number of replication messages due to public
	    folder hierarchy changes that have been sent to
	    other servers since service startup."
    ::= { informationStorePublicEntry 33 }

ispReplicationFolderDataMsgsRcvd OBJECT-TYPE
    SYNTAX     Gauge32
    MAX-ACCESS read-only
    STATUS     current
    DESCRIPTION
	    "Replication Folder Data Messages Received is
	    the number of replication messages due to
	    changes to items in public folders that have
	    been received from other service since service
	    startup."
    ::= { informationStorePublicEntry 34 }

ispReplicationFolderDataMsgsSent OBJECT-TYPE
    SYNTAX     Gauge32
    MAX-ACCESS read-only
    STATUS     current
    DESCRIPTION
	    "Replication Folder Data Message Messages sent
	    is the number of replication messages due to
	    changes to items in public folders that have
	    been sent to other servers since service
	    startup."
    ::= { informationStorePublicEntry 35 }

ispReplicationFolderTreeMsgsRcvd OBJECT-TYPE
    SYNTAX     Gauge32
    MAX-ACCESS read-only
    STATUS     current
    DESCRIPTION
	    "Replication Folder Tree Messages Received is
	    the number of replication messages due to
	    public folder hierarchy changes that have been
	    received from other servers since service
	    startup."
    ::= { informationStorePublicEntry 36 }

ispReplicationFolderTreeMsgsSent OBJECT-TYPE
    SYNTAX     Gauge32
    MAX-ACCESS read-only
    STATUS     current
    DESCRIPTION
	    "Replication Folder Tree Messages Sent is the
	    number of replication messages due to public
	    folder hierarchy changes that have been sent to
	    other servers since service startup."
    ::= { informationStorePublicEntry 37 }

ispReplicationMsgChangesRcvd OBJECT-TYPE
    SYNTAX     Gauge32
    MAX-ACCESS read-only
    STATUS     current
    DESCRIPTION
	    "Replication Message Changes Received is the
	    number of changes to items in public folders
	    that have been received from other servers
	    since service startup."
    ::= { informationStorePublicEntry 38 }

ispReplicationMsgChangesSent OBJECT-TYPE
    SYNTAX     Gauge32
    MAX-ACCESS read-only
    STATUS     current
    DESCRIPTION
	    "Replication Message Changes Sent is the number
	    of changes to items in public folders that have
	    been replicated to other servers since service
	    startup."
    ::= { informationStorePublicEntry 39 }

ispReplicationMsgsRcvd OBJECT-TYPE
    SYNTAX     Gauge32
    MAX-ACCESS read-only
    STATUS     current
    DESCRIPTION
	    "Replication Messages Received is the total
	    number of replication messages received from
	    other servers since service startup."
    ::= { informationStorePublicEntry 40 }

ispReplicationMsgsSent OBJECT-TYPE
    SYNTAX     Gauge32
    MAX-ACCESS read-only
    STATUS     current
    DESCRIPTION
	    "Replication Messages Sent is the total number
	    of replication messages that have been sent to
	    other servers since service startup."
    ::= { informationStorePublicEntry 41 }

ispReplicationRcvQueueSize OBJECT-TYPE
    SYNTAX     Gauge32
    MAX-ACCESS read-only
    STATUS     current
    DESCRIPTION
	    "Replication Receive Queue Size is the number
	    of replication messages waiting to be
	    processed."
    ::= { informationStorePublicEntry 42 }

ispReplicationStatusMsgsRcvd OBJECT-TYPE
    SYNTAX     Gauge32
    MAX-ACCESS read-only
    STATUS     current
    DESCRIPTION
	    "Status Messages Received is the number of
	    replication status request or response messages
	    that have been received from other servers
	    since service startup."
    ::= { informationStorePublicEntry 43 }

ispReplicationStatusMsgsSent OBJECT-TYPE
    SYNTAX     Gauge32
    MAX-ACCESS read-only
    STATUS     current
    DESCRIPTION
	    "Replication Status Messages Sent is the number
	    of replication status request or response
	    messages that have been sent to other servers
	    since service startup."
    ::= { informationStorePublicEntry 44 }

ispSendQueueSize OBJECT-TYPE
    SYNTAX     Gauge32
    MAX-ACCESS read-only
    STATUS     current
    DESCRIPTION
	    "Send Queue Size is the number of messages in
	    the public store's send queue."
    ::= { informationStorePublicEntry 45 }

ispSingleInstanceRatio OBJECT-TYPE
    SYNTAX     Gauge32
    MAX-ACCESS read-only
    STATUS     current
    DESCRIPTION
	    "Single Instance Ratio is the average number of
	    references to each message in the public
	    store."
    ::= { informationStorePublicEntry 46 }

ispTotalCountOfRecoverableItems OBJECT-TYPE
    SYNTAX     Gauge32
    MAX-ACCESS read-only
    STATUS     current
    DESCRIPTION
	    "Total Count of Recoverable Items is the total
	    number of items retained for Item Recovery"
    ::= { informationStorePublicEntry 47 }

ispTotalSizeOfRecoverableItems OBJECT-TYPE
    SYNTAX     Gauge32
    MAX-ACCESS read-only
    STATUS     current
    DESCRIPTION
	    "Total Size of Recoverable Items is the total
	    size in kilobytes of items retained for Item
	    Recovery"
    ::= { informationStorePublicEntry 48 }

ispRestrictedViewCacheHitRate OBJECT-TYPE
    SYNTAX     Gauge32
    MAX-ACCESS read-only
    STATUS     current
    DESCRIPTION
	    "Restricted View Cache Hit Rate is the rate at
	    which restricted views are reused in the public
	    store."
    ::= { informationStorePublicEntry 49 }

ispRestrictedViewCacheMissRate OBJECT-TYPE
    SYNTAX     Gauge32
    MAX-ACCESS read-only
    STATUS     current
    DESCRIPTION
	    "Restricted View Cache Miss Rate is the rate at
	    which restricted views are created in the
	    public store."
    ::= { informationStorePublicEntry 50 }

ispSearchTaskRate OBJECT-TYPE
    SYNTAX     Gauge32
    MAX-ACCESS read-only
    STATUS     current
    DESCRIPTION
	    "Number of search tasks created per second."
    ::= { informationStorePublicEntry 51 }

ispSlowFindRowRate OBJECT-TYPE
    SYNTAX     Gauge32
    MAX-ACCESS read-only
    STATUS     current
    DESCRIPTION
	    "Slow FindRow Rate is the rate at which the
	    slower FindRow needs to be used in the public
	    store."
    ::= { informationStorePublicEntry 52 }

ispAbortOpRate OBJECT-TYPE
    SYNTAX     Gauge32
    MAX-ACCESS read-only
    STATUS     current
    DESCRIPTION
	    "AbortOpRate."
    ::= { informationStorePublicEntry 53 }

ispAbortOpTotal OBJECT-TYPE
    SYNTAX     Gauge32
    MAX-ACCESS read-only
    STATUS     current
    DESCRIPTION
	    "AbortOpTotal."
    ::= { informationStorePublicEntry 54 }

ispAbortSubmitOpRate OBJECT-TYPE
    SYNTAX     Gauge32
    MAX-ACCESS read-only
    STATUS     current
    DESCRIPTION
	    "AbortSubmitOpRate."
    ::= { informationStorePublicEntry 55 }

ispAbortSubmitOpTotal OBJECT-TYPE
    SYNTAX     Gauge32
    MAX-ACCESS read-only
    STATUS     current
    DESCRIPTION
	    "AbortSubmitOpTotal."
    ::= { informationStorePublicEntry 56 }

ispAddMsgToSendqRate OBJECT-TYPE
    SYNTAX     Gauge32
    MAX-ACCESS read-only
    STATUS     current
    DESCRIPTION
	    "Messages added to the send queue."
    ::= { informationStorePublicEntry 57 }

ispAddMsgToSendqTotal OBJECT-TYPE
    SYNTAX     Gauge32
    MAX-ACCESS read-only
    STATUS     current
    DESCRIPTION
	    "Messages added to the send queue."
    ::= { informationStorePublicEntry 58 }

ispAddNamedCalcPropOpRate OBJECT-TYPE
    SYNTAX     Gauge32
    MAX-ACCESS read-only
    STATUS     current
    DESCRIPTION
	    "AddNamedCalcPropOpRate."
    ::= { informationStorePublicEntry 59 }

ispAddNamedCalcPropOpTotal OBJECT-TYPE
    SYNTAX     Gauge32
    MAX-ACCESS read-only
    STATUS     current
    DESCRIPTION
	    "AddNamedCalcPropOpTotal."
    ::= { informationStorePublicEntry 60 }

ispAddressTypesOpRate OBJECT-TYPE
    SYNTAX     Gauge32
    MAX-ACCESS read-only
    STATUS     current
    DESCRIPTION
	    "AddressTypesOpRate."
    ::= { informationStorePublicEntry 61 }

ispAddressTypesOpTotal OBJECT-TYPE
    SYNTAX     Gauge32
    MAX-ACCESS read-only
    STATUS     current
    DESCRIPTION
	    "AddressTypesOpTotal."
    ::= { informationStorePublicEntry 62 }

ispCacheCcnReadOpRate OBJECT-TYPE
    SYNTAX     Gauge32
    MAX-ACCESS read-only
    STATUS     current
    DESCRIPTION
	    "CacheCcnReadOpRate."
    ::= { informationStorePublicEntry 63 }

ispCacheCcnReadOpTotal OBJECT-TYPE
    SYNTAX     Gauge32
    MAX-ACCESS read-only
    STATUS     current
    DESCRIPTION
	    "CacheCcnReadOpTotal."
    ::= { informationStorePublicEntry 64 }

ispCheckFolderNameOpRate OBJECT-TYPE
    SYNTAX     Gauge32
    MAX-ACCESS read-only
    STATUS     current
    DESCRIPTION
	    "CheckFolderNameOpRate."
    ::= { informationStorePublicEntry 65 }

ispCheckFolderNameOpTotal OBJECT-TYPE
    SYNTAX     Gauge32
    MAX-ACCESS read-only
    STATUS     current
    DESCRIPTION
	    "CheckFolderNameOpTotal."
    ::= { informationStorePublicEntry 66 }

ispCheckRightsOnFolderRate OBJECT-TYPE
    SYNTAX     Gauge32
    MAX-ACCESS read-only
    STATUS     current
    DESCRIPTION
	    "CheckRightsOnFolderRate."
    ::= { informationStorePublicEntry 67 }

ispCheckRightsOnFolderTotal OBJECT-TYPE
    SYNTAX     Gauge32
    MAX-ACCESS read-only
    STATUS     current
    DESCRIPTION
	    "CheckRightsOnFolderTotal."
    ::= { informationStorePublicEntry 68 }

ispCloneStreamOpRate OBJECT-TYPE
    SYNTAX     Gauge32
    MAX-ACCESS read-only
    STATUS     current
    DESCRIPTION
	    "CloneStreamOpRate."
    ::= { informationStorePublicEntry 69 }

ispCloneStreamOpTotal OBJECT-TYPE
    SYNTAX     Gauge32
    MAX-ACCESS read-only
    STATUS     current
    DESCRIPTION
	    "CloneStreamOpTotal."
    ::= { informationStorePublicEntry 70 }

ispCollapseRowOpRate OBJECT-TYPE
    SYNTAX     Gauge32
    MAX-ACCESS read-only
    STATUS     current
    DESCRIPTION
	    "CollapseRowOpRate."
    ::= { informationStorePublicEntry 71 }

ispCollapseRowOpTotal OBJECT-TYPE
    SYNTAX     Gauge32
    MAX-ACCESS read-only
    STATUS     current
    DESCRIPTION
	    "CollapseRowOpTotal."
    ::= { informationStorePublicEntry 72 }

ispCommitStreamOpRate OBJECT-TYPE
    SYNTAX     Gauge32
    MAX-ACCESS read-only
    STATUS     current
    DESCRIPTION
	    "CommitStreamOpRate."
    ::= { informationStorePublicEntry 73 }

ispCommitStreamOpTotal OBJECT-TYPE
    SYNTAX     Gauge32
    MAX-ACCESS read-only
    STATUS     current
    DESCRIPTION
	    "CommitStreamOpTotal."
    ::= { informationStorePublicEntry 74 }

ispCopyPropsOpRate OBJECT-TYPE
    SYNTAX     Gauge32
    MAX-ACCESS read-only
    STATUS     current
    DESCRIPTION
	    "CopyPropsOpRate."
    ::= { informationStorePublicEntry 75 }

ispCopyPropsOpTotal OBJECT-TYPE
    SYNTAX     Gauge32
    MAX-ACCESS read-only
    STATUS     current
    DESCRIPTION
	    "CopyPropsOpTotal."
    ::= { informationStorePublicEntry 76 }

ispCopyToOpRate OBJECT-TYPE
    SYNTAX     Gauge32
    MAX-ACCESS read-only
    STATUS     current
    DESCRIPTION
	    "CopyToOpRate."
    ::= { informationStorePublicEntry 77 }

ispCopyToOpTotal OBJECT-TYPE
    SYNTAX     Gauge32
    MAX-ACCESS read-only
    STATUS     current
    DESCRIPTION
	    "CopyToOpTotal."
    ::= { informationStorePublicEntry 78 }

ispCopyToStreamOpRate OBJECT-TYPE
    SYNTAX     Gauge32
    MAX-ACCESS read-only
    STATUS     current
    DESCRIPTION
	    "CopyToStreamOpRate."
    ::= { informationStorePublicEntry 79 }

ispCopyToStreamOpTotal OBJECT-TYPE
    SYNTAX     Gauge32
    MAX-ACCESS read-only
    STATUS     current
    DESCRIPTION
	    "CopyToStreamOpTotal."
    ::= { informationStorePublicEntry 80 }

ispCreateAttachOpRate OBJECT-TYPE
    SYNTAX     Gauge32
    MAX-ACCESS read-only
    STATUS     current
    DESCRIPTION
	    "CreateAttachOpRate."
    ::= { informationStorePublicEntry 81 }

ispCreateAttachOpTotal OBJECT-TYPE
    SYNTAX     Gauge32
    MAX-ACCESS read-only
    STATUS     current
    DESCRIPTION
	    "CreateAttachOpTotal."
    ::= { informationStorePublicEntry 82 }

ispCreateBookMarkOperationPerSec OBJECT-TYPE
    SYNTAX     Gauge32
    MAX-ACCESS read-only
    STATUS     current
    DESCRIPTION
	    "CreateBookMark Operations/sec is the rate of
	    CreateBookMark requests in the public store."
    ::= { informationStorePublicEntry 83 }

ispCreateFolderOpRate OBJECT-TYPE
    SYNTAX     Gauge32
    MAX-ACCESS read-only
    STATUS     current
    DESCRIPTION
	    "CreateFolderOpRate."
    ::= { informationStorePublicEntry 84 }

ispCreateFolderOpTotal OBJECT-TYPE
    SYNTAX     Gauge32
    MAX-ACCESS read-only
    STATUS     current
    DESCRIPTION
	    "CreateFolderOpTotal."
    ::= { informationStorePublicEntry 85 }

ispDatabaseSessionActiveCount OBJECT-TYPE
    SYNTAX     Gauge32
    MAX-ACCESS read-only
    STATUS     current
    DESCRIPTION
	    "Number of database sessions in use at the
	    current time"
    ::= { informationStorePublicEntry 86 }

ispDatabaseSessionCount OBJECT-TYPE
    SYNTAX     Gauge32
    MAX-ACCESS read-only
    STATUS     current
    DESCRIPTION
	    "Number of database sessions allocated"
    ::= { informationStorePublicEntry 87 }

ispDeleteAttachOpRate OBJECT-TYPE
    SYNTAX     Gauge32
    MAX-ACCESS read-only
    STATUS     current
    DESCRIPTION
	    "DeleteAttachOpRate."
    ::= { informationStorePublicEntry 88 }

ispDeleteAttachOpTotal OBJECT-TYPE
    SYNTAX     Gauge32
    MAX-ACCESS read-only
    STATUS     current
    DESCRIPTION
	    "DeleteAttachOpTotal."
    ::= { informationStorePublicEntry 89 }

ispDeleteFolderOpRate OBJECT-TYPE
    SYNTAX     Gauge32
    MAX-ACCESS read-only
    STATUS     current
    DESCRIPTION
	    "DeleteFolderOpRate."
    ::= { informationStorePublicEntry 90 }

ispDeleteFolderOpTotal OBJECT-TYPE
    SYNTAX     Gauge32
    MAX-ACCESS read-only
    STATUS     current
    DESCRIPTION
	    "DeleteFolderOpTotal."
    ::= { informationStorePublicEntry 91 }

ispDeleteMessagesOpRate OBJECT-TYPE
    SYNTAX     Gauge32
    MAX-ACCESS read-only
    STATUS     current
    DESCRIPTION
	    "DeleteMessagesOpRate."
    ::= { informationStorePublicEntry 92 }

ispDeleteMessagesOpTotal OBJECT-TYPE
    SYNTAX     Gauge32
    MAX-ACCESS read-only
    STATUS     current
    DESCRIPTION
	    "DeleteMessagesOpTotal."
    ::= { informationStorePublicEntry 93 }

ispDelMsgFromSendqRate OBJECT-TYPE
    SYNTAX     Gauge32
    MAX-ACCESS read-only
    STATUS     current
    DESCRIPTION
	    "Messages deleted from the send queue."
    ::= { informationStorePublicEntry 94 }

ispDelMsgFromSendqTotal OBJECT-TYPE
    SYNTAX     Gauge32
    MAX-ACCESS read-only
    STATUS     current
    DESCRIPTION
	    "Messages deleted from the send queue."
    ::= { informationStorePublicEntry 95 }

ispDelPropertyOperationsPerSec OBJECT-TYPE
    SYNTAX     Gauge32
    MAX-ACCESS read-only
    STATUS     current
    DESCRIPTION
	    "DelProperty Operations/sec is the rate of
	    DelProperty requests in the public store."
    ::= { informationStorePublicEntry 96 }

ispDeregisterTableNotifyOpRate OBJECT-TYPE
    SYNTAX     Gauge32
    MAX-ACCESS read-only
    STATUS     current
    DESCRIPTION
	    "DeregisterTableNotificationOpRate."
    ::= { informationStorePublicEntry 97 }

ispDeregisterTableNotifyOpTotal OBJECT-TYPE
    SYNTAX     Gauge32
    MAX-ACCESS read-only
    STATUS     current
    DESCRIPTION
	    "DeregisterTableNotificationOpTotal."
    ::= { informationStorePublicEntry 98 }

ispDoCrossPostOpRate OBJECT-TYPE
    SYNTAX     Gauge32
    MAX-ACCESS read-only
    STATUS     current
    DESCRIPTION
	    "DoCrossPostOpRate."
    ::= { informationStorePublicEntry 99 }

ispDoCrossPostOpTotal OBJECT-TYPE
    SYNTAX     Gauge32
    MAX-ACCESS read-only
    STATUS     current
    DESCRIPTION
	    "DoCrossPostOpTotal."
    ::= { informationStorePublicEntry 100 }

ispEmptyFolderOpRate OBJECT-TYPE
    SYNTAX     Gauge32
    MAX-ACCESS read-only
    STATUS     current
    DESCRIPTION
	    "EmptyFolderOpRate."
    ::= { informationStorePublicEntry 101 }

ispEmptyFolderOpTotal OBJECT-TYPE
    SYNTAX     Gauge32
    MAX-ACCESS read-only
    STATUS     current
    DESCRIPTION
	    "EmptyFolderOpTotal."
    ::= { informationStorePublicEntry 102 }

ispExpandRowOpRate OBJECT-TYPE
    SYNTAX     Gauge32
    MAX-ACCESS read-only
    STATUS     current
    DESCRIPTION
	    "ExpandRowOpRate."
    ::= { informationStorePublicEntry 103 }

ispExpandRowOpTotal OBJECT-TYPE
    SYNTAX     Gauge32
    MAX-ACCESS read-only
    STATUS     current
    DESCRIPTION
	    "ExpandRowOpTotal."
    ::= { informationStorePublicEntry 104 }

ispFghostedOpRate OBJECT-TYPE
    SYNTAX     Gauge32
    MAX-ACCESS read-only
    STATUS     current
    DESCRIPTION
	    "FghostedOpRate."
    ::= { informationStorePublicEntry 105 }

ispFghostedOpTotal OBJECT-TYPE
    SYNTAX     Gauge32
    MAX-ACCESS read-only
    STATUS     current
    DESCRIPTION
	    "FghostedOpTotal."
    ::= { informationStorePublicEntry 106 }

ispFindRowOperationsPerSec OBJECT-TYPE
    SYNTAX     Gauge32
    MAX-ACCESS read-only
    STATUS     current
    DESCRIPTION
	    "FindRow operations/sec is the rate of FindRow
	    requests in the public store."
    ::= { informationStorePublicEntry 107 }

ispFlushPerUserOpRate OBJECT-TYPE
    SYNTAX     Gauge32
    MAX-ACCESS read-only
    STATUS     current
    DESCRIPTION
	    "FlushPerUserOpRate."
    ::= { informationStorePublicEntry 108 }

ispFlushPerUserOpTotal OBJECT-TYPE
    SYNTAX     Gauge32
    MAX-ACCESS read-only
    STATUS     current
    DESCRIPTION
	    "FlushPerUserOpTotal."
    ::= { informationStorePublicEntry 109 }

ispFolderCount OBJECT-TYPE
    SYNTAX     Gauge32
    MAX-ACCESS read-only
    STATUS     current
    DESCRIPTION
	    "Folder Count is the number of separate folders
	    (including top-level folders and subfolders)
	    that exist in the public store."
    ::= { informationStorePublicEntry 110 }

ispFreeBookmarkOpRate OBJECT-TYPE
    SYNTAX     Gauge32
    MAX-ACCESS read-only
    STATUS     current
    DESCRIPTION
	    "FreeBookmarkOpRate."
    ::= { informationStorePublicEntry 111 }

ispFreeBookmarkOpTotal OBJECT-TYPE
    SYNTAX     Gauge32
    MAX-ACCESS read-only
    STATUS     current
    DESCRIPTION
	    "FreeBookmarkOpTotal."
    ::= { informationStorePublicEntry 112 }

ispFXDstCopyFolderOpRate OBJECT-TYPE
    SYNTAX     Gauge32
    MAX-ACCESS read-only
    STATUS     current
    DESCRIPTION
	    "FXDstCopyFolderOpRate."
    ::= { informationStorePublicEntry 113 }

ispFXDstCopyFolderOpTotal OBJECT-TYPE
    SYNTAX     Gauge32
    MAX-ACCESS read-only
    STATUS     current
    DESCRIPTION
	    "FXDstCopyFolderOpTotal."
    ::= { informationStorePublicEntry 114 }

ispFXDstCopyMessagesOpRate OBJECT-TYPE
    SYNTAX     Gauge32
    MAX-ACCESS read-only
    STATUS     current
    DESCRIPTION
	    "FXDstCopyMessagesOpRate."
    ::= { informationStorePublicEntry 115 }

ispFXDstCopyMessagesOpTotal OBJECT-TYPE
    SYNTAX     Gauge32
    MAX-ACCESS read-only
    STATUS     current
    DESCRIPTION
	    "FXDstCopyMessagesOpTotal."
    ::= { informationStorePublicEntry 116 }

ispFXDstCopyPropsOpRate OBJECT-TYPE
    SYNTAX     Gauge32
    MAX-ACCESS read-only
    STATUS     current
    DESCRIPTION
	    "FXDstCopyPropsOpRate."
    ::= { informationStorePublicEntry 117 }

ispFXDstCopyPropsOpTotal OBJECT-TYPE
    SYNTAX     Gauge32
    MAX-ACCESS read-only
    STATUS     current
    DESCRIPTION
	    "FXDstCopyPropsOpTotal."
    ::= { informationStorePublicEntry 118 }

ispFXDstCopyToOpRate OBJECT-TYPE
    SYNTAX     Gauge32
    MAX-ACCESS read-only
    STATUS     current
    DESCRIPTION
	    "FXDstCopyToOpRate."
    ::= { informationStorePublicEntry 119 }

ispFXDstCopyToOpTotal OBJECT-TYPE
    SYNTAX     Gauge32
    MAX-ACCESS read-only
    STATUS     current
    DESCRIPTION
	    "FXDstCopyToOpTotal."
    ::= { informationStorePublicEntry 120 }

ispFXDstPutBufferOpRate OBJECT-TYPE
    SYNTAX     Gauge32
    MAX-ACCESS read-only
    STATUS     current
    DESCRIPTION
	    "FXDstPutBufferOpRate."
    ::= { informationStorePublicEntry 121 }

ispFXDstPutBufferOpTotal OBJECT-TYPE
    SYNTAX     Gauge32
    MAX-ACCESS read-only
    STATUS     current
    DESCRIPTION
	    "FXDstPutBufferOpTotal."
    ::= { informationStorePublicEntry 122 }

ispFXGetBufferCurrentCallerCount OBJECT-TYPE
    SYNTAX     Gauge32
    MAX-ACCESS read-only
    STATUS     current
    DESCRIPTION
	    "Simultaneous FXGetBuffer rops being called."
    ::= { informationStorePublicEntry 123 }

ispFXGetBufferCurrentUsersExec OBJECT-TYPE
    SYNTAX     Gauge32
    MAX-ACCESS read-only
    STATUS     current
    DESCRIPTION
	    "Simultaneous FXGetBuffer rops being executed."
    ::= { informationStorePublicEntry 124 }

ispFXGetBufferRopsAccepted OBJECT-TYPE
    SYNTAX     Gauge32
    MAX-ACCESS read-only
    STATUS     current
    DESCRIPTION
	    "The total number of FXGetBuffer rops
	    accepted."
    ::= { informationStorePublicEntry 125 }

ispFXGetBufferRopsAcceptedPerSec OBJECT-TYPE
    SYNTAX     Gauge32
    MAX-ACCESS read-only
    STATUS     current
    DESCRIPTION
	    "FXGetBuffer rops calls accepted per sec."
    ::= { informationStorePublicEntry 126 }

ispFXGetBufferRopsCalled OBJECT-TYPE
    SYNTAX     Gauge32
    MAX-ACCESS read-only
    STATUS     current
    DESCRIPTION
	    "The total number of FXGetBuffer rops."
    ::= { informationStorePublicEntry 127 }

ispFXGetBufferRopsCalledPerSec OBJECT-TYPE
    SYNTAX     Gauge32
    MAX-ACCESS read-only
    STATUS     current
    DESCRIPTION
	    "Number of FXGetBuffer rops per sec."
    ::= { informationStorePublicEntry 128 }

ispFXGetBufferRopsDenied OBJECT-TYPE
    SYNTAX     Gauge32
    MAX-ACCESS read-only
    STATUS     current
    DESCRIPTION
	    "The total number of FXGetBuffer rops denied."
    ::= { informationStorePublicEntry 129 }

ispFXGetBufferRopsDeniedPerSec OBJECT-TYPE
    SYNTAX     Gauge32
    MAX-ACCESS read-only
    STATUS     current
    DESCRIPTION
	    "FXGetBuffer rops denied per sec."
    ::= { informationStorePublicEntry 130 }

ispFXGetIncrStateOpRate OBJECT-TYPE
    SYNTAX     Gauge32
    MAX-ACCESS read-only
    STATUS     current
    DESCRIPTION
	    "FXGetIncrStateOpRate."
    ::= { informationStorePublicEntry 131 }

ispFXGetIncrStateOpTotal OBJECT-TYPE
    SYNTAX     Gauge32
    MAX-ACCESS read-only
    STATUS     current
    DESCRIPTION
	    "FXGetIncrStateOpTotal."
    ::= { informationStorePublicEntry 132 }

ispFXSrcCopyFolderOpRate OBJECT-TYPE
    SYNTAX     Gauge32
    MAX-ACCESS read-only
    STATUS     current
    DESCRIPTION
	    "FXSrcCopyFolderOpRate."
    ::= { informationStorePublicEntry 133 }

ispFXSrcCopyFolderOpTotal OBJECT-TYPE
    SYNTAX     Gauge32
    MAX-ACCESS read-only
    STATUS     current
    DESCRIPTION
	    "FXSrcCopyFolderOpTotal."
    ::= { informationStorePublicEntry 134 }

ispFXSrcCopyMessagesOpRate OBJECT-TYPE
    SYNTAX     Gauge32
    MAX-ACCESS read-only
    STATUS     current
    DESCRIPTION
	    "FXSrcCopyMessagesOpRate."
    ::= { informationStorePublicEntry 135 }

ispFXSrcCopyMessagesOpTotal OBJECT-TYPE
    SYNTAX     Gauge32
    MAX-ACCESS read-only
    STATUS     current
    DESCRIPTION
	    "FXSrcCopyMessagesOpTotal."
    ::= { informationStorePublicEntry 136 }

ispFXSrcCopyPropsOpRate OBJECT-TYPE
    SYNTAX     Gauge32
    MAX-ACCESS read-only
    STATUS     current
    DESCRIPTION
	    "FXSrcCopyPropsOpRate."
    ::= { informationStorePublicEntry 137 }

ispFXSrcCopyPropsOpTotal OBJECT-TYPE
    SYNTAX     Gauge32
    MAX-ACCESS read-only
    STATUS     current
    DESCRIPTION
	    "FXSrcCopyPropsOpTotal."
    ::= { informationStorePublicEntry 138 }

ispFXSrcCopyToOpRate OBJECT-TYPE
    SYNTAX     Gauge32
    MAX-ACCESS read-only
    STATUS     current
    DESCRIPTION
	    "FXSrcCopyToOpRate."
    ::= { informationStorePublicEntry 139 }

ispFXSrcCopyToOpTotal OBJECT-TYPE
    SYNTAX     Gauge32
    MAX-ACCESS read-only
    STATUS     current
    DESCRIPTION
	    "FXSrcCopyToOpTotal."
    ::= { informationStorePublicEntry 140 }

ispFXSrcGetBufferOpRate OBJECT-TYPE
    SYNTAX     Gauge32
    MAX-ACCESS read-only
    STATUS     current
    DESCRIPTION
	    "FXSrcGetBufferOpRate."
    ::= { informationStorePublicEntry 141 }

ispFXSrcGetBufferOpTotal OBJECT-TYPE
    SYNTAX     Gauge32
    MAX-ACCESS read-only
    STATUS     current
    DESCRIPTION
	    "FXSrcGetBufferOpTotal."
    ::= { informationStorePublicEntry 142 }

ispGetAdrListOpRate OBJECT-TYPE
    SYNTAX     Gauge32
    MAX-ACCESS read-only
    STATUS     current
    DESCRIPTION
	    "GetAdrListOpRate."
    ::= { informationStorePublicEntry 143 }

ispGetAdrListOpTotal OBJECT-TYPE
    SYNTAX     Gauge32
    MAX-ACCESS read-only
    STATUS     current
    DESCRIPTION
	    "GetAdrListOpTotal."
    ::= { informationStorePublicEntry 144 }

ispGetAllPerUserLtidsOpRate OBJECT-TYPE
    SYNTAX     Gauge32
    MAX-ACCESS read-only
    STATUS     current
    DESCRIPTION
	    "GetAllPerUserLtidsOpRate."
    ::= { informationStorePublicEntry 145 }

ispGetAllPerUserLtidsOpTotal OBJECT-TYPE
    SYNTAX     Gauge32
    MAX-ACCESS read-only
    STATUS     current
    DESCRIPTION
	    "GetAllPerUserLtidsOpTotal."
    ::= { informationStorePublicEntry 146 }

ispGetCollapseStateOpRate OBJECT-TYPE
    SYNTAX     Gauge32
    MAX-ACCESS read-only
    STATUS     current
    DESCRIPTION
	    "GetCollapseStateOpRate."
    ::= { informationStorePublicEntry 147 }

ispGetCollapseStateOpTotal OBJECT-TYPE
    SYNTAX     Gauge32
    MAX-ACCESS read-only
    STATUS     current
    DESCRIPTION
	    "GetCollapseStateOpTotal."
    ::= { informationStorePublicEntry 148 }

ispGetFileHandlePropOpRate OBJECT-TYPE
    SYNTAX     Gauge32
    MAX-ACCESS read-only
    STATUS     current
    DESCRIPTION
	    "GetFileHandlePropOpRate"
    ::= { informationStorePublicEntry 149 }

ispGetFileHandlePropOpTotal OBJECT-TYPE
    SYNTAX     Gauge32
    MAX-ACCESS read-only
    STATUS     current
    DESCRIPTION
	    "GetFileHandlePropOpTotal"
    ::= { informationStorePublicEntry 150 }

ispGetFoldersTableRpcIntfRate OBJECT-TYPE
    SYNTAX     Gauge32
    MAX-ACCESS read-only
    STATUS     current
    DESCRIPTION
	    "GetFoldersTableRpcIntfRate."
    ::= { informationStorePublicEntry 151 }

ispGetFoldersTableRpcIntfTotal OBJECT-TYPE
    SYNTAX     Gauge32
    MAX-ACCESS read-only
    STATUS     current
    DESCRIPTION
	    "GetFoldersTableRpcIntfTotal."
    ::= { informationStorePublicEntry 152 }

ispGetIDsFromNamesOpRate OBJECT-TYPE
    SYNTAX     Gauge32
    MAX-ACCESS read-only
    STATUS     current
    DESCRIPTION
	    "GetIDsFromNamesOpRate."
    ::= { informationStorePublicEntry 153 }

ispGetIDsFromNamesOpTotal OBJECT-TYPE
    SYNTAX     Gauge32
    MAX-ACCESS read-only
    STATUS     current
    DESCRIPTION
	    "GetIDsFromNamesOpTotal."
    ::= { informationStorePublicEntry 154 }

ispGetLocalRepIdsOpRate OBJECT-TYPE
    SYNTAX     Gauge32
    MAX-ACCESS read-only
    STATUS     current
    DESCRIPTION
	    "GetLocalRepIdsOpRate."
    ::= { informationStorePublicEntry 155 }

ispGetLocalRepIdsOpTotal OBJECT-TYPE
    SYNTAX     Gauge32
    MAX-ACCESS read-only
    STATUS     current
    DESCRIPTION
	    "GetLocalRepIdsOpTotal."
    ::= { informationStorePublicEntry 156 }

ispGetMailboxTableRpcIntfRate OBJECT-TYPE
    SYNTAX     Gauge32
    MAX-ACCESS read-only
    STATUS     current
    DESCRIPTION
	    "GetMailboxTableRpcIntfRate."
    ::= { informationStorePublicEntry 157 }

ispGetMailboxTableRpcIntfTotal OBJECT-TYPE
    SYNTAX     Gauge32
    MAX-ACCESS read-only
    STATUS     current
    DESCRIPTION
	    "GetMailboxTableRpcIntfTotal."
    ::= { informationStorePublicEntry 158 }

ispGetMessagePropOpRate OBJECT-TYPE
    SYNTAX     Gauge32
    MAX-ACCESS read-only
    STATUS     current
    DESCRIPTION
	    "GetMessagePropOpRate."
    ::= { informationStorePublicEntry 159 }

ispGetMessagePropOpTotal OBJECT-TYPE
    SYNTAX     Gauge32
    MAX-ACCESS read-only
    STATUS     current
    DESCRIPTION
	    "GetMessagePropOpTotal."
    ::= { informationStorePublicEntry 160 }

ispGetMessageStatusOpRate OBJECT-TYPE
    SYNTAX     Gauge32
    MAX-ACCESS read-only
    STATUS     current
    DESCRIPTION
	    "GetMessageStatusOpRate."
    ::= { informationStorePublicEntry 161 }

ispGetMessageStatusOpTotal OBJECT-TYPE
    SYNTAX     Gauge32
    MAX-ACCESS read-only
    STATUS     current
    DESCRIPTION
	    "GetMessageStatusOpTotal."
    ::= { informationStorePublicEntry 162 }

ispGetNamesFromIDsOpRate OBJECT-TYPE
    SYNTAX     Gauge32
    MAX-ACCESS read-only
    STATUS     current
    DESCRIPTION
	    "GetNamesFromIDsOpRate."
    ::= { informationStorePublicEntry 163 }

ispGetNamesFromIDsOpTotal OBJECT-TYPE
    SYNTAX     Gauge32
    MAX-ACCESS read-only
    STATUS     current
    DESCRIPTION
	    "GetNamesFromIDsOpTotal."
    ::= { informationStorePublicEntry 164 }

ispGetOwningMDBsOpRate OBJECT-TYPE
    SYNTAX     Gauge32
    MAX-ACCESS read-only
    STATUS     current
    DESCRIPTION
	    "GetOwningMDBsOpRate."
    ::= { informationStorePublicEntry 165 }

ispGetOwningMDBsOpTotal OBJECT-TYPE
    SYNTAX     Gauge32
    MAX-ACCESS read-only
    STATUS     current
    DESCRIPTION
	    "GetOwningMDBsOpTotal."
    ::= { informationStorePublicEntry 166 }

ispGetPerUserGuidOpRate OBJECT-TYPE
    SYNTAX     Gauge32
    MAX-ACCESS read-only
    STATUS     current
    DESCRIPTION
	    "GetPerUserGuidOpRate."
    ::= { informationStorePublicEntry 167 }

ispGetPerUserGuidOpTotal OBJECT-TYPE
    SYNTAX     Gauge32
    MAX-ACCESS read-only
    STATUS     current
    DESCRIPTION
	    "GetPerUserGuidOpTotal."
    ::= { informationStorePublicEntry 168 }

ispGetPerUserLtidsOpRate OBJECT-TYPE
    SYNTAX     Gauge32
    MAX-ACCESS read-only
    STATUS     current
    DESCRIPTION
	    "GetPerUserLtidsOpRate."
    ::= { informationStorePublicEntry 169 }

ispGetPerUserLtidsOpTotal OBJECT-TYPE
    SYNTAX     Gauge32
    MAX-ACCESS read-only
    STATUS     current
    DESCRIPTION
	    "GetPerUserLtidsOpTotal."
    ::= { informationStorePublicEntry 170 }

ispGetPerUserOpRate OBJECT-TYPE
    SYNTAX     Gauge32
    MAX-ACCESS read-only
    STATUS     current
    DESCRIPTION
	    "GetPerUserOpRate."
    ::= { informationStorePublicEntry 171 }

ispGetPerUserOpTotal OBJECT-TYPE
    SYNTAX     Gauge32
    MAX-ACCESS read-only
    STATUS     current
    DESCRIPTION
	    "GetPerUserOpTotal."
    ::= { informationStorePublicEntry 172 }

ispGetPropertyOperationsPerSec OBJECT-TYPE
    SYNTAX     Gauge32
    MAX-ACCESS read-only
    STATUS     current
    DESCRIPTION
	    "GetProperty Operations/sec is the rate of
	    GetProperty requests in the public store."
    ::= { informationStorePublicEntry 173 }

ispGetPropListOpRate OBJECT-TYPE
    SYNTAX     Gauge32
    MAX-ACCESS read-only
    STATUS     current
    DESCRIPTION
	    "GetPropListOpRate."
    ::= { informationStorePublicEntry 174 }

ispGetPropListOpTotal OBJECT-TYPE
    SYNTAX     Gauge32
    MAX-ACCESS read-only
    STATUS     current
    DESCRIPTION
	    "GetPropListOpTotal."
    ::= { informationStorePublicEntry 175 }

ispGetReceiveFolderOpRate OBJECT-TYPE
    SYNTAX     Gauge32
    MAX-ACCESS read-only
    STATUS     current
    DESCRIPTION
	    "GetReceiveFolderOpRate."
    ::= { informationStorePublicEntry 176 }

ispGetReceiveFolderOpTotal OBJECT-TYPE
    SYNTAX     Gauge32
    MAX-ACCESS read-only
    STATUS     current
    DESCRIPTION
	    "GetReceiveFolderOpTotal."
    ::= { informationStorePublicEntry 177 }

ispGetReceiveFolderTableOpRate OBJECT-TYPE
    SYNTAX     Gauge32
    MAX-ACCESS read-only
    STATUS     current
    DESCRIPTION
	    "GetReceiveFolderTableOpRate."
    ::= { informationStorePublicEntry 178 }

ispGetReceiveFolderTableOpTotal OBJECT-TYPE
    SYNTAX     Gauge32
    MAX-ACCESS read-only
    STATUS     current
    DESCRIPTION
	    "GetReceiveFolderTableOpTotal."
    ::= { informationStorePublicEntry 179 }

ispGetRecipColumnsOpRate OBJECT-TYPE
    SYNTAX     Gauge32
    MAX-ACCESS read-only
    STATUS     current
    DESCRIPTION
	    "Get the available columns in a recipient
	    table."
    ::= { informationStorePublicEntry 180 }

ispGetRecipColumnsOpTotal OBJECT-TYPE
    SYNTAX     Gauge32
    MAX-ACCESS read-only
    STATUS     current
    DESCRIPTION
	    "Get the available columns in a recipient
	    table."
    ::= { informationStorePublicEntry 181 }

ispGetRecipCountOpRate OBJECT-TYPE
    SYNTAX     Gauge32
    MAX-ACCESS read-only
    STATUS     current
    DESCRIPTION
	    "GetRecipCountOpRate."
    ::= { informationStorePublicEntry 182 }

ispGetRecipCountOpTotal OBJECT-TYPE
    SYNTAX     Gauge32
    MAX-ACCESS read-only
    STATUS     current
    DESCRIPTION
	    "GetRecipCountOpTotal."
    ::= { informationStorePublicEntry 183 }

ispGetRecipOpRate OBJECT-TYPE
    SYNTAX     Gauge32
    MAX-ACCESS read-only
    STATUS     current
    DESCRIPTION
	    "GetRecipOpRate."
    ::= { informationStorePublicEntry 184 }

ispGetRecipOpTotal OBJECT-TYPE
    SYNTAX     Gauge32
    MAX-ACCESS read-only
    STATUS     current
    DESCRIPTION
	    "GetRecipOpTotal."
    ::= { informationStorePublicEntry 185 }

ispGetRightsOpRate OBJECT-TYPE
    SYNTAX     Gauge32
    MAX-ACCESS read-only
    STATUS     current
    DESCRIPTION
	    "GetRightsOpRate."
    ::= { informationStorePublicEntry 186 }

ispGetRightsOpTotal OBJECT-TYPE
    SYNTAX     Gauge32
    MAX-ACCESS read-only
    STATUS     current
    DESCRIPTION
	    "GetRightsOpTotal."
    ::= { informationStorePublicEntry 187 }

ispGetSearchCriteriaOpRate OBJECT-TYPE
    SYNTAX     Gauge32
    MAX-ACCESS read-only
    STATUS     current
    DESCRIPTION
	    "GetSearchCriteriaOpRate."
    ::= { informationStorePublicEntry 188 }

ispGetSearchCriteriaOpTotal OBJECT-TYPE
    SYNTAX     Gauge32
    MAX-ACCESS read-only
    STATUS     current
    DESCRIPTION
	    "GetSearchCriteriaOpTotal."
    ::= { informationStorePublicEntry 189 }

ispGetStatusOpRate OBJECT-TYPE
    SYNTAX     Gauge32
    MAX-ACCESS read-only
    STATUS     current
    DESCRIPTION
	    "GetStatusOpRate."
    ::= { informationStorePublicEntry 190 }

ispGetStatusOpTotal OBJECT-TYPE
    SYNTAX     Gauge32
    MAX-ACCESS read-only
    STATUS     current
    DESCRIPTION
	    "GetStatusOpTotal."
    ::= { informationStorePublicEntry 191 }

ispGetStreamSizeOpRate OBJECT-TYPE
    SYNTAX     Gauge32
    MAX-ACCESS read-only
    STATUS     current
    DESCRIPTION
	    "GetStreamSizeOpRate."
    ::= { informationStorePublicEntry 192 }

ispGetStreamSizeOpTotal OBJECT-TYPE
    SYNTAX     Gauge32
    MAX-ACCESS read-only
    STATUS     current
    DESCRIPTION
	    "GetStreamSizeOpTotal."
    ::= { informationStorePublicEntry 193 }

ispGetTableOpRate OBJECT-TYPE
    SYNTAX     Gauge32
    MAX-ACCESS read-only
    STATUS     current
    DESCRIPTION
	    "GetTableOpRate."
    ::= { informationStorePublicEntry 194 }

ispGetTableOpTotal OBJECT-TYPE
    SYNTAX     Gauge32
    MAX-ACCESS read-only
    STATUS     current
    DESCRIPTION
	    "GetTableOpTotal."
    ::= { informationStorePublicEntry 195 }

ispGetXhdrListOpRate OBJECT-TYPE
    SYNTAX     Gauge32
    MAX-ACCESS read-only
    STATUS     current
    DESCRIPTION
	    "GetXhdrListOpRate."
    ::= { informationStorePublicEntry 196 }

ispGetXhdrListOpTotal OBJECT-TYPE
    SYNTAX     Gauge32
    MAX-ACCESS read-only
    STATUS     current
    DESCRIPTION
	    "GetXhdrListOpTotal."
    ::= { informationStorePublicEntry 197 }

ispIdFromLtidOpRate OBJECT-TYPE
    SYNTAX     Gauge32
    MAX-ACCESS read-only
    STATUS     current
    DESCRIPTION
	    "IdFromLtidOpRate."
    ::= { informationStorePublicEntry 198 }

ispIdFromLtidOpTotal OBJECT-TYPE
    SYNTAX     Gauge32
    MAX-ACCESS read-only
    STATUS     current
    DESCRIPTION
	    "IdFromLtidOpTotal."
    ::= { informationStorePublicEntry 199 }

ispImportDeleteOpRate OBJECT-TYPE
    SYNTAX     Gauge32
    MAX-ACCESS read-only
    STATUS     current
    DESCRIPTION
	    "ImportDeleteOpRate."
    ::= { informationStorePublicEntry 200 }

ispImportDeleteOpTotal OBJECT-TYPE
    SYNTAX     Gauge32
    MAX-ACCESS read-only
    STATUS     current
    DESCRIPTION
	    "ImportDeleteOpTotal."
    ::= { informationStorePublicEntry 201 }

ispImportHierChgOpRate OBJECT-TYPE
    SYNTAX     Gauge32
    MAX-ACCESS read-only
    STATUS     current
    DESCRIPTION
	    "ImportHierChgOpRate."
    ::= { informationStorePublicEntry 202 }

ispImportHierChgOpTotal OBJECT-TYPE
    SYNTAX     Gauge32
    MAX-ACCESS read-only
    STATUS     current
    DESCRIPTION
	    "ImportHierChgOpTotal."
    ::= { informationStorePublicEntry 203 }

ispImportHierDelOpRate OBJECT-TYPE
    SYNTAX     Gauge32
    MAX-ACCESS read-only
    STATUS     current
    DESCRIPTION
	    "ImportHierDelOpRate."
    ::= { informationStorePublicEntry 204 }

ispImportHierDelOpTotal OBJECT-TYPE
    SYNTAX     Gauge32
    MAX-ACCESS read-only
    STATUS     current
    DESCRIPTION
	    "ImportHierDelOpTotal."
    ::= { informationStorePublicEntry 205 }

ispImportMsgChgOpRate OBJECT-TYPE
    SYNTAX     Gauge32
    MAX-ACCESS read-only
    STATUS     current
    DESCRIPTION
	    "ImportMsgChgOpRate."
    ::= { informationStorePublicEntry 206 }

ispImportMsgChgOpTotal OBJECT-TYPE
    SYNTAX     Gauge32
    MAX-ACCESS read-only
    STATUS     current
    DESCRIPTION
	    "ImportMsgChgOpTotal."
    ::= { informationStorePublicEntry 207 }

ispImportMsgMoveOpRate OBJECT-TYPE
    SYNTAX     Gauge32
    MAX-ACCESS read-only
    STATUS     current
    DESCRIPTION
	    "ImportMsgMoveOpRate."
    ::= { informationStorePublicEntry 208 }

ispImportMsgMoveOpTotal OBJECT-TYPE
    SYNTAX     Gauge32
    MAX-ACCESS read-only
    STATUS     current
    DESCRIPTION
	    "ImportMsgMoveOpTotal."
    ::= { informationStorePublicEntry 209 }

ispImportReadsOpRate OBJECT-TYPE
    SYNTAX     Gauge32
    MAX-ACCESS read-only
    STATUS     current
    DESCRIPTION
	    "ImportReadsOpRate."
    ::= { informationStorePublicEntry 210 }

ispImportReadsOpTotal OBJECT-TYPE
    SYNTAX     Gauge32
    MAX-ACCESS read-only
    STATUS     current
    DESCRIPTION
	    "ImportReadsOpTotal."
    ::= { informationStorePublicEntry 211 }

ispIncrCfgOpRate OBJECT-TYPE
    SYNTAX     Gauge32
    MAX-ACCESS read-only
    STATUS     current
    DESCRIPTION
	    "IncrCfgOpRate."
    ::= { informationStorePublicEntry 212 }

ispIncrCfgOpTotal OBJECT-TYPE
    SYNTAX     Gauge32
    MAX-ACCESS read-only
    STATUS     current
    DESCRIPTION
	    "IncrCfgOpTotal."
    ::= { informationStorePublicEntry 213 }

ispLocalDeliveryOpRate OBJECT-TYPE
    SYNTAX     Gauge32
    MAX-ACCESS read-only
    STATUS     current
    DESCRIPTION
	    "LocalDeliveryOpRate."
    ::= { informationStorePublicEntry 214 }

ispLocalDeliveryOpTotal OBJECT-TYPE
    SYNTAX     Gauge32
    MAX-ACCESS read-only
    STATUS     current
    DESCRIPTION
	    "Number of messages delivered locally through
	    the Local Delivery RPCINTF API."
    ::= { informationStorePublicEntry 215 }

ispLockRegionStreamOpRate OBJECT-TYPE
    SYNTAX     Gauge32
    MAX-ACCESS read-only
    STATUS     current
    DESCRIPTION
	    "LockRegionStreamOpRate."
    ::= { informationStorePublicEntry 216 }

ispLockRegionStreamOpTotal OBJECT-TYPE
    SYNTAX     Gauge32
    MAX-ACCESS read-only
    STATUS     current
    DESCRIPTION
	    "LockRegionStreamOpTotal."
    ::= { informationStorePublicEntry 217 }

ispLtidFromIdOpRate OBJECT-TYPE
    SYNTAX     Gauge32
    MAX-ACCESS read-only
    STATUS     current
    DESCRIPTION
	    "LtidFromIdOpRate."
    ::= { informationStorePublicEntry 218 }

ispLtidFromIdOpTotal OBJECT-TYPE
    SYNTAX     Gauge32
    MAX-ACCESS read-only
    STATUS     current
    DESCRIPTION
	    "LtidFromIdOpTotal."
    ::= { informationStorePublicEntry 219 }

ispModifyACLOpRate OBJECT-TYPE
    SYNTAX     Gauge32
    MAX-ACCESS read-only
    STATUS     current
    DESCRIPTION
	    "ModifyACLOpRate."
    ::= { informationStorePublicEntry 220 }

ispModifyACLOpTotal OBJECT-TYPE
    SYNTAX     Gauge32
    MAX-ACCESS read-only
    STATUS     current
    DESCRIPTION
	    "ModifyACLOpTotal."
    ::= { informationStorePublicEntry 221 }

ispModifyMvPropOpRate OBJECT-TYPE
    SYNTAX     Gauge32
    MAX-ACCESS read-only
    STATUS     current
    DESCRIPTION
	    "ModifyMvPropOpRate."
    ::= { informationStorePublicEntry 222 }

ispModifyMvPropOpTotal OBJECT-TYPE
    SYNTAX     Gauge32
    MAX-ACCESS read-only
    STATUS     current
    DESCRIPTION
	    "ModifyMvPropOpTotal."
    ::= { informationStorePublicEntry 223 }

ispModifyRcpntsOperationsPerSec OBJECT-TYPE
    SYNTAX     Gauge32
    MAX-ACCESS read-only
    STATUS     current
    DESCRIPTION
	    "ModifyRecipients Operations/sec is the rate of
	    ModifyRecipients requests in the public store."
    ::= { informationStorePublicEntry 224 }

ispModifyRulesOpRate OBJECT-TYPE
    SYNTAX     Gauge32
    MAX-ACCESS read-only
    STATUS     current
    DESCRIPTION
	    "ModifyRulesOpRate."
    ::= { informationStorePublicEntry 225 }

ispModifyRulesOpTotal OBJECT-TYPE
    SYNTAX     Gauge32
    MAX-ACCESS read-only
    STATUS     current
    DESCRIPTION
	    "ModifyRulesOpTotal."
    ::= { informationStorePublicEntry 226 }

ispModifyRulesRate OBJECT-TYPE
    SYNTAX     Gauge32
    MAX-ACCESS read-only
    STATUS     current
    DESCRIPTION
	    "ModifyRulesRate."
    ::= { informationStorePublicEntry 227 }

ispModifyRulesTotal OBJECT-TYPE
    SYNTAX     Gauge32
    MAX-ACCESS read-only
    STATUS     current
    DESCRIPTION
	    "ModifyRulesTotal."
    ::= { informationStorePublicEntry 228 }

ispMoveCopyFolderOpRate OBJECT-TYPE
    SYNTAX     Gauge32
    MAX-ACCESS read-only
    STATUS     current
    DESCRIPTION
	    "MoveCopyFolderOpRate."
    ::= { informationStorePublicEntry 229 }

ispMoveCopyFolderOpTotal OBJECT-TYPE
    SYNTAX     Gauge32
    MAX-ACCESS read-only
    STATUS     current
    DESCRIPTION
	    "MoveCopyFolderOpTotal."
    ::= { informationStorePublicEntry 230 }

ispMoveCopyMessagesOpRate OBJECT-TYPE
    SYNTAX     Gauge32
    MAX-ACCESS read-only
    STATUS     current
    DESCRIPTION
	    "MoveCopyMessagesOpRate."
    ::= { informationStorePublicEntry 231 }

ispMoveCopyMessagesOpTotal OBJECT-TYPE
    SYNTAX     Gauge32
    MAX-ACCESS read-only
    STATUS     current
    DESCRIPTION
	    "MoveCopyMessagesOpTotal."
    ::= { informationStorePublicEntry 232 }

ispNextNewsgroupOpRate OBJECT-TYPE
    SYNTAX     Gauge32
    MAX-ACCESS read-only
    STATUS     current
    DESCRIPTION
	    "NextNewsgroupOpRate."
    ::= { informationStorePublicEntry 233 }

ispNextNewsgroupOpTotal OBJECT-TYPE
    SYNTAX     Gauge32
    MAX-ACCESS read-only
    STATUS     current
    DESCRIPTION
	    "NextNewsgroupOpTotal."
    ::= { informationStorePublicEntry 234 }

ispNukeRecipientsOpRate OBJECT-TYPE
    SYNTAX     Gauge32
    MAX-ACCESS read-only
    STATUS     current
    DESCRIPTION
	    "NukeRecipientsOpRate."
    ::= { informationStorePublicEntry 235 }

ispNukeRecipientsOpTotal OBJECT-TYPE
    SYNTAX     Gauge32
    MAX-ACCESS read-only
    STATUS     current
    DESCRIPTION
	    "NukeRecipientsOpTotal."
    ::= { informationStorePublicEntry 236 }

ispOpenAdvisorOpRate OBJECT-TYPE
    SYNTAX     Gauge32
    MAX-ACCESS read-only
    STATUS     current
    DESCRIPTION
	    "OpenAdvisorOpRate."
    ::= { informationStorePublicEntry 237 }

ispOpenAdvisorOpTotal OBJECT-TYPE
    SYNTAX     Gauge32
    MAX-ACCESS read-only
    STATUS     current
    DESCRIPTION
	    "OpenAdvisorOpTotal."
    ::= { informationStorePublicEntry 238 }

ispOpenAttachOpRate OBJECT-TYPE
    SYNTAX     Gauge32
    MAX-ACCESS read-only
    STATUS     current
    DESCRIPTION
	    "OpenAttachOpRate."
    ::= { informationStorePublicEntry 239 }

ispOpenAttachOpTotal OBJECT-TYPE
    SYNTAX     Gauge32
    MAX-ACCESS read-only
    STATUS     current
    DESCRIPTION
	    "OpenAttachOpTotal."
    ::= { informationStorePublicEntry 240 }

ispOpenCollectOpRate OBJECT-TYPE
    SYNTAX     Gauge32
    MAX-ACCESS read-only
    STATUS     current
    DESCRIPTION
	    "OpenCollectOpRate."
    ::= { informationStorePublicEntry 241 }

ispOpenCollectOpTotal OBJECT-TYPE
    SYNTAX     Gauge32
    MAX-ACCESS read-only
    STATUS     current
    DESCRIPTION
	    "OpenCollectOpTotal."
    ::= { informationStorePublicEntry 242 }

ispOpenFolderByNntpNameOpRate OBJECT-TYPE
    SYNTAX     Gauge32
    MAX-ACCESS read-only
    STATUS     current
    DESCRIPTION
	    "OpenFolderByNntpNameOpRate."
    ::= { informationStorePublicEntry 243 }

ispOpenFolderByNntpNameOpTotal OBJECT-TYPE
    SYNTAX     Gauge32
    MAX-ACCESS read-only
    STATUS     current
    DESCRIPTION
	    "OpenFolderByNntpNameOpTotal."
    ::= { informationStorePublicEntry 244 }

ispOpenImailConvObjectOpRate OBJECT-TYPE
    SYNTAX     Gauge32
    MAX-ACCESS read-only
    STATUS     current
    DESCRIPTION
	    "OpenImailConversionObjectOpRate."
    ::= { informationStorePublicEntry 245 }

ispOpenImailConvObjectOpTotal OBJECT-TYPE
    SYNTAX     Gauge32
    MAX-ACCESS read-only
    STATUS     current
    DESCRIPTION
	    "OpenImailConversionObjectOpTotal."
    ::= { informationStorePublicEntry 246 }

ispOpenImailConvStreamOpRate OBJECT-TYPE
    SYNTAX     Gauge32
    MAX-ACCESS read-only
    STATUS     current
    DESCRIPTION
	    "OpenImailConversionStreamOpRate."
    ::= { informationStorePublicEntry 247 }

ispOpenImailConvStreamOpTotal OBJECT-TYPE
    SYNTAX     Gauge32
    MAX-ACCESS read-only
    STATUS     current
    DESCRIPTION
	    "OpenImailConversionStreamOpTotal."
    ::= { informationStorePublicEntry 248 }

ispOpenMessageByArticleNumOpRate OBJECT-TYPE
    SYNTAX     Gauge32
    MAX-ACCESS read-only
    STATUS     current
    DESCRIPTION
	    "OpenMessageByArticleNumberOpRate."
    ::= { informationStorePublicEntry 249 }

ispOpenMessageByArticleNmOpTotal OBJECT-TYPE
    SYNTAX     Gauge32
    MAX-ACCESS read-only
    STATUS     current
    DESCRIPTION
	    "OpenMessageByArticleNumberOpTotal."
    ::= { informationStorePublicEntry 250 }

ispOpenMessageByMsgIdOpRate OBJECT-TYPE
    SYNTAX     Gauge32
    MAX-ACCESS read-only
    STATUS     current
    DESCRIPTION
	    "OpenMessageByMsgIdOpRate."
    ::= { informationStorePublicEntry 251 }

ispOpenMessageByMsgIdOpTotal OBJECT-TYPE
    SYNTAX     Gauge32
    MAX-ACCESS read-only
    STATUS     current
    DESCRIPTION
	    "OpenMessageByMsgIdOpTotal."
    ::= { informationStorePublicEntry 252 }

ispOpenMessagePropOpRate OBJECT-TYPE
    SYNTAX     Gauge32
    MAX-ACCESS read-only
    STATUS     current
    DESCRIPTION
	    "OpenMessagePropOpRate."
    ::= { informationStorePublicEntry 253 }

ispOpenMessagePropOpTotal OBJECT-TYPE
    SYNTAX     Gauge32
    MAX-ACCESS read-only
    STATUS     current
    DESCRIPTION
	    "OpenMessagePropOpTotal."
    ::= { informationStorePublicEntry 254 }

ispOpenStreamOperationsPerSec OBJECT-TYPE
    SYNTAX     Gauge32
    MAX-ACCESS read-only
    STATUS     current
    DESCRIPTION
	    "OpenStream Operations/sec is the rate of
	    OpenStream requests in the public store."
    ::= { informationStorePublicEntry 255 }

ispUserReadCacheConsumed OBJECT-TYPE
    SYNTAX     Gauge32
    MAX-ACCESS read-only
    STATUS     current
    DESCRIPTION
	    "Number of entries in the Per User Read cache
	    consumed for use (but may or may not be
	    currently in use)."
    ::= { informationStorePublicEntry 256 }

ispUserReadCacheDirty OBJECT-TYPE
    SYNTAX     Gauge32
    MAX-ACCESS read-only
    STATUS     current
    DESCRIPTION
	    "Number of entries in the Per User Read cache
	    which have been updated but have not yet been
	    flushed to disk."
    ::= { informationStorePublicEntry 257 }

ispUserReadCacheEntriesReUsedSec OBJECT-TYPE
    SYNTAX     Gauge32
    MAX-ACCESS read-only
    STATUS     current
    DESCRIPTION
	    "Rate of entries that were victimized from the
	    Per User Read cache in order to accommodate new
	    entries."
    ::= { informationStorePublicEntry 258 }

ispUserReadCacheEntriesScanSec OBJECT-TYPE
    SYNTAX     Gauge32
    MAX-ACCESS read-only
    STATUS     current
    DESCRIPTION
	    "Rate of entries inspected during each scan of
	    the Per User Read cache in order to identify a
	    victimization candidate."
    ::= { informationStorePublicEntry 259 }

ispUserReadCacheInUse OBJECT-TYPE
    SYNTAX     Gauge32
    MAX-ACCESS read-only
    STATUS     current
    DESCRIPTION
	    "Number of entries in the Per User Read cache
	    actually in use."
    ::= { informationStorePublicEntry 260 }

ispUserReadCacheInsertsSec OBJECT-TYPE
    SYNTAX     Gauge32
    MAX-ACCESS read-only
    STATUS     current
    DESCRIPTION
	    "Rate of insertions of new entries into the Per
	    User Read cache."
    ::= { informationStorePublicEntry 261 }

ispUserReadCacheLookupHitRatio OBJECT-TYPE
    SYNTAX     Gauge32
    MAX-ACCESS read-only
    STATUS     current
    DESCRIPTION
	    "Rate of successful Per User Read cache lookup
	    requests."
    ::= { informationStorePublicEntry 262 }

ispUserReadCacheLookHitRatioBase OBJECT-TYPE
    SYNTAX     Gauge32
    MAX-ACCESS read-only
    STATUS     current
    DESCRIPTION
	    "Rate of successful Per User Read cache lookup
	    requests. (base)"
    ::= { informationStorePublicEntry 263 }

ispUserReadCacheLookupsSec OBJECT-TYPE
    SYNTAX     Gauge32
    MAX-ACCESS read-only
    STATUS     current
    DESCRIPTION
	    "Rate of lookup requests in the Per User Read
	    cache."
    ::= { informationStorePublicEntry 264 }

ispUserReadCacheScansSec OBJECT-TYPE
    SYNTAX     Gauge32
    MAX-ACCESS read-only
    STATUS     current
    DESCRIPTION
	    "Rate of scans performed of the Per User Read
	    cache in order to identify a victimization
	    candidate."
    ::= { informationStorePublicEntry 265 }

ispUserReadCacheSize OBJECT-TYPE
    SYNTAX     Gauge32
    MAX-ACCESS read-only
    STATUS     current
    DESCRIPTION
	    "Total size (number of entries) of the Per User
	    Read cache."
    ::= { informationStorePublicEntry 266 }

ispPrepareReadRecipientsRate OBJECT-TYPE
    SYNTAX     Gauge32
    MAX-ACCESS read-only
    STATUS     current
    DESCRIPTION
	    "PrepareReadRecipientsRate."
    ::= { informationStorePublicEntry 267 }

ispPrepareReadRecipientsTotal OBJECT-TYPE
    SYNTAX     Gauge32
    MAX-ACCESS read-only
    STATUS     current
    DESCRIPTION
	    "PrepareReadRecipientsTotal."
    ::= { informationStorePublicEntry 268 }

ispQryNamedPropsOpRate OBJECT-TYPE
    SYNTAX     Gauge32
    MAX-ACCESS read-only
    STATUS     current
    DESCRIPTION
	    "QryNamedPropsOpRate."
    ::= { informationStorePublicEntry 269 }

ispQryNamedPropsOpTotal OBJECT-TYPE
    SYNTAX     Gauge32
    MAX-ACCESS read-only
    STATUS     current
    DESCRIPTION
	    "QryNamedPropsOpTotal."
    ::= { informationStorePublicEntry 270 }

ispQueryColumnsAllOpRate OBJECT-TYPE
    SYNTAX     Gauge32
    MAX-ACCESS read-only
    STATUS     current
    DESCRIPTION
	    "QueryColumnsAllOpRate."
    ::= { informationStorePublicEntry 271 }

ispQueryColumnsAllOpTotal OBJECT-TYPE
    SYNTAX     Gauge32
    MAX-ACCESS read-only
    STATUS     current
    DESCRIPTION
	    "QueryColumnsAllOpTotal."
    ::= { informationStorePublicEntry 272 }

ispQueryPositionOperationsPerSec OBJECT-TYPE
    SYNTAX     Gauge32
    MAX-ACCESS read-only
    STATUS     current
    DESCRIPTION
	    "QueryPosition Operations/sec is the rate of
	    QueryPosition requests in the public store."
    ::= { informationStorePublicEntry 273 }

ispQueryRowsOpRate OBJECT-TYPE
    SYNTAX     Gauge32
    MAX-ACCESS read-only
    STATUS     current
    DESCRIPTION
	    "QueryRowsOpRate."
    ::= { informationStorePublicEntry 274 }

ispQueryRowsOpTotal OBJECT-TYPE
    SYNTAX     Gauge32
    MAX-ACCESS read-only
    STATUS     current
    DESCRIPTION
	    "QueryRowsOpTotal."
    ::= { informationStorePublicEntry 275 }

ispReadStreamOpRate OBJECT-TYPE
    SYNTAX     Gauge32
    MAX-ACCESS read-only
    STATUS     current
    DESCRIPTION
	    "ReadStreamOpRate."
    ::= { informationStorePublicEntry 276 }

ispReadStreamOpTotal OBJECT-TYPE
    SYNTAX     Gauge32
    MAX-ACCESS read-only
    STATUS     current
    DESCRIPTION
	    "ReadStreamOpTotal."
    ::= { informationStorePublicEntry 277 }

ispRegICSNotifsOpRate OBJECT-TYPE
    SYNTAX     Gauge32
    MAX-ACCESS read-only
    STATUS     current
    DESCRIPTION
	    "RegICSNotifsOpRate."
    ::= { informationStorePublicEntry 278 }

ispRegICSNotifsOpTotal OBJECT-TYPE
    SYNTAX     Gauge32
    MAX-ACCESS read-only
    STATUS     current
    DESCRIPTION
	    "RegICSNotifsOpTotal."
    ::= { informationStorePublicEntry 279 }

ispRegisterNotifyOperationPerSec OBJECT-TYPE
    SYNTAX     Gauge32
    MAX-ACCESS read-only
    STATUS     current
    DESCRIPTION
	    "RegisterNotification Operations/sec is the
	    rate of RegisterNotification requests in the
	    public store."
    ::= { informationStorePublicEntry 280 }

ispRegisterTableNotifyOpRate OBJECT-TYPE
    SYNTAX     Gauge32
    MAX-ACCESS read-only
    STATUS     current
    DESCRIPTION
	    "RegisterTableNotificationOpRate."
    ::= { informationStorePublicEntry 281 }

ispRegisterTableNotifyOpTotal OBJECT-TYPE
    SYNTAX     Gauge32
    MAX-ACCESS read-only
    STATUS     current
    DESCRIPTION
	    "RegisterTableNotificationOpTotal."
    ::= { informationStorePublicEntry 282 }

ispRenderMessageOpRate OBJECT-TYPE
    SYNTAX     Gauge32
    MAX-ACCESS read-only
    STATUS     current
    DESCRIPTION
	    "RenderMessageOpRate."
    ::= { informationStorePublicEntry 283 }

ispRenderMessageOpTotal OBJECT-TYPE
    SYNTAX     Gauge32
    MAX-ACCESS read-only
    STATUS     current
    DESCRIPTION
	    "RenderMessageOpTotal."
    ::= { informationStorePublicEntry 284 }

ispResetTableOpRate OBJECT-TYPE
    SYNTAX     Gauge32
    MAX-ACCESS read-only
    STATUS     current
    DESCRIPTION
	    "ResetTableOpRate."
    ::= { informationStorePublicEntry 285 }

ispResetTableOpTotal OBJECT-TYPE
    SYNTAX     Gauge32
    MAX-ACCESS read-only
    STATUS     current
    DESCRIPTION
	    "ResetTableOpTotal."
    ::= { informationStorePublicEntry 286 }

ispRestrictOperationsPerSec OBJECT-TYPE
    SYNTAX     Gauge32
    MAX-ACCESS read-only
    STATUS     current
    DESCRIPTION
	    "Restrict Operations/sec is the rate of
	    Restrict requests in the public store."
    ::= { informationStorePublicEntry 287 }

ispRowsInACLListTable OBJECT-TYPE
    SYNTAX     Gauge32
    MAX-ACCESS read-only
    STATUS     current
    DESCRIPTION
	    "Total number of rows in the ACLList Table."
    ::= { informationStorePublicEntry 288 }

ispRowsInACLMemberTable OBJECT-TYPE
    SYNTAX     Gauge32
    MAX-ACCESS read-only
    STATUS     current
    DESCRIPTION
	    "Total number of rows in the ACLMember Table."
    ::= { informationStorePublicEntry 289 }

ispRowsInCategTables OBJECT-TYPE
    SYNTAX     Gauge32
    MAX-ACCESS read-only
    STATUS     current
    DESCRIPTION
	    "Total number of rows in the Categ Tables."
    ::= { informationStorePublicEntry 290 }

ispRowsInDeletedAttachmentsTable OBJECT-TYPE
    SYNTAX     Gauge32
    MAX-ACCESS read-only
    STATUS     current
    DESCRIPTION
	    "Total number of rows in the DeletedAttachments
	    Table."
    ::= { informationStorePublicEntry 291 }

ispRowsInDeletedFoldersTable OBJECT-TYPE
    SYNTAX     Gauge32
    MAX-ACCESS read-only
    STATUS     current
    DESCRIPTION
	    "Total number of rows in the DeletedFolders
	    Table."
    ::= { informationStorePublicEntry 292 }

ispRowsInDeletedMessagesTable OBJECT-TYPE
    SYNTAX     Gauge32
    MAX-ACCESS read-only
    STATUS     current
    DESCRIPTION
	    "Total number of rows in the DeletedMessages
	    Table."
    ::= { informationStorePublicEntry 293 }

ispRowsInDeliveredToTable OBJECT-TYPE
    SYNTAX     Gauge32
    MAX-ACCESS read-only
    STATUS     current
    DESCRIPTION
	    "Total number of rows in the DeliveredTo
	    Table."
    ::= { informationStorePublicEntry 294 }

ispRowsInFolderTombstoneTable OBJECT-TYPE
    SYNTAX     Gauge32
    MAX-ACCESS read-only
    STATUS     current
    DESCRIPTION
	    "Total number of rows in the Folder Tombstone
	    Table."
    ::= { informationStorePublicEntry 295 }

ispRowsInIdxAgeTable OBJECT-TYPE
    SYNTAX     Gauge32
    MAX-ACCESS read-only
    STATUS     current
    DESCRIPTION
	    "Total number of rows in the IdxAge Table."
    ::= { informationStorePublicEntry 296 }

ispRowsInMailboxTable OBJECT-TYPE
    SYNTAX     Gauge32
    MAX-ACCESS read-only
    STATUS     current
    DESCRIPTION
	    "Total number of rows in the Mailbox Table."
    ::= { informationStorePublicEntry 297 }

ispRowsInMessageTable OBJECT-TYPE
    SYNTAX     Gauge32
    MAX-ACCESS read-only
    STATUS     current
    DESCRIPTION
	    "Total number of rows in the Message Table."
    ::= { informationStorePublicEntry 298 }

ispRowsInMessageTombstoneTable OBJECT-TYPE
    SYNTAX     Gauge32
    MAX-ACCESS read-only
    STATUS     current
    DESCRIPTION
	    "Total number of rows in the Message Tombstone
	    Table."
    ::= { informationStorePublicEntry 299 }

ispRowsInMsgFolderTables OBJECT-TYPE
    SYNTAX     Gauge32
    MAX-ACCESS read-only
    STATUS     current
    DESCRIPTION
	    "Total number of rows in the MsgFolder Tables."
    ::= { informationStorePublicEntry 300 }

ispRowsInNamedPropsTable OBJECT-TYPE
    SYNTAX     Gauge32
    MAX-ACCESS read-only
    STATUS     current
    DESCRIPTION
	    "Total number of rows in the NamedProps Table."
    ::= { informationStorePublicEntry 301 }

ispRowsInNeedRNTable OBJECT-TYPE
    SYNTAX     Gauge32
    MAX-ACCESS read-only
    STATUS     current
    DESCRIPTION
	    "Total number of rows in the NeedRN Table."
    ::= { informationStorePublicEntry 302 }

ispRowsInPerUserReadTable OBJECT-TYPE
    SYNTAX     Gauge32
    MAX-ACCESS read-only
    STATUS     current
    DESCRIPTION
	    "Total number of rows in the PerUserRead
	    Table."
    ::= { informationStorePublicEntry 303 }

ispRowsInReceiveFoldersTable OBJECT-TYPE
    SYNTAX     Gauge32
    MAX-ACCESS read-only
    STATUS     current
    DESCRIPTION
	    "Total number of rows in the ReceiveFolders
	    Table."
    ::= { informationStorePublicEntry 304 }

ispRowsInReplicationTable OBJECT-TYPE
    SYNTAX     Gauge32
    MAX-ACCESS read-only
    STATUS     current
    DESCRIPTION
	    "Total number of rows in the Replication
	    Table."
    ::= { informationStorePublicEntry 305 }

ispRowsInReplidMapTable OBJECT-TYPE
    SYNTAX     Gauge32
    MAX-ACCESS read-only
    STATUS     current
    DESCRIPTION
	    "Total number of rows in the ReplidMap Table."
    ::= { informationStorePublicEntry 306 }

ispRowsInRulesTable OBJECT-TYPE
    SYNTAX     Gauge32
    MAX-ACCESS read-only
    STATUS     current
    DESCRIPTION
	    "Total number of rows in the Rules Table."
    ::= { informationStorePublicEntry 307 }

ispRowsInSearchQueueTable OBJECT-TYPE
    SYNTAX     Gauge32
    MAX-ACCESS read-only
    STATUS     current
    DESCRIPTION
	    "Total number of rows in the SearchQueue
	    Table."
    ::= { informationStorePublicEntry 308 }

ispRowsInTimedEventsTable OBJECT-TYPE
    SYNTAX     Gauge32
    MAX-ACCESS read-only
    STATUS     current
    DESCRIPTION
	    "Total number of rows in the TimedEvents
	    Table."
    ::= { informationStorePublicEntry 309 }

ispSaveChangesAttachOpRate OBJECT-TYPE
    SYNTAX     Gauge32
    MAX-ACCESS read-only
    STATUS     current
    DESCRIPTION
	    "SaveChangesAttachOpRate."
    ::= { informationStorePublicEntry 310 }

ispSaveChangesAttachOpTotal OBJECT-TYPE
    SYNTAX     Gauge32
    MAX-ACCESS read-only
    STATUS     current
    DESCRIPTION
	    "SaveChangesAttachOpTotal."
    ::= { informationStorePublicEntry 311 }

ispSaveChangesMessageOpRate OBJECT-TYPE
    SYNTAX     Gauge32
    MAX-ACCESS read-only
    STATUS     current
    DESCRIPTION
	    "SaveChangesMessageOpRate."
    ::= { informationStorePublicEntry 312 }

ispSaveChangesMessageOpTotal OBJECT-TYPE
    SYNTAX     Gauge32
    MAX-ACCESS read-only
    STATUS     current
    DESCRIPTION
	    "SaveChangesMessageOpTotal."
    ::= { informationStorePublicEntry 313 }

ispSeekRowOperationsPerSec OBJECT-TYPE
    SYNTAX     Gauge32
    MAX-ACCESS read-only
    STATUS     current
    DESCRIPTION
	    "SeekRow Operations/sec is the rate of SeekRow
	    requests in the public store."
    ::= { informationStorePublicEntry 314 }

ispSeekRowApproxOperationsPerSec OBJECT-TYPE
    SYNTAX     Gauge32
    MAX-ACCESS read-only
    STATUS     current
    DESCRIPTION
	    "SeekRowApproximate Operations/sec is the rate
	    of SeekRowApproximate requests in the public
	    store."
    ::= { informationStorePublicEntry 315 }

ispSeekRowBookMarkOpPerSec OBJECT-TYPE
    SYNTAX     Gauge32
    MAX-ACCESS read-only
    STATUS     current
    DESCRIPTION
	    "SeekRowBookMark Operations/sec is the rate of
	    SeekRowBookMark requests in the public store."
    ::= { informationStorePublicEntry 316 }

ispSeekStreamOpRate OBJECT-TYPE
    SYNTAX     Gauge32
    MAX-ACCESS read-only
    STATUS     current
    DESCRIPTION
	    "SeekStreamOpRate."
    ::= { informationStorePublicEntry 317 }

ispSeekStreamOpTotal OBJECT-TYPE
    SYNTAX     Gauge32
    MAX-ACCESS read-only
    STATUS     current
    DESCRIPTION
	    "SeekStreamOpTotal."
    ::= { informationStorePublicEntry 318 }

ispSendqTasksRate OBJECT-TYPE
    SYNTAX     Gauge32
    MAX-ACCESS read-only
    STATUS     current
    DESCRIPTION
	    "Send queue tasks to process messages on the
	    send queue."
    ::= { informationStorePublicEntry 319 }

ispSendqTasksTotal OBJECT-TYPE
    SYNTAX     Gauge32
    MAX-ACCESS read-only
    STATUS     current
    DESCRIPTION
	    "Send queue tasks to process messages on the
	    send queue."
    ::= { informationStorePublicEntry 320 }

ispSetCollapseStateOpRate OBJECT-TYPE
    SYNTAX     Gauge32
    MAX-ACCESS read-only
    STATUS     current
    DESCRIPTION
	    "SetCollapseStateOpRate."
    ::= { informationStorePublicEntry 321 }

ispSetCollapseStateOpTotal OBJECT-TYPE
    SYNTAX     Gauge32
    MAX-ACCESS read-only
    STATUS     current
    DESCRIPTION
	    "SetCollapseStateOpTotal."
    ::= { informationStorePublicEntry 322 }

ispSetColumnsOpRate OBJECT-TYPE
    SYNTAX     Gauge32
    MAX-ACCESS read-only
    STATUS     current
    DESCRIPTION
	    "SetColumnsOpRate."
    ::= { informationStorePublicEntry 323 }

ispSetColumnsOpTotal OBJECT-TYPE
    SYNTAX     Gauge32
    MAX-ACCESS read-only
    STATUS     current
    DESCRIPTION
	    "SetColumnsOpTotal."
    ::= { informationStorePublicEntry 324 }

ispSetFileHandlePropOpRate OBJECT-TYPE
    SYNTAX     Gauge32
    MAX-ACCESS read-only
    STATUS     current
    DESCRIPTION
	    "SetFileHandlePropOpRate"
    ::= { informationStorePublicEntry 325 }

ispSetFileHandlePropOpTotal OBJECT-TYPE
    SYNTAX     Gauge32
    MAX-ACCESS read-only
    STATUS     current
    DESCRIPTION
	    "SetFileHandlePropOpTotal"
    ::= { informationStorePublicEntry 326 }

ispSetfLocalizedOpRate OBJECT-TYPE
    SYNTAX     Gauge32
    MAX-ACCESS read-only
    STATUS     current
    DESCRIPTION
	    "SetfLocalizedOpRate."
    ::= { informationStorePublicEntry 327 }

ispSetfLocalizedOpTotal OBJECT-TYPE
    SYNTAX     Gauge32
    MAX-ACCESS read-only
    STATUS     current
    DESCRIPTION
	    "SetfLocalizedOpTotal."
    ::= { informationStorePublicEntry 328 }

ispSetICSNotifGUIDOpRate OBJECT-TYPE
    SYNTAX     Gauge32
    MAX-ACCESS read-only
    STATUS     current
    DESCRIPTION
	    "SetICSNotifGUIDOpRate."
    ::= { informationStorePublicEntry 329 }

ispSetICSNotifGUIDOpTotal OBJECT-TYPE
    SYNTAX     Gauge32
    MAX-ACCESS read-only
    STATUS     current
    DESCRIPTION
	    "SetICSNotifGUIDOpTotal."
    ::= { informationStorePublicEntry 330 }

ispSetLocalRepMidsetDeleteOpRate OBJECT-TYPE
    SYNTAX     Gauge32
    MAX-ACCESS read-only
    STATUS     current
    DESCRIPTION
	    "SetLocalRepMidsetDeletedOpRate."
    ::= { informationStorePublicEntry 331 }

ispSetLocalRepMidsetDelOpTotal OBJECT-TYPE
    SYNTAX     Gauge32
    MAX-ACCESS read-only
    STATUS     current
    DESCRIPTION
	    "SetLocalRepMidsetDeletedOpTotal."
    ::= { informationStorePublicEntry 332 }

ispSetMessageFolderFlagsOpRate OBJECT-TYPE
    SYNTAX     Gauge32
    MAX-ACCESS read-only
    STATUS     current
    DESCRIPTION
	    "SetMessageFolderFlagsOpRate."
    ::= { informationStorePublicEntry 333 }

ispSetMessageFolderFlagsOpTotal OBJECT-TYPE
    SYNTAX     Gauge32
    MAX-ACCESS read-only
    STATUS     current
    DESCRIPTION
	    "SetMessageFolderFlagsOpTotal."
    ::= { informationStorePublicEntry 334 }

ispSetMessagePropOpRate OBJECT-TYPE
    SYNTAX     Gauge32
    MAX-ACCESS read-only
    STATUS     current
    DESCRIPTION
	    "SetMessagePropOpRate."
    ::= { informationStorePublicEntry 335 }

ispSetMessagePropOpTotal OBJECT-TYPE
    SYNTAX     Gauge32
    MAX-ACCESS read-only
    STATUS     current
    DESCRIPTION
	    "SetMessagePropOpTotal."
    ::= { informationStorePublicEntry 336 }

ispSetMessageStatusOpRate OBJECT-TYPE
    SYNTAX     Gauge32
    MAX-ACCESS read-only
    STATUS     current
    DESCRIPTION
	    "SetMessageStatusOpRate."
    ::= { informationStorePublicEntry 337 }

ispSetMessageStatusOpTotal OBJECT-TYPE
    SYNTAX     Gauge32
    MAX-ACCESS read-only
    STATUS     current
    DESCRIPTION
	    "SetMessageStatusOpTotal."
    ::= { informationStorePublicEntry 338 }

ispSetPerUserOpRate OBJECT-TYPE
    SYNTAX     Gauge32
    MAX-ACCESS read-only
    STATUS     current
    DESCRIPTION
	    "SetPerUserOpRate."
    ::= { informationStorePublicEntry 339 }

ispSetPerUserOpTotal OBJECT-TYPE
    SYNTAX     Gauge32
    MAX-ACCESS read-only
    STATUS     current
    DESCRIPTION
	    "SetPerUserOpTotal."
    ::= { informationStorePublicEntry 340 }

ispSetPropertyOperationsPerSec OBJECT-TYPE
    SYNTAX     Gauge32
    MAX-ACCESS read-only
    STATUS     current
    DESCRIPTION
	    "SetProperty Operations/sec is the rate of
	    SetProperty requests in the public store."
    ::= { informationStorePublicEntry 341 }

ispSetReadFlagOpRate OBJECT-TYPE
    SYNTAX     Gauge32
    MAX-ACCESS read-only
    STATUS     current
    DESCRIPTION
	    "SetReadFlagOpRate."
    ::= { informationStorePublicEntry 342 }

ispSetReadFlagOpTotal OBJECT-TYPE
    SYNTAX     Gauge32
    MAX-ACCESS read-only
    STATUS     current
    DESCRIPTION
	    "SetReadFlagOpTotal."
    ::= { informationStorePublicEntry 343 }

ispSetReadFlagsOpRate OBJECT-TYPE
    SYNTAX     Gauge32
    MAX-ACCESS read-only
    STATUS     current
    DESCRIPTION
	    "SetReadFlagsOpRate."
    ::= { informationStorePublicEntry 344 }

ispSetReadFlagsOpTotal OBJECT-TYPE
    SYNTAX     Gauge32
    MAX-ACCESS read-only
    STATUS     current
    DESCRIPTION
	    "SetReadFlagsOpTotal."
    ::= { informationStorePublicEntry 345 }

ispSetReceiveFolderOpRate OBJECT-TYPE
    SYNTAX     Gauge32
    MAX-ACCESS read-only
    STATUS     current
    DESCRIPTION
	    "SetReceiveFolderOpRate."
    ::= { informationStorePublicEntry 346 }

ispSetReceiveFolderOpTotal OBJECT-TYPE
    SYNTAX     Gauge32
    MAX-ACCESS read-only
    STATUS     current
    DESCRIPTION
	    "SetReceiveFolderOpTotal."
    ::= { informationStorePublicEntry 347 }

ispSetRecipOpRate OBJECT-TYPE
    SYNTAX     Gauge32
    MAX-ACCESS read-only
    STATUS     current
    DESCRIPTION
	    "SetRecipOpRate."
    ::= { informationStorePublicEntry 348 }

ispSetRecipOpTotal OBJECT-TYPE
    SYNTAX     Gauge32
    MAX-ACCESS read-only
    STATUS     current
    DESCRIPTION
	    "SetRecipOpTotal."
    ::= { informationStorePublicEntry 349 }

ispSetSearchCriteriaOpRate OBJECT-TYPE
    SYNTAX     Gauge32
    MAX-ACCESS read-only
    STATUS     current
    DESCRIPTION
	    "SetSearchCriteriaOpRate."
    ::= { informationStorePublicEntry 350 }

ispSetSearchCriteriaOpTotal OBJECT-TYPE
    SYNTAX     Gauge32
    MAX-ACCESS read-only
    STATUS     current
    DESCRIPTION
	    "SetSearchCriteriaOpTotal."
    ::= { informationStorePublicEntry 351 }

ispSetSizeStreamOpRate OBJECT-TYPE
    SYNTAX     Gauge32
    MAX-ACCESS read-only
    STATUS     current
    DESCRIPTION
	    "SetSizeStreamOpRate."
    ::= { informationStorePublicEntry 352 }

ispSetSizeStreamOpTotal OBJECT-TYPE
    SYNTAX     Gauge32
    MAX-ACCESS read-only
    STATUS     current
    DESCRIPTION
	    "SetSizeStreamOpTotal."
    ::= { informationStorePublicEntry 353 }

ispSetSpoolerOpRate OBJECT-TYPE
    SYNTAX     Gauge32
    MAX-ACCESS read-only
    STATUS     current
    DESCRIPTION
	    "SetSpoolerOpRate."
    ::= { informationStorePublicEntry 354 }

ispSetSpoolerOpTotal OBJECT-TYPE
    SYNTAX     Gauge32
    MAX-ACCESS read-only
    STATUS     current
    DESCRIPTION
	    "SetSpoolerOpTotal."
    ::= { informationStorePublicEntry 355 }

ispSetXportOpRate OBJECT-TYPE
    SYNTAX     Gauge32
    MAX-ACCESS read-only
    STATUS     current
    DESCRIPTION
	    "SetXportOpRate."
    ::= { informationStorePublicEntry 356 }

ispSetXportOpTotal OBJECT-TYPE
    SYNTAX     Gauge32
    MAX-ACCESS read-only
    STATUS     current
    DESCRIPTION
	    "SetXportOpTotal."
    ::= { informationStorePublicEntry 357 }

ispSortTableOpRate OBJECT-TYPE
    SYNTAX     Gauge32
    MAX-ACCESS read-only
    STATUS     current
    DESCRIPTION
	    "SortTableOpRate."
    ::= { informationStorePublicEntry 358 }

ispSortTableOpTotal OBJECT-TYPE
    SYNTAX     Gauge32
    MAX-ACCESS read-only
    STATUS     current
    DESCRIPTION
	    "SortTableOpTotal."
    ::= { informationStorePublicEntry 359 }

ispSpoolerLockMsgOpRate OBJECT-TYPE
    SYNTAX     Gauge32
    MAX-ACCESS read-only
    STATUS     current
    DESCRIPTION
	    "SpoolerLockMsgOpRate."
    ::= { informationStorePublicEntry 360 }

ispSpoolerLockMsgOpTotal OBJECT-TYPE
    SYNTAX     Gauge32
    MAX-ACCESS read-only
    STATUS     current
    DESCRIPTION
	    "SpoolerLockMsgOpTotal."
    ::= { informationStorePublicEntry 361 }

ispSpoolerRulesOpRate OBJECT-TYPE
    SYNTAX     Gauge32
    MAX-ACCESS read-only
    STATUS     current
    DESCRIPTION
	    "SpoolerRulesOpRate."
    ::= { informationStorePublicEntry 362 }

ispSpoolerRulesOpTotal OBJECT-TYPE
    SYNTAX     Gauge32
    MAX-ACCESS read-only
    STATUS     current
    DESCRIPTION
	    "SpoolerRulesOpTotal."
    ::= { informationStorePublicEntry 363 }

ispTellVersionOpRate OBJECT-TYPE
    SYNTAX     Gauge32
    MAX-ACCESS read-only
    STATUS     current
    DESCRIPTION
	    "TellVersionOpRate."
    ::= { informationStorePublicEntry 364 }

ispTellVersionOpTotal OBJECT-TYPE
    SYNTAX     Gauge32
    MAX-ACCESS read-only
    STATUS     current
    DESCRIPTION
	    "TellVersionOpTotal."
    ::= { informationStorePublicEntry 365 }

ispTranRateFromMimeToMapi OBJECT-TYPE
    SYNTAX     Gauge32
    MAX-ACCESS read-only
    STATUS     current
    DESCRIPTION
	    "Rate of transitions from mime to mapi (per
	    sec)."
    ::= { informationStorePublicEntry 366 }

ispTranRateFromMimeToMimebyref OBJECT-TYPE
    SYNTAX     Gauge32
    MAX-ACCESS read-only
    STATUS     current
    DESCRIPTION
	    "Rate of transitions from mime to mimebyref
	    (per sec)."
    ::= { informationStorePublicEntry 367 }

ispTranRateFromMimebyrefToMapi OBJECT-TYPE
    SYNTAX     Gauge32
    MAX-ACCESS read-only
    STATUS     current
    DESCRIPTION
	    "Rate of transitions from mimebyref to mapi
	    (per sec)."
    ::= { informationStorePublicEntry 368 }

ispTranRateFromNewToMime OBJECT-TYPE
    SYNTAX     Gauge32
    MAX-ACCESS read-only
    STATUS     current
    DESCRIPTION
	    "Rate of new messages created with mime."
    ::= { informationStorePublicEntry 369 }

ispTransFromMimeToMapi OBJECT-TYPE
    SYNTAX     Gauge32
    MAX-ACCESS read-only
    STATUS     current
    DESCRIPTION
	    "Total number of transitions from mime to
	    mapi."
    ::= { informationStorePublicEntry 370 }

ispTransFromMimeToMimebyref OBJECT-TYPE
    SYNTAX     Gauge32
    MAX-ACCESS read-only
    STATUS     current
    DESCRIPTION
	    "Total number of transitions from mime to
	    mimebyref."
    ::= { informationStorePublicEntry 371 }

ispTransFromMimebyrefToMapi OBJECT-TYPE
    SYNTAX     Gauge32
    MAX-ACCESS read-only
    STATUS     current
    DESCRIPTION
	    "Total number of transitions from mimebyref to
	    mapi."
    ::= { informationStorePublicEntry 372 }

ispTransFromNewToMime OBJECT-TYPE
    SYNTAX     Gauge32
    MAX-ACCESS read-only
    STATUS     current
    DESCRIPTION
	    "Total number of new messages created with
	    mime."
    ::= { informationStorePublicEntry 373 }

ispTransportSendOpRate OBJECT-TYPE
    SYNTAX     Gauge32
    MAX-ACCESS read-only
    STATUS     current
    DESCRIPTION
	    "TransportSendOpRate."
    ::= { informationStorePublicEntry 374 }

ispTransportSendOpTotal OBJECT-TYPE
    SYNTAX     Gauge32
    MAX-ACCESS read-only
    STATUS     current
    DESCRIPTION
	    "TransportSendOpTotal."
    ::= { informationStorePublicEntry 375 }

ispUpdateDAMsOpRate OBJECT-TYPE
    SYNTAX     Gauge32
    MAX-ACCESS read-only
    STATUS     current
    DESCRIPTION
	    "UpdateDAMsOpRate."
    ::= { informationStorePublicEntry 376 }

ispUpdateDAMsOpTotal OBJECT-TYPE
    SYNTAX     Gauge32
    MAX-ACCESS read-only
    STATUS     current
    DESCRIPTION
	    "UpdateDAMsOpTotal."
    ::= { informationStorePublicEntry 377 }

ispUpdateFolderInternetIdOpRate OBJECT-TYPE
    SYNTAX     Gauge32
    MAX-ACCESS read-only
    STATUS     current
    DESCRIPTION
	    "UpdateFolderInternetIdOpRate."
    ::= { informationStorePublicEntry 378 }

ispUpdateFolderInternetIdOpTotal OBJECT-TYPE
    SYNTAX     Gauge32
    MAX-ACCESS read-only
    STATUS     current
    DESCRIPTION
	    "UpdateFolderInternetIdOpTotal."
    ::= { informationStorePublicEntry 379 }

ispUpdateRecipPtagsOpRate OBJECT-TYPE
    SYNTAX     Gauge32
    MAX-ACCESS read-only
    STATUS     current
    DESCRIPTION
	    "UpdateRecipPtagsOpRate."
    ::= { informationStorePublicEntry 380 }

ispUpdateRecipPtagsOpTotal OBJECT-TYPE
    SYNTAX     Gauge32
    MAX-ACCESS read-only
    STATUS     current
    DESCRIPTION
	    "UpdateRecipPtagsOpTotal."
    ::= { informationStorePublicEntry 381 }

ispUpldStStrmBeginOpRate OBJECT-TYPE
    SYNTAX     Gauge32
    MAX-ACCESS read-only
    STATUS     current
    DESCRIPTION
	    "UpldStStrmBeginOpRate."
    ::= { informationStorePublicEntry 382 }

ispUpldStStrmBeginOpTotal OBJECT-TYPE
    SYNTAX     Gauge32
    MAX-ACCESS read-only
    STATUS     current
    DESCRIPTION
	    "UpldStStrmBeginOpTotal."
    ::= { informationStorePublicEntry 383 }

ispUpldStStrmContinueOpRate OBJECT-TYPE
    SYNTAX     Gauge32
    MAX-ACCESS read-only
    STATUS     current
    DESCRIPTION
	    "UpldStStrmContinueOpRate."
    ::= { informationStorePublicEntry 384 }

ispUpldStStrmContinueOpTotal OBJECT-TYPE
    SYNTAX     Gauge32
    MAX-ACCESS read-only
    STATUS     current
    DESCRIPTION
	    "UpldStStrmContinueOpTotal."
    ::= { informationStorePublicEntry 385 }

ispUpldStStrmEndOpRate OBJECT-TYPE
    SYNTAX     Gauge32
    MAX-ACCESS read-only
    STATUS     current
    DESCRIPTION
	    "UpldStStrmEndOpRate."
    ::= { informationStorePublicEntry 386 }

ispUpldStStrmEndOpTotal OBJECT-TYPE
    SYNTAX     Gauge32
    MAX-ACCESS read-only
    STATUS     current
    DESCRIPTION
	    "UpldStStrmEndOpTotal."
    ::= { informationStorePublicEntry 387 }

ispValidAttachsOpRate OBJECT-TYPE
    SYNTAX     Gauge32
    MAX-ACCESS read-only
    STATUS     current
    DESCRIPTION
	    "ValidAttachsOpRate."
    ::= { informationStorePublicEntry 388 }

ispValidAttachsOpTotal OBJECT-TYPE
    SYNTAX     Gauge32
    MAX-ACCESS read-only
    STATUS     current
    DESCRIPTION
	    "ValidAttachsOpTotal."
    ::= { informationStorePublicEntry 389 }

ispWriteStreamOpRate OBJECT-TYPE
    SYNTAX     Gauge32
    MAX-ACCESS read-only
    STATUS     current
    DESCRIPTION
	    "WriteStreamOpRate."
    ::= { informationStorePublicEntry 390 }

ispWriteStreamOpTotal OBJECT-TYPE
    SYNTAX     Gauge32
    MAX-ACCESS read-only
    STATUS     current
    DESCRIPTION
	    "WriteStreamOpTotal."
    ::= { informationStorePublicEntry 391 }

ispXportNewMailOpRate OBJECT-TYPE
    SYNTAX     Gauge32
    MAX-ACCESS read-only
    STATUS     current
    DESCRIPTION
	    "XportNewMailOpRate."
    ::= { informationStorePublicEntry 392 }

ispXportNewMailOpTotal OBJECT-TYPE
    SYNTAX     Gauge32
    MAX-ACCESS read-only
    STATUS     current
    DESCRIPTION
	    "XportNewMailOpTotal."
    ::= { informationStorePublicEntry 393 }

informStoreTransportDriverTable OBJECT-TYPE
    SYNTAX     SEQUENCE OF ISTransportDriverEntry
    MAX-ACCESS not-accessible
    STATUS     current
    DESCRIPTION
	    "This object represents global counters for the
	    MSExchangeIS Transport driver."
    ::= { exchange 17 }

informStoreTransportDriverEntry OBJECT-TYPE
    SYNTAX     ISTransportDriverEntry
    MAX-ACCESS not-accessible
    STATUS     current
    DESCRIPTION
	    "Performance information for one particular
	    instance of 'MSExchangeIS Transport Driver'
	    object."
    INDEX      { istdInstance }
    ::= { informStoreTransportDriverTable 1 }

ISTransportDriverEntry ::= SEQUENCE {
    istdInstance InstanceName,
    istdCreateMailMsgThreads Gauge32,
    istdCreateRecipListThreads Gauge32,
    istdCurrentDeliveryThreads Gauge32,
    istdCurrentMessageFromMTA Gauge32,
    istdCurrentMessagesToMTA Gauge32,
    istdHSOTCacheCurrent Gauge32,
    istdHSOTCacheHits Gauge32,
    istdHSOTCacheSearches Gauge32,
    istdInboundMessages Gauge32,
    istdLocalDelivery Gauge32,
    istdLocalDeliveryRecipients Gauge32,
    istdLocalDeliveryWriteConflicts Gauge32,
    istdMAPIClientMovedList Gauge32,
    istdMAPIClientMovesTotal Gauge32,
    istdMAPIClientSubmitDeletions Gauge32,
    istdMAPIClientSubmitList Gauge32,
    istdMAPIClientSubmitRequeues Gauge32,
    istdMAPIClientSubmits Gauge32,
    istdMSExchangeMTADeletes Gauge32,
    istdMSExchangeMTADelivery Gauge32,
    istdMSExchangeMTADeliveryRcpnts Gauge32,
    istdMSExchangeMTASubmits Gauge32,
    istdMailMsgGetSize Gauge32,
    istdMailMsgP1TotalBytes Gauge32,
    istdMailMsgReadBlocks Gauge32,
    istdMailMsgReopen Gauge32,
    istdMailMsgWriteBlocks Gauge32,
    istdPendingCreateMailMsg Gauge32,
    istdPendingCreateRecipientLists Gauge32,
    istdRequestsPendingTransportAcks Gauge32,
    istdTempTableCurrent Gauge32,
    istdTempTableDeletes Gauge32,
    istdTempTableTotal Gauge32,
    istdUnusedCounter Gauge32
}

istdInstance OBJECT-TYPE
    SYNTAX     InstanceName
    MAX-ACCESS read-only
    STATUS     current
    DESCRIPTION
	    "Instance name."
    ::= { informStoreTransportDriverEntry 1 }

istdCreateMailMsgThreads OBJECT-TYPE
    SYNTAX     Gauge32
    MAX-ACCESS read-only
    STATUS     current
    DESCRIPTION
	    "Current number of threads creating MailMsg"
    ::= { informStoreTransportDriverEntry 2 }

istdCreateRecipListThreads OBJECT-TYPE
    SYNTAX     Gauge32
    MAX-ACCESS read-only
    STATUS     current
    DESCRIPTION
	    "Current number of threads creating recipient
	    lists"
    ::= { informStoreTransportDriverEntry 3 }

istdCurrentDeliveryThreads OBJECT-TYPE
    SYNTAX     Gauge32
    MAX-ACCESS read-only
    STATUS     current
    DESCRIPTION
	    "Current number of threads doing delivery to an
	    MDB or MSExchangeMTA."
    ::= { informStoreTransportDriverEntry 4 }

istdCurrentMessageFromMTA OBJECT-TYPE
    SYNTAX     Gauge32
    MAX-ACCESS read-only
    STATUS     current
    DESCRIPTION
	    "Current number of messages in transit to
	    Transport from MSExchangeMTA."
    ::= { informStoreTransportDriverEntry 5 }

istdCurrentMessagesToMTA OBJECT-TYPE
    SYNTAX     Gauge32
    MAX-ACCESS read-only
    STATUS     current
    DESCRIPTION
	    "Current number of messages in transit to
	    MSExchangeMTA."
    ::= { informStoreTransportDriverEntry 6 }

istdHSOTCacheCurrent OBJECT-TYPE
    SYNTAX     Gauge32
    MAX-ACCESS read-only
    STATUS     current
    DESCRIPTION
	    "Current number of opened message references
	    that have been cached."
    ::= { informStoreTransportDriverEntry 7 }

istdHSOTCacheHits OBJECT-TYPE
    SYNTAX     Gauge32
    MAX-ACCESS read-only
    STATUS     current
    DESCRIPTION
	    "Total number of searches in open message
	    reference cache that succeeded."
    ::= { informStoreTransportDriverEntry 8 }

istdHSOTCacheSearches OBJECT-TYPE
    SYNTAX     Gauge32
    MAX-ACCESS read-only
    STATUS     current
    DESCRIPTION
	    "Total searches in open message reference
	    cache."
    ::= { informStoreTransportDriverEntry 9 }

istdInboundMessages OBJECT-TYPE
    SYNTAX     Gauge32
    MAX-ACCESS read-only
    STATUS     current
    DESCRIPTION
	    "Total number of messages received from
	    Transport for processing"
    ::= { informStoreTransportDriverEntry 10 }

istdLocalDelivery OBJECT-TYPE
    SYNTAX     Gauge32
    MAX-ACCESS read-only
    STATUS     current
    DESCRIPTION
	    "Total number of messages that have been
	    delivered to an MDB."
    ::= { informStoreTransportDriverEntry 11 }

istdLocalDeliveryRecipients OBJECT-TYPE
    SYNTAX     Gauge32
    MAX-ACCESS read-only
    STATUS     current
    DESCRIPTION
	    "Total number of MDB recipients delivered."
    ::= { informStoreTransportDriverEntry 12 }

istdLocalDeliveryWriteConflicts OBJECT-TYPE
    SYNTAX     Gauge32
    MAX-ACCESS read-only
    STATUS     current
    DESCRIPTION
	    "Total number of Local Delivery attempts that
	    failed with a Write-Conflict error and were
	    marked for retry."
    ::= { informStoreTransportDriverEntry 13 }

istdMAPIClientMovedList OBJECT-TYPE
    SYNTAX     Gauge32
    MAX-ACCESS read-only
    STATUS     current
    DESCRIPTION
	    "Current number of messages that have been
	    submitted that have been moved to Transport
	    Temporary Tables because of delays/congestion."
    ::= { informStoreTransportDriverEntry 14 }

istdMAPIClientMovesTotal OBJECT-TYPE
    SYNTAX     Gauge32
    MAX-ACCESS read-only
    STATUS     current
    DESCRIPTION
	    "Total number of MAPI client submissions that
	    were moved to Transport Temporary Tables
	    because of delays/congestion."
    ::= { informStoreTransportDriverEntry 15 }

istdMAPIClientSubmitDeletions OBJECT-TYPE
    SYNTAX     Gauge32
    MAX-ACCESS read-only
    STATUS     current
    DESCRIPTION
	    "MAPI Client Submissions that have been
	    processed and deleted."
    ::= { informStoreTransportDriverEntry 16 }

istdMAPIClientSubmitList OBJECT-TYPE
    SYNTAX     Gauge32
    MAX-ACCESS read-only
    STATUS     current
    DESCRIPTION
	    "Current number of messages that are still in
	    client outboxes that are being processed."
    ::= { informStoreTransportDriverEntry 17 }

istdMAPIClientSubmitRequeues OBJECT-TYPE
    SYNTAX     Gauge32
    MAX-ACCESS read-only
    STATUS     current
    DESCRIPTION
	    "MAPI Client Submissions that were requeued for
	    deferred delivery."
    ::= { informStoreTransportDriverEntry 18 }

istdMAPIClientSubmits OBJECT-TYPE
    SYNTAX     Gauge32
    MAX-ACCESS read-only
    STATUS     current
    DESCRIPTION
	    "Total number of messages submitted by MAPI
	    Clients."
    ::= { informStoreTransportDriverEntry 19 }

istdMSExchangeMTADeletes OBJECT-TYPE
    SYNTAX     Gauge32
    MAX-ACCESS read-only
    STATUS     current
    DESCRIPTION
	    "Total number of messages from MSExchangeMTA
	    that have been processed and deleted."
    ::= { informStoreTransportDriverEntry 20 }

istdMSExchangeMTADelivery OBJECT-TYPE
    SYNTAX     Gauge32
    MAX-ACCESS read-only
    STATUS     current
    DESCRIPTION
	    "Total number of messages transferred to the
	    MSExchangeMTA for processing."
    ::= { informStoreTransportDriverEntry 21 }

istdMSExchangeMTADeliveryRcpnts OBJECT-TYPE
    SYNTAX     Gauge32
    MAX-ACCESS read-only
    STATUS     current
    DESCRIPTION
	    "Total number of MSExchangeMTA recipients
	    delivered."
    ::= { informStoreTransportDriverEntry 22 }

istdMSExchangeMTASubmits OBJECT-TYPE
    SYNTAX     Gauge32
    MAX-ACCESS read-only
    STATUS     current
    DESCRIPTION
	    "Total number of messages received from the
	    MSExchangeMTA for processing."
    ::= { informStoreTransportDriverEntry 23 }

istdMailMsgGetSize OBJECT-TYPE
    SYNTAX     Gauge32
    MAX-ACCESS read-only
    STATUS     current
    DESCRIPTION
	    "Total number of MailMsg GetSize operations."
    ::= { informStoreTransportDriverEntry 24 }

istdMailMsgP1TotalBytes OBJECT-TYPE
    SYNTAX     Gauge32
    MAX-ACCESS read-only
    STATUS     current
    DESCRIPTION
	    "Total number of bytes commited to disk for
	    MailMsg P1 stream."
    ::= { informStoreTransportDriverEntry 25 }

istdMailMsgReadBlocks OBJECT-TYPE
    SYNTAX     Gauge32
    MAX-ACCESS read-only
    STATUS     current
    DESCRIPTION
	    "Total number of MailMsg ReadBlock operations."
    ::= { informStoreTransportDriverEntry 26 }

istdMailMsgReopen OBJECT-TYPE
    SYNTAX     Gauge32
    MAX-ACCESS read-only
    STATUS     current
    DESCRIPTION
	    "Total number of MailMsg Reopen operations."
    ::= { informStoreTransportDriverEntry 27 }

istdMailMsgWriteBlocks OBJECT-TYPE
    SYNTAX     Gauge32
    MAX-ACCESS read-only
    STATUS     current
    DESCRIPTION
	    "Total number of MailMsg WriteBlock
	    operations."
    ::= { informStoreTransportDriverEntry 28 }

istdPendingCreateMailMsg OBJECT-TYPE
    SYNTAX     Gauge32
    MAX-ACCESS read-only
    STATUS     current
    DESCRIPTION
	    "Current items pending creation of MailMsg"
    ::= { informStoreTransportDriverEntry 29 }

istdPendingCreateRecipientLists OBJECT-TYPE
    SYNTAX     Gauge32
    MAX-ACCESS read-only
    STATUS     current
    DESCRIPTION
	    "Current items pending recipient list creation"
    ::= { informStoreTransportDriverEntry 30 }

istdRequestsPendingTransportAcks OBJECT-TYPE
    SYNTAX     Gauge32
    MAX-ACCESS read-only
    STATUS     current
    DESCRIPTION
	    "The current number of requests pending acks
	    from Transport (SMTP)."
    ::= { informStoreTransportDriverEntry 31 }

istdTempTableCurrent OBJECT-TYPE
    SYNTAX     Gauge32
    MAX-ACCESS read-only
    STATUS     current
    DESCRIPTION
	    "Current number of messages in Transport
	    Temporary Tables."
    ::= { informStoreTransportDriverEntry 32 }

istdTempTableDeletes OBJECT-TYPE
    SYNTAX     Gauge32
    MAX-ACCESS read-only
    STATUS     current
    DESCRIPTION
	    "Running Total of messages that have been
	    deleted from Transport Temporary Tables."
    ::= { informStoreTransportDriverEntry 33 }

istdTempTableTotal OBJECT-TYPE
    SYNTAX     Gauge32
    MAX-ACCESS read-only
    STATUS     current
    DESCRIPTION
	    "Running Total of messages that have been
	    created in Transport Temporary Tables"
    ::= { informStoreTransportDriverEntry 34 }

istdUnusedCounter OBJECT-TYPE
    SYNTAX     Gauge32
    MAX-ACCESS read-only
    STATUS     current
    DESCRIPTION
	    "Counter reserved for future use."
    ::= { informStoreTransportDriverEntry 35 }

messageTransferAgent OBJECT-IDENTITY
    STATUS     current
    DESCRIPTION
	    "Only one instance : global MTA performance
	    data."
    ::= { exchange 18 }

mtaAdjacentmtaAssociations OBJECT-TYPE
    SYNTAX     Gauge32
    MAX-ACCESS read-only
    STATUS     current
    DESCRIPTION
	    "Adjacent MTA Associations is the number of
	    open associations this MTA has to other MTAs."
    ::= { messageTransferAgent 1 }

mtaAdminConnections OBJECT-TYPE
    SYNTAX     Gauge32
    MAX-ACCESS read-only
    STATUS     current
    DESCRIPTION
	    "Admin Connections is the number of Microsoft
	    Exchange Administrator programs connected to
	    this MTA."
    ::= { messageTransferAgent 2 }

mtaAdminInterfaceRcvBytesPerSec OBJECT-TYPE
    SYNTAX     Gauge32
    MAX-ACCESS read-only
    STATUS     current
    DESCRIPTION
	    "Admin Interface Receive Bytes/sec is the rate
	    that bytes are received over an Admin
	    connection."
    ::= { messageTransferAgent 3 }

mtaAdminInterfaceXmitBytesPerSec OBJECT-TYPE
    SYNTAX     Gauge32
    MAX-ACCESS read-only
    STATUS     current
    DESCRIPTION
	    "Admin Interface Transmit Bytes/sec is the rate
	    that bytes are transmitted over an Admin
	    connection."
    ::= { messageTransferAgent 4 }

mtaDeferredDeliveryMsgs OBJECT-TYPE
    SYNTAX     Gauge32
    MAX-ACCESS read-only
    STATUS     current
    DESCRIPTION
	    "Deferred Delivery Msgs is the total number of
	    deferred delivery messages currently stored in
	    the MTA."
    ::= { messageTransferAgent 5 }

mtaDiskFileDeletesPerSec OBJECT-TYPE
    SYNTAX     Gauge32
    MAX-ACCESS read-only
    STATUS     current
    DESCRIPTION
	    "Disk File Deletes/sec is the rate of disk file
	    delete operations."
    ::= { messageTransferAgent 6 }

mtaDiskFileOpensPerSec OBJECT-TYPE
    SYNTAX     Gauge32
    MAX-ACCESS read-only
    STATUS     current
    DESCRIPTION
	    "Disk File Opens/sec is the rate of disk file
	    open operations."
    ::= { messageTransferAgent 7 }

mtaDiskFileReadsPerSec OBJECT-TYPE
    SYNTAX     Gauge32
    MAX-ACCESS read-only
    STATUS     current
    DESCRIPTION
	    "Disk File Reads/sec is the rate of disk file
	    read operations."
    ::= { messageTransferAgent 8 }

mtaDiskFileSyncsPerSec OBJECT-TYPE
    SYNTAX     Gauge32
    MAX-ACCESS read-only
    STATUS     current
    DESCRIPTION
	    "Disk File Syncs/sec is the rate of disk file
	    sync operations."
    ::= { messageTransferAgent 9 }

mtaDiskFileWritesPerSec OBJECT-TYPE
    SYNTAX     Gauge32
    MAX-ACCESS read-only
    STATUS     current
    DESCRIPTION
	    "Disk File Writes/sec is the rate of disk file
	    write operations."
    ::= { messageTransferAgent 10 }

mtaExDSReadCallsPerSec OBJECT-TYPE
    SYNTAX     Gauge32
    MAX-ACCESS read-only
    STATUS     current
    DESCRIPTION
	    "ExDS Read Calls/sec is the rate of read calls
	    to the directory service."
    ::= { messageTransferAgent 11 }

mtaFreeElements OBJECT-TYPE
    SYNTAX     Gauge32
    MAX-ACCESS read-only
    STATUS     current
    DESCRIPTION
	    "Free Elements is the number of free buffer
	    elements in the MTA pool."
    ::= { messageTransferAgent 12 }

mtaFreeHeaders OBJECT-TYPE
    SYNTAX     Gauge32
    MAX-ACCESS read-only
    STATUS     current
    DESCRIPTION
	    "Free Headers is the number of free buffer
	    headers in the MTA pool."
    ::= { messageTransferAgent 13 }

mtaInboundBytesTotal OBJECT-TYPE
    SYNTAX     Gauge32
    MAX-ACCESS read-only
    STATUS     current
    DESCRIPTION
	    "Inbound Bytes Total is the total volume of
	    message content received since MTA
	    initialization, measured in kilobytes."
    ::= { messageTransferAgent 14 }

mtaInboundMessagesTotal OBJECT-TYPE
    SYNTAX     Gauge32
    MAX-ACCESS read-only
    STATUS     current
    DESCRIPTION
	    "Inbound Messages Total is the total number of
	    messages received since MTA initialization."
    ::= { messageTransferAgent 15 }

mtaLANReceiveBytesPerSec OBJECT-TYPE
    SYNTAX     Gauge32
    MAX-ACCESS read-only
    STATUS     current
    DESCRIPTION
	    "LAN Receive Bytes/sec is the rate that bytes
	    are received over a LAN from MTAs."
    ::= { messageTransferAgent 16 }

mtaLANTransmitBytesPerSec OBJECT-TYPE
    SYNTAX     Gauge32
    MAX-ACCESS read-only
    STATUS     current
    DESCRIPTION
	    "LAN Transmit Bytes/sec is the rate that bytes
	    are transmitted over a LAN to MTAs."
    ::= { messageTransferAgent 17 }

mtaMessageBytesPerSec OBJECT-TYPE
    SYNTAX     Gauge32
    MAX-ACCESS read-only
    STATUS     current
    DESCRIPTION
	    "Message Bytes/sec is the rate that message
	    bytes are processed."
    ::= { messageTransferAgent 18 }

mtaMessagesPerSec OBJECT-TYPE
    SYNTAX     Gauge32
    MAX-ACCESS read-only
    STATUS     current
    DESCRIPTION
	    "Messages/sec is the rate that messages are
	    processed."
    ::= { messageTransferAgent 19 }

mtaOutboundBytesTotal OBJECT-TYPE
    SYNTAX     Gauge32
    MAX-ACCESS read-only
    STATUS     current
    DESCRIPTION
	    "Outbound Bytes Total is the total volume of
	    message content transmitted since MTA
	    initialization, measured in kilobytes."
    ::= { messageTransferAgent 20 }

mtaOutboundMessagesTotal OBJECT-TYPE
    SYNTAX     Gauge32
    MAX-ACCESS read-only
    STATUS     current
    DESCRIPTION
	    "Outbound Messages Total is the total number of
	    messages transmitted since MTA initialization."
    ::= { messageTransferAgent 21 }

mtaRASReceiveBytesPerSec OBJECT-TYPE
    SYNTAX     Gauge32
    MAX-ACCESS read-only
    STATUS     current
    DESCRIPTION
	    "RAS Receive Bytes/sec is the rate that bytes
	    are received over a RAS connection."
    ::= { messageTransferAgent 22 }

mtaRASTransmitBytesPerSec OBJECT-TYPE
    SYNTAX     Gauge32
    MAX-ACCESS read-only
    STATUS     current
    DESCRIPTION
	    "RAS Transmit Bytes/sec is the rate that bytes
	    are transmitted over a RAS connection."
    ::= { messageTransferAgent 23 }

mtaTCPPerIPReceiveBytesPerSec OBJECT-TYPE
    SYNTAX     Gauge32
    MAX-ACCESS read-only
    STATUS     current
    DESCRIPTION
	    "TCP/IP Receive Bytes/sec is the rate that
	    bytes are received over a TCP/IP connection."
    ::= { messageTransferAgent 24 }

mtaTCPPerIPTransmitBytesPerSec OBJECT-TYPE
    SYNTAX     Gauge32
    MAX-ACCESS read-only
    STATUS     current
    DESCRIPTION
	    "TCP/IP Transmit Bytes/sec is the rate that
	    bytes are transmitted over a TCP/IP
	    connection."
    ::= { messageTransferAgent 25 }

mtaTP4ReceiveBytesPerSec OBJECT-TYPE
    SYNTAX     Gauge32
    MAX-ACCESS read-only
    STATUS     current
    DESCRIPTION
	    "TP4 Receive Bytes/sec is the rate that bytes
	    are received over a TP4 connection."
    ::= { messageTransferAgent 26 }

mtaTP4TransmitBytesPerSec OBJECT-TYPE
    SYNTAX     Gauge32
    MAX-ACCESS read-only
    STATUS     current
    DESCRIPTION
	    "TP4 Transmit Bytes/sec is the rate that bytes
	    are transmitted over a TP4 connection."
    ::= { messageTransferAgent 27 }

mtaThreadsInUse OBJECT-TYPE
    SYNTAX     Gauge32
    MAX-ACCESS read-only
    STATUS     current
    DESCRIPTION
	    "Threads in Use is the number of threads in use
	    by the MTA (does not include RPC threads). This
	    number can be used to determine whether
	    additional processors could be of benefit."
    ::= { messageTransferAgent 28 }

mtaTotalFailedConversions OBJECT-TYPE
    SYNTAX     Gauge32
    MAX-ACCESS read-only
    STATUS     current
    DESCRIPTION
	    "Total Failed Conversions is the total number
	    of messages which failed to be converted from
	    one form to another since MTA initialization."
    ::= { messageTransferAgent 29 }

mtaTotalLoopsDetected OBJECT-TYPE
    SYNTAX     Gauge32
    MAX-ACCESS read-only
    STATUS     current
    DESCRIPTION
	    "Total Loops Detected is the total number  of
	    messages detected to have looped since MTA
	    initialization."
    ::= { messageTransferAgent 30 }

mtaTotalRecipientsInbound OBJECT-TYPE
    SYNTAX     Gauge32
    MAX-ACCESS read-only
    STATUS     current
    DESCRIPTION
	    "Total Recipients Inbound is the total number
	    of recipients specified in all messages
	    received since MTA initialization."
    ::= { messageTransferAgent 31 }

mtaTotalRecipientsOutbound OBJECT-TYPE
    SYNTAX     Gauge32
    MAX-ACCESS read-only
    STATUS     current
    DESCRIPTION
	    "Total Recipients Outbound is the total number
	    of recipients specified in all messages
	    transmitted since MTA initialization."
    ::= { messageTransferAgent 32 }

mtaTotalRecipientsQueued OBJECT-TYPE
    SYNTAX     Gauge32
    MAX-ACCESS read-only
    STATUS     current
    DESCRIPTION
	    "Total Recipients Queued is the total number of
	    recipients specified in all messages currently
	    stored in the MTA."
    ::= { messageTransferAgent 33 }

mtaTotalSuccessfulConversions OBJECT-TYPE
    SYNTAX     Gauge32
    MAX-ACCESS read-only
    STATUS     current
    DESCRIPTION
	    "Total Successful Conversions is the total
	    number of messages successfully converted from
	    one form to another since MTA initialization."
    ::= { messageTransferAgent 34 }

mtaWorkQueueBytes OBJECT-TYPE
    SYNTAX     Gauge32
    MAX-ACCESS read-only
    STATUS     current
    DESCRIPTION
	    "Work Queue Bytes is the total volume of
	    message content currently stored in the MTA,
	    measured in kilobytes."
    ::= { messageTransferAgent 35 }

mtaWorkQueueLength OBJECT-TYPE
    SYNTAX     Gauge32
    MAX-ACCESS read-only
    STATUS     current
    DESCRIPTION
	    "Work Queue Length is the number of outstanding
	    messages in the Work Queue, which indicates the
	    number of messages not yet processed to
	    completion by the MTA."
    ::= { messageTransferAgent 36 }

mtaX25ReceiveBytesPerSec OBJECT-TYPE
    SYNTAX     Gauge32
    MAX-ACCESS read-only
    STATUS     current
    DESCRIPTION
	    "X.25 Receive Bytes/sec is the rate that bytes
	    are received over an X.25 connection."
    ::= { messageTransferAgent 37 }

mtaX25TransmitBytesPerSec OBJECT-TYPE
    SYNTAX     Gauge32
    MAX-ACCESS read-only
    STATUS     current
    DESCRIPTION
	    "X.25 Transmit Bytes/sec is the rate that bytes
	    are transmitted over an X.25 connection."
    ::= { messageTransferAgent 38 }

mtaXAPIClients OBJECT-TYPE
    SYNTAX     Gauge32
    MAX-ACCESS read-only
    STATUS     current
    DESCRIPTION
	    "XAPI Clients is the number of XAPI clients
	    connected to the MTA using the XAPI MA/OM
	    interface. A single client may have multiple
	    XAPI client sessions."
    ::= { messageTransferAgent 39 }

mtaXAPIGateways OBJECT-TYPE
    SYNTAX     Gauge32
    MAX-ACCESS read-only
    STATUS     current
    DESCRIPTION
	    "XAPI Gateways is the number of gateways
	    connected to the MTA using the XAPI MT/OM
	    interface. A single gateway may have multiple
	    XAPI gateway sessions."
    ::= { messageTransferAgent 40 }

mtaXAPIReceiveBytesPerSec OBJECT-TYPE
    SYNTAX     Gauge32
    MAX-ACCESS read-only
    STATUS     current
    DESCRIPTION
	    "XAPI Receive Bytes/sec is the rate that bytes
	    are received over a XAPI connection."
    ::= { messageTransferAgent 41 }

mtaXAPITransmitBytesPerSec OBJECT-TYPE
    SYNTAX     Gauge32
    MAX-ACCESS read-only
    STATUS     current
    DESCRIPTION
	    "XAPI Transmit Bytes/sec is the rate that bytes
	    are transmitted over a XAPI connection."
    ::= { messageTransferAgent 42 }

mtaConnectionsTable OBJECT-TYPE
    SYNTAX     SEQUENCE OF MTAConnectionsEntry
    MAX-ACCESS not-accessible
    STATUS     current
    DESCRIPTION
	    "Each instance describes a single known
	    entity."
    ::= { exchange 19 }

mtaConnectionsEntry OBJECT-TYPE
    SYNTAX     MTAConnectionsEntry
    MAX-ACCESS not-accessible
    STATUS     current
    DESCRIPTION
	    "Performance information for one particular
	    instance of 'MSExchangeMTA Connections'
	    object."
    INDEX      { mtacInstance }
    ::= { mtaConnectionsTable 1 }

MTAConnectionsEntry ::= SEQUENCE {
    mtacInstance InstanceName,
    mtacAssociations Gauge32,
    mtacConnectorIndex Gauge32,
    mtacCumulativeInboundAssoc Gauge32,
    mtacCumulativeOutboundAssoc Gauge32,
    mtacCurrentInboundAssociations Gauge32,
    mtacCurrentOutboundAssociations Gauge32,
    mtacFailedOutboundAssociations Gauge32,
    mtacInboundBytesTotal Gauge32,
    mtacInboundMessagesTotal Gauge32,
    mtacInboundRejectReason Gauge32,
    mtacInboundRejectedTotal Gauge32,
    mtacLastInboundAssociation Gauge32,
    mtacLastOutboundAssociation Gauge32,
    mtacNextAssociationRetry Gauge32,
    mtacOldestMessageQueued Gauge32,
    mtacOutboundBytesTotal Gauge32,
    mtacOutboundFailureReason Gauge32,
    mtacOutboundMessagesTotal Gauge32,
    mtacQueueLength Gauge32,
    mtacQueuedBytes Gauge32,
    mtacReceiveBytesPerSec Gauge32,
    mtacReceiveMessagesPerSec Gauge32,
    mtacRejectedInboundAssociations Gauge32,
    mtacSendBytesPerSec Gauge32,
    mtacSendMessagesPerSec Gauge32,
    mtacTotalRecipientsInbound Gauge32,
    mtacTotalRecipientsOutbound Gauge32,
    mtacTotalRecipientsQueued Gauge32
}

mtacInstance OBJECT-TYPE
    SYNTAX     InstanceName
    MAX-ACCESS read-only
    STATUS     current
    DESCRIPTION
	    "Instance name."
    ::= { mtaConnectionsEntry 1 }

mtacAssociations OBJECT-TYPE
    SYNTAX     Gauge32
    MAX-ACCESS read-only
    STATUS     current
    DESCRIPTION
	    "Associations is the number of associations
	    between the MTA and the connected entity. MTAs
	    may open multiple associations if additional
	    transfer throughput is necessary."
    ::= { mtaConnectionsEntry 2 }

mtacConnectorIndex OBJECT-TYPE
    SYNTAX     Gauge32
    MAX-ACCESS read-only
    STATUS     current
    DESCRIPTION
	    "Connector Index is a unique index associated
	    with a connector entity."
    ::= { mtaConnectionsEntry 3 }

mtacCumulativeInboundAssoc OBJECT-TYPE
    SYNTAX     Gauge32
    MAX-ACCESS read-only
    STATUS     current
    DESCRIPTION
	    "Cumulative Inbound Associations is the total
	    number of inbound (remote initiated)
	    associations with the entity, since MTA
	    initialization."
    ::= { mtaConnectionsEntry 4 }

mtacCumulativeOutboundAssoc OBJECT-TYPE
    SYNTAX     Gauge32
    MAX-ACCESS read-only
    STATUS     current
    DESCRIPTION
	    "Cumulative Outbound Associations is the total
	    number of outbound (locally initiated)
	    associations with the entity, since MTA
	    initialization."
    ::= { mtaConnectionsEntry 5 }

mtacCurrentInboundAssociations OBJECT-TYPE
    SYNTAX     Gauge32
    MAX-ACCESS read-only
    STATUS     current
    DESCRIPTION
	    "Current Inbound Associations is the current
	    number of inbound (remote initiated)
	    associations with the entity."
    ::= { mtaConnectionsEntry 6 }

mtacCurrentOutboundAssociations OBJECT-TYPE
    SYNTAX     Gauge32
    MAX-ACCESS read-only
    STATUS     current
    DESCRIPTION
	    "Current Outbound Associations is the current
	    number of outbound (locally initiated)
	    associations with the entity."
    ::= { mtaConnectionsEntry 7 }

mtacFailedOutboundAssociations OBJECT-TYPE
    SYNTAX     Gauge32
    MAX-ACCESS read-only
    STATUS     current
    DESCRIPTION
	    "Failed Outbound Associations is the total
	    number of outbound (locally initiated)
	    associations that have failed, since MTA
	    initialization."
    ::= { mtaConnectionsEntry 8 }

mtacInboundBytesTotal OBJECT-TYPE
    SYNTAX     Gauge32
    MAX-ACCESS read-only
    STATUS     current
    DESCRIPTION
	    "Inbound Bytes Total is the total volume of
	    message content received from this entity since
	    MTA initialization, measured in kilobytes."
    ::= { mtaConnectionsEntry 9 }

mtacInboundMessagesTotal OBJECT-TYPE
    SYNTAX     Gauge32
    MAX-ACCESS read-only
    STATUS     current
    DESCRIPTION
	    "Inbound Messages Total is the total number of
	    messages received from this entity since MTA
	    initialization."
    ::= { mtaConnectionsEntry 10 }

mtacInboundRejectReason OBJECT-TYPE
    SYNTAX     Gauge32
    MAX-ACCESS read-only
    STATUS     current
    DESCRIPTION
	    "Inbound Reject Reason is the reject reason
	    code, if any, for the last association rejected
	    from this entity."
    ::= { mtaConnectionsEntry 11 }

mtacInboundRejectedTotal OBJECT-TYPE
    SYNTAX     Gauge32
    MAX-ACCESS read-only
    STATUS     current
    DESCRIPTION
	    "Inbound Rejected Total is the total number of
	    messages rejected from this entity since MTA
	    initialization."
    ::= { mtaConnectionsEntry 12 }

mtacLastInboundAssociation OBJECT-TYPE
    SYNTAX     Gauge32
    MAX-ACCESS read-only
    STATUS     current
    DESCRIPTION
	    "Last Inbound Association is the time (secs)
	    since the last time an inbound (remote
	    initiated) association for this entity was
	    active."
    ::= { mtaConnectionsEntry 13 }

mtacLastOutboundAssociation OBJECT-TYPE
    SYNTAX     Gauge32
    MAX-ACCESS read-only
    STATUS     current
    DESCRIPTION
	    "Last Outbound Association is the time (secs)
	    since the last time an outbound (locally
	    initiated) association for this entity was
	    active."
    ::= { mtaConnectionsEntry 14 }

mtacNextAssociationRetry OBJECT-TYPE
    SYNTAX     Gauge32
    MAX-ACCESS read-only
    STATUS     current
    DESCRIPTION
	    "Next Association Retry is the time (secs since
	    00:00 1st Jan 1970) when this entity is next
	    scheduled to attempt to open an association."
    ::= { mtaConnectionsEntry 15 }

mtacOldestMessageQueued OBJECT-TYPE
    SYNTAX     Gauge32
    MAX-ACCESS read-only
    STATUS     current
    DESCRIPTION
	    "Oldest Message Queued is the time (secs) since
	    the oldest message in this entity's queue was
	    placed in the queue."
    ::= { mtaConnectionsEntry 16 }

mtacOutboundBytesTotal OBJECT-TYPE
    SYNTAX     Gauge32
    MAX-ACCESS read-only
    STATUS     current
    DESCRIPTION
	    "Outbound Bytes Total is the total volume of
	    message content transmitted to this entity
	    since MTA initialization, measured in
	    kilobytes."
    ::= { mtaConnectionsEntry 17 }

mtacOutboundFailureReason OBJECT-TYPE
    SYNTAX     Gauge32
    MAX-ACCESS read-only
    STATUS     current
    DESCRIPTION
	    "Outbound Failure Reason is the failure reason
	    code, if any, for the last association attempt
	    to this entity."
    ::= { mtaConnectionsEntry 18 }

mtacOutboundMessagesTotal OBJECT-TYPE
    SYNTAX     Gauge32
    MAX-ACCESS read-only
    STATUS     current
    DESCRIPTION
	    "Outbound Messages Total is the total number of
	    messages transmitted to this entity since MTA
	    initialization."
    ::= { mtaConnectionsEntry 19 }

mtacQueueLength OBJECT-TYPE
    SYNTAX     Gauge32
    MAX-ACCESS read-only
    STATUS     current
    DESCRIPTION
	    "Queue Length is the number of outstanding
	    messages queued for transfer to the entity."
    ::= { mtaConnectionsEntry 20 }

mtacQueuedBytes OBJECT-TYPE
    SYNTAX     Gauge32
    MAX-ACCESS read-only
    STATUS     current
    DESCRIPTION
	    "Queued Bytes is the total volume of message
	    content currently stored in this entity's
	    queue, measured in kilobytes."
    ::= { mtaConnectionsEntry 21 }

mtacReceiveBytesPerSec OBJECT-TYPE
    SYNTAX     Gauge32
    MAX-ACCESS read-only
    STATUS     current
    DESCRIPTION
	    "Receive Bytes/sec is the rate that bytes are
	    received from the connected entity."
    ::= { mtaConnectionsEntry 22 }

mtacReceiveMessagesPerSec OBJECT-TYPE
    SYNTAX     Gauge32
    MAX-ACCESS read-only
    STATUS     current
    DESCRIPTION
	    "Receive Messages/sec is the rate that messages
	    are received from the connected entity."
    ::= { mtaConnectionsEntry 23 }

mtacRejectedInboundAssociations OBJECT-TYPE
    SYNTAX     Gauge32
    MAX-ACCESS read-only
    STATUS     current
    DESCRIPTION
	    "Rejected Inbound Associations is the total
	    number of inbound (remote initiated)
	    associations that have been rejected, since MTA
	    initialization."
    ::= { mtaConnectionsEntry 24 }

mtacSendBytesPerSec OBJECT-TYPE
    SYNTAX     Gauge32
    MAX-ACCESS read-only
    STATUS     current
    DESCRIPTION
	    "Send Bytes/sec is the rate that bytes are sent
	    to the connected entity."
    ::= { mtaConnectionsEntry 25 }

mtacSendMessagesPerSec OBJECT-TYPE
    SYNTAX     Gauge32
    MAX-ACCESS read-only
    STATUS     current
    DESCRIPTION
	    "Send Messages/sec is the rate that messages
	    are sent to the connected entity."
    ::= { mtaConnectionsEntry 26 }

mtacTotalRecipientsInbound OBJECT-TYPE
    SYNTAX     Gauge32
    MAX-ACCESS read-only
    STATUS     current
    DESCRIPTION
	    "Total Recipients Inbound is the total number
	    of recipients specified in all messages
	    received from this entity since MTA
	    initialization."
    ::= { mtaConnectionsEntry 27 }

mtacTotalRecipientsOutbound OBJECT-TYPE
    SYNTAX     Gauge32
    MAX-ACCESS read-only
    STATUS     current
    DESCRIPTION
	    "Total Recipients Outbound is the total number
	    of recipients specified in all messages
	    transmitted to this entity since MTA
	    initialization."
    ::= { mtaConnectionsEntry 28 }

mtacTotalRecipientsQueued OBJECT-TYPE
    SYNTAX     Gauge32
    MAX-ACCESS read-only
    STATUS     current
    DESCRIPTION
	    "Total Recipients Queued is the total number of
	    recipients specified in all messages currently
	    stored in this entity's queue."
    ::= { mtaConnectionsEntry 29 }

oledbEventsTable OBJECT-TYPE
    SYNTAX     SEQUENCE OF OledbEventsEntry
    MAX-ACCESS not-accessible
    STATUS     current
    DESCRIPTION
	    "The ExOledb Events object type contains
	    counters specific to the ExOledb Events"
    ::= { exchange 20 }

oledbEventsEntry OBJECT-TYPE
    SYNTAX     OledbEventsEntry
    MAX-ACCESS not-accessible
    STATUS     current
    DESCRIPTION
	    "Performance information for one particular
	    instance of 'MSExchange Oledb Events' object."
    INDEX      { oledbeInstance }
    ::= { oledbEventsTable 1 }

OledbEventsEntry ::= SEQUENCE {
    oledbeInstance InstanceName,
    oledbeEventsCompletionRate Gauge32,
    oledbeEventsCompletionTotal Gauge32,
    oledbeEventsSubmissionRate Gauge32,
    oledbeEventsSubmissionTotal Gauge32
}

oledbeInstance OBJECT-TYPE
    SYNTAX     InstanceName
    MAX-ACCESS read-only
    STATUS     current
    DESCRIPTION
	    "Instance name."
    ::= { oledbEventsEntry 1 }

oledbeEventsCompletionRate OBJECT-TYPE
    SYNTAX     Gauge32
    MAX-ACCESS read-only
    STATUS     current
    DESCRIPTION
	    "The number of events completed per second."
    ::= { oledbEventsEntry 2 }

oledbeEventsCompletionTotal OBJECT-TYPE
    SYNTAX     Gauge32
    MAX-ACCESS read-only
    STATUS     current
    DESCRIPTION
	    "The total number of events that have been
	    completed."
    ::= { oledbEventsEntry 3 }

oledbeEventsSubmissionRate OBJECT-TYPE
    SYNTAX     Gauge32
    MAX-ACCESS read-only
    STATUS     current
    DESCRIPTION
	    "The number of events submitted per second."
    ::= { oledbEventsEntry 4 }

oledbeEventsSubmissionTotal OBJECT-TYPE
    SYNTAX     Gauge32
    MAX-ACCESS read-only
    STATUS     current
    DESCRIPTION
	    "The total number of events that have been
	    submitted."
    ::= { oledbEventsEntry 5 }

oledbResourceTable OBJECT-TYPE
    SYNTAX     SEQUENCE OF OledbResourceEntry
    MAX-ACCESS not-accessible
    STATUS     current
    DESCRIPTION
	    "The ExOledb Resource object type contains
	    counters specific to the ExOledb Resources"
    ::= { exchange 21 }

oledbResourceEntry OBJECT-TYPE
    SYNTAX     OledbResourceEntry
    MAX-ACCESS not-accessible
    STATUS     current
    DESCRIPTION
	    "Performance information for one particular
	    instance of 'MSExchange Oledb Resource'
	    object."
    INDEX      { oledbrInstance }
    ::= { oledbResourceTable 1 }

OledbResourceEntry ::= SEQUENCE {
    oledbrInstance InstanceName,
    oledbrActiveCommands Gauge32,
    oledbrActiveDataSources Gauge32,
    oledbrActiveRows Gauge32,
    oledbrActiveRowsets Gauge32,
    oledbrActiveSessions Gauge32,
    oledbrActiveStreams Gauge32,
    oledbrResourceBindingsRate Gauge32,
    oledbrResourceBindingsTotal Gauge32,
    oledbrRowsetsOpenedRate Gauge32,
    oledbrRowsetsOpenedTotal Gauge32,
    oledbRsrcTransactionsAbortRate Gauge32,
    oledbRsrcTransactionsAbortTotal Gauge32,
    oledbrTransactionsCommittedRate Gauge32,
    oledbrTransactionsCommittedTotal Gauge32,
    oledbrTransactionsStartedRate Gauge32,
    oledbrTransactionsStartedTotal Gauge32
}

oledbrInstance OBJECT-TYPE
    SYNTAX     InstanceName
    MAX-ACCESS read-only
    STATUS     current
    DESCRIPTION
	    "Instance name."
    ::= { oledbResourceEntry 1 }

oledbrActiveCommands OBJECT-TYPE
    SYNTAX     Gauge32
    MAX-ACCESS read-only
    STATUS     current
    DESCRIPTION
	    "The number of Command objects which are
	    currently active."
    ::= { oledbResourceEntry 2 }

oledbrActiveDataSources OBJECT-TYPE
    SYNTAX     Gauge32
    MAX-ACCESS read-only
    STATUS     current
    DESCRIPTION
	    "The number of Data Source objects which are
	    currently active."
    ::= { oledbResourceEntry 3 }

oledbrActiveRows OBJECT-TYPE
    SYNTAX     Gauge32
    MAX-ACCESS read-only
    STATUS     current
    DESCRIPTION
	    "The number of Row objects which are currently
	    active."
    ::= { oledbResourceEntry 4 }

oledbrActiveRowsets OBJECT-TYPE
    SYNTAX     Gauge32
    MAX-ACCESS read-only
    STATUS     current
    DESCRIPTION
	    "The number of Rowset objects which are
	    currently active."
    ::= { oledbResourceEntry 5 }

oledbrActiveSessions OBJECT-TYPE
    SYNTAX     Gauge32
    MAX-ACCESS read-only
    STATUS     current
    DESCRIPTION
	    "The number of Session objects which are
	    currently active."
    ::= { oledbResourceEntry 6 }

oledbrActiveStreams OBJECT-TYPE
    SYNTAX     Gauge32
    MAX-ACCESS read-only
    STATUS     current
    DESCRIPTION
	    "The number of Stream objects which are
	    currently active."
    ::= { oledbResourceEntry 7 }

oledbrResourceBindingsRate OBJECT-TYPE
    SYNTAX     Gauge32
    MAX-ACCESS read-only
    STATUS     current
    DESCRIPTION
	    "The number of successful resource bindings per
	    second."
    ::= { oledbResourceEntry 8 }

oledbrResourceBindingsTotal OBJECT-TYPE
    SYNTAX     Gauge32
    MAX-ACCESS read-only
    STATUS     current
    DESCRIPTION
	    "The total number of successful resource
	    bindings."
    ::= { oledbResourceEntry 9 }

oledbrRowsetsOpenedRate OBJECT-TYPE
    SYNTAX     Gauge32
    MAX-ACCESS read-only
    STATUS     current
    DESCRIPTION
	    "The number of times that rowsets are opened
	    per second."
    ::= { oledbResourceEntry 10 }

oledbrRowsetsOpenedTotal OBJECT-TYPE
    SYNTAX     Gauge32
    MAX-ACCESS read-only
    STATUS     current
    DESCRIPTION
	    "The total number of times that rowsets have
	    been opened."
    ::= { oledbResourceEntry 11 }

oledbRsrcTransactionsAbortRate OBJECT-TYPE
    SYNTAX     Gauge32
    MAX-ACCESS read-only
    STATUS     current
    DESCRIPTION
	    "The number of transactions aborted
	    successfully per second."
    ::= { oledbResourceEntry 12 }

oledbRsrcTransactionsAbortTotal OBJECT-TYPE
    SYNTAX     Gauge32
    MAX-ACCESS read-only
    STATUS     current
    DESCRIPTION
	    "The total number of transactions that have
	    been successfully aborted."
    ::= { oledbResourceEntry 13 }

oledbrTransactionsCommittedRate OBJECT-TYPE
    SYNTAX     Gauge32
    MAX-ACCESS read-only
    STATUS     current
    DESCRIPTION
	    "The number of transactions committed
	    successfully per second."
    ::= { oledbResourceEntry 14 }

oledbrTransactionsCommittedTotal OBJECT-TYPE
    SYNTAX     Gauge32
    MAX-ACCESS read-only
    STATUS     current
    DESCRIPTION
	    "The total number of transactions that have
	    been successfully committed."
    ::= { oledbResourceEntry 15 }

oledbrTransactionsStartedRate OBJECT-TYPE
    SYNTAX     Gauge32
    MAX-ACCESS read-only
    STATUS     current
    DESCRIPTION
	    "The number of transactions started per
	    second."
    ::= { oledbResourceEntry 16 }

oledbrTransactionsStartedTotal OBJECT-TYPE
    SYNTAX     Gauge32
    MAX-ACCESS read-only
    STATUS     current
    DESCRIPTION
	    "The total number of transactions that have
	    been started."
    ::= { oledbResourceEntry 17 }

outlookMobileAccess OBJECT IDENTIFIER
    ::= { exchange 22 }

omaAverageResponseTime OBJECT-TYPE
    SYNTAX     Gauge32
    MAX-ACCESS read-only
    STATUS     current
    DESCRIPTION
	    "Running average of the response time in
	    milliseconds"
    ::= { outlookMobileAccess 1 }

omaBrowseRate OBJECT-TYPE
    SYNTAX     Gauge32
    MAX-ACCESS read-only
    STATUS     current
    DESCRIPTION
	    "Number of browses per second"
    ::= { outlookMobileAccess 2 }

omaBrowseCount OBJECT-TYPE
    SYNTAX     Gauge32
    MAX-ACCESS read-only
    STATUS     current
    DESCRIPTION
	    "Current total number of browse requests"
    ::= { outlookMobileAccess 3 }

omaCalendarRequestRate OBJECT-TYPE
    SYNTAX     Gauge32
    MAX-ACCESS read-only
    STATUS     current
    DESCRIPTION
	    "Calendar requests per second"
    ::= { outlookMobileAccess 4 }

omaContactRequestRate OBJECT-TYPE
    SYNTAX     Gauge32
    MAX-ACCESS read-only
    STATUS     current
    DESCRIPTION
	    "Current total number of Contact requests per
	    second"
    ::= { outlookMobileAccess 5 }

omaCumulativeTimeForAllRequests OBJECT-TYPE
    SYNTAX     Gauge32
    MAX-ACCESS read-only
    STATUS     current
    DESCRIPTION
	    "Cumulative time for all requests in
	    milliseconds"
    ::= { outlookMobileAccess 6 }

omaCurrentSimultaneousBrowses OBJECT-TYPE
    SYNTAX     Gauge32
    MAX-ACCESS read-only
    STATUS     current
    DESCRIPTION
	    "The current number of active browses"
    ::= { outlookMobileAccess 7 }

omaHTTPStatus100Count OBJECT-TYPE
    SYNTAX     Gauge32
    MAX-ACCESS read-only
    STATUS     current
    DESCRIPTION
	    "Total status 100 codes returned"
    ::= { outlookMobileAccess 8 }

omaHTTPStatus200Count OBJECT-TYPE
    SYNTAX     Gauge32
    MAX-ACCESS read-only
    STATUS     current
    DESCRIPTION
	    "Total status 200 codes returned"
    ::= { outlookMobileAccess 9 }

omaHTTPStatus300Count OBJECT-TYPE
    SYNTAX     Gauge32
    MAX-ACCESS read-only
    STATUS     current
    DESCRIPTION
	    "Total status 300 codes returned"
    ::= { outlookMobileAccess 10 }

omaHTTPStatus400Count OBJECT-TYPE
    SYNTAX     Gauge32
    MAX-ACCESS read-only
    STATUS     current
    DESCRIPTION
	    "Total status 400 codes returned"
    ::= { outlookMobileAccess 11 }

omaHTTPStatus500Count OBJECT-TYPE
    SYNTAX     Gauge32
    MAX-ACCESS read-only
    STATUS     current
    DESCRIPTION
	    "Total status 500 codes returned"
    ::= { outlookMobileAccess 12 }

omaInboxRequestsRate OBJECT-TYPE
    SYNTAX     Gauge32
    MAX-ACCESS read-only
    STATUS     current
    DESCRIPTION
	    "Current total number of Inbox requests per
	    second"
    ::= { outlookMobileAccess 13 }

omaLastResponseTime OBJECT-TYPE
    SYNTAX     Gauge32
    MAX-ACCESS read-only
    STATUS     current
    DESCRIPTION
	    "The response time of the last request in
	    milliseconds"
    ::= { outlookMobileAccess 14 }

omaMaximumSimultaneousBrowses OBJECT-TYPE
    SYNTAX     Gauge32
    MAX-ACCESS read-only
    STATUS     current
    DESCRIPTION
	    "The maximum number of active browses"
    ::= { outlookMobileAccess 15 }

omaTaskRequestRate OBJECT-TYPE
    SYNTAX     Gauge32
    MAX-ACCESS read-only
    STATUS     current
    DESCRIPTION
	    "Current Task requests per second"
    ::= { outlookMobileAccess 16 }

omaTotalCalendarRequests OBJECT-TYPE
    SYNTAX     Gauge32
    MAX-ACCESS read-only
    STATUS     current
    DESCRIPTION
	    "Current number of Calendar requests"
    ::= { outlookMobileAccess 17 }

omaTotalContactRequests OBJECT-TYPE
    SYNTAX     Gauge32
    MAX-ACCESS read-only
    STATUS     current
    DESCRIPTION
	    "Current total number of Contact requests"
    ::= { outlookMobileAccess 18 }

omaTotalInboxRequests OBJECT-TYPE
    SYNTAX     Gauge32
    MAX-ACCESS read-only
    STATUS     current
    DESCRIPTION
	    "Current total number of Inbox requests"
    ::= { outlookMobileAccess 19 }

omaTotalNumberOfTaskRequests OBJECT-TYPE
    SYNTAX     Gauge32
    MAX-ACCESS read-only
    STATUS     current
    DESCRIPTION
	    "Current total number of Task requests"
    ::= { outlookMobileAccess 20 }

routingOrganizationObjectTable OBJECT-TYPE
    SYNTAX     SEQUENCE OF RoutingOrganizationObjectEntry
    MAX-ACCESS not-accessible
    STATUS     current
    DESCRIPTION
	    "This object contains the counters for core
	    routing organization object."
    ::= { exchange 23 }

routingOrganizationObjectEntry OBJECT-TYPE
    SYNTAX     RoutingOrganizationObjectEntry
    MAX-ACCESS not-accessible
    STATUS     current
    DESCRIPTION
	    "Performance information for one particular
	    instance of 'Routing Organization Object'
	    object."
    INDEX      { rooInstance }
    ::= { routingOrganizationObjectTable 1 }

RoutingOrganizationObjectEntry ::= SEQUENCE {
    rooInstance InstanceName,
    rooConnectorRestrictCheckCounts Gauge32,
    rooFilterSequenceNumber Gauge32,
    rooInternalRGCount Gauge32,
    rooMsgTypeCount Gauge32,
    rooOrgHandleCount Gauge32,
    rooRoutingSequenceNumber Gauge32,
    rooUserSequenceNumber Gauge32
}

rooInstance OBJECT-TYPE
    SYNTAX     InstanceName
    MAX-ACCESS read-only
    STATUS     current
    DESCRIPTION
	    "Instance name."
    ::= { routingOrganizationObjectEntry 1 }

rooConnectorRestrictCheckCounts OBJECT-TYPE
    SYNTAX     Gauge32
    MAX-ACCESS read-only
    STATUS     current
    DESCRIPTION
	    "How many times routing has called Exrest to
	    check message against connector's delivery
	    restriction. Such operations can be expensive
	    if the restriction contains long DLs."
    ::= { routingOrganizationObjectEntry 2 }

rooFilterSequenceNumber OBJECT-TYPE
    SYNTAX     Gauge32
    MAX-ACCESS read-only
    STATUS     current
    DESCRIPTION
	    "Increased along with routing sequence number
	    if the cause is not from a connector link state
	    change."
    ::= { routingOrganizationObjectEntry 3 }

rooInternalRGCount OBJECT-TYPE
    SYNTAX     Gauge32
    MAX-ACCESS read-only
    STATUS     current
    DESCRIPTION
	    "Count of internal routing group objects in
	    this organization."
    ::= { routingOrganizationObjectEntry 4 }

rooMsgTypeCount OBJECT-TYPE
    SYNTAX     Gauge32
    MAX-ACCESS read-only
    STATUS     current
    DESCRIPTION
	    "Count of message types in the organization
	    object."
    ::= { routingOrganizationObjectEntry 5 }

rooOrgHandleCount OBJECT-TYPE
    SYNTAX     Gauge32
    MAX-ACCESS read-only
    STATUS     current
    DESCRIPTION
	    "Handle count on organization object (similar
	    to reference count)."
    ::= { routingOrganizationObjectEntry 6 }

rooRoutingSequenceNumber OBJECT-TYPE
    SYNTAX     Gauge32
    MAX-ACCESS read-only
    STATUS     current
    DESCRIPTION
	    "If there is change in routing topology or
	    connector linkstate, then Routing sequence
	    number is increased and routing may need to
	    recalculate the solution set."
    ::= { routingOrganizationObjectEntry 7 }

rooUserSequenceNumber OBJECT-TYPE
    SYNTAX     Gauge32
    MAX-ACCESS read-only
    STATUS     current
    DESCRIPTION
	    "Increased whenever a routing group's user
	    version is increased. This version is used to
	    indicate the change in routing group membership
	    as well as slave server's connection status
	    with their master. It is also used by Exchange
	    Status Monitor to monitor va"
    ::= { routingOrganizationObjectEntry 8 }

routingServiceTable OBJECT-TYPE
    SYNTAX     SEQUENCE OF RoutingServiceEntry
    MAX-ACCESS not-accessible
    STATUS     current
    DESCRIPTION
	    "This object contains the counters for the core
	    routing service."
    ::= { exchange 24 }

routingServiceEntry OBJECT-TYPE
    SYNTAX     RoutingServiceEntry
    MAX-ACCESS not-accessible
    STATUS     current
    DESCRIPTION
	    "Performance information for one particular
	    instance of 'Routing Service' object."
    INDEX      { routingServiceInstance }
    ::= { routingServiceTable 1 }

RoutingServiceEntry ::= SEQUENCE {
    routingServiceInstance InstanceName,
    routingServiceConnectionCount Gauge32
}

routingServiceInstance OBJECT-TYPE
    SYNTAX     InstanceName
    MAX-ACCESS read-only
    STATUS     current
    DESCRIPTION
	    "Instance name."
    ::= { routingServiceEntry 1 }

routingServiceConnectionCount OBJECT-TYPE
    SYNTAX     Gauge32
    MAX-ACCESS read-only
    STATUS     current
    DESCRIPTION
	    "Total number of client connection to Routing
	    Service."
    ::= { routingServiceEntry 2 }

sanspiProxy OBJECT-IDENTITY
    STATUS     current
    DESCRIPTION
	    "NSPI Proxy used by Microsoft Exchange System
	    Attendant"
    ::= { exchange 25 }

sanspipBytesTransmittedPerSec OBJECT-TYPE
    SYNTAX     Gauge32
    MAX-ACCESS read-only
    STATUS     current
    DESCRIPTION
	    "Bytes Transmitted/sec is the rate at which
	    data bytes are sent to the Domain Controller
	    and clients by the NSPI Proxy."
    ::= { sanspiProxy 1 }

sanspipClientConnectionCount OBJECT-TYPE
    SYNTAX     Gauge32
    MAX-ACCESS read-only
    STATUS     current
    DESCRIPTION
	    "Client Connect Count is the number of clients
	    that are presently connected to the NSPI
	    Proxy."
    ::= { sanspiProxy 2 }

sanspipClientConnectionPerSec OBJECT-TYPE
    SYNTAX     Gauge32
    MAX-ACCESS read-only
    STATUS     current
    DESCRIPTION
	    "Client Connection/sec is the rate at which new
	    client are connecting to the NSPI Proxy."
    ::= { sanspiProxy 3 }

sanspipClientDisconnectsPerSec OBJECT-TYPE
    SYNTAX     Gauge32
    MAX-ACCESS read-only
    STATUS     current
    DESCRIPTION
	    "Rate that clients are disconnecting from the
	    NSPI Proxy.  This counts normal disconnects and
	    disconnects forced by the Proxy after a network
	    error."
    ::= { sanspiProxy 4 }

sanspipClientReferrals OBJECT-TYPE
    SYNTAX     Gauge32
    MAX-ACCESS read-only
    STATUS     current
    DESCRIPTION
	    "How many MAPI client Referral requests have
	    been successfully satisfied, since the NSPI
	    Proxy service was started."
    ::= { sanspiProxy 5 }

sanspipClientReferralsPerSec OBJECT-TYPE
    SYNTAX     Gauge32
    MAX-ACCESS read-only
    STATUS     current
    DESCRIPTION
	    "Rate that MAPI client Referral requests are
	    satisfied."
    ::= { sanspiProxy 6 }

sanspipCumulativeClientConnCount OBJECT-TYPE
    SYNTAX     Gauge32
    MAX-ACCESS read-only
    STATUS     current
    DESCRIPTION
	    "Total client connections made with NSPI Proxy
	    for the life of the process."
    ::= { sanspiProxy 7 }

sanspipFailedClientConnsPerSec OBJECT-TYPE
    SYNTAX     Gauge32
    MAX-ACCESS read-only
    STATUS     current
    DESCRIPTION
	    "Failed Client Connections/sec is the rate at
	    which connect operations from clients have
	    failed."
    ::= { sanspiProxy 8 }

sanspipFailedReadsPerSec OBJECT-TYPE
    SYNTAX     Gauge32
    MAX-ACCESS read-only
    STATUS     current
    DESCRIPTION
	    "Failed Reads/sec is the rate at which read
	    operations from the Domain Controller and
	    clients have failed."
    ::= { sanspiProxy 9 }

sanspipFailedServerConnPerSec OBJECT-TYPE
    SYNTAX     Gauge32
    MAX-ACCESS read-only
    STATUS     current
    DESCRIPTION
	    "Failed Server Connections/sec is the rate at
	    which connect operations to the Domain
	    Controller have failed."
    ::= { sanspiProxy 10 }

sanspipFailedWritesPerSec OBJECT-TYPE
    SYNTAX     Gauge32
    MAX-ACCESS read-only
    STATUS     current
    DESCRIPTION
	    "Failed Writes/sec is the rate at which write
	    operationss to the Domain Controller and
	    clients have failed."
    ::= { sanspiProxy 11 }

sanspipPacketsTransmittedPerSec OBJECT-TYPE
    SYNTAX     Gauge32
    MAX-ACCESS read-only
    STATUS     current
    DESCRIPTION
	    "Packets Transmitted/sec is the rate at which
	    data packets are sent to the Domain Controller
	    and clients by the NSPI Proxy."
    ::= { sanspiProxy 12 }

sanspipPeakClientConnections OBJECT-TYPE
    SYNTAX     Gauge32
    MAX-ACCESS read-only
    STATUS     current
    DESCRIPTION
	    "Peak Client Connections is the maximum number
	    of clients that have been connected to the NSPI
	    Proxy at any one point, since the proxy was
	    started."
    ::= { sanspiProxy 13 }

sanspipPeakWorkerThreads OBJECT-TYPE
    SYNTAX     Gauge32
    MAX-ACCESS read-only
    STATUS     current
    DESCRIPTION
	    "Peak Worker Threads is the maximum number of
	    worker threads the NSPI Proxy has had since it
	    was started."
    ::= { sanspiProxy 14 }

sanspipTotalFailedClientConns OBJECT-TYPE
    SYNTAX     Gauge32
    MAX-ACCESS read-only
    STATUS     current
    DESCRIPTION
	    "Total Failed Client Connections is the number
	    of failed connect operations from clients. 
	    This is an accumulator counting all failures
	    since the NSPI Proxy was started."
    ::= { sanspiProxy 15 }

sanspipTotalFailedReads OBJECT-TYPE
    SYNTAX     Gauge32
    MAX-ACCESS read-only
    STATUS     current
    DESCRIPTION
	    "Total Failed Reads is the number of failed
	    read operations from the Domain Controller and
	    clients.  This is an accumulator counting all
	    failures since the NSPI Proxy was started."
    ::= { sanspiProxy 16 }

sanspipTotalFailedServerConns OBJECT-TYPE
    SYNTAX     Gauge32
    MAX-ACCESS read-only
    STATUS     current
    DESCRIPTION
	    "Total Failed Server Connections is the number
	    of failed connect operations to the Domain
	    Controller.  This is an accumulator counting
	    all failures since the NSPI Proxy was started."
    ::= { sanspiProxy 17 }

sanspipTotalFailedWrites OBJECT-TYPE
    SYNTAX     Gauge32
    MAX-ACCESS read-only
    STATUS     current
    DESCRIPTION
	    "Total Failed Writes is the number of failed
	    write operations to the Domain Controller and
	    clients.  This is an accumulator counting all
	    failures since the NSPI Proxy was started."
    ::= { sanspiProxy 18 }

sanspipWorkerThreadsInUse OBJECT-TYPE
    SYNTAX     Gauge32
    MAX-ACCESS read-only
    STATUS     current
    DESCRIPTION
	    "Worker Threads in Use is the number of worker
	    threads currently active in the NSPI Proxy.  A
	    worker thread handles receiving and re-sending
	    data between the Domain Controller and
	    connected clients.	More worker threads are
	    necessary to handle large number"
    ::= { sanspiProxy 19 }

siteReplicationService OBJECT-IDENTITY
    STATUS     current
    DESCRIPTION
	    "The MSExchangeSRS Object Type handles the
	    Microsoft Exchange Site Replication service on
	    your system."
    ::= { exchange 26 }

srsAccessDenials OBJECT-TYPE
    SYNTAX     Gauge32
    MAX-ACCESS read-only
    STATUS     current
    DESCRIPTION
	    "Access Denials is the number of times that
	    write operations were refused for security
	    reasons."
    ::= { siteReplicationService 1 }

srsExDSClientSessions OBJECT-TYPE
    SYNTAX     Gauge32
    MAX-ACCESS read-only
    STATUS     current
    DESCRIPTION
	    "ExDS Client Sessions is the number of
	    connected Extended Directory Service client
	    sessions.  This indicates the number of
	    connections from other Microsoft Exchange
	    services."
    ::= { siteReplicationService 2 }

srsExDSReadsPerSec OBJECT-TYPE
    SYNTAX     Gauge32
    MAX-ACCESS read-only
    STATUS     current
    DESCRIPTION
	    "ExDS Reads/sec is the rate at which Extended
	    Directory Service clients perform read
	    operations."
    ::= { siteReplicationService 3 }

srsExDSWritesPerSec OBJECT-TYPE
    SYNTAX     Gauge32
    MAX-ACCESS read-only
    STATUS     current
    DESCRIPTION
	    "ExDS Writes/sec is the rate at which Extended
	    Directory Service clients perform write
	    operations."
    ::= { siteReplicationService 4 }

srsInInterSiteRplctUpdsPerSec OBJECT-TYPE
    SYNTAX     Gauge32
    MAX-ACCESS read-only
    STATUS     current
    DESCRIPTION
	    "Incoming Inter-Site Replication Updates/sec is
	    the rate at which replication update messages
	    from other Microsoft Exchange sites are applied
	    by the local site replication service.  This
	    indicates how much inter-site replication
	    activity is occuring on the"
    ::= { siteReplicationService 5 }

srsLDAPSearches OBJECT-TYPE
    SYNTAX     Gauge32
    MAX-ACCESS read-only
    STATUS     current
    DESCRIPTION
	    "Total number of LDAP searches performed since
	    the SRS started."
    ::= { siteReplicationService 6 }

srsLDAPSearchesPerSec OBJECT-TYPE
    SYNTAX     Gauge32
    MAX-ACCESS read-only
    STATUS     current
    DESCRIPTION
	    "LDAP Searches/sec is the rate at which LDAP
	    clients perform search operations."
    ::= { siteReplicationService 7 }

srsObjectsReplicatedOutPerSec OBJECT-TYPE
    SYNTAX     Gauge32
    MAX-ACCESS read-only
    STATUS     current
    DESCRIPTION
	    "This is the number of objects replicated out
	    per second from this machine to Exchange
	    Directory Servers."
    ::= { siteReplicationService 8 }

srsOutInterSiteRplctMsgsPerSec OBJECT-TYPE
    SYNTAX     Gauge32
    MAX-ACCESS read-only
    STATUS     current
    DESCRIPTION
	    "Outgoing Inter-Site Replication Messages/sec
	    is the rate at which this Microsoft Exchange
	    site is sending replication update messages to
	    other Microsoft Exchange sites.  This indicates
	    how much inter-site replication activity is
	    occuring on the server."
    ::= { siteReplicationService 9 }

srsPendingReplicationSync OBJECT-TYPE
    SYNTAX     Gauge32
    MAX-ACCESS read-only
    STATUS     current
    DESCRIPTION
	    "Pending Replication Synchronizations is the
	    number of synchronizations that are queued for
	    this server but not yet processed."
    ::= { siteReplicationService 10 }

srsRemainingReplicationUpdates OBJECT-TYPE
    SYNTAX     Gauge32
    MAX-ACCESS read-only
    STATUS     current
    DESCRIPTION
	    "Remaining Replication Updates is the number of
	    object modifications received in the current
	    replication update packet that have not yet
	    been applied to the local server."
    ::= { siteReplicationService 11 }

srsReplicationUpdatesPerSec OBJECT-TYPE
    SYNTAX     Gauge32
    MAX-ACCESS read-only
    STATUS     current
    DESCRIPTION
	    "Replication Updates/sec is the rate at which
	    replication updates are applied by the local
	    site replication service.  This indicates how
	    much replication activity is occuring on the
	    server."
    ::= { siteReplicationService 12 }

srsThreadsInUse OBJECT-TYPE
    SYNTAX     Gauge32
    MAX-ACCESS read-only
    STATUS     current
    DESCRIPTION
	    "Threads in Use is the current number of RPC
	    threads active in the site replication service
	    (different than the number of threads in the
	    service process).  Threads in Use is the number
	    of RPC-generated threads currently in API calls
	    and can be used to indi"
    ::= { siteReplicationService 13 }

smtpRoutingTable OBJECT-TYPE
    SYNTAX     SEQUENCE OF SMTPRoutingEntry
    MAX-ACCESS not-accessible
    STATUS     current
    DESCRIPTION
	    "This object represents the counters for the
	    SMTP routing performance."
    ::= { exchange 27 }

smtpRoutingEntry OBJECT-TYPE
    SYNTAX     SMTPRoutingEntry
    MAX-ACCESS not-accessible
    STATUS     current
    DESCRIPTION
	    "Performance information for one particular
	    instance of 'SMTP Routing' object."
    INDEX      { smtprInstance }
    ::= { smtpRoutingTable 1 }

SMTPRoutingEntry ::= SEQUENCE {
    smtprInstance InstanceName,
    smtprGlobalResetRoute Gauge32,
    smtprLinkStateChange Gauge32,
    smtprLinkStateChangeIgnored Gauge32,
    smtprLocalResetRoute Gauge32,
    smtprServerCacheRefresh Gauge32,
    smtprSetXLSALinkState Gauge32
}

smtprInstance OBJECT-TYPE
    SYNTAX     InstanceName
    MAX-ACCESS read-only
    STATUS     current
    DESCRIPTION
	    "Instance name."
    ::= { smtpRoutingEntry 1 }

smtprGlobalResetRoute OBJECT-TYPE
    SYNTAX     Gauge32
    MAX-ACCESS read-only
    STATUS     current
    DESCRIPTION
	    "Count for global ResetRoutes."
    ::= { smtpRoutingEntry 2 }

smtprLinkStateChange OBJECT-TYPE
    SYNTAX     Gauge32
    MAX-ACCESS read-only
    STATUS     current
    DESCRIPTION
	    "Count of LinkState Changes that will be pushed
	    to master."
    ::= { smtpRoutingEntry 3 }

smtprLinkStateChangeIgnored OBJECT-TYPE
    SYNTAX     Gauge32
    MAX-ACCESS read-only
    STATUS     current
    DESCRIPTION
	    "Count of LinkState Changes ignored."
    ::= { smtpRoutingEntry 4 }

smtprLocalResetRoute OBJECT-TYPE
    SYNTAX     Gauge32
    MAX-ACCESS read-only
    STATUS     current
    DESCRIPTION
	    "Count for local ResetRoutes."
    ::= { smtpRoutingEntry 5 }

smtprServerCacheRefresh OBJECT-TYPE
    SYNTAX     Gauge32
    MAX-ACCESS read-only
    STATUS     current
    DESCRIPTION
	    "How many times server cache was refreshed."
    ::= { smtpRoutingEntry 6 }

smtprSetXLSALinkState OBJECT-TYPE
    SYNTAX     Gauge32
    MAX-ACCESS read-only
    STATUS     current
    DESCRIPTION
	    "Count of XLSA packet is sent to other RGs."
    ::= { smtpRoutingEntry 7 }

transportStoreDriverTable OBJECT-TYPE
    SYNTAX     SEQUENCE OF TransportStoreDriverEntry
    MAX-ACCESS not-accessible
    STATUS     current
    DESCRIPTION
	    "This object represents global counters for the
	    Exchange Store driver (IIS)"
    ::= { exchange 28 }

transportStoreDriverEntry OBJECT-TYPE
    SYNTAX     TransportStoreDriverEntry
    MAX-ACCESS not-accessible
    STATUS     current
    DESCRIPTION
	    "Performance information for one particular
	    instance of 'MSExchangeTransport Store Driver'
	    object."
    INDEX      { tsdInstance }
    ::= { transportStoreDriverTable 1 }

TransportStoreDriverEntry ::= SEQUENCE {
    tsdInstance InstanceName,
    tsdMailMsgAllocates Gauge32,
    tsdMailMsgCloseContents Gauge32,
    tsdMailMsgCommits Gauge32,
    tsdMailMsgCurOpenContentHandles Gauge32,
    tsdMailMsgCurOpenStreams Gauge32,
    tsdMailMsgDeletes Gauge32,
    tsdMailMsgGetsize Gauge32,
    tsdMailMsgReadblocks Gauge32,
    tsdMailMsgReallocates Gauge32,
    tsdMailMsgReopens Gauge32,
    tsdStoreRequestsPendingAcks Gauge32,
    tsdStorePerMTADelivery Gauge32,
    tsdStorePerMTALocalDeliveryRetry Gauge32,
    tsdStorePerMTASubmits Gauge32
}

tsdInstance OBJECT-TYPE
    SYNTAX     InstanceName
    MAX-ACCESS read-only
    STATUS     current
    DESCRIPTION
	    "Instance name."
    ::= { transportStoreDriverEntry 1 }

tsdMailMsgAllocates OBJECT-TYPE
    SYNTAX     Gauge32
    MAX-ACCESS read-only
    STATUS     current
    DESCRIPTION
	    "The total number of messages allocated."
    ::= { transportStoreDriverEntry 2 }

tsdMailMsgCloseContents OBJECT-TYPE
    SYNTAX     Gauge32
    MAX-ACCESS read-only
    STATUS     current
    DESCRIPTION
	    "The total number of messages contents closed."
    ::= { transportStoreDriverEntry 3 }

tsdMailMsgCommits OBJECT-TYPE
    SYNTAX     Gauge32
    MAX-ACCESS read-only
    STATUS     current
    DESCRIPTION
	    "The total number of calls to commit."
    ::= { transportStoreDriverEntry 4 }

tsdMailMsgCurOpenContentHandles OBJECT-TYPE
    SYNTAX     Gauge32
    MAX-ACCESS read-only
    STATUS     current
    DESCRIPTION
	    "The current number of open message contents."
    ::= { transportStoreDriverEntry 5 }

tsdMailMsgCurOpenStreams OBJECT-TYPE
    SYNTAX     Gauge32
    MAX-ACCESS read-only
    STATUS     current
    DESCRIPTION
	    "The current number of open streams."
    ::= { transportStoreDriverEntry 6 }

tsdMailMsgDeletes OBJECT-TYPE
    SYNTAX     Gauge32
    MAX-ACCESS read-only
    STATUS     current
    DESCRIPTION
	    "The total number of messages deleted."
    ::= { transportStoreDriverEntry 7 }

tsdMailMsgGetsize OBJECT-TYPE
    SYNTAX     Gauge32
    MAX-ACCESS read-only
    STATUS     current
    DESCRIPTION
	    "The total number of calls to get size."
    ::= { transportStoreDriverEntry 8 }

tsdMailMsgReadblocks OBJECT-TYPE
    SYNTAX     Gauge32
    MAX-ACCESS read-only
    STATUS     current
    DESCRIPTION
	    "The total number of calls to readblocks."
    ::= { transportStoreDriverEntry 9 }

tsdMailMsgReallocates OBJECT-TYPE
    SYNTAX     Gauge32
    MAX-ACCESS read-only
    STATUS     current
    DESCRIPTION
	    "The total number of messages reallocated."
    ::= { transportStoreDriverEntry 10 }

tsdMailMsgReopens OBJECT-TYPE
    SYNTAX     Gauge32
    MAX-ACCESS read-only
    STATUS     current
    DESCRIPTION
	    "The total number of messages reopened."
    ::= { transportStoreDriverEntry 11 }

tsdStoreRequestsPendingAcks OBJECT-TYPE
    SYNTAX     Gauge32
    MAX-ACCESS read-only
    STATUS     current
    DESCRIPTION
	    "The current number of requests pending acks
	    from the store."
    ::= { transportStoreDriverEntry 12 }

tsdStorePerMTADelivery OBJECT-TYPE
    SYNTAX     Gauge32
    MAX-ACCESS read-only
    STATUS     current
    DESCRIPTION
	    "The total number of messages delivered locally
	    to an MDB or MSExchangeMTA"
    ::= { transportStoreDriverEntry 13 }

tsdStorePerMTALocalDeliveryRetry OBJECT-TYPE
    SYNTAX     Gauge32
    MAX-ACCESS read-only
    STATUS     current
    DESCRIPTION
	    "The total number of times returned retry to
	    local delivery."
    ::= { transportStoreDriverEntry 14 }

tsdStorePerMTASubmits OBJECT-TYPE
    SYNTAX     Gauge32
    MAX-ACCESS read-only
    STATUS     current
    DESCRIPTION
	    "The total number of messages received from
	    Store/MTA and submitted to Transport"
    ::= { transportStoreDriverEntry 15 }

webMailTable OBJECT-TYPE
    SYNTAX     SEQUENCE OF WebMailEntry
    MAX-ACCESS not-accessible
    STATUS     current
    DESCRIPTION
	    "The WebMail object type contains counters
	    specific to the WebMail"
    ::= { exchange 29 }

webMailEntry OBJECT-TYPE
    SYNTAX     WebMailEntry
    MAX-ACCESS not-accessible
    STATUS     current
    DESCRIPTION
	    "Performance information for one particular
	    instance of 'MSExchange Web Mail' object."
    INDEX      { wmInstance }
    ::= { webMailTable 1 }

WebMailEntry ::= SEQUENCE {
    wmInstance InstanceName,
    wmApptAcceptPerDeclineTotal Gauge32,
    wmApptAcceptPerDeclinePerSec Gauge32,
    wmApptAttachmentEditsTotal Gauge32,
    wmApptAttachmentEditsPerSec Gauge32,
    wmApptDataRetrievesTotal Gauge32,
    wmApptDataRetrievesPerSec Gauge32,
    wmApptEditRecurrenceTotal Gauge32,
    wmApptEditRecurrencePerSec Gauge32,
    wmApptOpensTotal Gauge32,
    wmApptOpensPerSec Gauge32,
    wmApptResolveFreeBusyTotal Gauge32,
    wmApptResolveFreeBusyPerSec Gauge32,
    wmApptSaveRecurrencesTotal Gauge32,
    wmApptSaveRecurrencesPerSec Gauge32,
    wmApptSavesTotal Gauge32,
    wmApptSavesPerSec Gauge32,
    wmApptSendsTotal Gauge32,
    wmApptSendsPerSec Gauge32,
    wmApptUpdatesTotal Gauge32,
    wmApptUpdatesPerSec Gauge32,
    wmAttachmentsDeletedTotal Gauge32,
    wmAttachmentsDeletedPerSec Gauge32,
    wmAuthenticationCacheHitsTotal Gauge32,
    wmAuthenticationCacheHitsPerSec Gauge32,
    wmAuthenticationsInCache Gauge32,
    wmAuthenticationsTotal Gauge32,
    wmAuthenticationsPerSec Gauge32,
    wmFolderCreatesTotal Gauge32,
    wmFolderCreatesPerSec Gauge32,
    wmFolderGetContentsTotal Gauge32,
    wmFolderGetContentsPerSec Gauge32,
    wmFolderGetViewTotal Gauge32,
    wmFolderGetViewPerSec Gauge32,
    wmFolderRenamesTotal Gauge32,
    wmFolderRenamesPerSec Gauge32,
    wmFormsSentTotal Gauge32,
    wmFormsSentPerSec Gauge32,
    wmGetAppFrameTotal Gauge32,
    wmGetAppFramePerSec Gauge32,
    wmGetNavBarTotal Gauge32,
    wmGetNavBarPerSec Gauge32,
    wmMessageAttachmentEditsTotal Gauge32,
    wmMessageAttachmentEditsPerSec Gauge32,
    wmMessageMovesPerCopiesTotal Gauge32,
    wmMessageMovesPerCopiesPerSec Gauge32,
    wmMessageOpensTotal Gauge32,
    wmMessageOpensPerSec Gauge32,
    wmMessageSavesTotal Gauge32,
    wmMessageSavesPerSec Gauge32,
    wmMessageSendsTotal Gauge32,
    wmMessageSendsPerSec Gauge32,
    wmMessagePerApptDeletesTotal Gauge32,
    wmMessagePerApptDeletesPerSec Gauge32,
    wmMessagePerApptOpensTotal Gauge32,
    wmMessagePerApptOpensPerSec Gauge32,
    wmMessagePerApptSavesTotal Gauge32,
    wmMessagePerApptSavesPerSec Gauge32,
    wmNamesCheckedTotal Gauge32,
    wmNamesCheckedPerSec Gauge32,
    wmNavigationOptionsSavesTotal Gauge32,
    wmNavigationOptionsSavesPerSec Gauge32,
    wmNewFolderTemplateDataTotal Gauge32,
    wmNewFolderTemplateDataPerSec Gauge32,
    wmNewItemURLTotal Gauge32,
    wmNewItemURLPerSec Gauge32,
    wmPostsSubmittedTotal Gauge32,
    wmPostsSubmittedPerSec Gauge32,
    wmRecipientsEditedTotal Gauge32,
    wmRecipientsEditedPerSec Gauge32,
    wmRecipientsSavedTotal Gauge32,
    wmRecipientsSavedPerSec Gauge32,
    wmViewsOfCalendarsTotal Gauge32,
    wmViewsOfCalendarsPerSec Gauge32,
    wmViewsOfMailFoldersTotal Gauge32,
    wmViewsOfMailFoldersPerSec Gauge32
}

wmInstance OBJECT-TYPE
    SYNTAX     InstanceName
    MAX-ACCESS read-only
    STATUS     current
    DESCRIPTION
	    "Instance name."
    ::= { webMailEntry 1 }

wmApptAcceptPerDeclineTotal OBJECT-TYPE
    SYNTAX     Gauge32
    MAX-ACCESS read-only
    STATUS     current
    DESCRIPTION
	    "Total number of Appointment accept/decline."
    ::= { webMailEntry 2 }

wmApptAcceptPerDeclinePerSec OBJECT-TYPE
    SYNTAX     Gauge32
    MAX-ACCESS read-only
    STATUS     current
    DESCRIPTION
	    "Rate of Appointment accept/decline per
	    second."
    ::= { webMailEntry 3 }

wmApptAttachmentEditsTotal OBJECT-TYPE
    SYNTAX     Gauge32
    MAX-ACCESS read-only
    STATUS     current
    DESCRIPTION
	    "Total number of Appointment attachment edits."
    ::= { webMailEntry 4 }

wmApptAttachmentEditsPerSec OBJECT-TYPE
    SYNTAX     Gauge32
    MAX-ACCESS read-only
    STATUS     current
    DESCRIPTION
	    "Rate of Appointment attachment edits per
	    second."
    ::= { webMailEntry 5 }

wmApptDataRetrievesTotal OBJECT-TYPE
    SYNTAX     Gauge32
    MAX-ACCESS read-only
    STATUS     current
    DESCRIPTION
	    "Total number of Appointment data retrieves."
    ::= { webMailEntry 6 }

wmApptDataRetrievesPerSec OBJECT-TYPE
    SYNTAX     Gauge32
    MAX-ACCESS read-only
    STATUS     current
    DESCRIPTION
	    "Rate of Appointment data retrieves per
	    second."
    ::= { webMailEntry 7 }

wmApptEditRecurrenceTotal OBJECT-TYPE
    SYNTAX     Gauge32
    MAX-ACCESS read-only
    STATUS     current
    DESCRIPTION
	    "Total number of Appointment edit recurrence."
    ::= { webMailEntry 8 }

wmApptEditRecurrencePerSec OBJECT-TYPE
    SYNTAX     Gauge32
    MAX-ACCESS read-only
    STATUS     current
    DESCRIPTION
	    "Rate of Appointment edit recurrence per
	    second."
    ::= { webMailEntry 9 }

wmApptOpensTotal OBJECT-TYPE
    SYNTAX     Gauge32
    MAX-ACCESS read-only
    STATUS     current
    DESCRIPTION
	    "Total number of Appointment opens."
    ::= { webMailEntry 10 }

wmApptOpensPerSec OBJECT-TYPE
    SYNTAX     Gauge32
    MAX-ACCESS read-only
    STATUS     current
    DESCRIPTION
	    "Rate of Appointment opens per second."
    ::= { webMailEntry 11 }

wmApptResolveFreeBusyTotal OBJECT-TYPE
    SYNTAX     Gauge32
    MAX-ACCESS read-only
    STATUS     current
    DESCRIPTION
	    "Total number of Appointment resolve
	    Free-Busy."
    ::= { webMailEntry 12 }

wmApptResolveFreeBusyPerSec OBJECT-TYPE
    SYNTAX     Gauge32
    MAX-ACCESS read-only
    STATUS     current
    DESCRIPTION
	    "Rate of Appointment resolve Free-Busy per
	    second."
    ::= { webMailEntry 13 }

wmApptSaveRecurrencesTotal OBJECT-TYPE
    SYNTAX     Gauge32
    MAX-ACCESS read-only
    STATUS     current
    DESCRIPTION
	    "Total number of Appointment save recurrences."
    ::= { webMailEntry 14 }

wmApptSaveRecurrencesPerSec OBJECT-TYPE
    SYNTAX     Gauge32
    MAX-ACCESS read-only
    STATUS     current
    DESCRIPTION
	    "Rate of Appointment save recurrences per
	    second."
    ::= { webMailEntry 15 }

wmApptSavesTotal OBJECT-TYPE
    SYNTAX     Gauge32
    MAX-ACCESS read-only
    STATUS     current
    DESCRIPTION
	    "Total number of Appointment saves."
    ::= { webMailEntry 16 }

wmApptSavesPerSec OBJECT-TYPE
    SYNTAX     Gauge32
    MAX-ACCESS read-only
    STATUS     current
    DESCRIPTION
	    "Rate of Appointment saves per second."
    ::= { webMailEntry 17 }

wmApptSendsTotal OBJECT-TYPE
    SYNTAX     Gauge32
    MAX-ACCESS read-only
    STATUS     current
    DESCRIPTION
	    "Total number of Appointment sends."
    ::= { webMailEntry 18 }

wmApptSendsPerSec OBJECT-TYPE
    SYNTAX     Gauge32
    MAX-ACCESS read-only
    STATUS     current
    DESCRIPTION
	    "Rate of Appointment sends per second."
    ::= { webMailEntry 19 }

wmApptUpdatesTotal OBJECT-TYPE
    SYNTAX     Gauge32
    MAX-ACCESS read-only
    STATUS     current
    DESCRIPTION
	    "Total number of Appointment updates."
    ::= { webMailEntry 20 }

wmApptUpdatesPerSec OBJECT-TYPE
    SYNTAX     Gauge32
    MAX-ACCESS read-only
    STATUS     current
    DESCRIPTION
	    "Rate of Appointment updates per second."
    ::= { webMailEntry 21 }

wmAttachmentsDeletedTotal OBJECT-TYPE
    SYNTAX     Gauge32
    MAX-ACCESS read-only
    STATUS     current
    DESCRIPTION
	    "Total number of Attachments deleted."
    ::= { webMailEntry 22 }

wmAttachmentsDeletedPerSec OBJECT-TYPE
    SYNTAX     Gauge32
    MAX-ACCESS read-only
    STATUS     current
    DESCRIPTION
	    "Rate of Attachments deleted per second."
    ::= { webMailEntry 23 }

wmAuthenticationCacheHitsTotal OBJECT-TYPE
    SYNTAX     Gauge32
    MAX-ACCESS read-only
    STATUS     current
    DESCRIPTION
	    "Total number of Authentication cache hits.
	    This is the number of times that the needed
	    authentication is retrieved from a cache."
    ::= { webMailEntry 24 }

wmAuthenticationCacheHitsPerSec OBJECT-TYPE
    SYNTAX     Gauge32
    MAX-ACCESS read-only
    STATUS     current
    DESCRIPTION
	    "Rate of Authentication cache hits per second.
	    This is the number of times that the needed
	    authentication is retrieved from a cache."
    ::= { webMailEntry 25 }

wmAuthenticationsInCache OBJECT-TYPE
    SYNTAX     Gauge32
    MAX-ACCESS read-only
    STATUS     current
    DESCRIPTION
	    "Total number of Authentications (in cache).
	    This gives the number of different users who
	    have accessed the Exchange store via DAV in the
	    last few minutes."
    ::= { webMailEntry 26 }

wmAuthenticationsTotal OBJECT-TYPE
    SYNTAX     Gauge32
    MAX-ACCESS read-only
    STATUS     current
    DESCRIPTION
	    "Total number of Authentications. This is the
	    total number of times authentication is
	    needed."
    ::= { webMailEntry 27 }

wmAuthenticationsPerSec OBJECT-TYPE
    SYNTAX     Gauge32
    MAX-ACCESS read-only
    STATUS     current
    DESCRIPTION
	    "Rate of Authentications per second. This is
	    the total number of times authentication is
	    needed."
    ::= { webMailEntry 28 }

wmFolderCreatesTotal OBJECT-TYPE
    SYNTAX     Gauge32
    MAX-ACCESS read-only
    STATUS     current
    DESCRIPTION
	    "Total number of Folder creates*. This action
	    is handled in HTTP-DAV for IE5 browers"
    ::= { webMailEntry 29 }

wmFolderCreatesPerSec OBJECT-TYPE
    SYNTAX     Gauge32
    MAX-ACCESS read-only
    STATUS     current
    DESCRIPTION
	    "Rate of Folder creates* per second. This
	    action is handled in HTTP-DAV for IE5 browers"
    ::= { webMailEntry 30 }

wmFolderGetContentsTotal OBJECT-TYPE
    SYNTAX     Gauge32
    MAX-ACCESS read-only
    STATUS     current
    DESCRIPTION
	    "Total number of Folder get contents."
    ::= { webMailEntry 31 }

wmFolderGetContentsPerSec OBJECT-TYPE
    SYNTAX     Gauge32
    MAX-ACCESS read-only
    STATUS     current
    DESCRIPTION
	    "Rate of Folder get contents per second."
    ::= { webMailEntry 32 }

wmFolderGetViewTotal OBJECT-TYPE
    SYNTAX     Gauge32
    MAX-ACCESS read-only
    STATUS     current
    DESCRIPTION
	    "Total number of Folder get view*. This is only
	    incremented by IE5 clients.  Changing the view
	    from non-IE5 clients increments 'Folder get
	    contents'."
    ::= { webMailEntry 33 }

wmFolderGetViewPerSec OBJECT-TYPE
    SYNTAX     Gauge32
    MAX-ACCESS read-only
    STATUS     current
    DESCRIPTION
	    "Rate of Folder get view* per second. This is
	    only incremented by IE5 clients.  Changing the
	    view from non-IE5 clients increments 'Folder
	    get contents'."
    ::= { webMailEntry 34 }

wmFolderRenamesTotal OBJECT-TYPE
    SYNTAX     Gauge32
    MAX-ACCESS read-only
    STATUS     current
    DESCRIPTION
	    "Total number of Folder renames*. This action
	    is handled in HTTP-DAV for IE5 browers"
    ::= { webMailEntry 35 }

wmFolderRenamesPerSec OBJECT-TYPE
    SYNTAX     Gauge32
    MAX-ACCESS read-only
    STATUS     current
    DESCRIPTION
	    "Rate of Folder renames* per second. This
	    action is handled in HTTP-DAV for IE5 browers"
    ::= { webMailEntry 36 }

wmFormsSentTotal OBJECT-TYPE
    SYNTAX     Gauge32
    MAX-ACCESS read-only
    STATUS     current
    DESCRIPTION
	    "Total number of Forms sent."
    ::= { webMailEntry 37 }

wmFormsSentPerSec OBJECT-TYPE
    SYNTAX     Gauge32
    MAX-ACCESS read-only
    STATUS     current
    DESCRIPTION
	    "Rate of Forms sent per second."
    ::= { webMailEntry 38 }

wmGetAppFrameTotal OBJECT-TYPE
    SYNTAX     Gauge32
    MAX-ACCESS read-only
    STATUS     current
    DESCRIPTION
	    "Total number of Get app frame."
    ::= { webMailEntry 39 }

wmGetAppFramePerSec OBJECT-TYPE
    SYNTAX     Gauge32
    MAX-ACCESS read-only
    STATUS     current
    DESCRIPTION
	    "Rate of Get app frame per second."
    ::= { webMailEntry 40 }

wmGetNavBarTotal OBJECT-TYPE
    SYNTAX     Gauge32
    MAX-ACCESS read-only
    STATUS     current
    DESCRIPTION
	    "Total number of Get nav bar."
    ::= { webMailEntry 41 }

wmGetNavBarPerSec OBJECT-TYPE
    SYNTAX     Gauge32
    MAX-ACCESS read-only
    STATUS     current
    DESCRIPTION
	    "Rate of Get nav bar per second."
    ::= { webMailEntry 42 }

wmMessageAttachmentEditsTotal OBJECT-TYPE
    SYNTAX     Gauge32
    MAX-ACCESS read-only
    STATUS     current
    DESCRIPTION
	    "Total number of Message attachment edits."
    ::= { webMailEntry 43 }

wmMessageAttachmentEditsPerSec OBJECT-TYPE
    SYNTAX     Gauge32
    MAX-ACCESS read-only
    STATUS     current
    DESCRIPTION
	    "Rate of Message attachment edits per second."
    ::= { webMailEntry 44 }

wmMessageMovesPerCopiesTotal OBJECT-TYPE
    SYNTAX     Gauge32
    MAX-ACCESS read-only
    STATUS     current
    DESCRIPTION
	    "Total number of Message moves/copies*. This
	    action is handled in HTTP-DAV for IE5 browers"
    ::= { webMailEntry 45 }

wmMessageMovesPerCopiesPerSec OBJECT-TYPE
    SYNTAX     Gauge32
    MAX-ACCESS read-only
    STATUS     current
    DESCRIPTION
	    "Rate of Message moves/copies* per second. This
	    action is handled in HTTP-DAV for IE5 browers"
    ::= { webMailEntry 46 }

wmMessageOpensTotal OBJECT-TYPE
    SYNTAX     Gauge32
    MAX-ACCESS read-only
    STATUS     current
    DESCRIPTION
	    "Total number of Message opens."
    ::= { webMailEntry 47 }

wmMessageOpensPerSec OBJECT-TYPE
    SYNTAX     Gauge32
    MAX-ACCESS read-only
    STATUS     current
    DESCRIPTION
	    "Rate of Message opens per second."
    ::= { webMailEntry 48 }

wmMessageSavesTotal OBJECT-TYPE
    SYNTAX     Gauge32
    MAX-ACCESS read-only
    STATUS     current
    DESCRIPTION
	    "Total number of Message saves."
    ::= { webMailEntry 49 }

wmMessageSavesPerSec OBJECT-TYPE
    SYNTAX     Gauge32
    MAX-ACCESS read-only
    STATUS     current
    DESCRIPTION
	    "Rate of Message saves per second."
    ::= { webMailEntry 50 }

wmMessageSendsTotal OBJECT-TYPE
    SYNTAX     Gauge32
    MAX-ACCESS read-only
    STATUS     current
    DESCRIPTION
	    "Total number of Message sends."
    ::= { webMailEntry 51 }

wmMessageSendsPerSec OBJECT-TYPE
    SYNTAX     Gauge32
    MAX-ACCESS read-only
    STATUS     current
    DESCRIPTION
	    "Rate of Message sends per second."
    ::= { webMailEntry 52 }

wmMessagePerApptDeletesTotal OBJECT-TYPE
    SYNTAX     Gauge32
    MAX-ACCESS read-only
    STATUS     current
    DESCRIPTION
	    "Total number of Message/Appointment deletes*.
	    This action is handled in HTTP-DAV for IE5
	    browers"
    ::= { webMailEntry 53 }

wmMessagePerApptDeletesPerSec OBJECT-TYPE
    SYNTAX     Gauge32
    MAX-ACCESS read-only
    STATUS     current
    DESCRIPTION
	    "Rate of Message/Appointment deletes* per
	    second. This action is handled in HTTP-DAV for
	    IE5 browers"
    ::= { webMailEntry 54 }

wmMessagePerApptOpensTotal OBJECT-TYPE
    SYNTAX     Gauge32
    MAX-ACCESS read-only
    STATUS     current
    DESCRIPTION
	    "Total number of Message/Appointment opens."
    ::= { webMailEntry 55 }

wmMessagePerApptOpensPerSec OBJECT-TYPE
    SYNTAX     Gauge32
    MAX-ACCESS read-only
    STATUS     current
    DESCRIPTION
	    "Rate of Message/Appointment opens per second."
    ::= { webMailEntry 56 }

wmMessagePerApptSavesTotal OBJECT-TYPE
    SYNTAX     Gauge32
    MAX-ACCESS read-only
    STATUS     current
    DESCRIPTION
	    "Total number of Message/Appointment saves."
    ::= { webMailEntry 57 }

wmMessagePerApptSavesPerSec OBJECT-TYPE
    SYNTAX     Gauge32
    MAX-ACCESS read-only
    STATUS     current
    DESCRIPTION
	    "Rate of Message/Appointment saves per second."
    ::= { webMailEntry 58 }

wmNamesCheckedTotal OBJECT-TYPE
    SYNTAX     Gauge32
    MAX-ACCESS read-only
    STATUS     current
    DESCRIPTION
	    "Total number of Names checked."
    ::= { webMailEntry 59 }

wmNamesCheckedPerSec OBJECT-TYPE
    SYNTAX     Gauge32
    MAX-ACCESS read-only
    STATUS     current
    DESCRIPTION
	    "Rate of Names checked per second."
    ::= { webMailEntry 60 }

wmNavigationOptionsSavesTotal OBJECT-TYPE
    SYNTAX     Gauge32
    MAX-ACCESS read-only
    STATUS     current
    DESCRIPTION
	    "Total number of Navigation options saves.
	    These are the per-user options including Out of
	    Office Assistant, Calander Options and Contact
	    Options."
    ::= { webMailEntry 61 }

wmNavigationOptionsSavesPerSec OBJECT-TYPE
    SYNTAX     Gauge32
    MAX-ACCESS read-only
    STATUS     current
    DESCRIPTION
	    "Rate of Navigation options saves per second.
	    These are the per-user options including Out of
	    Office Assistant, Calander Options and Contact
	    Options."
    ::= { webMailEntry 62 }

wmNewFolderTemplateDataTotal OBJECT-TYPE
    SYNTAX     Gauge32
    MAX-ACCESS read-only
    STATUS     current
    DESCRIPTION
	    "Total number of New folder template data. This
	    is not incremented by IE5 clients."
    ::= { webMailEntry 63 }

wmNewFolderTemplateDataPerSec OBJECT-TYPE
    SYNTAX     Gauge32
    MAX-ACCESS read-only
    STATUS     current
    DESCRIPTION
	    "Rate of New folder template data per second.
	    This is not incremented by IE5 clients."
    ::= { webMailEntry 64 }

wmNewItemURLTotal OBJECT-TYPE
    SYNTAX     Gauge32
    MAX-ACCESS read-only
    STATUS     current
    DESCRIPTION
	    "Total number of New item URL. This is not
	    incremented by IE5 clients."
    ::= { webMailEntry 65 }

wmNewItemURLPerSec OBJECT-TYPE
    SYNTAX     Gauge32
    MAX-ACCESS read-only
    STATUS     current
    DESCRIPTION
	    "Rate of New item URL per second. This is not
	    incremented by IE5 clients."
    ::= { webMailEntry 66 }

wmPostsSubmittedTotal OBJECT-TYPE
    SYNTAX     Gauge32
    MAX-ACCESS read-only
    STATUS     current
    DESCRIPTION
	    "Total number of Posts submitted."
    ::= { webMailEntry 67 }

wmPostsSubmittedPerSec OBJECT-TYPE
    SYNTAX     Gauge32
    MAX-ACCESS read-only
    STATUS     current
    DESCRIPTION
	    "Rate of Posts submitted per second."
    ::= { webMailEntry 68 }

wmRecipientsEditedTotal OBJECT-TYPE
    SYNTAX     Gauge32
    MAX-ACCESS read-only
    STATUS     current
    DESCRIPTION
	    "Total number of Recipients edited."
    ::= { webMailEntry 69 }

wmRecipientsEditedPerSec OBJECT-TYPE
    SYNTAX     Gauge32
    MAX-ACCESS read-only
    STATUS     current
    DESCRIPTION
	    "Rate of Recipients edited per second."
    ::= { webMailEntry 70 }

wmRecipientsSavedTotal OBJECT-TYPE
    SYNTAX     Gauge32
    MAX-ACCESS read-only
    STATUS     current
    DESCRIPTION
	    "Total number of Recipients saved."
    ::= { webMailEntry 71 }

wmRecipientsSavedPerSec OBJECT-TYPE
    SYNTAX     Gauge32
    MAX-ACCESS read-only
    STATUS     current
    DESCRIPTION
	    "Rate of Recipients saved per second."
    ::= { webMailEntry 72 }

wmViewsOfCalendarsTotal OBJECT-TYPE
    SYNTAX     Gauge32
    MAX-ACCESS read-only
    STATUS     current
    DESCRIPTION
	    "Total number of Views of Calendars."
    ::= { webMailEntry 73 }

wmViewsOfCalendarsPerSec OBJECT-TYPE
    SYNTAX     Gauge32
    MAX-ACCESS read-only
    STATUS     current
    DESCRIPTION
	    "Rate of Views of Calendars per second."
    ::= { webMailEntry 74 }

wmViewsOfMailFoldersTotal OBJECT-TYPE
    SYNTAX     Gauge32
    MAX-ACCESS read-only
    STATUS     current
    DESCRIPTION
	    "Total number of Views of Mail Folders."
    ::= { webMailEntry 75 }

wmViewsOfMailFoldersPerSec OBJECT-TYPE
    SYNTAX     Gauge32
    MAX-ACCESS read-only
    STATUS     current
    DESCRIPTION
	    "Rate of Views of Mail Folders per second."
    ::= { webMailEntry 76 }

pop3Table OBJECT-TYPE
    SYNTAX     SEQUENCE OF Pop3Entry
    MAX-ACCESS not-accessible
    STATUS     current
    DESCRIPTION
	    "This object displays counters for the MS
	    Exchange POP3 Service."
    ::= { exchange 30 }

pop3Entry OBJECT-TYPE
    SYNTAX     Pop3Entry
    MAX-ACCESS not-accessible
    STATUS     current
    DESCRIPTION
	    "Performance information for one particular
	    instance of 'MSExchangePOP3' object."
    INDEX      { pop3Instance }
    ::= { pop3Table 1 }

Pop3Entry ::= SEQUENCE {
    pop3Instance InstanceName,
    pop3AUTHTotal Gauge32,
    pop3AUTHRate Gauge32,
    pop3AUTHFailures Gauge32,
    pop3PASSTotal Gauge32,
    pop3PASSRate Gauge32,
    pop3PASSFailures Gauge32,
    pop3QUITTotal Gauge32,
    pop3QUITRate Gauge32,
    pop3QUITFailures Gauge32,
    pop3STATTotal Gauge32,
    pop3STATRate Gauge32,
    pop3STATFailures Gauge32,
    pop3LISTTotal Gauge32,
    pop3LISTRate Gauge32,
    pop3LISTFailures Gauge32,
    pop3RETRTotal Gauge32,
    pop3RETRRate Gauge32,
    pop3RETRFailures Gauge32,
    pop3DELETotal Gauge32,
    pop3DELERate Gauge32,
    pop3DELEFailures Gauge32,
    pop3NOOPTotal Gauge32,
    pop3NOOPRate Gauge32,
    pop3NOOPFailures Gauge32,
    pop3RSETTotal Gauge32,
    pop3RSETRate Gauge32,
    pop3RSETFailures Gauge32,
    pop3TOPTotal Gauge32,
    pop3TOPRate Gauge32,
    pop3TOPFailures Gauge32,
    pop3UIDLTotal Gauge32,
    pop3UIDLRate Gauge32,
    pop3UIDLFailures Gauge32,
    pop3USERTotal Gauge32,
    pop3USERRate Gauge32,
    pop3USERFailures Gauge32,
    pop3LASTTotal Gauge32,
    pop3LASTRate Gauge32,
    pop3LASTFailures Gauge32,
    pop3InvalidCommands Gauge32,
    pop3InvalidCommandsRate Gauge32,
    pop3ConnectionsTotal Gauge32,
    pop3ConnectionsCurrent Gauge32,
    pop3ConnectionsFailed Gauge32,
    pop3ConnectionsRejected Gauge32,
    pop3CAPATotal Gauge32,
    pop3CAPARate Gauge32,
    pop3CAPAFailures Gauge32
}

pop3Instance OBJECT-TYPE
    SYNTAX     InstanceName
    MAX-ACCESS read-only
    STATUS     current
    DESCRIPTION
	    "Instance name."
    ::= { pop3Entry 1 }

pop3AUTHTotal OBJECT-TYPE
    SYNTAX     Gauge32
    MAX-ACCESS read-only
    STATUS     current
    DESCRIPTION
	    "Total number of AUTH commands received since
	    startup"
    ::= { pop3Entry 2 }

pop3AUTHRate OBJECT-TYPE
    SYNTAX     Gauge32
    MAX-ACCESS read-only
    STATUS     current
    DESCRIPTION
	    "Number of AUTH commands per sec"
    ::= { pop3Entry 3 }

pop3AUTHFailures OBJECT-TYPE
    SYNTAX     Gauge32
    MAX-ACCESS read-only
    STATUS     current
    DESCRIPTION
	    "Total number of AUTH failures since startup"
    ::= { pop3Entry 4 }

pop3PASSTotal OBJECT-TYPE
    SYNTAX     Gauge32
    MAX-ACCESS read-only
    STATUS     current
    DESCRIPTION
	    "Total number of PASS commands received since
	    startup"
    ::= { pop3Entry 5 }

pop3PASSRate OBJECT-TYPE
    SYNTAX     Gauge32
    MAX-ACCESS read-only
    STATUS     current
    DESCRIPTION
	    "Number of PASS commands per sec"
    ::= { pop3Entry 6 }

pop3PASSFailures OBJECT-TYPE
    SYNTAX     Gauge32
    MAX-ACCESS read-only
    STATUS     current
    DESCRIPTION
	    "Total number of PASS failures since startup"
    ::= { pop3Entry 7 }

pop3QUITTotal OBJECT-TYPE
    SYNTAX     Gauge32
    MAX-ACCESS read-only
    STATUS     current
    DESCRIPTION
	    "Total number of QUIT commands received since
	    startup"
    ::= { pop3Entry 8 }

pop3QUITRate OBJECT-TYPE
    SYNTAX     Gauge32
    MAX-ACCESS read-only
    STATUS     current
    DESCRIPTION
	    "Number of QUIT commands per sec"
    ::= { pop3Entry 9 }

pop3QUITFailures OBJECT-TYPE
    SYNTAX     Gauge32
    MAX-ACCESS read-only
    STATUS     current
    DESCRIPTION
	    "Total number of QUIT failures since startup"
    ::= { pop3Entry 10 }

pop3STATTotal OBJECT-TYPE
    SYNTAX     Gauge32
    MAX-ACCESS read-only
    STATUS     current
    DESCRIPTION
	    "Total number of STAT commands received since
	    startup"
    ::= { pop3Entry 11 }

pop3STATRate OBJECT-TYPE
    SYNTAX     Gauge32
    MAX-ACCESS read-only
    STATUS     current
    DESCRIPTION
	    "Number of STAT commands per sec"
    ::= { pop3Entry 12 }

pop3STATFailures OBJECT-TYPE
    SYNTAX     Gauge32
    MAX-ACCESS read-only
    STATUS     current
    DESCRIPTION
	    "Total number of STAT failures since startup"
    ::= { pop3Entry 13 }

pop3LISTTotal OBJECT-TYPE
    SYNTAX     Gauge32
    MAX-ACCESS read-only
    STATUS     current
    DESCRIPTION
	    "Total number of LIST commands received since
	    startup"
    ::= { pop3Entry 14 }

pop3LISTRate OBJECT-TYPE
    SYNTAX     Gauge32
    MAX-ACCESS read-only
    STATUS     current
    DESCRIPTION
	    "Number of LIST commands per sec"
    ::= { pop3Entry 15 }

pop3LISTFailures OBJECT-TYPE
    SYNTAX     Gauge32
    MAX-ACCESS read-only
    STATUS     current
    DESCRIPTION
	    "Total number of LIST failures since startup"
    ::= { pop3Entry 16 }

pop3RETRTotal OBJECT-TYPE
    SYNTAX     Gauge32
    MAX-ACCESS read-only
    STATUS     current
    DESCRIPTION
	    "Total number of RETR commands received since
	    startup"
    ::= { pop3Entry 17 }

pop3RETRRate OBJECT-TYPE
    SYNTAX     Gauge32
    MAX-ACCESS read-only
    STATUS     current
    DESCRIPTION
	    "Number of RETR commands per sec"
    ::= { pop3Entry 18 }

pop3RETRFailures OBJECT-TYPE
    SYNTAX     Gauge32
    MAX-ACCESS read-only
    STATUS     current
    DESCRIPTION
	    "Total number of RETR failures since startup"
    ::= { pop3Entry 19 }

pop3DELETotal OBJECT-TYPE
    SYNTAX     Gauge32
    MAX-ACCESS read-only
    STATUS     current
    DESCRIPTION
	    "Total number of DELE commands received since
	    startup"
    ::= { pop3Entry 20 }

pop3DELERate OBJECT-TYPE
    SYNTAX     Gauge32
    MAX-ACCESS read-only
    STATUS     current
    DESCRIPTION
	    "Number of DELE commands per sec"
    ::= { pop3Entry 21 }

pop3DELEFailures OBJECT-TYPE
    SYNTAX     Gauge32
    MAX-ACCESS read-only
    STATUS     current
    DESCRIPTION
	    "Total number of DELE failures since startup"
    ::= { pop3Entry 22 }

pop3NOOPTotal OBJECT-TYPE
    SYNTAX     Gauge32
    MAX-ACCESS read-only
    STATUS     current
    DESCRIPTION
	    "Total number of NOOP commands received since
	    startup"
    ::= { pop3Entry 23 }

pop3NOOPRate OBJECT-TYPE
    SYNTAX     Gauge32
    MAX-ACCESS read-only
    STATUS     current
    DESCRIPTION
	    "Number of NOOP commands per sec"
    ::= { pop3Entry 24 }

pop3NOOPFailures OBJECT-TYPE
    SYNTAX     Gauge32
    MAX-ACCESS read-only
    STATUS     current
    DESCRIPTION
	    "Total number of NOOP failures since startup"
    ::= { pop3Entry 25 }

pop3RSETTotal OBJECT-TYPE
    SYNTAX     Gauge32
    MAX-ACCESS read-only
    STATUS     current
    DESCRIPTION
	    "Total number of RSET commands received since
	    startup"
    ::= { pop3Entry 26 }

pop3RSETRate OBJECT-TYPE
    SYNTAX     Gauge32
    MAX-ACCESS read-only
    STATUS     current
    DESCRIPTION
	    "Number of RSET commands per sec"
    ::= { pop3Entry 27 }

pop3RSETFailures OBJECT-TYPE
    SYNTAX     Gauge32
    MAX-ACCESS read-only
    STATUS     current
    DESCRIPTION
	    "Total number of RSET failures since startup"
    ::= { pop3Entry 28 }

pop3TOPTotal OBJECT-TYPE
    SYNTAX     Gauge32
    MAX-ACCESS read-only
    STATUS     current
    DESCRIPTION
	    "Total number of TOP commands received since
	    startup"
    ::= { pop3Entry 29 }

pop3TOPRate OBJECT-TYPE
    SYNTAX     Gauge32
    MAX-ACCESS read-only
    STATUS     current
    DESCRIPTION
	    "Number of TOP commands per sec"
    ::= { pop3Entry 30 }

pop3TOPFailures OBJECT-TYPE
    SYNTAX     Gauge32
    MAX-ACCESS read-only
    STATUS     current
    DESCRIPTION
	    "Total number of TOP failures since startup"
    ::= { pop3Entry 31 }

pop3UIDLTotal OBJECT-TYPE
    SYNTAX     Gauge32
    MAX-ACCESS read-only
    STATUS     current
    DESCRIPTION
	    "Total number of UIDL commands received since
	    startup"
    ::= { pop3Entry 32 }

pop3UIDLRate OBJECT-TYPE
    SYNTAX     Gauge32
    MAX-ACCESS read-only
    STATUS     current
    DESCRIPTION
	    "Number of UIDL commands per sec"
    ::= { pop3Entry 33 }

pop3UIDLFailures OBJECT-TYPE
    SYNTAX     Gauge32
    MAX-ACCESS read-only
    STATUS     current
    DESCRIPTION
	    "Total number of UIDL failures since startup"
    ::= { pop3Entry 34 }

pop3USERTotal OBJECT-TYPE
    SYNTAX     Gauge32
    MAX-ACCESS read-only
    STATUS     current
    DESCRIPTION
	    "Total number of USER commands received since
	    startup"
    ::= { pop3Entry 35 }

pop3USERRate OBJECT-TYPE
    SYNTAX     Gauge32
    MAX-ACCESS read-only
    STATUS     current
    DESCRIPTION
	    "Number of USER commands per sec"
    ::= { pop3Entry 36 }

pop3USERFailures OBJECT-TYPE
    SYNTAX     Gauge32
    MAX-ACCESS read-only
    STATUS     current
    DESCRIPTION
	    "Total number of USER failures since startup"
    ::= { pop3Entry 37 }

pop3LASTTotal OBJECT-TYPE
    SYNTAX     Gauge32
    MAX-ACCESS read-only
    STATUS     current
    DESCRIPTION
	    "Total number of LAST commands received since
	    startup"
    ::= { pop3Entry 38 }

pop3LASTRate OBJECT-TYPE
    SYNTAX     Gauge32
    MAX-ACCESS read-only
    STATUS     current
    DESCRIPTION
	    "Number of LAST commands per sec"
    ::= { pop3Entry 39 }

pop3LASTFailures OBJECT-TYPE
    SYNTAX     Gauge32
    MAX-ACCESS read-only
    STATUS     current
    DESCRIPTION
	    "Total number of LAST failures since startup"
    ::= { pop3Entry 40 }

pop3InvalidCommands OBJECT-TYPE
    SYNTAX     Gauge32
    MAX-ACCESS read-only
    STATUS     current
    DESCRIPTION
	    "Total number of invalid commands since
	    startup"
    ::= { pop3Entry 41 }

pop3InvalidCommandsRate OBJECT-TYPE
    SYNTAX     Gauge32
    MAX-ACCESS read-only
    STATUS     current
    DESCRIPTION
	    "Number of invalid commands per second"
    ::= { pop3Entry 42 }

pop3ConnectionsTotal OBJECT-TYPE
    SYNTAX     Gauge32
    MAX-ACCESS read-only
    STATUS     current
    DESCRIPTION
	    "Total number of connections since startup"
    ::= { pop3Entry 43 }

pop3ConnectionsCurrent OBJECT-TYPE
    SYNTAX     Gauge32
    MAX-ACCESS read-only
    STATUS     current
    DESCRIPTION
	    "Total number of current connections"
    ::= { pop3Entry 44 }

pop3ConnectionsFailed OBJECT-TYPE
    SYNTAX     Gauge32
    MAX-ACCESS read-only
    STATUS     current
    DESCRIPTION
	    "Total number of failed connections since
	    startup"
    ::= { pop3Entry 45 }

pop3ConnectionsRejected OBJECT-TYPE
    SYNTAX     Gauge32
    MAX-ACCESS read-only
    STATUS     current
    DESCRIPTION
	    "Total number of rejected connections since
	    startup"
    ::= { pop3Entry 46 }

pop3CAPATotal OBJECT-TYPE
    SYNTAX     Gauge32
    MAX-ACCESS read-only
    STATUS     current
    DESCRIPTION
	    "Total number of CAPA commands received since
	    startup"
    ::= { pop3Entry 47 }

pop3CAPARate OBJECT-TYPE
    SYNTAX     Gauge32
    MAX-ACCESS read-only
    STATUS     current
    DESCRIPTION
	    "Number of CAPA commands per sec"
    ::= { pop3Entry 48 }

pop3CAPAFailures OBJECT-TYPE
    SYNTAX     Gauge32
    MAX-ACCESS read-only
    STATUS     current
    DESCRIPTION
	    "Total number of CAPA failures since startup"
    ::= { pop3Entry 49 }

transportFilterSinkTable OBJECT-TYPE
    SYNTAX     SEQUENCE OF TransportFilterSinkEntry
    MAX-ACCESS not-accessible
    STATUS     current
    DESCRIPTION
	    "This object represents global counters for the
	    Exchange Transport Filter Sink. These counters
	    monitor connection filtering, recipient
	    filtering, and sender filtering."
    ::= { exchange 31 }

transportFilterSinkEntry OBJECT-TYPE
    SYNTAX     TransportFilterSinkEntry
    MAX-ACCESS not-accessible
    STATUS     current
    DESCRIPTION
	    "Performance information for one particular
	    instance of 'MSExchangeTransport Filter Sink'
	    object."
    INDEX      { tfsInstance }
    ::= { transportFilterSinkTable 1 }

TransportFilterSinkEntry ::= SEQUENCE {
    tfsInstance InstanceName,
    tfsConnsRejByBlockListProviders Gauge32,
    tfsConnsRejByBlockListProvPerSec Gauge32,
    tfsRcptsInConnFilterExceptList Gauge32,
    tfsRcptsInConnFiltExptListPerSec Gauge32,
    tfsConnsRejectByDenyList Gauge32,
    tfsConnsRejectByDenyListPerSec Gauge32,
    tfsConnsAcceptByAcceptList Gauge32,
    tfsConnsAcceptByAcceptListPerSec Gauge32,
    tfsRcptsRejectByRcptFilter Gauge32,
    tfsRcptsRejectByRcptFilterPerSec Gauge32,
    tfsRcptsRejectByDirectoryLookups Gauge32,
    tfsRcptsRejectByDirLookupsPerSec Gauge32,
    tfsMsgsFilterBySenderFilter Gauge32,
    tfsMsgsFilterBySenderFiltrPerSec Gauge32,
    tfsMsgsFilterDueToBlankSender Gauge32,
    tfsMsgsFilterDueToBlnkSndrPerSec Gauge32,
    tfsBlockListDNSQueryIssue Gauge32,
    tfsBlockListDNSQueryIssuePerSec Gauge32,
    tfsFailedBlockListDNSQuery Gauge32,
    tfsFailedBlockListDNSQueryPerSec Gauge32,
    tfsDirectoryLookupsIssue Gauge32,
    tfsDirectoryLookupsIssuePerSec Gauge32,
    tfsFailedDirectoryLookups Gauge32,
    tfsFailedDirectoryLookupsPerSec Gauge32
}

tfsInstance OBJECT-TYPE
    SYNTAX     InstanceName
    MAX-ACCESS read-only
    STATUS     current
    DESCRIPTION
	    "Instance name."
    ::= { transportFilterSinkEntry 1 }

tfsConnsRejByBlockListProviders OBJECT-TYPE
    SYNTAX     Gauge32
    MAX-ACCESS read-only
    STATUS     current
    DESCRIPTION
	    "Total number of connections rejected by block
	    list connection filtering rules."
    ::= { transportFilterSinkEntry 2 }

tfsConnsRejByBlockListProvPerSec OBJECT-TYPE
    SYNTAX     Gauge32
    MAX-ACCESS read-only
    STATUS     current
    DESCRIPTION
	    "Total number of connections rejected per
	    second by block list connection filtering."
    ::= { transportFilterSinkEntry 3 }

tfsRcptsInConnFilterExceptList OBJECT-TYPE
    SYNTAX     Gauge32
    MAX-ACCESS read-only
    STATUS     current
    DESCRIPTION
	    "Total number of recipients in the exception
	    list for block list connection filtering
	    rules."
    ::= { transportFilterSinkEntry 4 }

tfsRcptsInConnFiltExptListPerSec OBJECT-TYPE
    SYNTAX     Gauge32
    MAX-ACCESS read-only
    STATUS     current
    DESCRIPTION
	    "Total number of recipients per second that
	    were not blocked by connection filtering rules
	    because they were configured in the exception
	    list for block list connection filtering
	    rules."
    ::= { transportFilterSinkEntry 5 }

tfsConnsRejectByDenyList OBJECT-TYPE
    SYNTAX     Gauge32
    MAX-ACCESS read-only
    STATUS     current
    DESCRIPTION
	    "Total number of connections denied because the
	    connecting IP address was configured on the
	    global deny list."
    ::= { transportFilterSinkEntry 6 }

tfsConnsRejectByDenyListPerSec OBJECT-TYPE
    SYNTAX     Gauge32
    MAX-ACCESS read-only
    STATUS     current
    DESCRIPTION
	    "Total number of connections denied per second
	    because the connecting IP address was
	    configured on the global deny list."
    ::= { transportFilterSinkEntry 7 }

tfsConnsAcceptByAcceptList OBJECT-TYPE
    SYNTAX     Gauge32
    MAX-ACCESS read-only
    STATUS     current
    DESCRIPTION
	    "Total number of connections accepted because
	    the connecting IP address was configured on the
	    global accept list."
    ::= { transportFilterSinkEntry 8 }

tfsConnsAcceptByAcceptListPerSec OBJECT-TYPE
    SYNTAX     Gauge32
    MAX-ACCESS read-only
    STATUS     current
    DESCRIPTION
	    "Total number of connections accepted per
	    second because the connecting IP was configured
	    on the global accept list."
    ::= { transportFilterSinkEntry 9 }

tfsRcptsRejectByRcptFilter OBJECT-TYPE
    SYNTAX     Gauge32
    MAX-ACCESS read-only
    STATUS     current
    DESCRIPTION
	    "Total number of recipients rejected by
	    recipient filtering because the recipient was
	    listed as a blocked recipient."
    ::= { transportFilterSinkEntry 10 }

tfsRcptsRejectByRcptFilterPerSec OBJECT-TYPE
    SYNTAX     Gauge32
    MAX-ACCESS read-only
    STATUS     current
    DESCRIPTION
	    "Total number of recipients rejected per second
	    by	recipient filtering."
    ::= { transportFilterSinkEntry 11 }

tfsRcptsRejectByDirectoryLookups OBJECT-TYPE
    SYNTAX     Gauge32
    MAX-ACCESS read-only
    STATUS     current
    DESCRIPTION
	    "Total number of recipients rejected because
	    the recipients did not exist in Active
	    Directory. "
    ::= { transportFilterSinkEntry 12 }

tfsRcptsRejectByDirLookupsPerSec OBJECT-TYPE
    SYNTAX     Gauge32
    MAX-ACCESS read-only
    STATUS     current
    DESCRIPTION
	    "Total number of recipients rejected per second
	    because the recipients did not exist in Active
	    Directory."
    ::= { transportFilterSinkEntry 13 }

tfsMsgsFilterBySenderFilter OBJECT-TYPE
    SYNTAX     Gauge32
    MAX-ACCESS read-only
    STATUS     current
    DESCRIPTION
	    "Total number of messages filtered by sender
	    filtering."
    ::= { transportFilterSinkEntry 14 }

tfsMsgsFilterBySenderFiltrPerSec OBJECT-TYPE
    SYNTAX     Gauge32
    MAX-ACCESS read-only
    STATUS     current
    DESCRIPTION
	    "Total number of messages filtered per second
	    by sender filtering."
    ::= { transportFilterSinkEntry 15 }

tfsMsgsFilterDueToBlankSender OBJECT-TYPE
    SYNTAX     Gauge32
    MAX-ACCESS read-only
    STATUS     current
    DESCRIPTION
	    "Total number of messages filtered because the
	    messages contained a blank sender address."
    ::= { transportFilterSinkEntry 16 }

tfsMsgsFilterDueToBlnkSndrPerSec OBJECT-TYPE
    SYNTAX     Gauge32
    MAX-ACCESS read-only
    STATUS     current
    DESCRIPTION
	    "Total number of messages filtered per second
	    because the message contained a blank sender
	    address."
    ::= { transportFilterSinkEntry 17 }

tfsBlockListDNSQueryIssue OBJECT-TYPE
    SYNTAX     Gauge32
    MAX-ACCESS read-only
    STATUS     current
    DESCRIPTION
	    "Total number of block list DNS queries issued
	    for block list connection filtering."
    ::= { transportFilterSinkEntry 18 }

tfsBlockListDNSQueryIssuePerSec OBJECT-TYPE
    SYNTAX     Gauge32
    MAX-ACCESS read-only
    STATUS     current
    DESCRIPTION
	    "Total number of block list DNS queries issued
	    per second for block list connection
	    filtering."
    ::= { transportFilterSinkEntry 19 }

tfsFailedBlockListDNSQuery OBJECT-TYPE
    SYNTAX     Gauge32
    MAX-ACCESS read-only
    STATUS     current
    DESCRIPTION
	    "Total number of failed block list DNS queries
	    issued for block list connection filtering.
	    These failures indicate connection timeouts, an
	    inability to connect to the block list provider
	    or DNS errors. Validate the configuration of
	    your connection filterin"
    ::= { transportFilterSinkEntry 20 }

tfsFailedBlockListDNSQueryPerSec OBJECT-TYPE
    SYNTAX     Gauge32
    MAX-ACCESS read-only
    STATUS     current
    DESCRIPTION
	    "Total number of failed block list DNS queries
	    issued per second for block list connection
	    filtering."
    ::= { transportFilterSinkEntry 21 }

tfsDirectoryLookupsIssue OBJECT-TYPE
    SYNTAX     Gauge32
    MAX-ACCESS read-only
    STATUS     current
    DESCRIPTION
	    "Total number of directory lookups in Active
	    Directory issued by recipient filtering."
    ::= { transportFilterSinkEntry 22 }

tfsDirectoryLookupsIssuePerSec OBJECT-TYPE
    SYNTAX     Gauge32
    MAX-ACCESS read-only
    STATUS     current
    DESCRIPTION
	    "Total number of directory lookups in Active
	    Directory issued per second by recipient
	    filtering."
    ::= { transportFilterSinkEntry 23 }

tfsFailedDirectoryLookups OBJECT-TYPE
    SYNTAX     Gauge32
    MAX-ACCESS read-only
    STATUS     current
    DESCRIPTION
	    "Total number of directory lookups that failed
	    to contact Active Directory."
    ::= { transportFilterSinkEntry 24 }

tfsFailedDirectoryLookupsPerSec OBJECT-TYPE
    SYNTAX     Gauge32
    MAX-ACCESS read-only
    STATUS     current
    DESCRIPTION
	    "Total number of directory lookups issued per
	    second that failed to contact Active
	    Directory."
    ::= { transportFilterSinkEntry 25 }

intelligentMessageFilterTable OBJECT-TYPE
    SYNTAX     SEQUENCE OF IntelligentMessageFilterEntry
    MAX-ACCESS not-accessible
    STATUS     current
    DESCRIPTION
	    "This object represents global counters for
	    Microsoft Exchange Intelligent Message Filter."
    ::= { exchange 32 }

intelligentMessageFilterEntry OBJECT-TYPE
    SYNTAX     IntelligentMessageFilterEntry
    MAX-ACCESS not-accessible
    STATUS     current
    DESCRIPTION
	    "Performance information for one particular
	    instance of 'MSExchange Intelligent Message
	    Filter' object."
    INDEX      { imfInstance }
    ::= { intelligentMessageFilterTable 1 }

IntelligentMessageFilterEntry ::= SEQUENCE {
    imfInstance InstanceName,
    imfPercentUCEMsgsScanPrev30Min Gauge32,
    imfPercentUCEOutTotalMsgsScanned Gauge32,
    imfMsgsScannedForUCEPerSec Gauge32,
    imfTotalMsgsAssignedSCLRating0 Gauge32,
    imfTotalMsgsAssignedSCLRating1 Gauge32,
    imfTotalMsgsAssignedSCLRating2 Gauge32,
    imfTotalMsgsAssignedSCLRating3 Gauge32,
    imfTotalMsgsAssignedSCLRating4 Gauge32,
    imfTotalMsgsAssignedSCLRating5 Gauge32,
    imfTotalMsgsAssignedSCLRating6 Gauge32,
    imfTotalMsgsAssignedSCLRating7 Gauge32,
    imfTotalMsgsAssignedSCLRating8 Gauge32,
    imfTotalMsgsAssignedSCLRating9 Gauge32,
    imfTotalMsgsScannedForUCE Gauge32,
    imfTotalUCEMsgsActedUpon Gauge32,
    imfUCEMsgsActedUponPerSec Gauge32
}

imfInstance OBJECT-TYPE
    SYNTAX     InstanceName
    MAX-ACCESS read-only
    STATUS     current
    DESCRIPTION
	    "Instance name."
    ::= { intelligentMessageFilterEntry 1 }

imfPercentUCEMsgsScanPrev30Min OBJECT-TYPE
    SYNTAX     Gauge32
    MAX-ACCESS read-only
    STATUS     current
    DESCRIPTION
	    "The percentage of the number of messages
	    scanned in the previous 30 minutes that were
	    determined to be Unsolicited Commercial Email
	    (UCE)"
    ::= { intelligentMessageFilterEntry 2 }

imfPercentUCEOutTotalMsgsScanned OBJECT-TYPE
    SYNTAX     Gauge32
    MAX-ACCESS read-only
    STATUS     current
    DESCRIPTION
	    "The percentage of the total number of messages
	    scanned that were determined to be Unsolicited
	    Commercial Email (UCE)"
    ::= { intelligentMessageFilterEntry 3 }

imfMsgsScannedForUCEPerSec OBJECT-TYPE
    SYNTAX     Gauge32
    MAX-ACCESS read-only
    STATUS     current
    DESCRIPTION
	    "The number of messages scanned per second by
	    Content Filtering."
    ::= { intelligentMessageFilterEntry 4 }

imfTotalMsgsAssignedSCLRating0 OBJECT-TYPE
    SYNTAX     Gauge32
    MAX-ACCESS read-only
    STATUS     current
    DESCRIPTION
	    "The total number of messages scanned by
	    Intelligent Message Filter and assigned a spam
	    confidence level (SCL) rating of 0"
    ::= { intelligentMessageFilterEntry 5 }

imfTotalMsgsAssignedSCLRating1 OBJECT-TYPE
    SYNTAX     Gauge32
    MAX-ACCESS read-only
    STATUS     current
    DESCRIPTION
	    "The total number of messages scanned by
	    Intelligent Message Filter and assigned a spam
	    confidence level (SCL) rating of 1"
    ::= { intelligentMessageFilterEntry 6 }

imfTotalMsgsAssignedSCLRating2 OBJECT-TYPE
    SYNTAX     Gauge32
    MAX-ACCESS read-only
    STATUS     current
    DESCRIPTION
	    "The total number of messages scanned by
	    Intelligent Message Filter and assigned a spam
	    confidence level (SCL) rating of 2"
    ::= { intelligentMessageFilterEntry 7 }

imfTotalMsgsAssignedSCLRating3 OBJECT-TYPE
    SYNTAX     Gauge32
    MAX-ACCESS read-only
    STATUS     current
    DESCRIPTION
	    "The total number of messages scanned by
	    Intelligent Message Filter and assigned a spam
	    confidence level (SCL) rating of 3"
    ::= { intelligentMessageFilterEntry 8 }

imfTotalMsgsAssignedSCLRating4 OBJECT-TYPE
    SYNTAX     Gauge32
    MAX-ACCESS read-only
    STATUS     current
    DESCRIPTION
	    "The total number of messages scanned by
	    Intelligent Message Filter and assigned a spam
	    confidence level (SCL) rating of 4"
    ::= { intelligentMessageFilterEntry 9 }

imfTotalMsgsAssignedSCLRating5 OBJECT-TYPE
    SYNTAX     Gauge32
    MAX-ACCESS read-only
    STATUS     current
    DESCRIPTION
	    "The total number of messages scanned by
	    Intelligent Message Filter and assigned a spam
	    confidence level (SCL) rating of 5"
    ::= { intelligentMessageFilterEntry 10 }

imfTotalMsgsAssignedSCLRating6 OBJECT-TYPE
    SYNTAX     Gauge32
    MAX-ACCESS read-only
    STATUS     current
    DESCRIPTION
	    "The total number of messages scanned by
	    Intelligent Message Filter and assigned a spam
	    confidence level (SCL) rating of 6"
    ::= { intelligentMessageFilterEntry 11 }

imfTotalMsgsAssignedSCLRating7 OBJECT-TYPE
    SYNTAX     Gauge32
    MAX-ACCESS read-only
    STATUS     current
    DESCRIPTION
	    "The total number of messages scanned by
	    Intelligent Message Filter and assigned a spam
	    confidence level (SCL) rating of 7"
    ::= { intelligentMessageFilterEntry 12 }

imfTotalMsgsAssignedSCLRating8 OBJECT-TYPE
    SYNTAX     Gauge32
    MAX-ACCESS read-only
    STATUS     current
    DESCRIPTION
	    "The total number of messages scanned by
	    Intelligent Message Filter and assigned a spam
	    confidence level (SCL) rating of 8"
    ::= { intelligentMessageFilterEntry 13 }

imfTotalMsgsAssignedSCLRating9 OBJECT-TYPE
    SYNTAX     Gauge32
    MAX-ACCESS read-only
    STATUS     current
    DESCRIPTION
	    "The total number of messages scanned by
	    Intelligent Message Filter and assigned a spam
	    confidence level (SCL) rating of 9"
    ::= { intelligentMessageFilterEntry 14 }

imfTotalMsgsScannedForUCE OBJECT-TYPE
    SYNTAX     Gauge32
    MAX-ACCESS read-only
    STATUS     current
    DESCRIPTION
	    "The total number of messages scanned by
	    Content Filtering."
    ::= { intelligentMessageFilterEntry 15 }

imfTotalUCEMsgsActedUpon OBJECT-TYPE
    SYNTAX     Gauge32
    MAX-ACCESS read-only
    STATUS     current
    DESCRIPTION
	    "The total number of messages marked as
	    Unsolicited Commercial Email (UCE) and acted
	    upon based on the gateway threshold."
    ::= { intelligentMessageFilterEntry 16 }

imfUCEMsgsActedUponPerSec OBJECT-TYPE
    SYNTAX     Gauge32
    MAX-ACCESS read-only
    STATUS     current
    DESCRIPTION
	    "The number of messages that were marked as
	    Unsolicited Commercial Email (UCE) and acted
	    upon based on the gateway threshold, per
	    second."
    ::= { intelligentMessageFilterEntry 17 }

END
