SECURITYMGREXT-MIB

   --FORCE-INCLUDE <mib.h>
   --FORCE-INCLUDE <snmpdefs.h>
   --FORCE-INCLUDE <snmpstat.h>
   --FORCE-INCLUDE "mibproto.h"
 
	DEFINITIONS ::= BEGIN

	IMPORTS
	MODULE-IDENTITY, OBJECT-TYPE
			FROM SNMPv2-SMI
		DisplayString, RowStatus
			FROM SNMPv2-TC
		securityMgrExt
			FROM APENT-MIB;

--  SECEXT MIB

securityMgrExtMib MODULE-IDENTITY
	LAST-UPDATED "9707202000Z" -- Wed July 20 20:00:00 EST 1997
	ORGANIZATION "ArrowPoint Communications Inc."
	CONTACT-INFO
	"                       Steve Colby
	Postal:               ArrowPoint Communications Inc.
				                 50 Nagog Park
				                 Acton, Massachusetts 01720
	   Tel:                   +1 978-206-3000  option 1
	   E-Mail:                support@arrowpoint.com"
	DESCRIPTION
		"This MIB module describes the ArrowPoint Communications
		MIB objects for Network Security."
	::= { securityMgrExt 1 }

-- Security Manager Globals

apSecurityMgrConsoleAuthType OBJECT-TYPE
	SYNTAX  INTEGER {
		enable(1)                                  ,
		radius(2)                                   ,
		none(3)                                   ,
		radius-enable(4)                                         ,
		enable-radius(5)                                                  ,
		enable-none(6)                                                ,
		radius-none(7)                                        ,
		radius-enable-none(8)                                                 ,
		enable-radius-none(9)                                            
	}
	MAX-ACCESS   read-write
	STATUS   current
	DESCRIPTION
		"This variable specifies the type of authentication used to for
  		console users."
	DEFVAL { enable }
	::= { securityMgrExt 2 }

apSecurityMgrVirtualAuthType OBJECT-TYPE
	SYNTAX  INTEGER {
		enable(1)                                  ,
		radius(2)                                   ,
		none(3)                                   ,
		radius-enable(4)                                         ,
		enable-radius(5)                                                  ,
		enable-none(6)                                                ,
		radius-none(7)                                        ,
		radius-enable-none(8)                                                 ,
		enable-radius-none(9)                                            ,
		disallowed(10)                             
	}
	MAX-ACCESS   read-write
	STATUS   current
	DESCRIPTION
		"This variable specifies the type of authentication used to for
		console users."
	DEFVAL { enable }
	::= { securityMgrExt 3 }

apSecurityMgrUsernameTable OBJECT-TYPE
	SYNTAX	SEQUENCE OF APSecurityMgrUsernameEntry
	MAX-ACCESS  not-accessible
	STATUS	current
	DESCRIPTION
		"This is the table of username and password pairs used for 
		local authentication."
	::= { securityMgrExt 4 }

apSecurityMgrUsernameEntry OBJECT-TYPE
	SYNTAX	APSecurityMgrUsernameEntry
	MAX-ACCESS  not-accessible
	STATUS	current
	DESCRIPTION
    	"The Username table is indexed by username."
	INDEX   { apSecurityMgrUsername }
	::= { apSecurityMgrUsernameTable 1 }

APSecurityMgrUsernameEntry ::= SEQUENCE {
	apSecurityMgrUsername
		DisplayString,
	apSecurityMgrPassword
		DisplayString,
	apSecurityMgrEncryptedPassword
		DisplayString,
	apSecurityMgrUserPriviledgeLevel
		INTEGER,
	apSecurityMgrStatus
		RowStatus
	}

apSecurityMgrUsername  OBJECT-TYPE
	SYNTAX	DisplayString (SIZE (1..16))
	MAX-ACCESS  read-create
	STATUS  current
	DESCRIPTION
    	"The local username."
	::= { apSecurityMgrUsernameEntry 1 }

apSecurityMgrPassword OBJECT-TYPE
	SYNTAX	DisplayString (SIZE (6..16))
	MAX-ACCESS  read-create
	STATUS  current
	DESCRIPTION
    	"The local password."
	::= { apSecurityMgrUsernameEntry 2 }

apSecurityMgrEncryptedPassword OBJECT-TYPE
	SYNTAX	DisplayString (SIZE (6..64))
	MAX-ACCESS  read-create
	STATUS  current
	DESCRIPTION
    	"The encrypted local password."
	::= { apSecurityMgrUsernameEntry 3 }

apSecurityMgrUserPriviledgeLevel OBJECT-TYPE
	SYNTAX  INTEGER {
		non-priviledge(1),
		priviledge(2)
	}
	MAX-ACCESS  read-create
	STATUS  current
	DESCRIPTION
    	"The priviledge level for this user."
	DEFVAL { priviledge }
	::= { apSecurityMgrUsernameEntry 4 }

apSecurityMgrStatus  OBJECT-TYPE
	SYNTAX	RowStatus
	MAX-ACCESS  read-create
	STATUS  current
	DESCRIPTION
 	  	"This object is used to create and destroy a local username
		 entry. This rowstatus object only supports CreateAndGo and 
	     Destroy."
	::= { apSecurityMgrUsernameEntry 5 }

	END
