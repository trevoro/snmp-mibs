--
--				"@(#)swtrap.smiv1 99/04/23"
--
-- Enterprise Specific Traps for Fibre Channel Switch (sw).
--		Version 2.0
--
-- This is specified based on RFC1215.
-- This specification is for reference in configuring your SNMP Station only.
-- DO NOT compile this file.
--
-- See also V2_0SW.mib (version 2.0 of SW-MIB).

--
SW-TRAP DEFINITIONS ::= BEGIN
  IMPORTS
	enterprises
		FROM RFC1155-SMI
	swDiagResult,
	swSensorStatus, swSensorIndex, swSensorType, swSensorValue,
	swSensorInfo,
	swFCPortOpStatus, swFCPortIndex,
	swEventIndex, swEventTimeInfo, swEventLevel, swEventRepeatCount,
	swEventDescr
		FROM SW-MIB
	TRAP-TYPE
		FROM RFC1215;

  --
  -- sw Traps
  --

  swFault		TRAP-TYPE
	ENTERPRISE	sw
	VARIABLES	{ swDiagResult }
	DESCRIPTION	"A swFault(1) is generated whenever the diagnostics
		detects a fault with the switch."
	--#TYPE		"Switch is faulty."
	--#SUMMARY	"Faulty reason: %d"
	--#ARGUMENTS	{ 0 }
	--#SEVERITY	CRITICAL
	--#TIMEINDEX	1
	--#STATE	NONOPERATIONAL
	::= 1

  swSensorScn	TRAP-TYPE
	ENTERPRISE	sw
	VARIABLES	{ swSensorStatus, swSensorIndex, swSensorType,
			  swSensorValue, swSensorInfo }
	DESCRIPTION	"A swSensorScn(2) is generated whenever an
		environment sensor changes its operational state. For instance,
		a fan stop working. The VarBind in the Trap Data Unit shall
		contain the corresponding instance of the sensor
		status, sensor index, sensor type, sensor value (reading)
		and sensor information. Note that the sensor information
		contains the type of sensor and its number in textual format."
	--#TYPE		"A sensor (temperature, fan, etc.) changed its operational state."
	--#SUMMARY	"%s: is currently in state %d"
	--#ARGUMENTS	{ 4, 0 }
	--#SEVERITY	INFORMATIONAL
	--#TIMEINDEX	1
	--#STATE	OPERATIONAL
	::= 2

   swFCPortScn		TRAP-TYPE
	ENTERPRISE	sw
	VARIABLES	{ swFCPortOpStatus, swFCPortIndex }
	DESCRIPTION	"A swFCPortScn(3) is generated whenever an FC_Port
		changes its operational state. For instance, the FC_Port
		goes from on-line to offline. The VarBind in the Trap Data
		Unit shall contain the corresponding instance of the
		FC_Port's operational status and index."
	--#TYPE		"A Fibre Channel Port changed its operational state."
	--#SUMMARY	"Port Index %d changed state to %d"
	--#ARGUMENTS	{ 1, 0 }
	--#SEVERITY	INFORMATIONAL
	--#TIMEINDEX	1
	--#STATE	OPERATIONAL
	::= 3

   swEventTrap           TRAP-TYPE
        ENTERPRISE      sw
        VARIABLES       { swEventIndex, swEventTimeInfo, swEventLevel,
                          swEventRepeatCount, swEventDescr }
        DESCRIPTION     "This trap is generated when an event whose
                level at or below swEventTrapLevel occurs."
	--#TYPE		"A firmware event has been logged"
	--#SUMMARY	"Event %d: %s (severity level %d) - %s"
	--#ARGUMENTS	{ 0, 1, 2, 4 }
	--#SEVERITY	INFORMATIONAL
	--#TIMEINDEX	1
	--#STATE	OPERATIONAL
	::= 4

   -- end of Enterprise Specific Traps for Fibre Channel Switch (sw)

END
