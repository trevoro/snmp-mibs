-- extracted from draft-stephan-pce-disc-mib-00.txt
-- at Tue Oct 17 06:07:40 2006

   PCE-DISC-STD-MIB DEFINITIONS ::= BEGIN

   IMPORTS
      MODULE-IDENTITY, OBJECT-TYPE, NOTIFICATION-TYPE,
      Counter32, Unsigned32, Gauge32, Integer32, IpAddress,
      experimental FROM SNMPv2-SMI
      RowStatus,
      TEXTUAL-CONVENTION,
      TimeStamp,
      TruthValue

         FROM SNMPv2-TC
      Ipv6Address
         FROM IPV6-TC
      MODULE-COMPLIANCE,
      OBJECT-GROUP,
      NOTIFICATION-GROUP
         FROM SNMPv2-CONF
      AddressFamilyNumbers
         FROM IANA-ADDRESS-FAMILY-NUMBERS-MIB
      IANAipRouteProtocol
         FROM IANA-RTPROTO-MIB;

   pceDiscStdMIB MODULE-IDENTITY
      LAST-UPDATED "200610150000Z" -- October 15, 2006
      ORGANIZATION "Path Computation Element (PCE) Working Group"
      CONTACT-INFO "
         Stephan Emile
         France Telecom DR&D
      Email: emile.stephan@orange-ft.com
      Email comments directly to the PCE WG Mailing List at pce@ietf.org
      WG-URL: http://www.ietf.org/html.charters/pce-charter.html
      "
   DESCRIPTION
      "This MIB module defines a collection of objects for managing Path
      Computation Elements (PCEs) Discovery."
   ::= { experimental 10000 } -- Temporary node ( for smilint)

   -- Textual Conventions used in this MIB module --

   -- Defined in PCE TC STD MIB

   -- Currently duplicated for Smilint

   PceRoutingDomainID ::= TEXTUAL-CONVENTION
      STATUS current
      DESCRIPTION
         ""
      SYNTAX OCTET STRING (SIZE (0..20))

   -- Notification --

   pceDiscNotifications OBJECT IDENTIFIER ::= { pceDiscStdMIB 0 }

   -- empty for now

   pceDiscMIBObjects OBJECT IDENTIFIER ::= { pceDiscStdMIB 1 }

   pceDiscoveryObjects OBJECT IDENTIFIER ::= { pceDiscMIBObjects 1 }

   pceDiscoveryAdminStatus OBJECT-TYPE
      SYNTAX INTEGER {
         enabled(1),
         disabled(2)
      }
      MAX-ACCESS read-write
      STATUS current
      DESCRIPTION
         "Setting this object to disabled(2) disables the discovery of
         PCEs.  Once disabled, The discovery must be explicitly enabled
         to restore discovery of PCEs.  Setting this object to
         enabled(1) enables the discovery of PCEs."
      ::= { pceDiscoveryObjects 1 }

   pceDiscoveryKnowPCEs OBJECT-TYPE
      SYNTAX Counter32
      MAX-ACCESS read-only
      STATUS current
      DESCRIPTION
         "The number of PCEs the PCC is potentially in relation with.
         This includes PCE manually declared and active PCEs"
      ::= { pceDiscoveryObjects 2 }

   pceDiscoveryActivePCEs OBJECT-TYPE
      SYNTAX Counter32
      MAX-ACCESS read-only
      STATUS current
      DESCRIPTION
         "The number of active PCEs.
         The detection of the activity a a PCE depends on the nature
         discovery mechanism.
         PCE discovered using PCED information received:
            The relation between the PCC and a PCE is active while the
            PCE discovery protocol maintains a communication between the
            PCC and this PCE.
         PCE Manually declared:
            The relation between the PCC and a PCE is active and the
            discovery mechanism is implementation specific;
         "
      ::= { pceDiscoveryObjects 3 }

   pceDiscoveryTable OBJECT-TYPE
      SYNTAX SEQUENCE OF PceDiscoveryEntry
      MAX-ACCESS not-accessible
      STATUS current
      DESCRIPTION
         "Information describing the PCEs discovered."
      ::= { pceDiscoveryObjects 4 }

   pceDiscoveryEntry OBJECT-TYPE
      SYNTAX PceDiscoveryEntry
      MAX-ACCESS not-accessible
      STATUS current
      DESCRIPTION
         "Information describing general information of each PCE
         discovered."
      INDEX { pceDiscoveryIndex }
      ::= { pceDiscoveryTable 1 }

   PceDiscoveryEntry ::= SEQUENCE {
      pceDiscoveryIndex Integer32,
      pceDiscoveryMechanism IANAipRouteProtocol,
      pceDiscoveryIPv4Address IpAddress,
      pceDiscoveryIPv6Address Ipv6Address,
      pceDiscoveryTime TimeStamp,
      pceDiscoveryLastUpdated TimeStamp,
      pceDiscoveryCongestion TruthValue,
      pceDiscoveryCongestionDuration Unsigned32
   }

   pceDiscoveryIndex OBJECT-TYPE
      SYNTAX Integer32 (1..2147483647)
      MAX-ACCESS not-accessible
      STATUS current
      DESCRIPTION
         "This object identifies locally the PCE for which this entry
         contains information."
      ::= { pceDiscoveryEntry 1 }

   pceDiscoveryMechanism OBJECT-TYPE
      SYNTAX IANAipRouteProtocol
      MAX-ACCESS read-only
      STATUS current
      DESCRIPTION
         "This object identifies the type of discovery mechanism used to
         discover the PCE.
         The discovery mechanisms covered by PCE WG at the time of the
         specification are :
            other (1), --not specified
            local (2), -- local interface
            isIs (9), -- Dual IS-IS
            ospf (13), -- Open Shortest Path First
            bgp (14), -- Border Gateway Protocol
         It does not preclude the usage of another routing protocol
         numbered by this IANAipRouteProtocol
         "
      ::= { pceDiscoveryEntry 2 }

   pceDiscoveryIPv4Address OBJECT-TYPE
      SYNTAX IpAddress
      MAX-ACCESS read-only
      STATUS current
      DESCRIPTION
         "This object is the IP address to be used to reach the PCE.  It
         corresponds to the PCED PCE-ADDRESS.
         .
         A value of 0.0.0.0 indicates the absence of this address."
      ::= { pceDiscoveryEntry 3 }

   pceDiscoveryIPv6Address OBJECT-TYPE
      SYNTAX Ipv6Address
      MAX-ACCESS read-only
      STATUS current
      DESCRIPTION
         "This object is the IPv6 address to be used to reach the PCE.
         It corresponds to the PCED PCE-ADDRESS.
         A value of ::0 indicates the absence of this address."
      ::= { pceDiscoveryEntry 4 }

   pceDiscoveryTime OBJECT-TYPE
      SYNTAX TimeStamp
      MAX-ACCESS read-only
      STATUS current
      DESCRIPTION
         "The value of sysUpTime at the time this entry was created.
         local entry: the value of sysUpTime at the time the PCC
         restarted."
      ::= { pceDiscoveryEntry 5 }

   pceDiscoveryLastUpdated OBJECT-TYPE
      SYNTAX TimeStamp
      MAX-ACCESS read-only
      STATUS current
      DESCRIPTION
         "The value of sysUpTime at the time this entry was last
         updated.
         Static entry: if the entry values keep unchanged since the re-
         initialization of the PCC then this object contains a zero
         value."
      ::= { pceDiscoveryEntry 6 }

   pceDiscoveryCongestion OBJECT-TYPE
      SYNTAX TruthValue
      MAX-ACCESS read-only
      STATUS current
      DESCRIPTION
         "This object indicates whether a PCE experiences a processing
         congestion state or not.
         "
      ::= { pceDiscoveryEntry 7 }

   pceDiscoveryCongestionDuration OBJECT-TYPE
      SYNTAX Unsigned32
      MAX-ACCESS read-only
      STATUS current
      DESCRIPTION
         "This object specifies, in seconds, the congestion duration.
         When the value of pceDiscoveryCongestion is 'false' then this
         objet MUST be to '0'"
      ::= { pceDiscoveryEntry 8 }

   pceDiscCapabilityObjects OBJECT IDENTIFIER ::= { pceDiscMIBObjects 2
   }

   --

   -- PCE-PATHSCOPE informations elements

   --

   pceDiscCapPathScopeTable OBJECT-TYPE
      SYNTAX SEQUENCE OF PceDiscCapPathScopeEntry
      MAX-ACCESS not-accessible
      STATUS current
      DESCRIPTION
         "Information describing the capacity of the PCEs discovered."
      ::= { pceDiscCapabilityObjects 1 }

   pceDiscCapPathScopeEntry OBJECT-TYPE
      SYNTAX PceDiscCapPathScopeEntry
      MAX-ACCESS not-accessible
      STATUS current
      DESCRIPTION
         "Information describing the capacity of each PCE discovered."
      INDEX { pceDiscoveryIndex }
      ::= { pceDiscCapPathScopeTable 1 }

   PceDiscCapPathScopeEntry ::= SEQUENCE {
      pceDiscCapPathScopeIntraArea TruthValue,
      pceDiscCapPathScopeInterArea TruthValue,
      pceDiscCapPathScopeDefInterArea TruthValue,
      pceDiscCapPathScopeInterAS TruthValue,
      pceDiscCapPathScopeDefInterAS TruthValue,
      pceDiscCapPathScopeInterLayer TruthValue,
      pceDiscCapPathScopePrefIntraArea Integer32,
      pceDiscCapPathScopePrefInterArea Integer32,
      pceDiscCapPathScopePrefInterAS Integer32,
      pceDiscCapPathScopePrefIntLayer Integer32
   }

   pceDiscCapPathScopeIntraArea OBJECT-TYPE
      SYNTAX TruthValue
      MAX-ACCESS read-only
      STATUS current
      DESCRIPTION
         "Indicates whether the PCE supports the L option of the PATH-
         SCOPE sub TLV:
            The value is 'true' if the PCE can compute intra-area path."
      ::= { pceDiscCapPathScopeEntry 1 }

   pceDiscCapPathScopeInterArea OBJECT-TYPE
      SYNTAX TruthValue
      MAX-ACCESS read-only
      STATUS current
      DESCRIPTION
         "Indicates whether the PCE supports the R option of the PATH-
         SCOPE sub TLV:
            The value is 'true' if the PCE can act as PCE for inter-area
            TE LSPs computation."
      ::= { pceDiscCapPathScopeEntry 2 }

   pceDiscCapPathScopeDefInterArea OBJECT-TYPE
      SYNTAX TruthValue
      MAX-ACCESS read-only
      STATUS current
      DESCRIPTION
         "Indicates whether the PCE supports the Rd option of the PATH-
         SCOPE sub TLV:
            The value is 'true' if the PCE can act as a default PCE for
            inter-area TE LSPs computation."
      ::= { pceDiscCapPathScopeEntry 3 }

   pceDiscCapPathScopeInterAS OBJECT-TYPE
      SYNTAX TruthValue
      MAX-ACCESS read-only
      STATUS current
      DESCRIPTION
         "Indicates whether the PCE supports the S option of the PATH-
         SCOPE sub TLV:
            The value is 'true' if the PCE can act as PCE for inter-AS
            TE LSPs computation."
      ::= { pceDiscCapPathScopeEntry 4 }

   pceDiscCapPathScopeDefInterAS OBJECT-TYPE
      SYNTAX TruthValue
      MAX-ACCESS read-only
      STATUS current
      DESCRIPTION
         "Indicates whether the PCE supports the Sd option of the PATH-
         SCOPE sub TLV:
            The value is 'true' if the PCE can act as a default PCE for
            inter-AS TE LSPs computation."
      ::= { pceDiscCapPathScopeEntry 5 }

   pceDiscCapPathScopeInterLayer OBJECT-TYPE
      SYNTAX TruthValue
      MAX-ACCESS read-only
      STATUS current
      DESCRIPTION
         "Indicates whether the PCE supports the Y option of the PATH-
         SCOPE sub TLV:
            The value is 'true' if the PCE can compute or take part into
            the computation of paths across layers."
      ::= { pceDiscCapPathScopeEntry 6}

   pceDiscCapPathScopePrefIntraArea OBJECT-TYPE
      SYNTAX Integer32 (0..7)
      MAX-ACCESS read-only
      STATUS current
      DESCRIPTION
         "Indicates the level of preference of the option of computation
         'L' compared to other computation options:
            A value of 7 reflects the highest preference.
            When the value of PceDiscCapCompIntraArea is 'false' then
            this objet MUST be to '0'."
      ::= { pceDiscCapPathScopeEntry 7}

   pceDiscCapPathScopePrefInterArea OBJECT-TYPE
      SYNTAX Integer32 (0..7)
      MAX-ACCESS read-only
      STATUS current
      DESCRIPTION
         "Indicates the level of preference of the option of computation
         'R' compared to other computation options:
            A value of 7 reflects the highest preference.
            When the value of PceDiscCapCompInterArea is 'false' then
            this objet MUST be to '0'."
      ::= { pceDiscCapPathScopeEntry 8}

   pceDiscCapPathScopePrefInterAS OBJECT-TYPE
      SYNTAX Integer32 (0..7)
      MAX-ACCESS read-only
      STATUS current
      DESCRIPTION
         "Indicates the level of preference of the option of computation
         'S' compared to other computation options:
            A value of 7 reflects the highest preference.
            When the value of PceDiscCapCompInterAS is 'false' then this
            objet MUST be to '0'."
      ::= { pceDiscCapPathScopeEntry 9}

   pceDiscCapPathScopePrefIntLayer OBJECT-TYPE
      SYNTAX Integer32 (0..7)
      MAX-ACCESS read-only
      STATUS current
      DESCRIPTION
         "Indicates the level of preference of the option of computation
         'Y' compared to other computation options:
            A value of 7 reflects the highest preference.
            When the value of PceDiscCapCompInterLayer is 'false' then
            this objet MUST be to '0'."
      ::= { pceDiscCapPathScopeEntry 10}

   --

   -- PCE-DOMAINS information elements

   --

   pceDiscCapDomainTable OBJECT-TYPE
      SYNTAX SEQUENCE OF PceDiscCapDomainEntry
      MAX-ACCESS not-accessible
      STATUS current
      DESCRIPTION
         "Information describing the set of domains where the PCE has
         topology visibility and can compute paths."
      ::= { pceDiscCapabilityObjects 2 }

   pceDiscCapDomainEntry OBJECT-TYPE
      SYNTAX PceDiscCapDomainEntry
      MAX-ACCESS not-accessible
      STATUS current
      DESCRIPTION
         "Information describing the domains of each PCE discovered."
      INDEX { pceDiscoveryIndex, pceDiscCapDomainIndex }
      ::= { pceDiscCapDomainTable 1 }

   PceDiscCapDomainEntry ::= SEQUENCE {
      pceDiscCapDomainIndex Integer32,
      pceDiscCapDomainIDType AddressFamilyNumbers,
      pceDiscCapDomainID PceRoutingDomainID
   }

   pceDiscCapDomainIndex OBJECT-TYPE
      SYNTAX Integer32 (1..2147483647)
      MAX-ACCESS not-accessible
      STATUS current
      DESCRIPTION
         "This object identifies locally a domain for which the PCE
         identified by pceDiscoveryIndex has topology visibility and can
         compute paths."
      ::= { pceDiscCapDomainEntry 1 }

   pceDiscCapDomainIDType OBJECT-TYPE
      SYNTAX AddressFamilyNumbers
      MAX-ACCESS read-only
      STATUS current
      DESCRIPTION
         "This object identifies the type of the domainID of a PCE-
         DOMAIN SUB TLV.
         Acceptable types are :
            ipV4(1) and ipV6(2) for an OSPF area ID;
            nsap(3) for and ISIS area ID;
            asNumber(18) for an BGP AS number"
      ::= { pceDiscCapDomainEntry 2 }

   pceDiscCapDomainID OBJECT-TYPE
      SYNTAX PceRoutingDomainID
      MAX-ACCESS read-only
      STATUS current
      DESCRIPTION
         "The ID (area,AS) of the routing domain for which this entry
         contains information."
      ::= { pceDiscCapDomainEntry 3 }

   --

   -- PCE-DEST-DOMAINS information elements

   --

   pceDiscCapDestDomainTable OBJECT-TYPE
      SYNTAX SEQUENCE OF PceDiscCapDestDomainEntry
      MAX-ACCESS not-accessible
      STATUS current
      DESCRIPTION
         "Information describing the set of destination domains toward
         which a PCE can compute path."
      ::= { pceDiscCapabilityObjects 3 }

   pceDiscCapDestDomainEntry OBJECT-TYPE
      SYNTAX PceDiscCapDestDomainEntry
      MAX-ACCESS not-accessible
      STATUS current
      DESCRIPTION
         "Information describing the destination domains of each PCE."
      INDEX { pceDiscoveryIndex, pceDiscCapDestDomainIndex }
      ::= { pceDiscCapDestDomainTable 1 }

   PceDiscCapDestDomainEntry ::= SEQUENCE {
      pceDiscCapDestDomainIndex Integer32,
      pceDiscCapDestDomainIDType AddressFamilyNumbers,
      pceDiscCapDestDomainID PceRoutingDomainID
   }

   pceDiscCapDestDomainIndex OBJECT-TYPE
      SYNTAX Integer32 (1..2147483647)
      MAX-ACCESS not-accessible
      STATUS current
      DESCRIPTION
         "This object identifies locally a destination domain toward
         which a PCE identified by pceDiscoveryIndex can compute path."
      ::= { pceDiscCapDestDomainEntry 1 }

   pceDiscCapDestDomainIDType OBJECT-TYPE
      SYNTAX AddressFamilyNumbers
      MAX-ACCESS read-only
      STATUS current
      DESCRIPTION
         "This object identifies the type of the routing domain.
         Acceptable types are :
            ipV4(1) and ipV6(2) for an OSPF area ID;
            nsap(3) for and ISIS area ID;
            asNumber(18) for an BGP AS number"
      ::= { pceDiscCapDestDomainEntry 2 }

   pceDiscCapDestDomainID OBJECT-TYPE
      SYNTAX PceRoutingDomainID
      MAX-ACCESS read-only
      STATUS current
      DESCRIPTION
         "The ID (area,AS) of the routing domain for which this entry
         contains information."
      ::= { pceDiscCapDestDomainEntry 3 }

   pceDiscComputationOptionsObjects OBJECT IDENTIFIER ::= {
   pceDiscMIBObjects 3 }

   -- GENERAL-CAP and PATH-COMP-CAP

   pceDiscComputationOptionsTable OBJECT-TYPE
      SYNTAX SEQUENCE OF PceDiscComputationOptionsEntry
      MAX-ACCESS not-accessible
      STATUS current
      DESCRIPTION
         "Information describing options supported by each PCE."
      ::= { pceDiscComputationOptionsObjects 1 }

   pceDiscComputationOptionsEntry OBJECT-TYPE
      SYNTAX PceDiscComputationOptionsEntry
      MAX-ACCESS not-accessible
      STATUS current
      DESCRIPTION
         "Information describing the activity of the discovery mechanism
         of a PCE discovered.  "
      INDEX { pceDiscoveryIndex }
      ::= { pceDiscComputationOptionsTable 1 }

   PceDiscComputationOptionsEntry ::= SEQUENCE {
      pceDiscCompOptionsRpriority INTEGER,
      pceDiscCompOptionsMmessages INTEGER
      }

   pceDiscCompOptionsRpriority OBJECT-TYPE
      SYNTAX INTEGER {

         supported(1),
         notSupported(2)
      }
      MAX-ACCESS read-only
      STATUS current
      DESCRIPTION
         "The PCE identified by pceDiscoveryIndex supports for Request
         prioritization if the value of this object is supported(1)."
      ::= { pceDiscComputationOptionsEntry 1 }

   pceDiscCompOptionsMmessages OBJECT-TYPE
      SYNTAX INTEGER {
         supported(1),
         notSupported(2)
      }
      MAX-ACCESS read-only
      STATUS current
      DESCRIPTION
         " If the value of this object is supported(1), then the PCE
         identified by pceDiscoveryIndex supports for multiple messages
         within the same request message."
      ::= { pceDiscComputationOptionsEntry 2 }

   -- Activity objects

   pceDiscActivityObjects OBJECT IDENTIFIER ::= { pceDiscMIBObjects 4 }

   pceDiscActivityTable OBJECT-TYPE
      SYNTAX SEQUENCE OF PceDiscActivityEntry
      MAX-ACCESS not-accessible
      STATUS current
      DESCRIPTION
         "Information describing for each PCE the activity of the
         discovery mechanism."
      ::= { pceDiscActivityObjects 1 }

   pceDiscActivityEntry OBJECT-TYPE
      SYNTAX PceDiscActivityEntry
      MAX-ACCESS not-accessible
      STATUS current
      DESCRIPTION
         "Information describing the activity of the discovery mechanism
         of a PCE discovered.  "
      INDEX { pceDiscoveryIndex }
      ::= { pceDiscActivityTable 1 }

   PceDiscActivityEntry ::= SEQUENCE {
      pceDiscActivityTlvsRecv Integer32,
      pceDiscActivityErroredTlvsRecv Integer32
      }

   pceDiscActivityTlvsRecv OBJECT-TYPE
      SYNTAX Integer32 (1..2147483647)
      MAX-ACCESS not-accessible
      STATUS current
      DESCRIPTION
         "This object counts the number of TLV received since the
         discovery of the PCE."
      ::= { pceDiscActivityEntry 1 }

   pceDiscActivityErroredTlvsRecv OBJECT-TYPE
      SYNTAX Integer32 (1..2147483647)
      MAX-ACCESS not-accessible
      STATUS current
      DESCRIPTION
         "This object counts the number of Errored TVL received since
         the discovery of the PCE."
      ::= { pceDiscActivityEntry 2 }

   --

   -- PCE DISC agents conformance statement

   --

   pceDiscConformance OBJECT IDENTIFIER ::= { pceDiscStdMIB 2 }

   pceDiscGroups OBJECT IDENTIFIER ::= { pceDiscConformance 1 }

   pceDiscCompliances OBJECT IDENTIFIER ::= { pceDiscConformance 2 }

   -- PCE DISC agent compliance statements

   pceDiscGeneralPceInformation MODULE-COMPLIANCE
      STATUS current
      DESCRIPTION
      "The compliance statement for SNMP entities that implement only
      general information monitoring as proposed in the 2nd S. of the
      section 6.1 of [RFC4674]."
      MODULE
      --
      -- objets of pceDiscoveryTable
      -- objects of pceDiscPathScopeTable
      --
   ::= { pceDiscCompliances 1 }

   pceDiscDetailledPceInformation MODULE-COMPLIANCE
      STATUS current
      DESCRIPTION
      "The compliance statement for SNMP entities that implement
      detailled monitoring as proposed in the 3rd S. of the section 6.1
      of [RFC4674]."
      MODULE
      --
      -- objets of pceDiscoveryTable;
      -- objects of pceDiscPathScopeTable;
      -- objects of pceDiscDomainTable;
      -- objects of pceDiscDestDomainTable
      --
   ::= { pceDiscCompliances 2 }

   END

-- 
--    Copyright (C) The Internet Society (2006).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
-- 
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
-- 
-- 
-- Acknowledgment
-- 
--    Funding for the RFC Editor function is provided by the IETF
--    Administrative Support Activity (IASA).
