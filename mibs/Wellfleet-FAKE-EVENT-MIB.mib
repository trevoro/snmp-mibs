Wellfleet-FAKE-EVENT-MIB DEFINITIONS ::= BEGIN

-- Created by mdl2asn version 3.1
-- Creation date: Wed Aug 30 16:40:48 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfSnmpGroup
        FROM Wellfleet-COMMON-MIB;


    wfFakeEvent	OBJECT IDENTIFIER ::= { wfSnmpGroup 4 }

    wfFakeEventString OBJECT-TYPE
        SYNTAX	DisplayString
        ACCESS	read-only
        STATUS	mandatory
        DESCRIPTION
                "A dummy display string. While no string will actually be kept here, the
                full identifier (object id + attribute id + instance ID ) will be used to
                wrap event strings passed from the system logger into an SNMP Trap message."
        ::= { wfFakeEvent 1 }

    wfLogTrapSeverity OBJECT-TYPE
        SYNTAX	INTEGER {
    		    fault(1),
    		    warning(2),
    		    informational(3),
    		    trace(4),
    		    debug(5)
    		}
        ACCESS	read-only
        STATUS	mandatory
        DESCRIPTION
                "This object is used for wrapping log event severity information
                in a log event specific trap.  The severity information is the thrid
                variable binding in a log event specific trap."
        ::= { wfFakeEvent 2 }

    END  -- Wellfleet-FAKE-EVENT-MIB
