Nortel-MsCarrier-MscPassport-HuntGroupMIB
DEFINITIONS ::= BEGIN



IMPORTS

      OBJECT-TYPE
   FROM RFC-1212

      mscPassportMIBs,
      mscComponents
   FROM Nortel-MsCarrier-MscPassport-UsefulDefinitionsMIB

      Counter32,
      DisplayString,
      StorageType,
      RowStatus,
      Integer32,
      Unsigned32
   FROM Nortel-MsCarrier-MscPassport-StandardTextualConventionsMIB

      AsciiString,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     HuntGroup Enterprise MIB."

huntGroupMIB OBJECT IDENTIFIER ::= { mscPassportMIBs 130 }










-- HuntGroup/n
-- The HuntGroup component provides a hunt group capability for 
-- switched calls (SVCs).
-- A hunt group is a single DNA used to represent a group of service 
-- DNAs. A customer calling the DNA of the hunt group receives the 
-- benefits of higher capacity and availability as calls are spread across 
-- several lines.

mscHg OBJECT IDENTIFIER ::= { mscComponents 131 }



mscHgRowStatusTable OBJECT-TYPE
   SYNTAX     SEQUENCE OF MscHgRowStatusEntry
   ACCESS     not-accessible
   STATUS     mandatory
   DESCRIPTION
     "This entry controls the addition and deletion of 
      mscHg components."
::= { mscHg 1 }

mscHgRowStatusEntry OBJECT-TYPE
   SYNTAX     MscHgRowStatusEntry
   ACCESS     not-accessible
   STATUS     mandatory
   DESCRIPTION
     "A single entry in the table represents a single 
      mscHg component."
   INDEX {
      mscHgIndex }
::= { mscHgRowStatusTable 1 }

MscHgRowStatusEntry ::= SEQUENCE {
   mscHgRowStatus
      RowStatus,
   mscHgComponentName
      DisplayString,
   mscHgStorageType
      StorageType,
   mscHgIndex
      Integer32 }

mscHgRowStatus OBJECT-TYPE
   SYNTAX     RowStatus 
   ACCESS     read-write
   STATUS     mandatory
   DESCRIPTION
     "This variable is used as the basis for SNMP naming of
      mscHg components.
      These components can be added and deleted."
::= { mscHgRowStatusEntry 1 }

mscHgComponentName OBJECT-TYPE
   SYNTAX     DisplayString 
   ACCESS     read-only
   STATUS     mandatory
   DESCRIPTION
     "This variable provides the component's string name for
      use with the ASCII Console Interface"
::= { mscHgRowStatusEntry 2 }

mscHgStorageType OBJECT-TYPE
   SYNTAX     StorageType 
   ACCESS     read-only
   STATUS     mandatory
   DESCRIPTION
     "This variable represents the storage type value for the
      mscHg tables."
::= { mscHgRowStatusEntry 4 }

mscHgIndex OBJECT-TYPE
   SYNTAX     Integer32 (1..65535)
   ACCESS     not-accessible
   STATUS     mandatory
   DESCRIPTION
     "This variable represents the index for the mscHg tables."
::= { mscHgRowStatusEntry 10 }

mscHgCidDataTable OBJECT-TYPE
   SYNTAX     SEQUENCE OF MscHgCidDataEntry
   ACCESS     not-accessible
   STATUS     mandatory
   DESCRIPTION
     "This group contains the attribute for a component's Customer 
      Identifier (CID). Refer to the attribute description for a detailed 
      explanation of CIDs."
::= { mscHg 10 }

mscHgCidDataEntry OBJECT-TYPE
   SYNTAX     MscHgCidDataEntry
   ACCESS     not-accessible
   STATUS     mandatory
   DESCRIPTION
     "An entry in the mscHgCidDataTable."
   INDEX {
      mscHgIndex }
::= { mscHgCidDataTable 1 }

MscHgCidDataEntry ::= SEQUENCE {
   mscHgCustomerIdentifier
      Unsigned32 }

mscHgCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscHgCidDataEntry 1 }

mscHgNsapAddressTable OBJECT-TYPE
   SYNTAX     SEQUENCE OF MscHgNsapAddressEntry
   ACCESS     not-accessible
   STATUS     mandatory
   DESCRIPTION
     "This group contains attributes common to all NSAP format 
      addresses."
::= { mscHg 11 }

mscHgNsapAddressEntry OBJECT-TYPE
   SYNTAX     MscHgNsapAddressEntry
   ACCESS     not-accessible
   STATUS     mandatory
   DESCRIPTION
     "An entry in the mscHgNsapAddressTable."
   INDEX {
      mscHgIndex }
::= { mscHgNsapAddressTable 1 }

MscHgNsapAddressEntry ::= SEQUENCE {
   mscHgAddress
      AsciiString }

mscHgAddress OBJECT-TYPE
   SYNTAX     AsciiString (SIZE (1..17))
   ACCESS     read-write
   STATUS     mandatory
   DESCRIPTION
     "The address attribute specifies the numbering plan and digits which 
      form a unique DNA identifier of the hunt group. The format of the 
      address attribute is <numberingPlan>.<digits> where numbering 
      plan is x for X.121 and e for E.164. An example X.121 address is 
      x.12345678."
::= { mscHgNsapAddressEntry 1 }

mscHgProvTable OBJECT-TYPE
   SYNTAX     SEQUENCE OF MscHgProvEntry
   ACCESS     not-accessible
   STATUS     mandatory
   DESCRIPTION
     "The Provisioned group contains the provisioned attributes of the 
      hunt group."
::= { mscHg 12 }

mscHgProvEntry OBJECT-TYPE
   SYNTAX     MscHgProvEntry
   ACCESS     not-accessible
   STATUS     mandatory
   DESCRIPTION
     "An entry in the mscHgProvTable."
   INDEX {
      mscHgIndex }
::= { mscHgProvTable 1 }

MscHgProvEntry ::= SEQUENCE {
   mscHgLogicalProcessor
      Link,
   mscHgSelectionPolicy
      INTEGER,
   mscHgMaxHuntAttempts
      Unsigned32,
   mscHgAppendSuffixDigits
      INTEGER }

mscHgLogicalProcessor OBJECT-TYPE
   SYNTAX     Link 
   ACCESS     read-write
   STATUS     mandatory
   DESCRIPTION
     "This attribute specifies the logical processor on which the hunt 
      group process will execute. The Lp/n Eng Hgs component contains 
      statistics for all hunt groups on the LP."
::= { mscHgProvEntry 1 }

mscHgSelectionPolicy OBJECT-TYPE
   SYNTAX     INTEGER  {
                 startFromZero(0),
                 rotary(1),
                 mostAvailable(2) }
   ACCESS     read-write
   STATUS     mandatory
   DESCRIPTION
     "The selectionPolicy attribute specifies the algorithm used to select a 
      hunt group member.
      
      A value of startFromZero means that on a new call, the first 
      available member starting from the member with the lowest 
      instance value is selected. Subsequent hunts for the same call select 
      the first available member starting from the previously chosen 
      member. This algorithm is used when it is desirable to have the first 
      member receive the majority of the calls and subsequent members 
      only receive calls in overflow situations.
      
      A value of rotary means that on a new call, the first available 
      member is selected starting from the member which received the 
      last new call. Subsequent hunts for the same call select the first 
      available member starting from the previously chosen member. This 
      algorithm is used when it is desirable to loadspread the calls equally 
      across the members.
      
      A value of mostAvailable means that on a new call, the most 
      available member is selected based on the availability information 
      received from the member. Subsequent hunts for the same call 
      select the most available member starting from the previously 
      chosen member. This algorithm is used when it is desirable to send 
      each call to the member which has the highest probability of 
      connecting it."
   DEFVAL     { mostAvailable }
::= { mscHgProvEntry 2 }

mscHgMaxHuntAttempts OBJECT-TYPE
   SYNTAX     Unsigned32 (1..63)
   ACCESS     read-write
   STATUS     mandatory
   DESCRIPTION
     "The maxHuntAttempts attribute specifies the maximum attempts 
      allowed to hunt the call. Hunting ceases if either this maximum is 
      exceeded or the member list is exhausted."
   DEFVAL     { 63 }
::= { mscHgProvEntry 3 }

mscHgAppendSuffixDigits OBJECT-TYPE
   SYNTAX     INTEGER  {
                 no(0),
                 yes(1) }
   ACCESS     read-write
   STATUS     mandatory
   DESCRIPTION
     "The appendSuffixDigits attribute specifies how suffix called address 
      digits are handled. Suffix called address digits are any trailing 
      digits, signalled in a call, beyond the provisioned hunt group 
      address. If this attribute is set to yes, suffix digits are appended to 
      the member address before the call is forwarded to the member. If it 
      is set to no, suffix digits are not appended to the member address."
   DEFVAL     { yes }
::= { mscHgProvEntry 4 }

mscHgStateTable OBJECT-TYPE
   SYNTAX     SEQUENCE OF MscHgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscHg 20 }

mscHgStateEntry OBJECT-TYPE
   SYNTAX     MscHgStateEntry
   ACCESS     not-accessible
   STATUS     mandatory
   DESCRIPTION
     "An entry in the mscHgStateTable."
   INDEX {
      mscHgIndex }
::= { mscHgStateTable 1 }

MscHgStateEntry ::= SEQUENCE {
   mscHgAdminState
      INTEGER,
   mscHgOperationalState
      INTEGER,
   mscHgUsageState
      INTEGER }

mscHgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscHgStateEntry 1 }

mscHgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscHgStateEntry 2 }

mscHgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscHgStateEntry 3 }

mscHgOperationalTable OBJECT-TYPE
   SYNTAX     SEQUENCE OF MscHgOperationalEntry
   ACCESS     not-accessible
   STATUS     mandatory
   DESCRIPTION
     "The Operational group contains the operational attributes of the 
      hunt group."
::= { mscHg 21 }

mscHgOperationalEntry OBJECT-TYPE
   SYNTAX     MscHgOperationalEntry
   ACCESS     not-accessible
   STATUS     mandatory
   DESCRIPTION
     "An entry in the mscHgOperationalTable."
   INDEX {
      mscHgIndex }
::= { mscHgOperationalTable 1 }

MscHgOperationalEntry ::= SEQUENCE {
   mscHgHuntAttempts
      Counter32,
   mscHgFailedCalls
      Counter32,
   mscHgInitialHuntAttempts
      Counter32,
   mscHgAvailabilityUpdates
      Counter32,
   mscHgMaxAddrLenExceeded
      Counter32,
   mscHgBadPackets
      Counter32 }

mscHgHuntAttempts OBJECT-TYPE
   SYNTAX     Counter32 
   ACCESS     read-only
   STATUS     mandatory
   DESCRIPTION
     "This attribute counts the total number of hunt attempts made by the 
      hunt group. The count includes both initial and subsequent hunt 
      attempts. This count is contained within the huntAttempts attribute 
      of the Lp/n Eng Hgs component. This counter wraps to 0 when it 
      exceeds its maximum value."
::= { mscHgOperationalEntry 2 }

mscHgFailedCalls OBJECT-TYPE
   SYNTAX     Counter32 
   ACCESS     read-only
   STATUS     mandatory
   DESCRIPTION
     "This attribute counts the number of calls which could not be 
      connected by any of the hunt group members. This could occur if 
      the hunt group is locked or has exhausted its member list. If a call 
      cannot be connected by the hunt group it is sent to call redirection. 
      This counter wraps to 0 when it exceeds its maximum value."
::= { mscHgOperationalEntry 3 }

mscHgInitialHuntAttempts OBJECT-TYPE
   SYNTAX     Counter32 
   ACCESS     read-only
   STATUS     mandatory
   DESCRIPTION
     "This attribute counts the number of new (non-hunted) calls received 
      by the hunt group which are forwarded to a member. This counter 
      wraps to 0 when it exceeds its maximum value."
::= { mscHgOperationalEntry 4 }

mscHgAvailabilityUpdates OBJECT-TYPE
   SYNTAX     Counter32 
   ACCESS     read-only
   STATUS     mandatory
   DESCRIPTION
     "This attribute counts the number of availability update packets 
      received by the hunt group from its members. This counter wraps to 
      0 when it exceeds its maximum value."
::= { mscHgOperationalEntry 5 }

mscHgMaxAddrLenExceeded OBJECT-TYPE
   SYNTAX     Counter32 
   ACCESS     read-only
   STATUS     mandatory
   DESCRIPTION
     "This attribute counts the number of times a member could not be 
      selected to receive a call with suffix address digits because its DNA 
      length would exceed the maximum of 14 digits with the suffix digits 
      appended. This counter wraps to 0 when it exceeds its maximum 
      value."
::= { mscHgOperationalEntry 6 }

mscHgBadPackets OBJECT-TYPE
   SYNTAX     Counter32 
   ACCESS     read-only
   STATUS     mandatory
   DESCRIPTION
     "This attribute counts the number of unrecognizable packets received 
      by the hunt group and discarded. This counter wraps to 0 when it 
      exceeds its maximum value."
::= { mscHgOperationalEntry 7 }


-- Hg/n HuntGroupMember/n
-- The HuntGroupMember component defines an instance of a hunt 
-- group member.

mscHgHgM OBJECT IDENTIFIER ::= { mscHg 2 }



mscHgHgMRowStatusTable OBJECT-TYPE
   SYNTAX     SEQUENCE OF MscHgHgMRowStatusEntry
   ACCESS     not-accessible
   STATUS     mandatory
   DESCRIPTION
     "This entry controls the addition and deletion of 
      mscHgHgM components."
::= { mscHgHgM 1 }

mscHgHgMRowStatusEntry OBJECT-TYPE
   SYNTAX     MscHgHgMRowStatusEntry
   ACCESS     not-accessible
   STATUS     mandatory
   DESCRIPTION
     "A single entry in the table represents a single 
      mscHgHgM component."
   INDEX {
      mscHgIndex,
      mscHgHgMIndex }
::= { mscHgHgMRowStatusTable 1 }

MscHgHgMRowStatusEntry ::= SEQUENCE {
   mscHgHgMRowStatus
      RowStatus,
   mscHgHgMComponentName
      DisplayString,
   mscHgHgMStorageType
      StorageType,
   mscHgHgMIndex
      Integer32 }

mscHgHgMRowStatus OBJECT-TYPE
   SYNTAX     RowStatus 
   ACCESS     read-write
   STATUS     mandatory
   DESCRIPTION
     "This variable is used as the basis for SNMP naming of
      mscHgHgM components.
      These components can be added and deleted."
::= { mscHgHgMRowStatusEntry 1 }

mscHgHgMComponentName OBJECT-TYPE
   SYNTAX     DisplayString 
   ACCESS     read-only
   STATUS     mandatory
   DESCRIPTION
     "This variable provides the component's string name for
      use with the ASCII Console Interface"
::= { mscHgHgMRowStatusEntry 2 }

mscHgHgMStorageType OBJECT-TYPE
   SYNTAX     StorageType 
   ACCESS     read-only
   STATUS     mandatory
   DESCRIPTION
     "This variable represents the storage type value for the
      mscHgHgM tables."
::= { mscHgHgMRowStatusEntry 4 }

mscHgHgMIndex OBJECT-TYPE
   SYNTAX     Integer32 (1..63)
   ACCESS     not-accessible
   STATUS     mandatory
   DESCRIPTION
     "This variable represents the index for the mscHgHgM tables."
::= { mscHgHgMRowStatusEntry 10 }

mscHgHgMProvTable OBJECT-TYPE
   SYNTAX     SEQUENCE OF MscHgHgMProvEntry
   ACCESS     not-accessible
   STATUS     mandatory
   DESCRIPTION
     "The Provisioned group contains the provisioned attributes of the 
      hunt group member."
::= { mscHgHgM 10 }

mscHgHgMProvEntry OBJECT-TYPE
   SYNTAX     MscHgHgMProvEntry
   ACCESS     not-accessible
   STATUS     mandatory
   DESCRIPTION
     "An entry in the mscHgHgMProvTable."
   INDEX {
      mscHgIndex,
      mscHgHgMIndex }
::= { mscHgHgMProvTable 1 }

MscHgHgMProvEntry ::= SEQUENCE {
   mscHgHgMAddress
      AsciiString }

mscHgHgMAddress OBJECT-TYPE
   SYNTAX     AsciiString (SIZE (1..17))
   ACCESS     read-write
   STATUS     mandatory
   DESCRIPTION
     "The address attribute specifies the numbering plan and digits which 
      form a unique DNA identifier of the hunt group member. The 
      format of the address attribute is <numberingPlan>.<digits> where 
      numbering plan is x for X.121 and e for E.164. An example X.121 
      address is x.12345678."
::= { mscHgHgMProvEntry 1 }

mscHgHgMStateTable OBJECT-TYPE
   SYNTAX     SEQUENCE OF MscHgHgMStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscHgHgM 11 }

mscHgHgMStateEntry OBJECT-TYPE
   SYNTAX     MscHgHgMStateEntry
   ACCESS     not-accessible
   STATUS     mandatory
   DESCRIPTION
     "An entry in the mscHgHgMStateTable."
   INDEX {
      mscHgIndex,
      mscHgHgMIndex }
::= { mscHgHgMStateTable 1 }

MscHgHgMStateEntry ::= SEQUENCE {
   mscHgHgMAdminState
      INTEGER,
   mscHgHgMOperationalState
      INTEGER,
   mscHgHgMUsageState
      INTEGER }

mscHgHgMAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscHgHgMStateEntry 1 }

mscHgHgMOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscHgHgMStateEntry 2 }

mscHgHgMUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscHgHgMStateEntry 3 }

mscHgHgMOperationalTable OBJECT-TYPE
   SYNTAX     SEQUENCE OF MscHgHgMOperationalEntry
   ACCESS     not-accessible
   STATUS     mandatory
   DESCRIPTION
     "The Operational group defines operational attributes associated 
      with the HuntGroupMember component."
::= { mscHgHgM 12 }

mscHgHgMOperationalEntry OBJECT-TYPE
   SYNTAX     MscHgHgMOperationalEntry
   ACCESS     not-accessible
   STATUS     mandatory
   DESCRIPTION
     "An entry in the mscHgHgMOperationalTable."
   INDEX {
      mscHgIndex,
      mscHgHgMIndex }
::= { mscHgHgMOperationalTable 1 }

MscHgHgMOperationalEntry ::= SEQUENCE {
   mscHgHgMAvailability
      Unsigned32,
   mscHgHgMAvailabilityUpdates
      Counter32,
   mscHgHgMCallsRefused
      Counter32 }

mscHgHgMAvailability OBJECT-TYPE
   SYNTAX     Unsigned32 (0..4095)
   ACCESS     read-write
   STATUS     mandatory
   DESCRIPTION
     "This attribute indicates the current availability of the member.
      The higher the value, the more available the member is perceived to 
      be. A value of 0 indicates the member is unavailable.
      
      A member must be considered 'available' by the hunt group in 
      order to receive a call, regardless of the selection policy in use. The 
      hunt group members report whether or not they are available to 
      receive calls to the hunt group. Some services base their availability 
      on unused logical channels, others on bandwidth or memory 
      capacity.
      
      During initialization, the hunt group assumes all of its members are 
      equally available and sets their availability value to the maximum 
      of 4095. Similarly, a new hunt group member added to an existing 
      hunt group has its availability value initialized to 4095. This 
      ensures that members which have not reported their availability to 
      the hunt group are tried in order to trigger the member to report its 
      true availability.
      
      The availability of a member can change in the following ways:
      - Hunt group members can report their availability to the hunt group 
      using a DPRS availability packet.
      - A network operator can temporarily change the value by the Set 
      command. This change remains in effect until changed again by any 
      of these ways.
      - The hunt group resets a member's availability to the maximum of 
      4095 if it has been 0 for at least 2.5 hours. This ensures that 'lost' 
      availability information does not prevent a member from returning 
      to service."
   DEFVAL     { 4095 }
::= { mscHgHgMOperationalEntry 1 }

mscHgHgMAvailabilityUpdates OBJECT-TYPE
   SYNTAX     Counter32 
   ACCESS     read-only
   STATUS     mandatory
   DESCRIPTION
     "This attribute counts the number of availability update packets 
      received by the hunt group member. This counter wraps to 0 when it 
      exceeds its maximum value."
::= { mscHgHgMOperationalEntry 2 }

mscHgHgMCallsRefused OBJECT-TYPE
   SYNTAX     Counter32 
   ACCESS     read-only
   STATUS     mandatory
   DESCRIPTION
     "This attribute counts the number of call packets which were 
      returned to the hunt group by the member because it could not 
      connect the call. If this counter increments frequently, it could 
      indicate a problem with the member's reporting of its availability to 
      the hunt group or an incompatibility in the call options. This 
      counter wraps to 0 when it exceeds its maximum value."
::= { mscHgHgMOperationalEntry 3 }




-- 
-- Version and Compliance statements
-- 



-- Object-Group Statement:
-- A list of all current accessible leaf objects.

-- OBJECTS { mscHgStorageType,
--           mscHgHgMStorageType,
--           mscHgHgMAddress,
--           mscHgHgMUsageState,
--           mscHgMaxAddrLenExceeded,
--           mscHgAppendSuffixDigits,
--           mscHgUsageState,
--           mscHgHgMOperationalState,
--           mscHgSelectionPolicy,
--           mscHgHgMAvailability,
--           mscHgComponentName,
--           mscHgMaxHuntAttempts,
--           mscHgHgMAdminState,
--           mscHgAvailabilityUpdates,
--           mscHgOperationalState,
--           mscHgAddress,
--           mscHgHgMRowStatus,
--           mscHgFailedCalls,
--           mscHgHuntAttempts,
--           mscHgLogicalProcessor,
--           mscHgInitialHuntAttempts,
--           mscHgAdminState,
--           mscHgHgMCallsRefused,
--           mscHgHgMAvailabilityUpdates,
--           mscHgBadPackets,
--           mscHgRowStatus,
--           mscHgHgMComponentName,
--           mscHgCustomerIdentifier }
-- STATUS  mandatory
-- DESCRIPTION
--   "A list of all current accessible leaf objects."

huntGroupGroup OBJECT IDENTIFIER ::= { huntGroupMIB 1 }
huntGroupGroupCA OBJECT IDENTIFIER ::= { huntGroupGroup 1 }
huntGroupGroupCA02 OBJECT IDENTIFIER ::= { huntGroupGroupCA 3 }
huntGroupGroupCA02A OBJECT IDENTIFIER ::= { huntGroupGroupCA02 2 }



-- Agent-Capabilities Statement:

-- PRODUCT-RELEASE "MscPassport Release 1.2 HuntGroup."
-- STATUS          mandatory
-- DESCRIPTION     "Carrier Passport HuntGroup MIB: MIB Version CA02A,
--                  Software Version CA02S9C."
-- SUPPORTS        Nortel-MsCarrier-MscPassport-HuntGroupMIB
--    INCLUDES     { huntGroupGroupCA02A }

huntGroupCapabilities OBJECT IDENTIFIER ::= { huntGroupMIB 3 }
huntGroupCapabilitiesCA OBJECT IDENTIFIER ::= { huntGroupCapabilities 1 }
huntGroupCapabilitiesCA02 OBJECT IDENTIFIER ::= { huntGroupCapabilitiesCA 3 }
huntGroupCapabilitiesCA02A OBJECT IDENTIFIER ::= { huntGroupCapabilitiesCA02 2 }





END
