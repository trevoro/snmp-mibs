-- MIB created 11/13/98 22:12:42, by
--   SMIC (the next generation) version 1.6.29, November 22, 1994.

CACHE-SERVER-MIB DEFINITIONS ::= BEGIN

-- From file: "ibmwebcache.mi2"
-- Compile options "G A T M"

IMPORTS
    Counter32, Integer32, Gauge32, IpAddress
            FROM SNMPv2-SMI
    OBJECT-TYPE
            FROM RFC-1212
    enterprises
            FROM RFC1155-SMI
    DisplayString
            FROM SNMPv2-TC;

ibmCacheServer OBJECT IDENTIFIER ::= { enterprises ibm(2) ibmProd(6) ibmIROC(119) ibmIROCrouting(4) 8 }
-- MODULE-IDENTITY
--  LastUpdated
--    9809031200Z
--  OrgName
--    IBM
--  ContactInfo
--    John Averi
--     IBM Corporation
--     800 Park Offices Drive
--     V18A/664
--     P.O. Box 12195
--     Research Triangle Park, NC 27709, USA
--     Tel:    1 919 254 2463
--     E-mail: javeri@us.ibm.com
--  Descr
--    MIB for managing the Cache Server function.

ibmcacheserverCore OBJECT IDENTIFIER ::= { ibmCacheServer 1 }
ibmcacheserverPartition OBJECT IDENTIFIER ::= { ibmCacheServer 2 }
ibmcacheserverURL OBJECT IDENTIFIER ::= { ibmCacheServer 3 }
ibmcacheserverProxy OBJECT IDENTIFIER ::= { ibmCacheServer 4 }

ibmcacheserverCoreActivePartitions OBJECT-TYPE
    SYNTAX Gauge32
    ACCESS read-only
    STATUS mandatory
    DESCRIPTION
        "Number of active partitions."
    ::= { ibmcacheserverCore 1 }

ibmcacheserverCoreECCPort OBJECT-TYPE
    SYNTAX Integer32(0..65535)
    ACCESS read-only
    STATUS mandatory
    DESCRIPTION
        "The ECC port number."
    ::= { ibmcacheserverCore 2 }

ibmcacheserverPartitionTable OBJECT-TYPE
    SYNTAX SEQUENCE OF IbmcacheserverPartitionEntry
    ACCESS not-accessible
    STATUS mandatory
    DESCRIPTION
        "Table of information pertaining to an individual
         partition."
    ::= { ibmcacheserverPartition 1 }

ibmcacheserverPartitionEntry OBJECT-TYPE
    SYNTAX IbmcacheserverPartitionEntry
    ACCESS not-accessible
    STATUS mandatory
    DESCRIPTION
        "An entry containing objects for a particular
         partition."
    INDEX { ibmcacheserverPartitionIndex }
    ::= { ibmcacheserverPartitionTable 1 }

IbmcacheserverPartitionEntry ::= SEQUENCE {
    ibmcacheserverPartitionIndex Integer32,
    ibmcacheserverPartitionCacheControl INTEGER,
    ibmcacheserverPartitionCacheTransparent INTEGER,
    ibmcacheserverPartitionUseHTTPCacheHdrs INTEGER,
    ibmcacheserverPartitionCacheDynamic INTEGER,
    ibmcacheserverPartitionCacheDynamicURL DisplayString,
    ibmcacheserverPartitionCacheImage INTEGER,
    ibmcacheserverPartitionCacheStatic INTEGER,
    ibmcacheserverPartitionMaxSize Integer32,
    ibmcacheserverPartitionMaxObjects Integer32,
    ibmcacheserverPartitionMaxObjectSize Integer32,
    ibmcacheserverPartitionDynamicDefaultLifetime Integer32,
    ibmcacheserverPartitionImageDefaultLifetime Integer32,
    ibmcacheserverPartitionStaticDefaultLifetime Integer32,
    ibmcacheserverPartitionCachePurgeInterval Integer32,
    ibmcacheserverPartitionNumBytesCurrent Gauge32,
    ibmcacheserverPartitionNumBytesHiWater Gauge32,
    ibmcacheserverPartitionNumObjectsCurrent Gauge32,
    ibmcacheserverPartitionNumObjectsHiWater Gauge32,
    ibmcacheserverPartitionHitTotal Counter32,
    ibmcacheserverPartitionMissTotal Counter32,
    ibmcacheserverPartitionAddInclude Counter32,
    ibmcacheserverPartitionNotAddCacheOff Counter32,
    ibmcacheserverPartitionNotAddTooLarge Counter32,
    ibmcacheserverPartitionNotAddHTTPHdr Counter32,
    ibmcacheserverPartitionNotAddExclude Counter32,
    ibmcacheserverPartitionNotAddExpire Counter32,
    ibmcacheserverPartitionNotAddImage Counter32,
    ibmcacheserverPartitionNotAddStatic Counter32,
    ibmcacheserverPartitionNotAddDynamic Counter32,
    ibmcacheserverPartitionPurgeCacheFull Counter32,
    ibmcacheserverPartitionPurgeItemStale Counter32,
    ibmcacheserverPartitionPurgeItemExplicit Counter32
    }

ibmcacheserverPartitionIndex OBJECT-TYPE
    SYNTAX Integer32
    ACCESS not-accessible
    STATUS mandatory
    DESCRIPTION
        "A unique value for each partition."
    ::= { ibmcacheserverPartitionEntry 1 }

ibmcacheserverPartitionCacheControl OBJECT-TYPE
    SYNTAX INTEGER {
        enabled(1),
        disabled(2)
        }
    ACCESS read-only
    STATUS mandatory
    DESCRIPTION
        "Global cache control."
    ::= { ibmcacheserverPartitionEntry 2 }

ibmcacheserverPartitionCacheTransparent OBJECT-TYPE
    SYNTAX INTEGER {
        enabled(1),
        disabled(2)
        }
    ACCESS read-only
    STATUS mandatory
    DESCRIPTION
        "Transparent cache control."
    ::= { ibmcacheserverPartitionEntry 3 }

ibmcacheserverPartitionUseHTTPCacheHdrs OBJECT-TYPE
    SYNTAX INTEGER {
        enabled(1),
        disabled(2)
        }
    ACCESS read-only
    STATUS mandatory
    DESCRIPTION
        "Use HTTP cache control directive"
    ::= { ibmcacheserverPartitionEntry 4 }

ibmcacheserverPartitionCacheDynamic OBJECT-TYPE
    SYNTAX INTEGER {
        enabled(1),
        disabled(2)
        }
    ACCESS read-only
    STATUS mandatory
    DESCRIPTION
        "Cache dynamic items (e.g. - /cgi-bin/) control"
    ::= { ibmcacheserverPartitionEntry 5 }

ibmcacheserverPartitionCacheDynamicURL OBJECT-TYPE
    SYNTAX DisplayString(SIZE(1..255))
--    Rsyntax OCTET STRING(SIZE(1..255))
    ACCESS read-only
    STATUS mandatory
    DESCRIPTION
        "Cache dynamic items URL"
    ::= { ibmcacheserverPartitionEntry 6 }

ibmcacheserverPartitionCacheImage OBJECT-TYPE
    SYNTAX INTEGER {
        enabled(1),
        disabled(2)
        }
    ACCESS read-only
    STATUS mandatory
    DESCRIPTION
        "Cache image items (.gif, .jpg) control"
    ::= { ibmcacheserverPartitionEntry 7 }

ibmcacheserverPartitionCacheStatic OBJECT-TYPE
    SYNTAX INTEGER {
        enabled(1),
        disabled(2)
        }
    ACCESS read-only
    STATUS mandatory
    DESCRIPTION
        "Cache static items control"
    ::= { ibmcacheserverPartitionEntry 8 }

ibmcacheserverPartitionMaxSize OBJECT-TYPE
    SYNTAX Integer32
    ACCESS read-only
    STATUS mandatory
    DESCRIPTION
        "Maximum partition size in MegaBytes"
    ::= { ibmcacheserverPartitionEntry 9 }

ibmcacheserverPartitionMaxObjects OBJECT-TYPE
    SYNTAX Integer32
    ACCESS read-only
    STATUS mandatory
    DESCRIPTION
        "Max number of objects in partition"
    ::= { ibmcacheserverPartitionEntry 10 }

ibmcacheserverPartitionMaxObjectSize OBJECT-TYPE
    SYNTAX Integer32
    ACCESS read-only
    STATUS mandatory
    DESCRIPTION
        "Max size of object allowed in partition"
    ::= { ibmcacheserverPartitionEntry 11 }

ibmcacheserverPartitionDynamicDefaultLifetime OBJECT-TYPE
    SYNTAX Integer32
    ACCESS read-only
    STATUS mandatory
    DESCRIPTION
        "Default lifetime for dynamic items"
    ::= { ibmcacheserverPartitionEntry 12 }

ibmcacheserverPartitionImageDefaultLifetime OBJECT-TYPE
    SYNTAX Integer32
    ACCESS read-only
    STATUS mandatory
    DESCRIPTION
        "Default lifetime for image items"
    ::= { ibmcacheserverPartitionEntry 13 }

ibmcacheserverPartitionStaticDefaultLifetime OBJECT-TYPE
    SYNTAX Integer32
    ACCESS read-only
    STATUS mandatory
    DESCRIPTION
        "Default lifetime for static items"
    ::= { ibmcacheserverPartitionEntry 14 }

ibmcacheserverPartitionCachePurgeInterval OBJECT-TYPE
    SYNTAX Integer32
    ACCESS read-only
    STATUS mandatory
    DESCRIPTION
        "Time between garbage collection"
    ::= { ibmcacheserverPartitionEntry 15 }

ibmcacheserverPartitionNumBytesCurrent OBJECT-TYPE
    SYNTAX Gauge32
    ACCESS read-only
    STATUS mandatory
    DESCRIPTION
        "Current number of bytes in partition"
    ::= { ibmcacheserverPartitionEntry 16 }

ibmcacheserverPartitionNumBytesHiWater OBJECT-TYPE
    SYNTAX Gauge32
    ACCESS read-only
    STATUS mandatory
    DESCRIPTION
        "High water mark for number of bytes in partition"
    ::= { ibmcacheserverPartitionEntry 17 }

ibmcacheserverPartitionNumObjectsCurrent OBJECT-TYPE
    SYNTAX Gauge32
    ACCESS read-only
    STATUS mandatory
    DESCRIPTION
        "Current number of objects in partition"
    ::= { ibmcacheserverPartitionEntry 18 }

ibmcacheserverPartitionNumObjectsHiWater OBJECT-TYPE
    SYNTAX Gauge32
    ACCESS read-only
    STATUS mandatory
    DESCRIPTION
        "High water mark for number of objects in partition"
    ::= { ibmcacheserverPartitionEntry 19 }

ibmcacheserverPartitionHitTotal OBJECT-TYPE
    SYNTAX Counter32
    ACCESS read-only
    STATUS mandatory
    DESCRIPTION
        "Total number of cache retrieval attempts in which item found
         in cache"
    ::= { ibmcacheserverPartitionEntry 20 }

ibmcacheserverPartitionMissTotal OBJECT-TYPE
    SYNTAX Counter32
    ACCESS read-only
    STATUS mandatory
    DESCRIPTION
        "Total number of cache retrieval attempts in which item not
         found in cache"
    ::= { ibmcacheserverPartitionEntry 21 }

ibmcacheserverPartitionAddInclude OBJECT-TYPE
    SYNTAX Counter32
    ACCESS read-only
    STATUS mandatory
    DESCRIPTION
        "Items added explicitly via INCLUDE"
    ::= { ibmcacheserverPartitionEntry 22 }

ibmcacheserverPartitionNotAddCacheOff OBJECT-TYPE
    SYNTAX Counter32
    ACCESS read-only
    STATUS mandatory
    DESCRIPTION
        "Items not added to partition due to
         caching turned off"
    ::= { ibmcacheserverPartitionEntry 23 }

ibmcacheserverPartitionNotAddTooLarge OBJECT-TYPE
    SYNTAX Counter32
    ACCESS read-only
    STATUS mandatory
    DESCRIPTION
        "Items not added to partition due to
         item larger than max allowed"
    ::= { ibmcacheserverPartitionEntry 24 }

ibmcacheserverPartitionNotAddHTTPHdr OBJECT-TYPE
    SYNTAX Counter32
    ACCESS read-only
    STATUS mandatory
    DESCRIPTION
        "Items not added to partition due to
         HTTP header specifying DO NOT CACHE"
    ::= { ibmcacheserverPartitionEntry 25 }

ibmcacheserverPartitionNotAddExclude OBJECT-TYPE
    SYNTAX Counter32
    ACCESS read-only
    STATUS mandatory
    DESCRIPTION
        "Items not added to partition due to
         item URL explicitly excluded"
    ::= { ibmcacheserverPartitionEntry 26 }

ibmcacheserverPartitionNotAddExpire OBJECT-TYPE
    SYNTAX Counter32
    ACCESS read-only
    STATUS mandatory
    DESCRIPTION
        "Items not added to partition due to
         item already expired"
    ::= { ibmcacheserverPartitionEntry 27 }

ibmcacheserverPartitionNotAddImage OBJECT-TYPE
    SYNTAX Counter32
    ACCESS read-only
    STATUS mandatory
    DESCRIPTION
        "Items not added to partition due to
         image items explicitly not cached"
    ::= { ibmcacheserverPartitionEntry 28 }

ibmcacheserverPartitionNotAddStatic OBJECT-TYPE
    SYNTAX Counter32
    ACCESS read-only
    STATUS mandatory
    DESCRIPTION
        "Items not added to partition due to
         static items explicitly not cached"
    ::= { ibmcacheserverPartitionEntry 29 }

ibmcacheserverPartitionNotAddDynamic OBJECT-TYPE
    SYNTAX Counter32
    ACCESS read-only
    STATUS mandatory
    DESCRIPTION
        "Items not added to partition due to
         dynamic items explicitly not cached"
    ::= { ibmcacheserverPartitionEntry 30 }

ibmcacheserverPartitionPurgeCacheFull OBJECT-TYPE
    SYNTAX Counter32
    ACCESS read-only
    STATUS mandatory
    DESCRIPTION
        "Items deleted from partition due to
         cache full"
    ::= { ibmcacheserverPartitionEntry 31 }

ibmcacheserverPartitionPurgeItemStale OBJECT-TYPE
    SYNTAX Counter32
    ACCESS read-only
    STATUS mandatory
    DESCRIPTION
        "Items deleted from partition due to
         item stale since expire time reached"
    ::= { ibmcacheserverPartitionEntry 32 }

ibmcacheserverPartitionPurgeItemExplicit OBJECT-TYPE
    SYNTAX Counter32
    ACCESS read-only
    STATUS mandatory
    DESCRIPTION
        "Items deleted from partition due to
         request for deletion"
    ::= { ibmcacheserverPartitionEntry 33 }

ibmcacheserverURLTable OBJECT-TYPE
    SYNTAX SEQUENCE OF IbmcacheserverURLEntry
    ACCESS not-accessible
    STATUS mandatory
    DESCRIPTION
        "Table of information pertaining to cache policies (URLs)"
    ::= { ibmcacheserverURL 1 }

ibmcacheserverURLEntry OBJECT-TYPE
    SYNTAX IbmcacheserverURLEntry
    ACCESS not-accessible
    STATUS mandatory
    DESCRIPTION
        "An entry containing objects for a particular cache policy (URLs)"
    INDEX { ibmcacheserverPartitionIndex, ibmcacheserverURLIndex }
    ::= { ibmcacheserverURLTable 1 }

IbmcacheserverURLEntry ::= SEQUENCE {
    ibmcacheserverURLIndex Integer32,
    ibmcacheserverURLContent INTEGER,
    ibmcacheserverURLMask DisplayString
    }

ibmcacheserverURLIndex OBJECT-TYPE
    SYNTAX Integer32
    ACCESS not-accessible
    STATUS mandatory
    DESCRIPTION
        "A unique value for each URL related to a particular partition.
         In this implementation, this index is a data structure pointer
         and therefore, may appear a bit odd looking. However, it is
         a valid, unique index value."
    ::= { ibmcacheserverURLEntry 1 }

ibmcacheserverURLContent OBJECT-TYPE
    SYNTAX INTEGER {
        include(1),
        exclude(2)
        }
    ACCESS read-only
    STATUS mandatory
    DESCRIPTION
        "Indication of whether URL is to be cached or excluded."
    ::= { ibmcacheserverURLEntry 2 }

ibmcacheserverURLMask OBJECT-TYPE
    SYNTAX DisplayString(SIZE(1..255))
--    Rsyntax OCTET STRING(SIZE(1..255))
    ACCESS read-only
    STATUS mandatory
    DESCRIPTION
        "URL string for this policy"
    ::= { ibmcacheserverURLEntry 3 }

ibmcacheserverProxyTable OBJECT-TYPE
    SYNTAX SEQUENCE OF IbmcacheserverProxyEntry
    ACCESS not-accessible
    STATUS mandatory
    DESCRIPTION
        "Table of information pertaining to HTTP proxy support"
    ::= { ibmcacheserverProxy 1 }

ibmcacheserverProxyEntry OBJECT-TYPE
    SYNTAX IbmcacheserverProxyEntry
    ACCESS not-accessible
    STATUS mandatory
    DESCRIPTION
        "An entry containing objects for a particular HTTP proxy socket"
    INDEX { ibmcacheserverProxyClusterAddr, ibmcacheserverProxyPort }
    ::= { ibmcacheserverProxyTable 1 }

IbmcacheserverProxyEntry ::= SEQUENCE {
    ibmcacheserverProxyClusterAddr IpAddress,
    ibmcacheserverProxyPort Integer32,
    ibmcacheserverProxyPartition Integer32,
    ibmcacheserverProxyClientCount Gauge32,
    ibmcacheserverProxyServerCount Gauge32,
    ibmcacheserverProxyClientMaxCount Gauge32,
    ibmcacheserverProxyServerMaxCount Gauge32,
    ibmcacheserverProxyCacheHits Counter32,
    ibmcacheserverProxyCacheMissMethod Counter32,
    ibmcacheserverProxyCacheMissStorage Counter32,
    ibmcacheserverProxyCacheMissNotInCache Counter32,
    ibmcacheserverProxyCacheMissHeaders Counter32
    }

ibmcacheserverProxyClusterAddr OBJECT-TYPE
    SYNTAX IpAddress
    ACCESS not-accessible
    STATUS mandatory
    DESCRIPTION
        "Cluster IP address"
    ::= { ibmcacheserverProxyEntry 1 }

ibmcacheserverProxyPort OBJECT-TYPE
    SYNTAX Integer32(0..65535)
    ACCESS not-accessible
    STATUS mandatory
    DESCRIPTION
        "Cluster IP port number"
    ::= { ibmcacheserverProxyEntry 2 }

ibmcacheserverProxyPartition OBJECT-TYPE
    SYNTAX Integer32
    ACCESS read-only
    STATUS mandatory
    DESCRIPTION
        "The partition identifier that this HTTP proxy is
         related to."
    ::= { ibmcacheserverProxyEntry 3 }

ibmcacheserverProxyClientCount OBJECT-TYPE
    SYNTAX Gauge32
    ACCESS read-only
    STATUS mandatory
    DESCRIPTION
        "Current number of TCP connections to clients"
    ::= { ibmcacheserverProxyEntry 4 }

ibmcacheserverProxyServerCount OBJECT-TYPE
    SYNTAX Gauge32
    ACCESS read-only
    STATUS mandatory
    DESCRIPTION
        "Current number of TCP connections to servers"
    ::= { ibmcacheserverProxyEntry 5 }

ibmcacheserverProxyClientMaxCount OBJECT-TYPE
    SYNTAX Gauge32
    ACCESS read-only
    STATUS mandatory
    DESCRIPTION
        "Highwater max number of TCP connections to clients"
    ::= { ibmcacheserverProxyEntry 6 }

ibmcacheserverProxyServerMaxCount OBJECT-TYPE
    SYNTAX Gauge32
    ACCESS read-only
    STATUS mandatory
    DESCRIPTION
        "Highwater max number of TCP connections to servers"
    ::= { ibmcacheserverProxyEntry 7 }

ibmcacheserverProxyCacheHits OBJECT-TYPE
    SYNTAX Counter32
    ACCESS read-only
    STATUS mandatory
    DESCRIPTION
        "Number of cache hits for this proxy"
    ::= { ibmcacheserverProxyEntry 8 }

ibmcacheserverProxyCacheMissMethod OBJECT-TYPE
    SYNTAX Counter32
    ACCESS read-only
    STATUS mandatory
    DESCRIPTION
        "Cache miss for this proxy due to method not being
         GET or HEAD."
    ::= { ibmcacheserverProxyEntry 9 }

ibmcacheserverProxyCacheMissStorage OBJECT-TYPE
    SYNTAX Counter32
    ACCESS read-only
    STATUS mandatory
    DESCRIPTION
        "Cache miss for this proxy due to lack of storage to
         generate a response."
    ::= { ibmcacheserverProxyEntry 10 }

ibmcacheserverProxyCacheMissNotInCache OBJECT-TYPE
    SYNTAX Counter32
    ACCESS read-only
    STATUS mandatory
    DESCRIPTION
        "Cache miss for this proxy due to not being in cache."
    ::= { ibmcacheserverProxyEntry 11 }

ibmcacheserverProxyCacheMissHeaders OBJECT-TYPE
    SYNTAX Counter32
    ACCESS read-only
    STATUS mandatory
    DESCRIPTION
        "Cache miss for this proxy due to headers on request cache
         not being used."
    ::= { ibmcacheserverProxyEntry 12 }


END
