XEDIA-ISDN-MIB DEFINITIONS ::= BEGIN

IMPORTS 
    MODULE-IDENTITY, OBJECT-TYPE
	FROM SNMPv2-SMI
    MODULE-COMPLIANCE, OBJECT-GROUP          
	FROM SNMPv2-CONF
    RowStatus, DisplayString
        FROM SNMPv2-TC
    isdnBasicRateEntry
        FROM ISDN-MIB
    isdnSignalingEntry
        FROM ISDN-MIB
    dialCtlPeerCfgEntry  
        FROM DIAL-CONTROL-MIB
    xediaMibs
        FROM XEDIA-REG
    ;    

xediaIsdnMIB MODULE-IDENTITY
    LAST-UPDATED "9909032155Z" -- September 3, 1999
    ORGANIZATION "Xedia Corp."
    CONTACT-INFO
        "support@xedia.com"
    DESCRIPTION
        "This module defines additional objects for management of ISDN
        in Xedia devices, above and beyond what is defined in the
        standard rfc2127, and proposed drafts."
    ::= { xediaMibs 37 }

-- Top-level organization of the MIB

xisdnObjects          OBJECT IDENTIFIER ::= { xediaIsdnMIB 1 }
xisdnConformance      OBJECT IDENTIFIER ::= { xediaIsdnMIB 2 }


-- ***************************************
-- Additions to the ISDN Basic Rate Table
-- ***************************************
xisdnTable        OBJECT-TYPE
    SYNTAX      SEQUENCE OF XisdnEntry
    MAX-ACCESS  not-accessible
    STATUS      current
    DESCRIPTION
            "A stupid SNMP construct."
    ::= { xisdnObjects 1 }

xisdnEntry        OBJECT-TYPE
    SYNTAX      XisdnEntry
    MAX-ACCESS  not-accessible
    STATUS      current
    DESCRIPTION
            "An entry containing additional management information
            applicable to an ISDN interface."
    AUGMENTS    { isdnBasicRateEntry }
    ::= { xisdnTable 1 }

XisdnEntry ::=
    SEQUENCE {
      xisdnLoopbackState INTEGER
    }

xisdnLoopbackState        OBJECT-TYPE
    SYNTAX      INTEGER {
        disabled(1),
        enabled(2)
    }
    MAX-ACCESS  read-write
    STATUS      current
    DESCRIPTION
            "loopback status"
    ::= { xisdnEntry 1 }
 
-- ***************************************
-- Additions to the peer configuration table
-- ***************************************

xisdnSignalingTable OBJECT-TYPE
        SYNTAX      SEQUENCE OF XIsdnSignalingEntry
        MAX-ACCESS  not-accessible
        STATUS      current
        DESCRIPTION
            "ISDN signaling table containing configuration and
             operational parameters for all ISDN signaling
             channels on this managed device."
        ::= { xisdnObjects 4 }

xisdnSignalingEntry OBJECT-TYPE
        SYNTAX      XIsdnSignalingEntry
        MAX-ACCESS  not-accessible
        STATUS      current
        DESCRIPTION
            "An entry in the ISDN Signaling Table. To create a new
             entry, only isdnSignalingProtocol needs to be specified
             before isdnSignalingStatus can become active(1)."
        AUGMENTS    { isdnSignalingEntry }
        ::= { xisdnSignalingTable 1 }

XIsdnSignalingEntry ::= SEQUENCE {
            isdnSignalingCallingAddress2 DisplayString,
            isdnEndpointSpid             DisplayString,
            isdnEndpointSpid2            DisplayString
        }

isdnSignalingCallingAddress2 OBJECT-TYPE
        SYNTAX      DisplayString
        MAX-ACCESS  read-create
        STATUS      current
        DESCRIPTION
            "The ISDN Address to be assigned to the second
             B channel.  Obviously not the right way to do this."

        REFERENCE
            "ITU-T E.164, Q.931 chapter 4.5.10"
        DEFVAL { "" }
        ::= { xisdnSignalingEntry 1 }

isdnEndpointSpid OBJECT-TYPE
        SYNTAX      DisplayString
        MAX-ACCESS  read-create
        STATUS      current
        DESCRIPTION
            "The Service profile IDentifier (SPID) information
             for this Terminal Endpoint.

             The SPID is composed of 9-20 numeric characters.

             This information has to be defined in addition to
             the local number for some switch protocol types,
             e.g. Bellcore NI-1 and NI-2.

             If this object is not required, it is a
             zero length string."
        REFERENCE
            "Bellcore SR-NWT-001953, Generic Guidelines for ISDN
             Terminal Equipment on Basic Access Interfaces,
             Chapter 8.5.1."
        DEFVAL { "" }
        ::= { xisdnSignalingEntry 2 }

isdnEndpointSpid2 OBJECT-TYPE
        SYNTAX      DisplayString
        MAX-ACCESS  read-create
        STATUS      current
        DESCRIPTION
            "The Service profile IDentifier (SPID) information
             for this Terminal Endpoint.

             The SPID is composed of 9-20 numeric characters.

             This information has to be defined in addition to
             the local number for some switch protocol types,
             e.g. Bellcore NI-1 and NI-2.

             If this object is not required, it is a
             zero length string."
        REFERENCE
            "Bellcore SR-NWT-001953, Generic Guidelines for ISDN
             Terminal Equipment on Basic Access Interfaces,
             Chapter 8.5.1."
        DEFVAL { "" }
        ::= { xisdnSignalingEntry 3 }


-- ***************************************
-- Additions to the peer configuration table
-- ***************************************
xdialCtlPeerCfgTable        OBJECT-TYPE
    SYNTAX      SEQUENCE OF XdialCtlPeerCfgEntry
    MAX-ACCESS  not-accessible
    STATUS      current
    DESCRIPTION
            "A stupid SNMP construct."
    ::= { xisdnObjects 2 }
 
xdialCtlPeerCfgEntry        OBJECT-TYPE
    SYNTAX      XdialCtlPeerCfgEntry
    MAX-ACCESS  not-accessible
    STATUS      current
    DESCRIPTION
            "An entry containing additional management information
            applicable to an ISDN interface."
    AUGMENTS    { dialCtlPeerCfgEntry }
    ::= { xdialCtlPeerCfgTable 1 }

XdialCtlPeerCfgEntry  ::=
    SEQUENCE {
      xcallControl INTEGER,
      xnailedUp INTEGER
    }

xcallControl    OBJECT-TYPE
    SYNTAX      INTEGER {
        noOp(1),
        connect(2),
        disconnect(3)
    }
    MAX-ACCESS  read-write
    STATUS      current
    DESCRIPTION
            "force outbound call"
    ::= { xdialCtlPeerCfgEntry 1 }
 
xnailedUp    OBJECT-TYPE
    SYNTAX      INTEGER {
        none(1),
        b1(2),
        b2(3)
    }
    MAX-ACCESS  read-write
    STATUS      current
    DESCRIPTION
            "permanant (non-signalling) B channel connection"
    ::= { xdialCtlPeerCfgEntry 2 }
-- ****************************************************************
-- Software Version
-- ****************************************************************

xisdnVersion OBJECT-TYPE
        SYNTAX DisplayString
        MAX-ACCESS  read-only
        STATUS      current
        DESCRIPTION
            "the ISDN subsystem software version number"
        ::= { xisdnObjects 3 }

-- ****************************************************************
-- Conformance Information
-- ****************************************************************

xisdnCompliances OBJECT IDENTIFIER ::= { xisdnConformance 1 }
xisdnGroups      OBJECT IDENTIFIER ::= { xisdnConformance 2 }

--
-- Compliance Statements
--

xisdnCompliance MODULE-COMPLIANCE
    STATUS      current
    DESCRIPTION
        "The compliance statement for all agents that support this
        MIB. A compliant agent implements all objects defined in this
        MIB."
    MODULE  -- this module
    MANDATORY-GROUPS {
        xisdnAllGroup
    }
    ::= { xisdnCompliances 1 }

--
-- All Object Groups
--
xisdnAllGroup OBJECT-GROUP
    OBJECTS {
        xisdnLoopbackState,
        xcallControl,
        xnailedUp,
        xisdnVersion,
        isdnSignalingCallingAddress2,
        isdnEndpointSpid,
        isdnEndpointSpid2
    }
    STATUS      current
    DESCRIPTION
        "The set of all accessible objects in this MIB."
    ::= { xisdnGroups 1 }

END
