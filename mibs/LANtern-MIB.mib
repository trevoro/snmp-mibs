LANtern-MIB DEFINITIONS ::= BEGIN

          -- Title: Lantern Network Monitor Version 1.3
          -- Date:  September 10, 1991

          -- Now RMON aligned (and politically correct!).


              IMPORTS
                     enterprises, TimeTicks, IpAddress, Counter, Gauge
                         FROM RFC1065-SMI
                     TRAP-TYPE
                         FROM RFC1215-MIB
                     OBJECT-TYPE
                         FROM RFC-1212;


          novell           OBJECT IDENTIFIER ::= { enterprises 23 }

          productType      OBJECT IDENTIFIER ::= { novell 1 }
          mibDoc           OBJECT IDENTIFIER ::= { novell 2 }

          networkMonitor   OBJECT IDENTIFIER ::= { productType 1 }

          ethernetLANtern  OBJECT IDENTIFIER ::= { networkMonitor 1 }

          lantern          OBJECT IDENTIFIER ::= { mibDoc 1 }

          lanternAdmin     OBJECT IDENTIFIER ::= { lantern 1 }
          lanternEthernet  OBJECT IDENTIFIER ::= { lantern 2 }
          lanternTokenRing OBJECT IDENTIFIER ::= { lantern 3 }
          lanternIp        OBJECT IDENTIFIER ::= { lantern 4 }
          lantern802dot2   OBJECT IDENTIFIER ::= { lantern 5 }
          lanternIpx       OBJECT IDENTIFIER ::= { lantern 6 }
          lanternProtocols OBJECT IDENTIFIER ::= { lantern 10 }



          -- textual conventions

          Time ::=
          INTEGER
          -- The date and time expressed as the number of seconds
          -- since midnight January 1, 1900 GMT

          DisplayString ::=
          OCTET STRING
          -- This type is used to model textual information taken
          -- from the NVT ASCII character set.

          PhysAddress ::=
          OCTET STRING
          -- This data type is used to model media addresses.

          Seconds ::=
          INTEGER
          -- This type is used to model durations in seconds.



          -- The Administrative Group

          adminIdentification OBJECT-TYPE
              SYNTAX DisplayString
              ACCESS read-write
              STATUS mandatory
              DESCRIPTION
                     "An identifying ASCII string may be attached to the
                     LANtern network monitor by writing
                     adminIdentification.  Conversely, the LANtern
                     network monitor may be identified by reading
                     adminIdentification.
                     adminIdentification is stored in nonvolatile RAM."
              DEFVAL { "" }
              ::= { lanternAdmin 1 }

          adminDateAndTime OBJECT-TYPE
              SYNTAX Time
              ACCESS read-write
              STATUS mandatory
              DESCRIPTION
                     "Reading adminDateAndTime returns the current date
                     and time in use by the LANtern network monitor.
                     The LANtern network monitor's date and time may be
                     adjusted at any time by writing to
                     adminDateAndTime.  However, although the new value
                     is updated correctly as time advances, it does not
                     replace the previous value until the LANtern
                     network monitor is restarted.
                     adminDateAndTime is stored in the clock/calendar
                     chip."
              ::= { lanternAdmin 2 }

          adminTimeZone OBJECT-TYPE
              SYNTAX DisplayString
              ACCESS read-write
              STATUS mandatory
              DESCRIPTION
                     "A DisplayString defining the time zone of the
                     LANtern network monitor.  adminTimeZone is neither
                     parsed nor used by the LANtern network monitor, it
                     is merely stored and divulged upon request.  It is
                     strongly recommended that adminTimeZone be used to
                     store time zone information in a manner identical
                     to the UNIX System V time zone environment variable
                     (TZ).  This standard approach would permit
                     interoperability with network management consoles
                     from multiple vendors.
                     adminTimeZone is stored in nonvolatile RAM."
              DEFVAL { "" }
              ::= { lanternAdmin 3 }

          adminPowerOnTime OBJECT-TYPE
              SYNTAX Time
              ACCESS read-only
              STATUS mandatory
              DESCRIPTION
                     "The date and time when the LANtern network monitor
                     was last powered on or restarted."
              ::= { lanternAdmin 4 }

          adminPowerOffTime OBJECT-TYPE
              SYNTAX Time
              ACCESS read-only
              STATUS mandatory
              DESCRIPTION
                     "The date and time when the LANtern network monitor
                     was last powered off or restarted.  The value is 0
                     (midnight, 1 January 1900) after a cold start."
              ::= { lanternAdmin 5 }

          adminNetworkDataLink OBJECT-TYPE
              SYNTAX INTEGER {
                         ethernetDIX(1)
                     }
              ACCESS read-write
              STATUS mandatory
              DESCRIPTION
                     "The type of data link encapsulation to be used on
                     the monitored network.  adminNetworkDataLink may be
                     written at any time; however, the change does not
                     take effect until the LANtern network monitor is
                     restarted.  When adminNetworkDataLink is read, it
                     returns the value currently in use, regardless of
                     any previous writes.
                     adminNetworkDataLink is stored in nonvolatile RAM."
              DEFVAL { 1 } -- ethernetDIX
              ::= { lanternAdmin 6 }

          adminNetworkIPAddr OBJECT-TYPE
              SYNTAX IpAddress
              ACCESS read-write
              STATUS mandatory
              DESCRIPTION
                     "The IP address to be used by the LANtern network
                     monitor on the monitored network.
                     adminNetworkIPAddr may be written at any time;
                     however, the change does not take effect until the
                     LANtern network monitor is restarted.  When
                     adminNetworkIPAddr is read, it returns the IP
                     address currently in use, regardless of any
                     previous writes.
                     adminNetworkIPAddr is stored in nonvolatile RAM.
                     On start up, if the LANtern does not have an IP
                     address, it will attempt to acquire one via BOOTP
                     and/or RARP.  If neither method is successful, the
                     address 192.68.205.1 is used."
              DEFVAL { 'c044cd01'H } --192.68.205.1
              ::= { lanternAdmin 7 }

          adminNetworkSubnetMask OBJECT-TYPE
              SYNTAX IpAddress
              ACCESS read-write
              STATUS mandatory
              DESCRIPTION
                     "The subnet mask for the monitored network.
                     adminNetworkSubnetMask may be written at any time;
                     however, the change does not take effect until the
                     LANtern network monitor is restarted.  When
                     adminNetworkSubnetMask is read, it returns the
                     subnet mask currently in use, regardless of any
                     previous writes.
                     adminNetworkSubnetMask is stored in nonvolatile
                     RAM.
                     When the value 0.0.0.0 is stored in this variable,
                     the LANtern assumes no subnetting.
                     This value is acquired via BOOTP if the value of
                     adminNetworkIPAddr is acquired via BOOTP.  If
                     neither BOOTP nor RARP succeeds in acquiring
                     adminNetworkIPAddr, the value 255.255.255.128 is
                     used"
              DEFVAL { 'ffffff80'H } -- 255.255.255.128
              ::= { lanternAdmin 8 }

          adminNetworkGateway OBJECT-TYPE
              SYNTAX IpAddress
              ACCESS read-write
              STATUS mandatory
              DESCRIPTION
                     "The IP address of a gateway directly connected to
                     the monitored network (the LANtern network
                     monitor's default gateway).  adminNetworkGateway
                     may be written at any time; however, the change
                     does not take effect until the LANtern network
                     monitor is restarted.  When adminNetworkGateway is
                     read it returns the gateway IP address currently in
                     use, regardless of any previous writes.
                     adminNetworkGateway is stored in nonvolatile RAM."
              DEFVAL { '00000000'H } -- No gateway
              ::= { lanternAdmin 9 }

          adminClientTable OBJECT-TYPE
              SYNTAX SEQUENCE OF AdminClientEntry
              ACCESS not-accessible
              STATUS mandatory
              DESCRIPTION
                     "A table providing data on all authorized LANtern
                     clients.  The table is accessed by
                     adminClientIPAddr.  A new entry may be created by
                     writing to a nonexistent instance.  Note that
                     adminClientIPAddr is set implicitly from this
                     write; it cannot be written directly.  An entry may
                     subsequently be deleted by writing (any value) to
                     adminClientDelete.
                     adminClientTable is stored in nonvolatile RAM.
                     Default:  a single entry with:
                         adminClientIPAddr.0.0.0.0=0.0.0.0,
                         adminClientIPMask.0.0.0.0=0.0.0.0,
                         adminClientCommunities.0.0.0.0=7"
              ::= { lanternAdmin 10 }

          adminClientEntry OBJECT-TYPE
              SYNTAX AdminClientEntry
              ACCESS not-accessible
              STATUS mandatory
              DESCRIPTION
                     "Data about each authorized client."
              INDEX  { adminClientIPAddr }
              ::= { adminClientTable 1 }

          AdminClientEntry ::=
              SEQUENCE {
                  adminClientIPAddr               IpAddress,
                  adminClientIPMask               IpAddress,
                  adminClientCommunities          INTEGER,
                  adminClientDelete               INTEGER
              }

          adminClientIPAddr OBJECT-TYPE
              SYNTAX IpAddress
              ACCESS read-only
              STATUS mandatory
              DESCRIPTION
                     "The IP address (or portion thereof) of a station
                     authorized to access the LANtern network monitor."
              ::= { adminClientEntry 1 }
          adminClientIPMask OBJECT-TYPE
              SYNTAX IpAddress
              ACCESS read-write
              STATUS mandatory
              DESCRIPTION
                     "A 32-bit mask that is bitwise anded with the
                     candidate client's IP address before attempting to
                     match against adminClientIPAddr."
              DEFVAL { 'ffffffff'H }
              ::= { adminClientEntry 2 }

          adminClientCommunities OBJECT-TYPE
              SYNTAX INTEGER
              ACCESS read-write
              STATUS mandatory
              DESCRIPTION
                     "A bit array where the presence of a particular bit
                     indicates that use of that particular community
                     name is permitted.
                         Bit  Community
                         2^0  administrator
                         2^1  logger
                         2^2  monitor."
              DEFVAL { 4 } -- monitor
              ::= { adminClientEntry 3 }

          adminClientDelete OBJECT-TYPE
              SYNTAX INTEGER
              ACCESS write-only
              STATUS mandatory
              DESCRIPTION
                     "A write (any value) causes the table entry to be
                     deleted."
              ::= { adminClientEntry 4 }

          adminUnauthorizedIPAddr OBJECT-TYPE
              SYNTAX IpAddress
              ACCESS not-accessible
              STATUS mandatory
              DESCRIPTION
                     "The IP address of the station that generated the
                     authentication failure."
              ::= { lanternAdmin 11 }

          adminUnauthorizedCommunity OBJECT-TYPE
              SYNTAX OCTET STRING
              ACCESS not-accessible
              STATUS mandatory
              DESCRIPTION
                     "The community name string used in the PDU that
                     generated the authentication failure."
              ::= { lanternAdmin 12 }

          adminNotificationTable OBJECT-TYPE
              SYNTAX SEQUENCE OF AdminNotificationEntry
              ACCESS not-accessible
              STATUS mandatory
              DESCRIPTION
                     "A list of all stations wishing to receive traps
                     from the LANtern network monitor; accessed by
                     adminNotificationIPAddr.  A new entry may be
                     created by writing to a nonexistent instance.  Note
                     that adminNotificationIPAddr is set implicitly from
                     this write; it cannot be written directly.  An
                     entry may subsequently be deleted by writing (any
                     value) to adminNotificationDelete
                     adminNotificationTable is stored in nonvolatile
                     RAM."
              ::= { lanternAdmin 13 }

          adminNotificationEntry OBJECT-TYPE
              SYNTAX AdminNotificationEntry
              ACCESS not-accessible
              STATUS mandatory
              DESCRIPTION
                     "Data for each station on the notification list."
              INDEX  { adminNotificationIPAddr }
              ::= { adminNotificationTable 1 }

          AdminNotificationEntry ::=
              SEQUENCE {
                  adminNotificationIPAddr         IpAddress,
                  adminNotificationStatus         INTEGER,
                  adminNotificationTrapMask       INTEGER,
                  adminNotificationConfirmMask    INTEGER,
                  adminNotificationTimeout        INTEGER,
                  adminNotificationRetries        INTEGER,
                  adminNotificationBackupIPAddr   IpAddress,
                  adminNotificationDelete         INTEGER
              }

          adminNotificationIPAddr OBJECT-TYPE
              SYNTAX IpAddress
              ACCESS read-only
              STATUS mandatory
              DESCRIPTION
                     "The IP address of the station wishing to receive
                     traps from the LANtern network monitor."
              ::= { adminNotificationEntry 1 }

          adminNotificationStatus OBJECT-TYPE
              SYNTAX INTEGER {
                         primaryContact(1),
                         backupContact(2)
                     }
              ACCESS read-write
              STATUS mandatory
              DESCRIPTION
                     "Traps are sent to all primaryContacts who have the
                     corresponding bit set in adminNotificationTrapMask.
                     Traps are sent to backupContacts only if they have
                     the corresponding bit set in
                     adminNotificationTrapMask and if a confirmed
                     delivery to a station naming it as backup failed.
                     Default:  primaryContact(1)"
              DEFVAL { 1 } -- primaryContact
              ::= { adminNotificationEntry 2 }

          adminNotificationTrapMask OBJECT-TYPE
              SYNTAX INTEGER
              ACCESS read-write
              STATUS mandatory
              DESCRIPTION
                     "A bit array specifying which traps the station
                     wishes to receive.
                         Bit  Trap
                         2^0  warmStart
                         2^1  cableFailure
                         2^2  reserved
                         2^3  duplicateIPAddr
                         2^4  utilizationAlarm
                         2^5  errorsAlarm
                         2^6  broadcastsAlarm
                         2^7  collisionsAlarm
                         2^8  authenticationFailure
                         2^9  hostInactive
                         2^10 hostActive
                         2^11 newHost
                         2^12 hostLimitExceeded"
              DEFVAL { 0 } -- No traps
              ::= { adminNotificationEntry 3 }

          adminNotificationConfirmMask OBJECT-TYPE
              SYNTAX INTEGER
              ACCESS read-write
              STATUS mandatory
              DESCRIPTION
                     "A bit array specifying which traps the station
                     wishes to receive with confirmed delivery.  Any
                     bits set must also be set in
                     adminNotificationTrapMask.  If a trap sent with
                     confirmed delivery is not acknowledged within
                     adminNotificationTimeout seconds it is sent again.
                     After adminNotificationRetries attempts to deliver
                     the trap, the LANtern network monitor gives up, and
                     tries to deliver it to the station specified by
                     adminNotificationBackup."
              DEFVAL { 0 } -- No confirmed traps
              ::= { adminNotificationEntry 4 }

          adminNotificationTimeout OBJECT-TYPE
              SYNTAX Seconds
              ACCESS read-write
              STATUS mandatory
              DESCRIPTION
                     "For traps with confirmed delivery,
                     adminNotificationTimeout specifies the interval (in
                     seconds) between retries."
              DEFVAL { 10 }
              ::= { adminNotificationEntry 5 }

          adminNotificationRetries OBJECT-TYPE
              SYNTAX INTEGER
              ACCESS read-write
              STATUS mandatory
              DESCRIPTION
                     "For traps with confirmed delivery,
                     adminNotificationRetries specifies the number of
                     retries that should be attempted before giving up
                     and trying to deliver the trap to
                     adminNotificationBackupIPAddr."
              DEFVAL { 2 }
              ::= { adminNotificationEntry 6 }

          adminNotificationBackupIPAddr OBJECT-TYPE
              SYNTAX IpAddress
              ACCESS read-write
              STATUS mandatory
              DESCRIPTION
                     "For traps with confirmed delivery,
                     adminNotificationBackupIPAddr specifies the IP
                     address of a backup station (also in
                     adminNotificationTable) to be contacted should
                     delivery of the trap to this station fail.
                     Default:  0.0.0.0  (no backup)"
              DEFVAL { '00000000'H } -- 0.0.0.0 (No backup)
              ::= { adminNotificationEntry 7 }
          adminNotificationDelete OBJECT-TYPE
              SYNTAX INTEGER
              ACCESS write-only
              STATUS mandatory
              DESCRIPTION
                     "A write (any value) causes the table entry to be
                     deleted."
              ::= { adminNotificationEntry 8 }

          adminTrapHandle OBJECT-TYPE
              SYNTAX INTEGER
              ACCESS not-accessible
              STATUS mandatory
              DESCRIPTION
                     "A unique handle that is generated for each trap
                     issued and that is passed in the trap-PDU along
                     with any other variable bindings."
              ::= { lanternAdmin 14 }

          adminTrapAcknowledge OBJECT-TYPE
              SYNTAX INTEGER
              ACCESS write-only
              STATUS mandatory
              DESCRIPTION
                     "A trap is acknowledged by writing the value of
                     adminTrapHandle passed in the trap-PDU to
                     adminTrapAcknowledge."
              ::= { lanternAdmin 15 }

          adminDownLoadFile OBJECT-TYPE
              SYNTAX OCTET STRING
              ACCESS read-write
              STATUS mandatory
              DESCRIPTION
                     "The name of the executable file to be downloaded
                     from adminDownLoadServer."
              ::= { lanternAdmin 16 }

          adminDownLoadServer OBJECT-TYPE
              SYNTAX IpAddress
              ACCESS read-write
              STATUS mandatory
              DESCRIPTION
                     "The name of the file server from which to download
                     a new executable image (adminDownLoadFile)."
              ::= { lanternAdmin 17 }

          adminDownload OBJECT-TYPE
              SYNTAX INTEGER {
                         temporaryChange(1),
                         permanentChange(2),
                         downloadSuccess(3),
                         tftpFailed(4),
                         badFile(5),
                         tftpUndefined(6),
                         tftpFileNotFound(7),
                         tftpAccessViolation(8),
                         tftpIllegalOperation(10),
                         tftpUnknownTransferID(11)
                     }
              ACCESS read-write
              STATUS mandatory
              DESCRIPTION
                     "A write to adminDownload of temporaryChange(1) or
                     permanentChange(2) causes the LANtern network
                     monitor to discontinue its normal functions and
                     perform a TFTP read of the file specified by
                     adminDownLoadFile from the server specified by
                     adminDownLoadServer into RAM.  Upon successful
                     completion of the file transfer, the new image is
                     written to the flash EPROM memory (permanentChange
                     only), destroying the previous image.  The LANtern
                     network monitor then performs a warm restart to
                     activate the new image.

                     A read of adminDownLoad returns the status of the
                     last download. The values temporaryChange(1) and
                     permanentChange(2) indicate a download is in
                     progress.  tftpFailed(4) indicates the server
                     failed to respond or the transfer timed out.
                     badFile(5)  occurs if the LANtern network monitor
                     determines the downloaded file has been corrupted
                     or is not a LANtern executable.  All other error
                     codes are the values defined by the TFTP protocol
                     [RFC 783], offset by six.

                     Note: adminDownloadFile and adminDownLoadServer
                     must be set prior (separate PDU) to setting
                     adminDownLoad."
              ::= { lanternAdmin 18 }

          adminReset OBJECT-TYPE
              SYNTAX INTEGER {
                         coldRestart(1),
                         warmRestart(2)
                     }
              ACCESS write-only
              STATUS mandatory
              DESCRIPTION
                     "A write to adminReset causes the LANtern network
                     monitor to discontinue its normal functions and
                     commence a restart sequence.  The contents of RAM,
                     including all counters and statistics, are lost.

                     A coldRestart destroys the contents of the
                     nonvolatile RAM and causes the LANtern network
                     monitor to start up exactly as if power was
                     supplied for the first time.  This is equivalent to
                     supplying power to the LANtern network monitor
                     while holding the hardware reset button depressed.

                     A warmRestart preserves the contents of the
                     nonvolatile RAM and causes the LANtern network
                     monitor to start up exactly as if the reset button
                     had been pressed (or power was being restored after
                     an outage)."
              ::= { lanternAdmin 19 }

          adminSerialDataLink OBJECT-TYPE
              SYNTAX INTEGER {
                         slip(1)
                     }
              ACCESS read-write
              STATUS mandatory
              DESCRIPTION
                     "The type of data link encapsulation to be used on
                     the serial line.  adminSerialDataLink may be
                     written at any time; however, the change does not
                     take effect until the LANtern network monitor is
                     restarted.  When adminSerialDataLink is read, it
                     returns the value currently in use, regardless of
                     any previous writes.
                     adminSerialDataLink is stored in nonvolatile RAM."
              DEFVAL { 1 } -- slip
              ::= { lanternAdmin 20 }

          adminSerialIPAddr OBJECT-TYPE
              SYNTAX IpAddress
              ACCESS read-write
              STATUS mandatory
              DESCRIPTION
                     "The IP address currently in use by the LANtern
                     network monitor on the serial channel.
                     adminSerialIPAddr may be written at any time;
                     however, the change does not take effect until the
                     LANtern network monitor is restarted.  When
                     adminSerialIPAddr is read, it returns the IP
                     address currently in use, regardless of any
                     previous writes.
                     adminSerialIPAddr is stored in nonvolatile RAM."
              DEFVAL { 'c044cd81'H } -- 192.68.205.129
              ::= { lanternAdmin 21 }

          adminSerialSubnetMask OBJECT-TYPE
              SYNTAX IpAddress
              ACCESS read-write
              STATUS mandatory
              DESCRIPTION
                     "The subnet mask for the serial channel.
                     adminSerialSubnetMask may be written at any time;
                     however, the change does not take effect until the
                     LANtern network monitor is restarted.  When this
                     variable is read, it returns the subnet mask
                     currently in use, regardless of any previous
                     writes. When the value 0.0.0.0 is stored in this
                     variable, the LANtern assumes no subnetting.
                     adminSerialSubnetMask is stored in nonvolatile
                     RAM."
              DEFVAL { 'ffffff80'H } -- 255.255.255.128
              ::= { lanternAdmin 22 }

          adminSerialBaudRate OBJECT-TYPE
              SYNTAX INTEGER {
                         baud300(1),
                         baud1200(2),
                         baud2400(3),
                         baud4800(4),
                         baud7200(5),
                         baud9600(6),
                         baud19200(7),
                         baud38400(8)
                     }
              ACCESS read-write
              STATUS mandatory
              DESCRIPTION
                     "A codification of the baud rate to be used on the
                     serial line for incoming calls or when the line is
                     directly connected.  Change does not switch line
                     speed until next state change of modem or reset.
                     adminSerialBaudRate is stored in nonvolatile RAM."
              DEFVAL { 3 } -- 2400 baud
              ::= { lanternAdmin 23 }

          adminSerialTimeout OBJECT-TYPE
              SYNTAX Seconds
              ACCESS read-write
              STATUS mandatory
              DESCRIPTION
                     "Once a phone connection has been established, the
                     LANtern network monitor maintains that connection
                     until either the other end hangs up or
                     adminSerialTimeout seconds elapses with no
                     communication.
                     adminSerialTimeout is stored in nonvolatile RAM."
              DEFVAL { 60 }
              ::= { lanternAdmin 24 }

          adminSerialConnection OBJECT-TYPE
              SYNTAX INTEGER {
                         modem(1),
                         direct(2)
                     }
              ACCESS read-write
              STATUS mandatory
              DESCRIPTION
                     "The type of connection used by the serial line.
                     adminSerialConnection may be written at any time;
                     however, the change does not take effect until the
                     LANtern network monitor is restarted. When
                     adminSerialConnection is read, it returns the value
                     currently in use, regardless of any previous
                     writes.
                     adminSerialConnection is stored in nonvolatile
                     RAM."
              DEFVAL { 1 } -- modem
              ::= { lanternAdmin 25 }

          adminSerialFlowControl OBJECT-TYPE
              SYNTAX INTEGER {
                         none(1),
                         rts-cts(2)
                     }
              ACCESS read-write
              STATUS mandatory
              DESCRIPTION
                     "The type of flow control used on the serial line.
                     adminSerialFlowControl may be written at any time;
                     however, the change does not take effect until the
                     LANtern network monitor is restarted. When
                     adminSerialFlowControl  is read, it returns the
                     value currently in use, regardless of any previous
                     writes.
                     adminSerialFlowControl is stored in nonvolatile
                     RAM."
              DEFVAL { 1 } -- No flow control
              ::= { lanternAdmin 26 }

          adminModemControl OBJECT-TYPE
              SYNTAX OCTET STRING
              ACCESS read-write
              STATUS mandatory
              DESCRIPTION
                     "A delimited string containing commands to
                     initialize, dial, and hang up the modem.  See
                     Section 3.1.2 for more details on the format of
                     this string.  adminModemControl may be written at
                     any time; however, the change does not take effect
                     until the LANtern network monitor is restarted.
                     When adminModemControl is read, it returns the
                     value currently in use, regardless of any previous
                     writes.
                     adminModemControl is stored in nonvolatile RAM."
              DEFVAL { "#^ATS0=1 Q0 V1 X4 &S1 &D2^M^1AT &W0
                     &Y0^M#^1ATDT#^2+++^2ATH0^M#" }
                     -- (Hayes-compatible commands)
              ::= { lanternAdmin 27 }

          adminModemConnect OBJECT-TYPE
              SYNTAX OCTET STRING
              ACCESS read-write
              STATUS mandatory
              DESCRIPTION
                     "A delimited string containing baud rates and modem
                     responses when it connects at particular baud
                     rates.  See Section 3.1.2 for more details on the
                     format of this string.  adminModemConnect may be
                     written at any time; however, the change does not
                     take effect until the LANtern network monitor is
                     restarted. When adminModemConnect is read, it
                     returns the value currently in use, regardless of
                     any previous writes.
                     adminModemConnect is stored in nonvolatile RAM."
              DEFVAL { "#19200#CONNECT 19200#9600#CONNECT
                     9600#4800#CONNECT 4800#2400#CONNECT
                     2400#1200#CONNECT 1200#300#CONNECT#" }
                     -- (Hayes modem compatible responses)
              ::= { lanternAdmin 28 }

          adminModemNoConnect OBJECT-TYPE
              SYNTAX OCTET STRING
              ACCESS read-write
              STATUS mandatory
              DESCRIPTION
                     "A delimited string containing baud rates and modem
                     responses when it connects at particular baud
                     rates. See Section 3 for more details on the format
                     of this string.  adminModemNoConnect may be written
                     at any time; however, the change does not take
                     effect until the LANtern network monitor is
                     restarted. When adminModemNoConnect is read, it
                     returns the value currently in use, regardless of
                     any previous writes.
                     adminModemNoConnect is stored in nonvolatile RAM."
              DEFVAL { "#NO DIALTONE#NO CARRIER#BUSY#VOICE#TIMEOUT#" }
              ::= { lanternAdmin 29 }

          adminGatewayControl OBJECT-TYPE
              SYNTAX INTEGER {
                         gateway-off(1),
                         gateway-on(2)
                     }
              ACCESS read-write
              STATUS mandatory
              DESCRIPTION
                     "A switch to enable or disable IP gatewaying
                     between the serial line and the network.
                     See Section 3 for more details on the format of
                     this string.  adminGatewayControl may be written at
                     any time; however, the change does not take effect
                     until the LANtern network monitor is restarted.
                     When adminGatewayControl is read, it returns the
                     value currently in use, regardless of any previous
                     writes.
                     adminGatewayControl is stored in nonvolatile RAM."
              DEFVAL { 1 } -- Gateway off
              ::= { lanternAdmin 30 }

          adminPhoneTable OBJECT-TYPE
              SYNTAX SEQUENCE OF AdminPhoneEntry
              ACCESS not-accessible
              STATUS mandatory
              DESCRIPTION
                     "A table that provides information about each
                     possible phone connection that can be made over the
                     serial channel.  The table is accessed by
                     adminPhoneIPAddr.  A new entry can be created by
                     writing to a nonexistent instance.  Note that
                     adminPhoneIPAddr is set implicitly from this write.
                     adminPhoneIPAddr cannot be written directly.  An
                     entry may subsequently be deleted by writing (any
                     value) to adminPhoneDelete.  See Section 3 for more
                     details about using the phone table.
                     adminPhoneTable is stored in nonvolatile RAM."
              ::= { lanternAdmin 31 }

          adminPhoneEntry OBJECT-TYPE
              SYNTAX AdminPhoneEntry
              ACCESS not-accessible
              STATUS mandatory
              DESCRIPTION
                     "Data for a particular phone connection that can be
                     established over the serial channel."
              INDEX  { adminPhoneIPAddr }
              ::= { adminPhoneTable 1 }

          AdminPhoneEntry ::=
              SEQUENCE {
                  adminPhoneIPAddr                IpAddress,
                  adminPhoneIPMask                IpAddress,
                  adminPhoneLocalIPAddr           IpAddress,
                  adminPhoneNumber                OCTET STRING,
                  adminPhoneConnectionProtocol    OCTET STRING,
                  adminPhoneDelete                INTEGER
              }

          adminPhoneIPAddr OBJECT-TYPE
              SYNTAX IpAddress
              ACCESS read-only
              STATUS mandatory
              DESCRIPTION
                     "The IP address of the machine or IP network (SLIP
                     gateway) at adminPhoneNumber."
              ::= { adminPhoneEntry 1 }

          adminPhoneIPMask OBJECT-TYPE
              SYNTAX IpAddress
              ACCESS read-write
              STATUS mandatory
              DESCRIPTION
                     "The IP subnet mask to be used when communicating
                     over this phone connection. When the value 0.0.0.0
                     is stored in this variable, the LANtern network
                     monitor assumes no subnetting.
                     Default:  0.0.0.0  (no subnetting)"
              DEFVAL { '00000000'H } -- 0.0.0.0 (No subnetting)
              ::= { adminPhoneEntry 2 }

          adminPhoneLocalIPAddr OBJECT-TYPE
              SYNTAX IpAddress
              ACCESS read-write
              STATUS mandatory
              DESCRIPTION
                     "The IP address the LANtern network monitor uses
                     for its serial port while communicating over this
                     phone connection."
              DEFVAL { '00000000'H } -- 0.0.0.0 (use adminSerialIPAddr)
              ::= { adminPhoneEntry 3 }

          adminPhoneNumber OBJECT-TYPE
              SYNTAX OCTET STRING
              ACCESS read-write
              STATUS mandatory
              DESCRIPTION
                     "The phone number string the modem uses to dial the
                     machine with IP address adminPhoneIPAddr."
              ::= { adminPhoneEntry 4 }

          adminPhoneConnectionProtocol OBJECT-TYPE
              SYNTAX OCTET STRING
              ACCESS read-write
              STATUS mandatory
              DESCRIPTION
                     "An ASCII string specifying the logon sequence once
                     the phone is connected."
              ::= { adminPhoneEntry 5 }

          adminPhoneDelete OBJECT-TYPE
              SYNTAX INTEGER
              ACCESS write-only
              STATUS mandatory
              DESCRIPTION
                     "A write (any value) causes the table entry to be
                     deleted."
              ::= { adminPhoneEntry 6 }



          -- The Ethernet Group

          eNetworkEvents OBJECT-TYPE
              SYNTAX Counter
              ACCESS read-only
              STATUS mandatory
              DESCRIPTION
                     "The total number of network events (good packets,
                     error packets, and collisions) observed since
                     counter initialization.  A network event is any
                     activity on the network in which signal transitions
                     cause carrier sense to be active for more than 0.5
                     microseconds.  Carrier sense dropouts that occur
                     during collisions, and sometimes at the beginning
                     or end of packets, are filtered out to ensure that
                     an individual packet is counted only once."
              ::= { lanternEthernet 1 }

          eGoodPkts OBJECT-TYPE
              SYNTAX Counter
              ACCESS read-only
              STATUS mandatory
              DESCRIPTION
                     "The total number of legally formed packets
                     received by the network controller since counter
                     initialization."
              ::= { lanternEthernet 2 }

          eBroadcastPkts OBJECT-TYPE
              SYNTAX Counter
              ACCESS read-only
              STATUS mandatory
              DESCRIPTION
                     "The total number of good packets with the
                     broadcast address as the destination address."
              ::= { lanternEthernet 3 }

          eMulticastPkts OBJECT-TYPE
              SYNTAX Counter
              ACCESS read-only
              STATUS mandatory
              DESCRIPTION
                     "The total number of good packets with a multicast
                     address as the destination address.  The broadcast
                     address is not included."
              ::= { lanternEthernet 4 }

          eUnicastPkts OBJECT-TYPE
              SYNTAX Counter
              ACCESS read-only
              STATUS mandatory
              DESCRIPTION
                     "The total number of good packets with an
                     individual host address as the destination
                     address."
              ::= { lanternEthernet 5 }

          ePkts64to127Octets OBJECT-TYPE
              SYNTAX Counter
              ACCESS read-only
              STATUS mandatory
              DESCRIPTION
                     "The total number of good packets between 64 and
                     127 octets in length, including the CRC."
              ::= { lanternEthernet 6 }
          ePkts128to255Octets OBJECT-TYPE
              SYNTAX Counter
              ACCESS read-only
              STATUS mandatory
              DESCRIPTION
                     "The total number of good packets between 128 and
                     255 octets in length, including the CRC."
              ::= { lanternEthernet 7 }

          ePkts256to511Octets OBJECT-TYPE
              SYNTAX Counter
              ACCESS read-only
              STATUS mandatory
              DESCRIPTION
                     "The total number of good packets between 256 and
                     511 octets in length, including CRC."
              ::= { lanternEthernet 8 }

          ePkts512to1023Octets OBJECT-TYPE
              SYNTAX Counter
              ACCESS read-only
              STATUS mandatory
              DESCRIPTION
                     "The total number of good packets between 512 and
                     1023 octets in length, including CRC."
              ::= { lanternEthernet 9 }

          ePkts1024to1518Octets OBJECT-TYPE
              SYNTAX Counter
              ACCESS read-only
              STATUS mandatory
              DESCRIPTION
                     "The total number of good packets between 1024 and
                     1518 octets in length, including CRC."
              ::= { lanternEthernet 10 }

          eErrors OBJECT-TYPE
              SYNTAX Counter
              ACCESS read-only
              STATUS mandatory
              DESCRIPTION
                     "The total number of errors detected since counter
                     initialization.  It is the sum of a CRC/Alignment
                     errors, Oversize errors, Undersize errors, and
                     Jabbers, as defined below."
              ::= { lanternEthernet 11 }

          eCRCAlignErrors OBJECT-TYPE
              SYNTAX Counter
              ACCESS read-only
              STATUS mandatory
              DESCRIPTION
                     "The total number of legal size packets with a bad
                     Frame Check Sequence (FCS) received by the network
                     controller since counter initialization."
              ::= { lanternEthernet 12 }

          eUndersizePkts OBJECT-TYPE
              SYNTAX Counter
              ACCESS read-only
              STATUS mandatory
              DESCRIPTION
                     "The total number of undersize packets received by
                     the network controller since counter
                     initialization.  An undersize packet is one that is
                     less than 64 octets long (including CRC) and is
                     otherwise well formed."
              ::= { lanternEthernet 13 }

          eOversizePkts OBJECT-TYPE
              SYNTAX Counter
              ACCESS read-only
              STATUS mandatory
              DESCRIPTION
                     "The total number of oversize packets received by
                     the network controller since counter
                     initialization.  An oversize packet is one that is
                     longer than 1518 octets (including CRC) and is
                     otherwise well-formed."
              ::= { lanternEthernet 14 }

          eJabbers OBJECT-TYPE
              SYNTAX Counter
              ACCESS read-only
              STATUS mandatory
              DESCRIPTION
                     "The total number of packets longer than 1518
                     octets with a bad Frame Check Sequence (FCS)
                     received by the network controller since counter
                     initialization."
              ::= { lanternEthernet 15 }

          eCollisions OBJECT-TYPE
              SYNTAX Counter
              ACCESS read-only
              STATUS mandatory
              DESCRIPTION
                     "The total number of local collisions observed
                     since counter initialization.  A local collision is
                     a collision or other 'signal quality error' event
                     that occurs on the segment to which the LANtern
                     network monitor is attached."
              ::= { lanternEthernet 16 }

          eFragments OBJECT-TYPE
              SYNTAX Counter
              ACCESS read-only
              STATUS mandatory
              DESCRIPTION
                     "The total number of packets shorter than 64 octets
                     with a bad Frame Check Sequence (FCS) received by
                     the network controller since counter
                     initialization."
              ::= { lanternEthernet 17 }

          eOctets OBJECT-TYPE
              SYNTAX Counter
              ACCESS read-only
              STATUS mandatory
              DESCRIPTION
                     "The total number of octets on the network in good
                     packets.  The source/destination address, the
                     type/length field, and the CRC are included.  This
                     measurement gives a good indication of useful
                     network throughput."
              ::= { lanternEthernet 18 }

          eTimeUSecs OBJECT-TYPE
              SYNTAX Counter
              ACCESS read-only
              STATUS mandatory
              DESCRIPTION
                     "Time in microseconds.  If read in the same PDU as
                     other counters, this can be used to accurately
                     compute statistics over time."
              ::= { lanternEthernet 19 }

          eCarrierUSecs OBJECT-TYPE
              SYNTAX Counter
              ACCESS read-only
              STATUS mandatory
              DESCRIPTION
                     "The number of microseconds during which carrier
                     was detected on the cable.  This can be used in
                     conjunction with eTimeUSecs to accurately compute
                     network utilization over time."
              ::= { lanternEthernet 20 }

          eHistoryBuckets OBJECT-TYPE
              SYNTAX INTEGER
              ACCESS read-only
              STATUS mandatory
              DESCRIPTION
                     "The number of discrete time intervals (or buckets)
                     over which the logged data is saved.  This number
                     is a constant."
              ::= { lanternEthernet 21 }

          eHistoryInterval OBJECT-TYPE
              SYNTAX Seconds (1..3600)
              ACCESS read-write
              STATUS mandatory
              DESCRIPTION
                     "The interval, in seconds, represented by each
                     bucket.
                     eHistoryInterval is stored in nonvolatile RAM."
              DEFVAL { 900 } -- 15 minutes
              ::= { lanternEthernet 22 }

          eHistoryTable OBJECT-TYPE
              SYNTAX SEQUENCE OF EHistoryEntry
              ACCESS not-accessible
              STATUS mandatory
              DESCRIPTION
                     "A log of the network events that occurred during
                     each of the preceding eHistoryBuckets intervals of
                     length eHistoryInterval."
              ::= { lanternEthernet 23 }

          eHistoryEntry OBJECT-TYPE
              SYNTAX EHistoryEntry
              ACCESS not-accessible
              STATUS mandatory
              DESCRIPTION
                     "Each logged counter has the same semantics as the
                     counter with a similar name defined above, except
                     that each counter records only those events that
                     occurred during the log interval.  The remaining
                     log entries are defined below."
              INDEX  { eHistoryIntervalStart }
              ::= { eHistoryTable 1 }

          EHistoryEntry ::=
              SEQUENCE {
                  eHistoryNetworkEvents           Counter,
                  eHistoryGoodPkts                Counter,
                  eHistoryBroadcastPkts           Counter,
                  eHistoryMulticastPkts           Counter,
                  eHistoryUnicastPkts             Counter,
                  eHistoryPkts64to127Octets       Counter,
                  eHistoryPkts128to255Octets      Counter,
                  eHistoryPkts256to511Octets      Counter,
                  eHistoryPkts512to1023Octets     Counter,
                  eHistoryPkts1024to1518Octets    Counter,
                  eHistoryErrors                  Counter,
                  eHistoryCRCAlignErrors          Counter,
                  eHistoryUndersizePkts           Counter,
                  eHistoryOversizePkts            Counter,
                  eHistoryJabbers                 Counter,
                  eHistoryCollisions              Counter,
                  eHistoryFragments               Counter,
                  eHistoryOctets                  Counter,
                  eHistoryUtilization             INTEGER,
                  eHistoryIntervalStart           Time,
                  eHistoryIntervalEnd             Time
              }

          eHistoryNetworkEvents OBJECT-TYPE
              SYNTAX Counter
              ACCESS read-only
              STATUS mandatory
              DESCRIPTION
                     "The number of network events (good packets, error
                     packets, and collisions) observed during the
                     interval.  A network event is any activity on the
                     network in which signal transitions cause carrier
                     sense to be active for more than 0.5 microseconds.
                     Carrier sense dropouts that occur during
                     collisions, and sometimes at the beginning or end
                     of packets, are filtered out to ensure that an
                     individual packet is counted only once."
              ::= { eHistoryEntry 1 }

          eHistoryGoodPkts OBJECT-TYPE
              SYNTAX Counter
              ACCESS read-only
              STATUS mandatory
              DESCRIPTION
                     "The number of legally formed packets received by
                     the network controller during the interval."
              ::= { eHistoryEntry 2 }

          eHistoryBroadcastPkts OBJECT-TYPE
              SYNTAX Counter
              ACCESS read-only
              STATUS mandatory
              DESCRIPTION
                     "The number of good packets with the broadcast
                     address as the destination address received during
                     the interval."
              ::= { eHistoryEntry 3 }

          eHistoryMulticastPkts OBJECT-TYPE
              SYNTAX Counter
              ACCESS read-only
              STATUS mandatory
              DESCRIPTION
                     "The number of good packets with a multicast
                     address as the destination address received during
                     the interval.  The broadcast address is not
                     included."
              ::= { eHistoryEntry 4 }
          eHistoryUnicastPkts OBJECT-TYPE
              SYNTAX Counter
              ACCESS read-only
              STATUS mandatory
              DESCRIPTION
                     "The number of good packets with an individual host
                     address as the destination address received during
                     the interval."
              ::= { eHistoryEntry 5 }

          eHistoryPkts64to127Octets OBJECT-TYPE
              SYNTAX Counter
              ACCESS read-only
              STATUS mandatory
              DESCRIPTION
                     "The number of good packets between 64 and 127
                     octets in length, including the CRC received during
                     the interval."
              ::= { eHistoryEntry 6 }

          eHistoryPkts128to255Octets OBJECT-TYPE
              SYNTAX Counter
              ACCESS read-only
              STATUS mandatory
              DESCRIPTION
                     "The number of good packets between 128 and 255
                     octets in length, including the CRC received during
                     the interval."
              ::= { eHistoryEntry 7 }

          eHistoryPkts256to511Octets OBJECT-TYPE
              SYNTAX Counter
              ACCESS read-only
              STATUS mandatory
              DESCRIPTION
                     "The number of good packets between 256 and 511
                     octets in length, including CRC received during the
                     interval."
              ::= { eHistoryEntry 8 }

          eHistoryPkts512to1023Octets OBJECT-TYPE
              SYNTAX Counter
              ACCESS read-only
              STATUS mandatory
              DESCRIPTION
                     "The number of good packets between 512 and 1023
                     octets in length, including CRC received during the
                     interval."
              ::= { eHistoryEntry 9 }

          eHistoryPkts1024to1518Octets OBJECT-TYPE
              SYNTAX Counter
              ACCESS read-only
              STATUS mandatory
              DESCRIPTION
                     "The  number of good packets between 1024 and 1518
                     octets in length, including CRC received during the
                     interval."
              ::= { eHistoryEntry 10 }

          eHistoryErrors OBJECT-TYPE
              SYNTAX Counter
              ACCESS read-only
              STATUS mandatory
              DESCRIPTION
                     "The number of errors detected during the interval.
                     It is the sum of a CRC/Alignment errors, Oversize
                     errors, Undersize errors, and Jabbers, as defined
                     below."
              ::= { eHistoryEntry 11 }

          eHistoryCRCAlignErrors OBJECT-TYPE
              SYNTAX Counter
              ACCESS read-only
              STATUS mandatory
              DESCRIPTION
                     "The number of legal size packets with a bad Frame
                     Check Sequence (FCS) received by the network
                     controller during the interval."
              ::= { eHistoryEntry 12 }

          eHistoryUndersizePkts OBJECT-TYPE
              SYNTAX Counter
              ACCESS read-only
              STATUS mandatory
              DESCRIPTION
                     "The number of undersize packets received by the
                     network controller during the interval.  An
                     undersize packet is one that is less than 64 octets
                     long (including CRC) and is otherwise well formed."
              ::= { eHistoryEntry 13 }

          eHistoryOversizePkts OBJECT-TYPE
              SYNTAX Counter
              ACCESS read-only
              STATUS mandatory
              DESCRIPTION
                     "The number of oversize packets received by the
                     network controller during the interval.  An
                     oversize packet is one that is longer than 1518
                     octets (including CRC) and is otherwise well-
                     formed."
              ::= { eHistoryEntry 14 }

          eHistoryJabbers OBJECT-TYPE
              SYNTAX Counter
              ACCESS read-only
              STATUS mandatory
              DESCRIPTION
                     "The number of packets longer than 1518 octets with
                     a bad Frame Check Sequence (FCS) received by the
                     network controller during the interval."
              ::= { eHistoryEntry 15 }

          eHistoryCollisions OBJECT-TYPE
              SYNTAX Counter
              ACCESS read-only
              STATUS mandatory
              DESCRIPTION
                     "The number of local collisions observed during the
                     interval.  A local collision is a collision or
                     other 'signal quality error' event that occurs on
                     the segment to which the LANtern network monitor is
                     attached."
              ::= { eHistoryEntry 16 }

          eHistoryFragments OBJECT-TYPE
              SYNTAX Counter
              ACCESS read-only
              STATUS mandatory
              DESCRIPTION
                     "The number of packets shorter than 64 octets with
                     a bad Frame Check Sequence (FCS) received by the
                     network controller during the interval."
              ::= { eHistoryEntry 17 }

          eHistoryOctets OBJECT-TYPE
              SYNTAX Counter
              ACCESS read-only
              STATUS mandatory
              DESCRIPTION
                     "The number of octets on the network in good
                     packets during the interval.  The
                     source/destination address, the type/length field,
                     and the CRC are included.  This measurement gives a
                     good indication of useful network throughput."
              ::= { eHistoryEntry 18 }

          eHistoryUtilization OBJECT-TYPE
              SYNTAX INTEGER
              ACCESS read-only
              STATUS mandatory
              DESCRIPTION
                     "The average network utilization during this
                     interval, in tenths of a percent."
              ::= { eHistoryEntry 19 }

          eHistoryIntervalStart OBJECT-TYPE
              SYNTAX Time
              ACCESS read-only
              STATUS mandatory
              DESCRIPTION
                     "The date and time of the start of the interval
                     represented by the data in this bucket.  This is
                     the same as eHistoryIntervalEnd of the previous
                     bucket."
              ::= { eHistoryEntry 20 }

          eHistoryIntervalEnd OBJECT-TYPE
              SYNTAX Time
              ACCESS read-only
              STATUS mandatory
              DESCRIPTION
                     "The date and time of the end of the interval
                     represented by the data in this bucket.  This is
                     the same as eHistoryIntervalStart of the next
                     bucket."
              ::= { eHistoryEntry 21 }

          eAlarmTable OBJECT-TYPE
              SYNTAX SEQUENCE OF EAlarmEntry
              ACCESS not-accessible
              STATUS mandatory
              DESCRIPTION
                     "A table of critical gauges for which an alarm is
                     generated, if one exceeds its predetermined
                     thresholds.  The table is accessed by gauge type.
                     The user-settable parameters of eAlarmTable are
                     stored in nonvolatile RAM."
              ::= { lanternEthernet 24 }

          eAlarmEntry OBJECT-TYPE
              SYNTAX EAlarmEntry
              ACCESS not-accessible
              STATUS mandatory
              DESCRIPTION
                     "Parameters for each alarmed gauge."
              INDEX  { eAlarmType }
              ::= { eAlarmTable 1 }

          EAlarmEntry ::=
              SEQUENCE {
                  eAlarmType                      INTEGER,
                  eAlarmValue                     Gauge,
                  eAlarmState                     INTEGER,
                  eAlarmSampleTime                Seconds,
                  eAlarmMinTraffic                INTEGER,
                  eAlarmLowThreshold              INTEGER,
                  eAlarmHighThreshold             INTEGER,
                  eAlarmLowDelta                  INTEGER,
                  eAlarmHighDelta                 INTEGER,
                  eAlarmLowWaterMark              INTEGER,
                  eAlarmHighWaterMark             INTEGER,
                  eAlarmLowSetTime                Time,
                  eAlarmHighSetTime               Time
              }

          eAlarmType OBJECT-TYPE
              SYNTAX INTEGER {
                         percentUtilization(1),
                         percentErrors(2),
                         percentBroadcasts(3),
                         percentCollisions(4)
                     }
              ACCESS read-only
              STATUS mandatory
              DESCRIPTION
                     "Defines the network parameter being monitored by
                     this gauge.

                     percentUtilization:     Average percent
                                             utilization.
                     percentErrors:          Errors as a percentage of
                                             total packets (good
                                             packets + errors).
                     percentBroadcasts:      Broadcast packets as a
                                             percentage of total good
                                             packets.
                     percentCollisions:      Local collisions as a
                                             percentage of total
                                             network events."
              ::= { eAlarmEntry 1 }

          eAlarmValue OBJECT-TYPE
              SYNTAX Gauge
              ACCESS read-only
              STATUS mandatory
              DESCRIPTION
                     "The value, in tenths of one percent, of the
                     monitored network parameter computed over the
                     previous sampling interval."
              ::= { eAlarmEntry 2 }

          eAlarmState OBJECT-TYPE
              SYNTAX INTEGER {
                         disarmed(1),
                         armed(2)
                     }
              ACCESS read-write
              STATUS mandatory
              DESCRIPTION
                     "If the gauge is enabled, its value is computed and
                     an alarm (trap-PDU) is generated if either of its
                     thresholds is exceeded.  Otherwise, its value is
                     not computed.
                     eAlarmState is stored in nonvolatile RAM."
              DEFVAL { 1 } -- Disabled
              ::= { eAlarmEntry 3 }

          eAlarmSampleTime OBJECT-TYPE
              SYNTAX Seconds (1..3600)
              ACCESS read-write
              STATUS mandatory
              DESCRIPTION
                     "The interval, in seconds, over which eAlarmValue
                     is sampled.
                     eAlarmSampleTime is stored in nonvolatile RAM."
              DEFVAL { 1 }
              ::= { eAlarmEntry 4 }

          eAlarmMinTraffic OBJECT-TYPE
              SYNTAX INTEGER
              ACCESS read-write
              STATUS mandatory
              DESCRIPTION
                     "The minimum value the denominator of the alarm
                     equation must achieve during the sample interval
                     before the LANtern network monitor updates
                     eAlarmValue.  This can be used to prevent spurious
                     alarms caused by very low traffic.
                     eAlarmMinTraffic is stored in nonvolatile RAM."
              DEFVAL { 100 }
              ::= { eAlarmEntry 5 }

          eAlarmLowThreshold OBJECT-TYPE
              SYNTAX INTEGER
              ACCESS read-write
              STATUS mandatory
              DESCRIPTION
                     "The low threshold for eAlarmValue, in tenths of
                     one percent.
                     eAlarmLowThreshold is stored in nonvolatile RAM."
              DEFVAL { 0 }
              ::= { eAlarmEntry 6 }

          eAlarmHighThreshold OBJECT-TYPE
              SYNTAX INTEGER
              ACCESS read-write
              STATUS mandatory
              DESCRIPTION
                     "The high threshold for eAlarmValue, in tenths of
                     one percent.
                     eAlarmHighThreshold is stored in nonvolatile RAM."
              DEFVAL { 1000 } -- 100%
              ::= { eAlarmEntry 7 }

          eAlarmLowDelta OBJECT-TYPE
              SYNTAX INTEGER
              ACCESS read-write
              STATUS mandatory
              DESCRIPTION
                     "The delta value used to offset the gauge value
                     when the low threshold is passed, in tenths of one
                     percent.
                     eAlarmLowDelta is stored in nonvolatile RAM."
              DEFVAL { 50 } -- 5%
              ::= { eAlarmEntry 8 }

          eAlarmHighDelta OBJECT-TYPE
              SYNTAX INTEGER
              ACCESS read-write
              STATUS mandatory
              DESCRIPTION
                     "The delta value used to offset the gauge value
                     when the high threshold is passed.
                     eAlarmHighDelta is stored in nonvolatile RAM."
              DEFVAL { 50 } -- 5%
              ::= { eAlarmEntry 9 }

          eAlarmLowWaterMark OBJECT-TYPE
              SYNTAX INTEGER
              ACCESS read-write
              STATUS mandatory
              DESCRIPTION
                     "The lowest value seen for eAlarmValue, in tenths
                     of one percent.  This can be reset by writing to
                     eAlarmLowWaterMark.  The value written is ignored,
                     and eAlarmLowWaterMark is set to the current value
                     of eAlarmValue."
              ::= { eAlarmEntry 10 }

          eAlarmHighWaterMark OBJECT-TYPE
              SYNTAX INTEGER
              ACCESS read-write
              STATUS mandatory
              DESCRIPTION
                     "The highest value seen for eAlarmValue, in tenths
                     of one percent.  This can be reset by writing to
                     eAlarmHighWaterMark.  The value written is ignored,
                     and eAlarmHighWaterMark is set to the current value
                     of eAlarmValue."
              ::= { eAlarmEntry 11 }

          eAlarmLowSetTime OBJECT-TYPE
              SYNTAX Time
              ACCESS read-only
              STATUS mandatory
              DESCRIPTION
                     "The date and time eAlarmLowWaterMark was last set.
                     This value is NULL until the first time
                     eAlarmLowWaterMark is set."
              ::= { eAlarmEntry 12 }

          eAlarmHighSetTime OBJECT-TYPE
              SYNTAX Time
              ACCESS read-only
              STATUS mandatory
              DESCRIPTION
                     "The date and time eAlarmHighWaterMark was last
                     set. This value is NULL until the first time
                     eAlarmHighWaterMark is set."
              ::= { eAlarmEntry 13 }

          eHostNewHostAlarm OBJECT-TYPE
              SYNTAX INTEGER {
                         disabled(1),
                         enabled(2)
                     }
              ACCESS read-write
              STATUS mandatory
              DESCRIPTION
                     "If enabled, the LANtern network monitor generates
                     a newHost trap whenever a new host first transmits
                     on the network segment.  Note that
                     eHostNewHostAlarm is NOT stored in nonvolatile RAM,
                     and returns to its default setting whenever the
                     LANtern network monitor is reset (or powered-on)."
              DEFVAL { 1 } -- Disabled
              ::= { lanternEthernet 25 }

          eHostTableEntries OBJECT-TYPE
              SYNTAX INTEGER
              ACCESS read-only
              STATUS mandatory
              DESCRIPTION
                     "The number of entries currently in eHostTable and
                     eHostTTable."
              ::= { lanternEthernet 26 }

          eHostPurge OBJECT-TYPE
              SYNTAX Time
              ACCESS read-write
              STATUS mandatory
              DESCRIPTION
                     "Writing a date and time to eHostPurge causes the
                     LANtern network monitor to purge all host table
                     entries eHostTable where the date and time of both
                     the most recent transmission and reception is
                     earlier than that specified.  All matrix entries
                     (eMatrixSDTable and eMatrixDSTable) associated with
                     the deleted host entries are also deleted. Hosts
                     with the purge disable flag set are not deleted.
                     Reading this variable returns the date and time of
                     the last purge. The value returned is 0 (midnight 1
                     January 1900), if the table has never been purged.
                     "
              ::= { lanternEthernet 27 }

          eHostTable OBJECT-TYPE
              SYNTAX SEQUENCE OF EHostEntry
              ACCESS not-accessible
              STATUS mandatory
              DESCRIPTION
                     "Statistical data for each host seen on the
                     network, accessed by MAC address.  Entries may be
                     'preloaded' into the table by writing to
                     eHostControl for the appropriate instance, which
                     also creates a corresponding entry in eHostTTable
                     and sets the date and time of first transmit to the
                     current date and time.  An entry can be deleted
                     from the table by writing (any value) to
                     eHostDelete.  This also deletes the corresponding
                     entry from eHostTTable and all entries from
                     eMatrixSDTable and eMatrixDSTable that reference
                     that host."
              ::= { lanternEthernet 28 }

          eHostEntry OBJECT-TYPE
              SYNTAX EHostEntry
              ACCESS not-accessible
              STATUS mandatory
              DESCRIPTION
                     "Statistical data for each host seen on the
                     network, accessed by eHostAddress."
              INDEX  { eHostAddress }
              ::= { eHostTable 1 }

          EHostEntry ::=
              SEQUENCE {
                  eHostAddress                    PhysAddress,
                  eHostInPkts                     Counter,
                  eHostOutPkts                    Counter,
                  eHostInOctets                   Counter,
                  eHostOutOctets                  Counter,
                  eHostInErrors                   Counter,
                  eHostOutErrors                  Counter,
                  eHostProtocols                  INTEGER,
                  eHostFirstTransmit              Time,
                  eHostLastTransmit               Time,
                  eHostLastReceive                Time,
                  eHostControl                    INTEGER,
                  eHostDelete                     INTEGER
              }

          eHostAddress OBJECT-TYPE
              SYNTAX PhysAddress
              ACCESS read-only
              STATUS mandatory
              DESCRIPTION
                     "The MAC layer physical address of the host."
              ::= { eHostEntry 1 }

          eHostInPkts OBJECT-TYPE
              SYNTAX Counter
              ACCESS read-only
              STATUS mandatory
              DESCRIPTION
                     "The total number of good packets transmitted to
                     this address."
              ::= { eHostEntry 2 }

          eHostOutPkts OBJECT-TYPE
              SYNTAX Counter
              ACCESS read-only
              STATUS mandatory
              DESCRIPTION
                     "The total number of good packets transmitted by
                     this host."
              ::= { eHostEntry 3 }

          eHostInOctets OBJECT-TYPE
              SYNTAX Counter
              ACCESS read-only
              STATUS mandatory
              DESCRIPTION
                     "The total number of octets in good packets
                     transmitted to this address."
              ::= { eHostEntry 4 }

          eHostOutOctets OBJECT-TYPE
              SYNTAX Counter
              ACCESS read-only
              STATUS mandatory
              DESCRIPTION
                     "The total number of octets in good packets
                     transmitted by this host."
              ::= { eHostEntry 5 }

          eHostInErrors OBJECT-TYPE
              SYNTAX Counter
              ACCESS read-only
              STATUS mandatory
              DESCRIPTION
                     "The total number of error (CRC, undersize, or
                     oversize) packets transmitted to this address."
              ::= { eHostEntry 6 }
          eHostOutErrors OBJECT-TYPE
              SYNTAX Counter
              ACCESS read-only
              STATUS mandatory
              DESCRIPTION
                     "The total number of error (CRC, undersize, or
                     oversize) packets transmitted by this host."
              ::= { eHostEntry 7 }

          eHostProtocols OBJECT-TYPE
              SYNTAX INTEGER
              ACCESS read-only
              STATUS mandatory
              DESCRIPTION
                     "A bit array where each bit indicates a protocol
                     that was seen in a packet transmitted by that host.
                     The protocols currently monitored are:
                     Bit Protocol
                     2^0 Unrecognized protocol (none of the following)
                     2^1 DOD (IP, ARP, RARP)
                     2^2 ISO
                     2^3 DEC
                     2^4 NetWare
                     2^5 AppleTalk (AppleTalk, AppleTalk ARP)
                     2^6 XNS
                     2^7 SNA
                     2^8 VINES"
              ::= { eHostEntry 8 }

          eHostFirstTransmit OBJECT-TYPE
              SYNTAX Time
              ACCESS read-only
              STATUS mandatory
              DESCRIPTION
                     "The date and time of the first good transmission
                     by this host.  If the host has not transmitted,
                     this value is 0"
              ::= { eHostEntry 9 }

          eHostLastTransmit OBJECT-TYPE
              SYNTAX Time
              ACCESS read-only
              STATUS mandatory
              DESCRIPTION
                     "The date and time of the most recent transmission
                     by this host.  If the host has not transmitted,
                     this value is 0"
              ::= { eHostEntry 10 }

          eHostLastReceive OBJECT-TYPE
              SYNTAX Time
              ACCESS read-only
              STATUS mandatory
              DESCRIPTION
                     "The data and time of the most recent transmission
                     to this address."
              ::= { eHostEntry 11 }

          eHostControl OBJECT-TYPE
              SYNTAX INTEGER
              ACCESS read-write
              STATUS mandatory
              DESCRIPTION
                     "A collection of control bits and bit fields.
                     These fields are grouped into one object to reduce
                     network traffic (especially over the serial line)
                     during startup.  Writing to eHostControl may be
                     used to pre-load entries into the table.  This also
                     has the side effect of inhibiting newHost traps for
                     that host.

                     BITS          MEANING
                     2^0-2^2  3-bit host timeout code
                              0 - host timeout disabled
                              1 - 1 minute
                              2 - 2 minutes
                              3 - 4 minutes
                              4 - 8 minutes
                              5 - 16 minutes
                              6 - 32 minutes
                              7 - 64 minutes
                     2^3      onSegmentBit: if set, host is on
                              LANtern's segment.
                     2^7      inhibitPurgeBit: if set, inhibit purge for
                              this host."
              DEFVAL { 0 }
                     -- Purge enabled, timeout disabled, off segment
              ::= { eHostEntry 12 }

          eHostDelete OBJECT-TYPE
              SYNTAX INTEGER
              ACCESS write-only
              STATUS mandatory
              DESCRIPTION
                     "An entry may be deleted from eHostTable by writing
                     (any value) to eHostDelete.  Note that this
                     overrides the purge disable flag in eHostControl.
                     Any entries in the matrix tables (eMatrixSDTable
                     and eMatrixDSTable) that reference the host being
                     deleted also are deleted."
              ::= { eHostEntry 13 }

          eHostTTable OBJECT-TYPE
              SYNTAX SEQUENCE OF EHostTEntry
              ACCESS not-accessible
              STATUS mandatory
              DESCRIPTION
                     "Statistical data for each host that has
                     transmitted on the network; accessed by
                     eHostTFirstTransmit  (and an ordinal number to
                     resolve ambiguities)."
              ::= { lanternEthernet 29 }

          eHostTEntry OBJECT-TYPE
              SYNTAX EHostTEntry
              ACCESS not-accessible
              STATUS mandatory
              DESCRIPTION
                     "The contents are identical to those described for
                     eHostTable above except that the access for
                     eHostTControl  is read-only for all communities.
                     The table is accessed by eHostTFirstTransmit  (and
                     an ordinal number to resolve ambiguities)"
              INDEX  { eHostTFirstTransmit, INTEGER }
              ::= { eHostTTable 1 }

          EHostTEntry ::=
              SEQUENCE {
                  eHostTAddress                   PhysAddress,
                  eHostTInPkts                    Counter,
                  eHostTOutPkts                   Counter,
                  eHostTInOctets                  Counter,
                  eHostTOutOctets                 Counter,
                  eHostTInErrors                  Counter,
                  eHostTOutErrors                 Counter,
                  eHostTProtocols                 INTEGER,
                  eHostTFirstTransmit             Time,
                  eHostTLastTransmit              Time,
                  eHostTLastReceive               Time,
                  eHostTControl                   INTEGER
              }

          eHostTAddress OBJECT-TYPE
              SYNTAX PhysAddress
              ACCESS read-only
              STATUS mandatory
              DESCRIPTION
                     "The MAC layer physical address of the host."
              ::= { eHostTEntry 1 }

          eHostTInPkts OBJECT-TYPE
              SYNTAX Counter
              ACCESS read-only
              STATUS mandatory
              DESCRIPTION
                     "The total number of good packets transmitted to
                     this address."
              ::= { eHostTEntry 2 }

          eHostTOutPkts OBJECT-TYPE
              SYNTAX Counter
              ACCESS read-only
              STATUS mandatory
              DESCRIPTION
                     "The total number of good packets transmitted by
                     this host."
              ::= { eHostTEntry 3 }

          eHostTInOctets OBJECT-TYPE
              SYNTAX Counter
              ACCESS read-only
              STATUS mandatory
              DESCRIPTION
                     "The total number of octets in good packets
                     transmitted to this address."
              ::= { eHostTEntry 4 }

          eHostTOutOctets OBJECT-TYPE
              SYNTAX Counter
              ACCESS read-only
              STATUS mandatory
              DESCRIPTION
                     "The total number of octets in good packets
                     transmitted by this host."
              ::= { eHostTEntry 5 }

          eHostTInErrors OBJECT-TYPE
              SYNTAX Counter
              ACCESS read-only
              STATUS mandatory
              DESCRIPTION
                     "The total number of error (CRC, undersize, or
                     oversize) packets transmitted to this address."
              ::= { eHostTEntry 6 }

          eHostTOutErrors OBJECT-TYPE
              SYNTAX Counter
              ACCESS read-only
              STATUS mandatory
              DESCRIPTION
                     "The total number of error (CRC, undersize, or
                     oversize) packets transmitted by this host."
              ::= { eHostTEntry 7 }

          eHostTProtocols OBJECT-TYPE
              SYNTAX INTEGER
              ACCESS read-only
              STATUS mandatory
              DESCRIPTION
                     "A bit array where each bit indicates a protocol
                     that was seen in a packet transmitted by that host.
                     The protocols currently monitored are:
                     Bit Protocol
                     2^0 Unrecognized protocol (none of the following)
                     2^1 DOD (IP, ARP, RARP)
                     2^2 ISO
                     2^3 DEC
                     2^4 NetWare
                     2^5 AppleTalk (AppleTalk, AppleTalk ARP)
                     2^6 XNS
                     2^7 SNA
                     2^8 VINES"
              ::= { eHostTEntry 8 }

          eHostTFirstTransmit OBJECT-TYPE
              SYNTAX Time
              ACCESS read-only
              STATUS mandatory
              DESCRIPTION
                     "The date and time of the first good transmission
                     by this host.  If the host has not transmitted,
                     this value is 0"
              ::= { eHostTEntry 9 }

          eHostTLastTransmit OBJECT-TYPE
              SYNTAX Time
              ACCESS read-only
              STATUS mandatory
              DESCRIPTION
                     "The date and time of the most recent transmission
                     by this host.  If the host has not transmitted,
                     this value is 0"
              ::= { eHostTEntry 10 }

          eHostTLastReceive OBJECT-TYPE
              SYNTAX Time
              ACCESS read-only
              STATUS mandatory
              DESCRIPTION
                     "The data and time of the most recent transmission
                     to this address."
              ::= { eHostTEntry 11 }

          eHostTControl OBJECT-TYPE
              SYNTAX INTEGER
              ACCESS read-only
              STATUS mandatory
              DESCRIPTION
                     "A collection of control bits and bit fields.
                     These fields are grouped into one object to reduce
                     network traffic (especially over the serial line)
                     during startup.  Writing to eHostControl may be
                     used to pre-load entries into the table.  This also
                     has the side effect of inhibiting newHost traps for
                     that host.

                     BITS          MEANING
                     2^0-2^2  3-bit host timeout code
                              0 - host timeout disabled
                              1 - 1 minute
                              2 - 2 minutes
                              3 - 4 minutes
                              4 - 8 minutes
                              5 - 16 minutes
                              6 - 32 minutes
                              7 - 64 minutes
                     2^3      onSegmentBit: if set, host is on
                              LANtern's segment.
                     2^7      inhibitPurgeBit: if set, inhibit purge for
                              this host."
              DEFVAL { 0 }
                     -- Purge enabled, timeout disabled, off segment
              ::= { eHostTEntry 12 }

          eMatrixTableEntries OBJECT-TYPE
              SYNTAX INTEGER
              ACCESS read-only
              STATUS mandatory
              DESCRIPTION
                     "The number of entries currently in eMatrixSDTable
                     and eMatrixDSTable."
              ::= { lanternEthernet 30 }

          eMatrixPurge OBJECT-TYPE
              SYNTAX Time
              ACCESS read-write
              STATUS mandatory
              DESCRIPTION
                     "Writing a date and time to eMatrixPurge causes the
                     LANtern network monitor to purge all matrix
                     (eMatrixSDTable and eMatrixDSTable) table entries
                     where the date and time of most recent transmission
                     is earlier than the specified time.  The whole
                     table can be purged by writing a time later than
                     the current time. Reading this variable returns the
                     time of most recent manual or automatic purge. The
                     value returned is 0 (midnight 1 January 1900), if
                     the table has never been purged."
              ::= { lanternEthernet 31 }

          eMatrixSDTable OBJECT-TYPE
              SYNTAX SEQUENCE OF EMatrixSDEntry
              ACCESS not-accessible
              STATUS mandatory
              DESCRIPTION
                     "A table of network traffic sent from one
                     particular source host to one particular
                     destination host.  A particular object instance is
                     accessed by appending the source host address
                     followed by the destination host address.  This
                     allows the table to be traversed with the source
                     address as the major key and the destination
                     address as the minor key.  An entry may be deleted
                     from the table by writing to eMatrixSDDelete."
              ::= { lanternEthernet 32 }

          eMatrixSDEntry OBJECT-TYPE
              SYNTAX EMatrixSDEntry
              ACCESS not-accessible
              STATUS mandatory
              DESCRIPTION
                     "The statistics for traffic in a particular
                     direction between two hosts on the network."
              INDEX  { eMatrixSDSourceAddress, eMatrixSDDestAddress }
              ::= { eMatrixSDTable 1 }

          EMatrixSDEntry ::=
              SEQUENCE {
                  eMatrixSDSourceAddress          PhysAddress,
                  eMatrixSDDestAddress            PhysAddress,
                  eMatrixSDPkts                   Counter,
                  eMatrixSDOctets                 Counter,
                  eMatrixSDErrors                 Counter,
                  eMatrixSDProtocols              INTEGER,
                  eMatrixSDFirstTransmit          Time,
                  eMatrixSDLastTransmit           Time,
                  eMatrixSDDelete                 INTEGER
              }

          eMatrixSDSourceAddress OBJECT-TYPE
              SYNTAX PhysAddress
              ACCESS read-only
              STATUS mandatory
              DESCRIPTION
                     "The MAC layer physical address of the source
                     host."
              ::= { eMatrixSDEntry 1 }

          eMatrixSDDestAddress OBJECT-TYPE
              SYNTAX PhysAddress
              ACCESS read-only
              STATUS mandatory
              DESCRIPTION
                     "The MAC layer physical address of the destination
                     host."
              ::= { eMatrixSDEntry 2 }

          eMatrixSDPkts OBJECT-TYPE
              SYNTAX Counter
              ACCESS read-only
              STATUS mandatory
              DESCRIPTION
                     "The number of good packets sent from
                     eMatrixSDSourceAddress to eMatrixSDDestAddress."
              ::= { eMatrixSDEntry 3 }

          eMatrixSDOctets OBJECT-TYPE
              SYNTAX Counter
              ACCESS read-only
              STATUS mandatory
              DESCRIPTION
                     "The number of octets in good packets sent from
                     eMatrixSDSourceAddress to eMatrixSDDestAddress."
              ::= { eMatrixSDEntry 4 }

          eMatrixSDErrors OBJECT-TYPE
              SYNTAX Counter
              ACCESS read-only
              STATUS mandatory
              DESCRIPTION
                     "The number of error (CRC/align/undersize/oversize)
                     packets sent from eMatrixSDSourceAddress to
                     eMatrixSDDestAddress."
              ::= { eMatrixSDEntry 5 }

          eMatrixSDProtocols OBJECT-TYPE
              SYNTAX INTEGER
              ACCESS read-only
              STATUS mandatory
              DESCRIPTION
                     "A bit array where each bit indicates a protocol
                     that was seen in a packet sent from
                     eMatrixSDSourceAddress to eMatrixSDDestAddress.
                     The protocols currently monitored are:
                     Bit Protocol
                     2^0 Unrecognized protocol (none of the following)
                     2^1 DOD (IP, ARP, RARP)
                     2^2 ISO
                     2^3 DEC
                     2^4 NetWare
                     2^5 AppleTalk (AppleTalk, AppleTalk ARP)
                     2^6 XNS
                     2^7 SNA
                     2^8 VINES"
              ::= { eMatrixSDEntry 6 }

          eMatrixSDFirstTransmit OBJECT-TYPE
              SYNTAX Time
              ACCESS read-only
              STATUS mandatory
              DESCRIPTION
                     "The date and time the first transmission from
                     eMatrixSDSourceAddress to eMatrixSDDestAddress."
              ::= { eMatrixSDEntry 7 }

          eMatrixSDLastTransmit OBJECT-TYPE
              SYNTAX Time
              ACCESS read-only
              STATUS mandatory
              DESCRIPTION
                     "The date and time of the most recent transmission
                     from eMatrixSDSourceAddress to
                     eMatrixSDDestAddress."
              ::= { eMatrixSDEntry 8 }

          eMatrixSDDelete OBJECT-TYPE
              SYNTAX INTEGER
              ACCESS write-only
              STATUS mandatory
              DESCRIPTION
                     "A write (any value) causes the table entry to be
                     deleted."
              ::= { eMatrixSDEntry 9 }

          eMatrixDSTable OBJECT-TYPE
              SYNTAX SEQUENCE OF EMatrixDSEntry
              ACCESS not-accessible
              STATUS mandatory
              DESCRIPTION
                     "A table of network traffic sent from one
                     particular source host to one particular
                     destination host.  A particular object instance is
                     accessed by appending the destination address
                     followed by the source address.  This allows the
                     table to be traversed with the destination address
                     as the major key and the source address as the
                     minor key.  An entry may be deleted from the table
                     by writing to eMatrixDSDelete."
              ::= { lanternEthernet 33 }

          eMatrixDSEntry OBJECT-TYPE
              SYNTAX EMatrixDSEntry
              ACCESS not-accessible
              STATUS mandatory
              DESCRIPTION
                     "The contents of the table are identical to those
                     described above for eMatrixSDTable."
              INDEX  { eMatrixDSDestAddress, eMatrixDSSourceAddress }
              ::= { eMatrixDSTable 1 }

          EMatrixDSEntry ::=
              SEQUENCE {
                  eMatrixDSSourceAddress          PhysAddress,
                  eMatrixDSDestAddress            PhysAddress,
                  eMatrixDSPkts                   Counter,
                  eMatrixDSOctets                 Counter,
                  eMatrixDSErrors                 Counter,
                  eMatrixDSProtocols              INTEGER,
                  eMatrixDSFirstTransmit          Time,
                  eMatrixDSLastTransmit           Time,
                  eMatrixDSDelete                 INTEGER
              }

          eMatrixDSSourceAddress OBJECT-TYPE
              SYNTAX PhysAddress
              ACCESS read-only
              STATUS mandatory
              DESCRIPTION
                     "The MAC layer physical address of the source
                     host."
              ::= { eMatrixDSEntry 1 }

          eMatrixDSDestAddress OBJECT-TYPE
              SYNTAX PhysAddress
              ACCESS read-only
              STATUS mandatory
            DESCRIPTION
                 "The MAC layer physical address of the destination
                     host."
              ::= { eMatrixDSEntry 2 }

          eMatrixDSPkts OBJECT-TYPE
              SYNTAX Counter
              ACCESS read-only
              STATUS mandatory
              DESCRIPTION
                     "The number of good packets sent from
                     eMatrixDSSourceAddress to eMatrixDSDestAddress."
              ::= { eMatrixDSEntry 3 }

          eMatrixDSOctets OBJECT-TYPE
              SYNTAX Counter
              ACCESS read-only
              STATUS mandatory
              DESCRIPTION
                     "The number of octets in good packets sent from
                     eMatrixDSSourceAddress to eMatrixDSDestAddress."
              ::= { eMatrixDSEntry 4 }

          eMatrixDSErrors OBJECT-TYPE
              SYNTAX Counter
              ACCESS read-only
              STATUS mandatory
              DESCRIPTION
                     "The number of error (CRC/align/undersize/oversize)
                     packets sent from eMatrixDSSourceAddress to
                     eMatrixDSDestAddress."
              ::= { eMatrixDSEntry 5 }
          eMatrixDSProtocols OBJECT-TYPE
              SYNTAX INTEGER
              ACCESS read-only
              STATUS mandatory
              DESCRIPTION
                     "A bit array where each bit indicates a protocol
                     that was seen in a packet sent from
                     eMatrixDSSourceAddress to eMatrixDSDestAng defining the time zone of thee protocols currently monitored are:
                     Bit Protocol
                     2^0 Unrecognized protocol (none of the following)
                     2^1 DOD (IP, ARP, RARP)
                     2^2 ISO
                     2^3 DEC
                     2^4 NetWare
                     2^5 AppleTalk (AppleTalk, AppleTalk ARP)
                     2^6 XNS
                     2^7 SNA
                     2^8 VINES"
              ::= { eMatrixDSEntry 6 }

          eMatrixDSFirstTransmit OBJECT-TYPE
              SYNTAX Time
              ACCESS read-only
              STATUS mandatory
              DESCRIPTION
                     "The date and time the first transmission from
                     eMatrixDSSourceAddress to eMatrixDSDestAddress."
              ::= { eMatrixDSEntry 7 }

          eMatrixDSLastTransmit OBJECT-TYPE
              SYNTAX Time
              ACCESS read-only
              STATUS mandatory
              DESCRIPTION
                     "The date and time of the most recent transmission
                     from eMatrixDSSourceAddress to
                     eMatrixDSDestAddress."
              ::= { eMatrixDSEntry 8 }

          eMatrixDSDelete OBJECT-TYPE
              SYNTAX INTEGER
              ACCESS write-only
              STATUS mandatory
              DESCRIPTION
                     "A write (any value) causes the table entry to be
                     deleted."
              ::= { eMatrixDSEntry 9 }

          eMediaCheckInterval OBJECT-TYPE
              SYNTAX Seconds (0..3600)
              ACCESS read-write
              STATUS mandatory
              DESCRIPTION
                     "The LANtern network monitor performs a periodic
                     cable check every eMediaCheckInterval  seconds.  If
                     eMediaCheckInterval is zero, periodic cable checks
                     are not performed.
                     eMediaCheckInterval  is stored in nonvolatile RAM."
              DEFVAL { 0 } -- Periodic cable checks disabled
              ::= { lanternEthernet 34 }

          eMediaStatus OBJECT-TYPE
              SYNTAX INTEGER {
                         cableOk(1),
                         transceiverCableBad(2),
                         ethernetCableBad(3)
                     }
              ACCESS read-only
              STATUS mandatory
              DESCRIPTION     "Reading eMediaStatus returns the most
                     recent cable check, automatic or manual. Writing
                     any value causby the LANtern network
         .
                     This object is also passed in the cableFailure
                     trap-PDU."
              ::= { lanternEthernet 35 }

          eHostLimit OBJECT-TYPE
              SYNTAX INTEGER
              ACCESS read-only
              STATUS mandatory
              DESCRIPTION
                     "The maximum number of unicast addresses which the
                     LANtern host table holds.  A value of 0 indicates
                     that there is no limit other than memory
                     constraints.  The value 0 will be returned by
                     LANtern and the value 32 will be returned by
                     LANtern LTD."
              ::= { lanternEthernet 37 }

          eOnSegmentPkts OBJECT-TYPE
              SYNTAX Counter
              ACCESS read-only
              STATUS mandatory
              DESCRIPTION
                     "The count of the number of packets which were
                     transmitted between hosts on the same segment as
                     the LANtern."
              ::= { lanternEthernet 38 }

          eOnSegmentOctets OBJECT-TYPE
              SYNTAX Counter
              ACCESS read-only
              STATUS mandatory
              DESCRIPTION
                     "The count of the number of octets in packets which
                     were transmitted between hosts on the same segment
                     as the LANtern."
              ::= { lanternEthernet 39 }

          eDepartingPkts OBJECT-TYPE
              SYNTAX Counter
              ACCESS read-only
              STATUS mandatory
              DESCRIPTION
                     "The count of the number of packets which were
                     transmitted by hosts on the same segment as the
                     LANtern to hosts on other segments."
              ::= { lanternEthernet 40 }

          eDepartingOctets OBJECT-TYPE
              SYNTAX Counter
              ACCESS read-only
              STATUS mandatory
              DESCRIPTION
                     "The count of the number of octets in packets which
                     were transmitted by hosts on the same segment as
                     the LANtern to hosts on other segments."
              ::= { lanternEthernet 41 }

          eArrivingPkts OBJECT-TYPE
              SYNTAX Counter
              ACCESS read-only
              STATUS mandatory
              DESCRIPTION
                     "The count of the number of packets which were
                     transmitted by hosts on other segments to hosts on
                     the same segment as the LANtern."
              ::= { lanternEthernet 42 }

          eArrivingOctets OBJECT-TYPE
              SYNTAX Counter
              ACCESS read-only
              STATUS mandatory
              DESCRIPTION
                     "The count of the number of octets in packets which
                     were transmitted by hosts on other segments to
                     hosts on the same segment as the LANtern."
              ::= { lanternEthernet 43 }

          eThruPkts OBJECT-TYPE
              SYNTAX Counter
              ACCESS read-only
              STATUS mandatory
              DESCRIPTION
                     "The count of the number of packets seen on the
                     LANtern's segment which were transmitted between
                     hosts which are not on the LANtern's segment."
              ::= { lanternEthernet 44 }

          eThruOctets OBJECT-TYPE
              SYNTAX Counter
              ACCESS read-only
              STATUS mandatory
              DESCRIPTION
                     "The count of the number of octets in packets seen
                     on the LANtern's segment which were transmitted
                     between hosts which are not on the LANtern's
                     segment."
              ::= { lanternEthernet 45 }

          eHostDeletes OBJECT-TYPE
              SYNTAX Counter
              ACCESS read-only
              STATUS mandatory
              DESCRIPTION
                     "A count of the number of hosts which have been
                     deleted since the LANtern was powered on."
              ::= { lanternEthernet 46 }

          eHostOTable OBJECT-TYPE
              SYNTAX SEQUENCE OF EHostOEntry
              ACCESS not-accessible
              STATUS mandatory
              DESCRIPTION
                     "Statistical data for each host that has
                     transmitted on the network; accessed by
                     eHostOOrderIndex.  This table exists to permit
                     rapid downloading of the host table."
              ::= { lanternEthernet 47 }

          eHostOEntry OBJECT-TYPE
              SYNTAX EHostOEntry
              ACCESS not-accessible
              STATUS mandatory
              DESCRIPTION
                     "The contents are identical to those described for
                     eHostTable above except that the access for
                     eHostOControl  is read-only for all communities and
                     eHostOOrderIndex appears only in this table."
              INDEX  { eHostOOrderIndex }
              ::= { eHostOTable 1 }

          EHostOEntry ::=
              SEQUENCE {
                  eHostOAddress                   PhysAddress,
                  eHostOInPkts                    Counter,
                  eHostOOutPkts                   Counter,
                  eHostOInOctets                  Counter,
                  eHostOOutOctets                 Counter,
                  eHostOInErrors                  Counter,
                  eHostOOutErrors                 Counter,
                  eHostOProtocols                 INTEGER,
                  eHostOFirstTransmit             Time,
                  eHostOLastTransmit              Time,
                  eHostOLastReceive               Time,
                  eHostOControl                   INTEGER,
                  eHostOOrderIndex                INTEGER
              }

          eHostOAddress OBJECT-TYPE
              SYNTAX PhysAddress
              ACCESS read-only
              STATUS mandatory
              DESCRIPTION
                     "The MAC layer physical address of the host."
              ::= { eHostOEntry 1 }

          eHostOInPkts OBJECT-TYPE
              SYNTAX Counter
              ACCESS read-only
              STATUS mandatory
              DESCRIPTION
                     "The total number of good packets transmitted to
                     this address."
              ::= { eHostOEntry 2 }

          eHostOOutPkts OBJECT-TYPE
              SYNTAX Counter
              ACCESS read-only
              STATUS mandatory
              DESCRIPTION
                     "The total number of good packets transmitted by
                     this host."
              ::= { eHostOEntry 3 }

          eHostOInOctets OBJECT-TYPE
              SYNTAX Counter
              ACCESS read-only
              STATUS mandatory
              DESCRIPTION
                     "The total number of octets in good packets
                     transmitted to this address."
              ::= { eHostOEntry 4 }

          eHostOOutOctets OBJECT-TYPE
              SYNTAX Counter
              ACCESS read-only
              STATUS mandatory
              DESCRIPTION
                     "The total number of octets in good packets
                     transmitted by this host."
              ::= { eHostOEntry 5 }
          eHostOInErrors OBJECT-TYPE
              SYNTAX Counter
              ACCESS read-only
              STATUS mandatory
              DESCRIPTION
                     "The total number of error (CRC, undersize, or
                     oversize) packets transmitted to this address."
              ::= { eHostOEntry 6 }

          eHostOOutErrors OBJECT-TYPE
              SYNTAX Counter
              ACCESS read-only
              STATUS mandatory
              DESCRIPTION
                     "The total number of error (CRC, undersize, or
                     oversize) packets transmitted by this host."
              ::= { eHostOEntry 7 }

          eHostOProtocols OBJECT-TYPE
              SYNTAX INTEGER
              ACCESS read-only
              STATUS mandatory
              DESCRIPTION
                     "A bit array where each bit indicates a protocol
                     that was seen in a packet transmitted by that host.
                     The protocols currently monitored are:
                     Bit Protocol
                     2^0 Unrecognized protocol (none of the following)
                     2^1 DOD (IP, ARP, RARP)
                     2^2 ISO
                     2^3 DEC
                     2^4 NetWare
                     2^5 AppleTalk (AppleTalk, AppleTalk ARP)
                     2^6 XNS
                     2^7 SNA
                     2^8 VINES"
              ::= { eHostOEntry 8 }

          eHostOFirstTransmit OBJECT-TYPE
              SYNTAX Time
              ACCESS read-only
              STATUS mandatory
              DESCRIPTION
                     "The date and time of the first good transmission
                     by this host.  If the host has not transmitted,
                     this value is 0"
              ::= { eHostOEntry 9 }

          eHostOLastTransmit OBJECT-TYPE
              SYNTAX Time
              ACCESS read-only
              STATUS mandatory
              DESCRIPTION
                     "The date and time of the most recent transmission
                     by this host.  If the host has not transmitted,
                     this value is 0"
              ::= { eHostOEntry 10 }

          eHostOLastReceive OBJECT-TYPE
              SYNTAX Time
              ACCESS read-only
              STATUS mandatory
              DESCRIPTION
                     "The data and time of the most recent transmission
                     to this address."
              ::= { eHostOEntry 11 }
          eHostOControl OBJECT-TYPE
              SYNTAX INTEGER
              ACCESS read-only
              STATUS mandatory
              DESCRIPTION
                     "A collection of control bits and bit fields.
                     These fields are grouped into one object to reduce
                     network traffic (especially over the serial line)
                     during startup.  Writing to eHostControl may be
                     used to pre-load entries into the table.  This also
                     has the side effect of inhibiting newHost traps for
                     that host.

                     BITS          MEANING
                     2^0-2^2  3-bit host timeout code
                              0 - host timeout disabled
                              1 - 1 minute
                              2 - 2 minutes
                              3 - 4 minutes
                              4 - 8 minutes
                              5 - 16 minutes
                              6 - 32 minutes
                              7 - 64 minutes
                     2^3      onSegmentBit: if set, host is on
                              LANtern's segment.
                     2^7      inhibitPurgeBit: if set, inhibit purge for
                              this host."
              DEFVAL { 0 }
                     -- Purge enabled, timeout disabled, off segment
              ::= { eHostOEntry 12 }

          eHostOOrderIndex OBJECT-TYPE
              SYNTAX INTEGER
              ACCESS read-only
              STATUS mandatory
              DESCRIPTION
                     "A (dense) ordinal that uniquely defines an entry
                     in the eHostOTable table."
              ::= { eHostOEntry 13 }



          -- The IP Services Group

          ipPingTarget OBJECT-TYPE
              SYNTAX IpAddress
              ACCESS write-only
              STATUS mandatory
              DESCRIPTION
                     "Writing an IP address to ipPingTarget causes the
                     LANtern network monitor to ping that host (using
                     ICMP Echo).  When the LANtern network monitor
                     receives the echo response, a pingNotification trap
                     is issued to the host that requested the ping.  The
                     data passed with the trap are ipPingTarget and
                     ipPingDuration.

                     Note:  There is a separate instance of this
                     variable (indexed by the IP address of the host to
                     receive the notification) for each ping
                     outstanding.  This is best illustrated by an
                     example; suppose one wants to request the LANtern
                     to ping host 130.57.1.2 and send the ping
                     notification trap to host 130.57.8.9. Accordingly,
                     a set request as follows has the desired effect:
                     ipPingTarget.130.57.8.9 = 130.57.1.2"
              ::= { lanternIp 1 }

          ipPingDuration OBJECT-TYPE
              SYNTAX TimeTicks
              ACCESS not-accessible
              STATUS mandatory
              DESCRIPTION
                     "The elapsed time between the LANtern network
                     monitor's issuance of the Ping and its receipt of
                     the response.  This data is passed with the
                     pingNotification trap.

                     Note:  There is a separate instance of this
                     variable (indexed by the IP address of the host to
                     receive the notification) for each ping
                     outstanding.  This is best illustrated by an
                     example; suppose one wants to request the LANtern
                     to ping host 130.57.1.2 and send the ping
                     notification trap to host 130.57.8.9. Accordingly,
                     a set request as follows has the desired effect:
                     ipPingDuration.130.57.8.9 = 130.57.1.2"
              ::= { lanternIp 2 }

          ipDupeCheck OBJECT-TYPE
              SYNTAX INTEGER {
                         disabled(1),
                         enabled(2)
                     }
              ACCESS read-write
              STATUS mandatory
              DESCRIPTION
                     "Enables or disables duplicate IP address checking.
                     ipDupeCheck may be written at any time; however,
                     the change does not take effect until the LANtern
                     network monitor is restarted.  When ipDupeCheck is
                     read, it returns the current state of duplicate IP
                     address checking, regardless of any previous
                     writes.
                     ipDupeCheck is stored in nonvolatile RAM."
              DEFVAL { 1 } -- Disabled
              ::= { lanternIp 3 }
          ipDupeTable OBJECT-TYPE
              SYNTAX SEQUENCE OF IpDupeEntry
              ACCESS not-accessible
              STATUS mandatory
              DESCRIPTION
                     "Table of active duplicate IP address alarms,
                     accessed by IP address."
              ::= { lanternIp 4 }

          ipDupeEntry OBJECT-TYPE
              SYNTAX IpDupeEntry
              ACCESS not-accessible
              STATUS mandatory
              DESCRIPTION
                     "Data pertinent to the duplicate IP address alarm."
              INDEX  { ipDupeIPAddr }
              ::= { ipDupeTable 1 }

          IpDupeEntry ::=
              SEQUENCE {
                  ipDupeIPAddr                    IpAddress,
                  ipDupeGoodMACAddr               PhysAddress,
                  ipDupeBadMACAddr                PhysAddress,
                  ipDupeTime                           Time,
                  ipDupeClear                     INTEGER
              }

          ipDupeIPAddr OBJECT-TYPE
              SYNTAX IpAddress
              ACCESS read-only
              STATUS mandatory
              DESCRIPTION
                     "The IP address that was observed being used by
                     more than one host."
              ::= { ipDupeEntry 1 }

          ipDupeGoodMACAddr OBJECT-TYPE
              SYNTAX PhysAddress
              ACCESS read-only
              STATUS mandatory
              DESCRIPTION
                     "The physical network address of the host that is
                     authorized to use the IP address.  Initially, this
                     is the host that was first seen to use the IP
                     address.  Once an alarm has been generated, the
                     administrator may override this assumption by
                     writing the real authorized physical address to
                     ipDupeGoodMACAddr."
              ::= { ipDupeEntry 2 }

          ipDupeBadMACAddr OBJECT-TYPE
              SYNTAX PhysAddress
              ACCESS read-only
              STATUS mandatory
              DESCRIPTION
                     "The physical network address of the host that is
                     erroneously using the IP address."
              ::= { ipDupeEntry 3 }

          ipDupeTime OBJECT-TYPE
              SYNTAX Time
              ACCESS read-only
              STATUS mandatory
              DESCRIPTION
                     "The date and time the duplicate usage of the IP
                     address was detected."
              ::= { ipDupeEntry 4 }

          ipDupeClear OBJECT-TYPE
              SYNTAX INTEGER {
                         sanctionGood(1),
                         sanctionBad(2),
                         sanctionNeither(3)
                     }
              ACCESS write-only
              STATUS mandatory
              DESCRIPTION
                     "When the condition causing the alarm has been
                     fixed, the administrator should clear the alarm by
                     writing to alarmDupIpClear.  Either of the two MAC
                     addresses can be sanctioned or, alternatively, all
                     knowledge of that IP address can be purged by
                     specifying  sanctionNeither."
              ::= { ipDupeEntry 5 }

          ipMACToIPTable OBJECT-TYPE
              SYNTAX SEQUENCE OF IpMACToIPEntry
              ACCESS not-accessible
              STATUS mandatory
              DESCRIPTION
                     "A table containing mappings from physical media
                     addresses to IP addresses; accessed by
                     ipMACToIPMACAddr.  ipMACToIPIPAddr is also required
                     as a secondary index to resolve ambiguities since
                     any given physical address may have more than one
                     IP address.  Note that this table is a by-product
                     of duplicate IP address checking and, as such, is
                     subject to the following limitations: the table has
                     no entries if ipDupeCheck is disabled, data is
                     available only for hosts on the (LANtern network
                     monitor's) local subnet, and data is available only
                     for hosts that have successfully transmitted an IP
                     packet while the LANtern network monitor has been
                     monitoring the segment.  An entry may be deleted by
                     writing (any value) to ipMACToIPDelete."
              ::= { lanternIp 5 }

          ipMACToIPEntry OBJECT-TYPE
              SYNTAX IpMACToIPEntry
              ACCESS not-accessible
              STATUS mandatory
              DESCRIPTION
                     "The mapping from a physical media address to an IP
                     address."
              INDEX  { ipMACToIPMACAddr, ipMACToIPIPAddr }
              ::= { ipMACToIPTable 1 }

          IpMACToIPEntry ::=
              SEQUENCE {
                  ipMACToIPMACAddr                PhysAddress,
                  ipMACToIPIPAddr                 IpAddress,
                  ipMACToIPDelete                 INTEGER
              }

          ipMACToIPMACAddr OBJECT-TYPE
              SYNTAX PhysAddress
              ACCESS read-only
              STATUS mandatory
              DESCRIPTION
                     "The physical media address."
              ::= { ipMACToIPEntry 1 }
          ipMACToIPIPAddr OBJECT-TYPE
              SYNTAX IpAddress
              ACCESS read-only
              STATUS mandatory
              DESCRIPTION
                     "The IP address."
              ::= { ipMACToIPEntry 2 }

          ipMACToIPDelete OBJECT-TYPE
              SYNTAX INTEGER
              ACCESS write-only
              STATUS mandatory
              DESCRIPTION
                     " An entry may be deleted from ipMACToIPTable by
                     writing (any value) to ipMACToIPDelete.  This also
                     deletes the entry in the ipDupeTable for the same
                     IP address if such an entry exists."
              ::= { ipMACToIPEntry 3 }



          -- The IEEE 802.2 group

          ieee8022TestTarget OBJECT-TYPE
              SYNTAX PhysAddress
              ACCESS write-only
              STATUS mandatory
              DESCRIPTION
                     "Writing an ethernet address to ieee8022TestTarget
                     causes the LANtern to send an 802.2 Test packet to
                     that address."
              ::= { lantern802dot2 1 }

          -- The IPX group

          ipxDiagnosticTarget OBJECT-TYPE
              SYNTAX PhysAddress
              ACCESS write-only
              STATUS mandatory
              DESCRIPTION
                     "Writing an ethernet address to ipxDiagnosticTarget
                     causes the LANtern to send two diagnostic packets,
                     one in ethernet frame format, and the other in
                     802.3 frame format."
              ::= { lanternIpx  1 }



          -- The Protocols group

          protoUnknownPkts OBJECT-TYPE
              SYNTAX Counter
              ACCESS read-only
              STATUS mandatory
              DESCRIPTION
                     "The count of packets observed with an unknown
                     protocol."
              ::= { lanternProtocols  1 }

          protoUnknownOctets OBJECT-TYPE
              SYNTAX Counter
              ACCESS read-only
              STATUS mandatory
              DESCRIPTION
                     "The count of octets in packets observed with an
                     unknown protocol."
              ::= { lanternProtocols  2 }

          protoTCPIPPkts OBJECT-TYPE
              SYNTAX Counter
              ACCESS read-only
              STATUS mandatory
              DESCRIPTION
                     "The count of packets observed with a protocol from
                     the TCP/IP suite (IP, ARP, and RARP)."
              ::= { lanternProtocols  3 }

          protoTCPIPOctets OBJECT-TYPE
              SYNTAX Counter
              ACCESS read-only
              STATUS mandatory
              DESCRIPTION
                     "The count of octets in packets observed with a
                     protocol from the TCP/IP suite (IP, ARP, and
                     RARP)."
              ::= { lanternProtocols  4 }

          protoISOPkts OBJECT-TYPE
              SYNTAX Counter
              ACCESS read-only
              STATUS mandatory
              DESCRIPTION
                     "The count of packets observed with a protocol from
                     the ISO suite."
              ::= { lanternProtocols  5 }

          protoISOOctets OBJECT-TYPE
              SYNTAX Counter
              ACCESS read-only
              STATUS mandatory
              DESCRIPTION
                     "The count of octets in packets observed with a
                     protocol from the ISO suite."
              ::= { lanternProtocols  6 }

          protoDECPkts OBJECT-TYPE
              SYNTAX Counter
              ACCESS read-only
              STATUS mandatory
              DESCRIPTION
                     "The count of packets observed with a protocol from
                     the Digital Equipment Corporation protocol suite."
              ::= { lanternProtocols  7 }
          protoDECOctets OBJECT-TYPE
              SYNTAX Counter
              ACCESS read-only
              STATUS mandatory
              DESCRIPTION
                     "The count of octets in packets observed with a
                     protocol from the Digital Equipment Corporation
                     protocol suite."
              ::= { lanternProtocols  8 }

          protoNetWarePkts OBJECT-TYPE
              SYNTAX Counter
              ACCESS read-only
              STATUS mandatory
              DESCRIPTION
                     "The count of packets observed with a protocol from
                     the NetWare suite."
              ::= { lanternProtocols  9 }

          protoNetWareOctets OBJECT-TYPE
              SYNTAX Counter
              ACCESS read-only
              STATUS mandatory
              DESCRIPTION
                     "The count of octets in packets observed with a
                     protocol from the NetWare suite."
              ::= { lanternProtocols  10 }

          protoAppleTalkPkts OBJECT-TYPE
              SYNTAX Counter
              ACCESS read-only
              STATUS mandatory
              DESCRIPTION
                     "The count of packets observed with a protocol from
                     the AppleTalk suite."
              ::= { lanternProtocols  11 }

          protoAppleTalkOctets OBJECT-TYPE
              SYNTAX Counter
              ACCESS read-only
              STATUS mandatory
              DESCRIPTION
                     "The count of octets in packets observed with a
                     protocol from the AppleTalk suite."
              ::= { lanternProtocols  12 }

          protoXNSPkts OBJECT-TYPE
              SYNTAX Counter
              ACCESS read-only
              STATUS mandatory
              DESCRIPTION
                     "The count of packets observed with a protocol from
                     the XNS suite."
              ::= { lanternProtocols  13 }

          protoXNSOctets OBJECT-TYPE
              SYNTAX Counter
              ACCESS read-only
              STATUS mandatory
              DESCRIPTION
                     "The count of octets in packets observed with a
                     protocol from the XNS suite."
              ::= { lanternProtocols  14 }

          protoSNAPkts OBJECT-TYPE
              SYNTAX Counter
              ACCESS read-only
              STATUS mandatory
              DESCRIPTION
                     "The count of packets observed with a protocol from
                     the SNA suite."
              ::= { lanternProtocols  15 }

          protoSNAOctets OBJECT-TYPE
              SYNTAX Counter
              ACCESS read-only
              STATUS mandatory
              DESCRIPTION
                     "The count of octets in packets observed with a
                     protocol from the SNA suite."
              ::= { lanternProtocols  16 }

          protoVINESPkts OBJECT-TYPE
              SYNTAX Counter
              ACCESS read-only
              STATUS mandatory
              DESCRIPTION
                     "The count of packets observed with a protocol from
                     the Banyan VINES suite."
              ::= { lanternProtocols  17 }

          protoVINESOctets OBJECT-TYPE
              SYNTAX Counter
              ACCESS read-only
              STATUS mandatory
              DESCRIPTION
                     "The count of octets in packets observed with a
                     protocol from the Banyan VINES suite."
              ::= { lanternProtocols  18 }



          -- LANtern Traps

          cableFailure TRAP-TYPE
              ENTERPRISE ethernetLANtern
              VARIABLES  { adminTrapHandle, adminDateAndTime,
                         eMediaStatus }
              DESCRIPTION
                     "A cableFailure(1) trap is generated whenever the
                     LANtern network monitor detects a fault with the
                     network cable."
              ::= 1

          pingNotification TRAP-TYPE
              ENTERPRISE ethernetLANtern
              VARIABLES  { adminTrapHandle, adminDateAndTime,
                         ipPingTarget, ipPingDuration }
              DESCRIPTION
                     "A pingNotification(2) trap is generated whenever
                     the LANtern network monitor receives the echo
                     response to a proxy ping."
              ::= 2

          duplicateIPAddr TRAP-TYPE
              ENTERPRISE ethernetLANtern
              VARIABLES  { adminTrapHandle, adminDateAndTime,
                         ipDupeIPAddr, ipDupeGoodMACAddr,
                         ipDupeBadMACAddr }
              DESCRIPTION
                     "A duplicateIPAddr(3) trap is generated whenever
                     the LANtern network monitor first detects more than
                     one host using the same IP address."
              ::= 3

          utilizationAlarm TRAP-TYPE
              ENTERPRISE ethernetLANtern
              VARIABLES  { adminTrapHandle, adminDateAndTime,
                         eAlarmType, eAlarmValue, eAlarmLowThreshold,
                         eAlarmHighThreshold, eAlarmSampleTime }
              DESCRIPTION
                     "A utilizationAlarm(4) trap is generated whenever
                     the percent utilization parameter enters or leaves
                     an alarm condition as defined by the thresholds set
                     in the eAlarmTable."
              ::= 4

          errorsAlarm TRAP-TYPE
              ENTERPRISE ethernetLANtern
              VARIABLES  { adminTrapHandle, adminDateAndTime,
                         eAlarmType, eAlarmValue, eAlarmLowThreshold,
                         eAlarmHighThreshold, eAlarmSampleTime }
              DESCRIPTION
                     "An errorsAlarm(5) trap is generated whenever the
                     percent errors parameter enters or leaves an alarm
                     condition as defined by the thresholds set in the
                     eAlarmTable."
              ::= 5

          broadcastsAlarm TRAP-TYPE
              ENTERPRISE ethernetLANtern
              VARIABLES  { adminTrapHandle, adminDateAndTime,
                         eAlarmType, eAlarmValue, eAlarmLowThreshold,
                         eAlarmHighThreshold, eAlarmSampleTime }
              DESCRIPTION
                     "A broadcastsAlarm(6) trap is generated whenever
                     the percent broadcasts parameter enters or leaves
                     an alarm condition as defined by the thresholds set
                     in the eAlarmTable."
              ::= 6

          collisionsAlarm TRAP-TYPE
              ENTERPRISE ethernetLANtern
              VARIABLES  { adminTrapHandle, adminDateAndTime,
                         eAlarmType, eAlarmValue, eAlarmLowThreshold,
                         eAlarmHighThreshold, eAlarmSampleTime }
              DESCRIPTION
                     "A collisionsAlarm(7) trap is generated whenever
                     the percent collisions parameter enters or leaves
                     an alarm condition as defined by the thresholds set
                     in the eAlarmTable."
              ::= 7

          hostInactive TRAP-TYPE
              ENTERPRISE ethernetLANtern
              VARIABLES  { adminTrapHandle, adminDateAndTime,
                         eHostAddress }
              DESCRIPTION
                     "A hostInactive(9) trap is generated whenever the
                     LANtern network monitor first detects that a
                     monitored host has not transmitted for the
                     specified interval. The LANtern will attempt to
                     verify that the host is actually dead by pinging it
                     before generating the trap."
              ::= 9

          hostActive TRAP-TYPE
              ENTERPRISE ethernetLANtern
              VARIABLES  { adminTrapHandle,
                         adminDateAndTime,eHostAddress }
              DESCRIPTION
                     "A hostActive(10) trap is generated whenever the
                     LANtern network monitor first detects that a
                     monitored host has begun transmitting again (after
                     being inactive)."
              ::= 10

          newHost TRAP-TYPE
              ENTERPRISE ethernetLANtern
              VARIABLES  { adminTrapHandle, adminDateAndTime,
                         eHostAddress }
              DESCRIPTION
                     "A newHost(11) trap is generated whenever the
                     LANtern network monitor first detects a new host
                     transmitting on its network segment."
              ::= 11

          hostLimitExceeded TRAP-TYPE
              ENTERPRISE ethernetLANtern
              VARIABLES  { adminTrapHandle, adminDateAndTime,
                         eHostAddress }
              DESCRIPTION
                     "A hostLimitExceeded(12) trap is generated the
                     first time the LANtern exceeds its host limit.
                     eHostAddress is the address of the host which
                     caused the limit to be exceeded."
              ::= 12

          END
