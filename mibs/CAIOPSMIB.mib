-- ********************************************************************
-- ********************************************************************
-- **      Copyright (c) 1996 Computer Associates International.     **
-- **                                                                **
-- **                                                                **
-- **                                                                **
-- ** Computer Associates Intl. retains the right to change this MIB **
-- ** without notification.                                          **
-- **                                                                **
-- **                                                                **
-- ** Author: Dave Edborg                                            **
-- **                                                                **
-- ** CAIOPSMIB: This MIB defines the traps issued by CA-OPS/MVS     **
-- **                                                                **
-- **                                                                **
-- ********************************************************************
-- ********************************************************************
-- ** Modification Log:                                              **
-- **                                                                **
-- ** MM/DD/YYYY USERID  :                                           **
-- **                                                                **
-- **                                                                **
-- ********************************************************************
-- ********************************************************************

CAIOPSMIB DEFINITIONS ::= BEGIN

--
-- The below statements import basic types from the relevant
-- definitions.
--


IMPORTS
 enterprises
  FROM RFC1155-SMI
 DisplayString
  FROM RFC1213-MIB
 TRAP-TYPE
  FROM RFC-1215
 OBJECT-TYPE
  FROM RFC-1212
 cai
  FROM CAISECMIB
  caiSysMgt FROM CAIMIB;

-- *******************************************************************
-- *******************************************************************
-- **                                                               **
-- ** Start the definition of CA-OPS/MVS MIB.                       **
-- **                                                               **
-- *******************************************************************
-- *******************************************************************

-- *******************************************************************
-- *******************************************************************
-- **                                                               **
-- ** This level expands 'caiSysMgt' branch.                        **
-- ** FYI->caiSysMgt       OBJECT IDENTIFIER ::= { cai          2 } **
-- **                                                               **
-- *******************************************************************
-- *******************************************************************

caiOps  OBJECT IDENTIFIER ::= { caiSysMgt   4 }

caiOpsLstMsg OBJECT-TYPE
 SYNTAX DisplayString (SIZE(0..256))
 ACCESS read-only
 STATUS mandatory
 DESCRIPTION "This object type is used when defining TRAPs to send
              Security messages in a trap.
             "
-- ** The CA-OPS/MVS TRAP List OID is 1.3.6.1.4.1.791.2.4.2         **
 ::= { caiOps    2 }

-- *******************************************************************
-- *******************************************************************
-- **                                                               **
-- ** Following defines the traps used by CA products.              **
-- ** Traps are defined using the conventions in RFC 1215.          **
-- ** Trap numbers are allocated as follows. If need be, they       **
-- ** can be expanded on an as per need basis.                      **
-- **                                                               **
-- ** 1-999  - Reserved for CA-Unicenter for Unix                   **
-- ** 1000-1099 - Reserved for CA-ACF2/MVS 1.3.6.1.4.1.791.2.3.2    **
-- ** 1100-1199 - Reserved for CA-TSS/MVS  1.3.6.1.4.1.791.2.3.3    **
-- ** 1200-1999 - Reserved for CA-Security 1.3.6.1.4.1.791.2.3      **
-- ** 2000-2099 - Reserved for CA-OPS/MVS  1.3.6.1.4.1.791.2.4      **
-- ** xxxxx  -                                                      **
-- **                                                               **
-- *******************************************************************
-- *******************************************************************

caiOpsT1      TRAP-TYPE
 ENTERPRISE  cai
 VARIABLES { caiOpsLstMsg }
 DESCRIPTION "Reason: A dataset violation occurred

              Action:

              Msgref: ACF99913
             "
-- ******************************************************************
-- * Value format: SYSID TASK DATE TIME CODE1 CODE2
-- ******************************************************************
 ::= 2000

caiOpsT2       TRAP-TYPE
 ENTERPRISE  cai
 VARIABLES { caiOpsLstMsg }
 DESCRIPTION "Reason: A resource violation occurred

              Action:

              Msgref: ACF04056
             "
-- *******************************************************************
-- * Value format: SYSID TASK DATE TIME CODE
-- *******************************************************************
 ::= 2001

END
