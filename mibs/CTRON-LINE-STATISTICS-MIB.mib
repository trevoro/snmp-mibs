CTRON-LINE-STATISTICS-MIB DEFINITIONS ::= BEGIN

--  CTRON-LINE-STATISTICS-MIB
--  Revision: x.xx.xx
--  Part Number:
--  Date:  Sept 23, 1998
--  Cabletron Systems, Inc.
--  35 Industrial Way, P.O. Box 5005
--  Rochester, NH 03867-0505
--  (603) 332-9400
--  support@ctron.com
--
--  This module provides an enterprise-specific MIB.
--
--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.

--  Copyright September 1998 Cabletron Systems

IMPORTS
        OBJECT-TYPE          FROM RFC-1212
        cabletron             FROM CTRON-OIDS;
                
        ctSSA                  OBJECT IDENTIFIER ::= { cabletron 4497 }
--      ctDsx1LineStatisticsTable    OBJECT IDENTIFIER ::= { ctSSA 21 }
        
-- Cabletron Ds1 Line Statistics
-- This group is optional for any platforms that have a t1 or e1 physical
-- port.

ctDsx1LineStatisticsTable OBJECT-TYPE
        SYNTAX  SEQUENCE OF CtDsx1LineStatisticsEntry
        ACCESS  not-accessible
        STATUS  mandatory
        DESCRIPTION
                "A list of statistics gathered at Layer 1 for the
installed WAN ports."
        ::= { ctSSA 21 }
--              1.3.6.1.4.1.52.4.2.27.21

ctDsx1LineStatisticsEntry OBJECT-TYPE
        SYNTAX  CtDsx1LineStatisticsEntry
        ACCESS  not-accessible
        STATUS  mandatory
        DESCRIPTION
                "A list of statistics gathered at Layer 1 for a given WAN port.
                The statistics include counts for qualified alarms and total
		alarms (qualified alarms and unqualified alarms).  A qualified
		alarm is an alarm whose presence has been detected for a finite
		amount of time (called its integration period).  An unqualified
		alarm is an alarm whose presence has not been detected for the
	 	entire integration period."
        INDEX   { lsLineIndex }
        ::= { ctDsx1LineStatisticsTable 1 }
--              1.3.6.1.4.1.52.4.2.27.21.1

CtDsx1LineStatisticsEntry ::=
        SEQUENCE {
                        lsLineIndex
                        INTEGER,
                        lsLayer1Up
                        INTEGER,
                        lsLayer1Down
                        INTEGER,
                        lsLayer1LOS
                        INTEGER,
                        lsLayer1LOF
                        INTEGER,
                        lsLayer1RAI
                        INTEGER,
                        lsLayer1AIS
                        INTEGER,
                        lsLayer1LOSAll
                        INTEGER,
                        lsLayer1LOFAll
                        INTEGER,
                        lsLayer1RAIAll
                        INTEGER,
                        lsLayer1AISAll
                        INTEGER,
                        lsLayer1Interrupts
                        INTEGER,
                        lsLayer1ClearStats
                        INTEGER         
                }
                
lsLineIndex OBJECT-TYPE
        SYNTAX  INTEGER
        ACCESS  read-only
        STATUS  mandatory
        DESCRIPTION     
                "The physical line index for this port."
        ::= { ctDsx1LineStatisticsEntry 1 }
--              1.3.6.1.4.1.52.4.2.27.21.1.1

lsLayer1Up  OBJECT-TYPE
        SYNTAX  INTEGER
        ACCESS  read-only
        STATUS  mandatory
        DESCRIPTION
                "The number of times Layer 1 has been brought up
                   (by a higher level software entity or administrator)
                   or has come up due to the disintegration of an
alarm."
        ::= { ctDsx1LineStatisticsEntry 2 }
--              1.3.6.1.4.1.52.4.2.27.21.1.2

lsLayer1Down  OBJECT-TYPE
        SYNTAX  INTEGER
        ACCESS  read-only
        STATUS  mandatory
        DESCRIPTION
                "The number of times Layer 1 has been taken down
                   (by a higher level software entity or administrator)
                   or has gone down due to the integration of an alarm."
        ::= { ctDsx1LineStatisticsEntry 3 }
--              1.3.6.1.4.1.52.4.2.27.21.1.3

lsLayer1LOS  OBJECT-TYPE
        SYNTAX  INTEGER
        ACCESS  read-only
        STATUS  mandatory
        DESCRIPTION
                "The number of times Layer 1 has qualified a Loss of
Signal."
        ::= { ctDsx1LineStatisticsEntry 4 }
--              1.3.6.1.4.1.52.4.2.27.21.1.4

lsLayer1LOF  OBJECT-TYPE
        SYNTAX  INTEGER
        ACCESS  read-only
        STATUS  mandatory
        DESCRIPTION
                "The number of times Layer 1 has qualified a Loss of
Frame."
        ::= { ctDsx1LineStatisticsEntry 5 }
--              1.3.6.1.4.1.52.4.2.27.21.1.5

lsLayer1RAI  OBJECT-TYPE
        SYNTAX  INTEGER
        ACCESS  read-only
        STATUS  mandatory
        DESCRIPTION
                "The number of times Layer 1 has qualified a Remote
Alarm Indication.
                   RAI is also known as a Yellow alarm."
        ::= { ctDsx1LineStatisticsEntry 6 }
--              1.3.6.1.4.1.52.4.2.27.21.1.6
                        
lsLayer1AIS  OBJECT-TYPE
        SYNTAX  INTEGER
        ACCESS  read-only
        STATUS  mandatory
        DESCRIPTION
                "The number of times Layer 1 has qualified an Alarm
Indication Signal.
                   AIS is also known as a Blue alarm."
        ::= { ctDsx1LineStatisticsEntry 7 }
--              1.3.6.1.4.1.52.4.2.27.21.1.7

lsLayer1LOSAll  OBJECT-TYPE
        SYNTAX  INTEGER
        ACCESS  read-only
        STATUS  mandatory
        DESCRIPTION
                "The number of times Layer 1 has detected a Loss of
Signal.
                   This includes both qualified and unqualified
                   Losses of Signal."
        ::= { ctDsx1LineStatisticsEntry 8 }
--              1.3.6.1.4.1.52.4.2.27.21.1.8

lsLayer1LOFAll  OBJECT-TYPE
        SYNTAX  INTEGER
        ACCESS  read-only
        STATUS  mandatory
        DESCRIPTION
                "The number of times Layer 1 has detected a Loss of
Frame.
                   This includes both qualified and unqualified
                   Losses of Frame."
        ::= { ctDsx1LineStatisticsEntry 9 }
--              1.3.6.1.4.1.52.4.2.27.21.1.9

lsLayer1RAIAll  OBJECT-TYPE
        SYNTAX  INTEGER
        ACCESS  read-only
        STATUS  mandatory
        DESCRIPTION
                "The number of times Layer 1 has detected a Remote Alarm
Indication.
                   This includes both qualified and unqualified
                   Remote Alarm Indications."
        ::= { ctDsx1LineStatisticsEntry 10 }
--              1.3.6.1.4.1.52.4.2.27.21.1.10
                        
lsLayer1AISAll  OBJECT-TYPE
        SYNTAX  INTEGER
        ACCESS  read-only
        STATUS  mandatory
        DESCRIPTION
                "The number of times Layer 1 has detected an Alarm
Indication Signal.
                   This includes both qualified and unqualified
                   Alarm Indication Signals."
        ::= { ctDsx1LineStatisticsEntry 11 }
--              1.3.6.1.4.1.52.4.2.27.21.1.11

lsLayer1Interrupts  OBJECT-TYPE
        SYNTAX  INTEGER
        ACCESS  read-only
        STATUS  mandatory
        DESCRIPTION
                "The number of interrupts seen at Layer 1."
        ::= { ctDsx1LineStatisticsEntry 12 }
--              1.3.6.1.4.1.52.4.2.27.21.1.12

lsLayer1ClearStats  OBJECT-TYPE
        SYNTAX  INTEGER
        ACCESS  read-write
        STATUS  mandatory
        DESCRIPTION
                "When written with any value, all statistics associated
with this
                   LineIndex will be cleared."
        ::= { ctDsx1LineStatisticsEntry 13 }
--              1.3.6.1.4.1.52.4.2.27.21.1.13

END
