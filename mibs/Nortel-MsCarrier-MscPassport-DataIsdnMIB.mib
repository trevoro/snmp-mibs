Nortel-MsCarrier-MscPassport-DataIsdnMIB
DEFINITIONS ::= BEGIN



IMPORTS

      OBJECT-TYPE
   FROM RFC-1212

      mscPassportMIBs,
      mscComponents
   FROM Nortel-MsCarrier-MscPassport-UsefulDefinitionsMIB

      DisplayString,
      StorageType,
      RowStatus,
      InterfaceIndex,
      Integer32,
      Unsigned32
   FROM Nortel-MsCarrier-MscPassport-StandardTextualConventionsMIB

      AsciiString,
      NonReplicated,
      DigitString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     DataIsdn Enterprise MIB."

dataIsdnMIB OBJECT IDENTIFIER ::= { mscPassportMIBs 113 }










-- DataSignallingChannel/n		
-- The DataSignallingChannel component defines the operational 
-- characteristics of the connection to the external ISDN PRI 
-- equipment. A DataSignallingChannel must be provisioned for each 
-- D-Channel.

mscDataSigChan OBJECT IDENTIFIER ::= { mscComponents 120 }



mscDataSigChanRowStatusTable OBJECT-TYPE
   SYNTAX     SEQUENCE OF MscDataSigChanRowStatusEntry
   ACCESS     not-accessible
   STATUS     mandatory
   DESCRIPTION
     "This entry controls the addition and deletion of 
      mscDataSigChan components."
::= { mscDataSigChan 1 }

mscDataSigChanRowStatusEntry OBJECT-TYPE
   SYNTAX     MscDataSigChanRowStatusEntry
   ACCESS     not-accessible
   STATUS     mandatory
   DESCRIPTION
     "A single entry in the table represents a single 
      mscDataSigChan component."
   INDEX {
      mscDataSigChanIndex }
::= { mscDataSigChanRowStatusTable 1 }

MscDataSigChanRowStatusEntry ::= SEQUENCE {
   mscDataSigChanRowStatus
      RowStatus,
   mscDataSigChanComponentName
      DisplayString,
   mscDataSigChanStorageType
      StorageType,
   mscDataSigChanIndex
      Integer32 }

mscDataSigChanRowStatus OBJECT-TYPE
   SYNTAX     RowStatus 
   ACCESS     read-write
   STATUS     mandatory
   DESCRIPTION
     "This variable is used as the basis for SNMP naming of
      mscDataSigChan components.
      These components can be added and deleted."
::= { mscDataSigChanRowStatusEntry 1 }

mscDataSigChanComponentName OBJECT-TYPE
   SYNTAX     DisplayString 
   ACCESS     read-only
   STATUS     mandatory
   DESCRIPTION
     "This variable provides the component's string name for
      use with the ASCII Console Interface"
::= { mscDataSigChanRowStatusEntry 2 }

mscDataSigChanStorageType OBJECT-TYPE
   SYNTAX     StorageType 
   ACCESS     read-only
   STATUS     mandatory
   DESCRIPTION
     "This variable represents the storage type value for the
      mscDataSigChan tables."
::= { mscDataSigChanRowStatusEntry 4 }

mscDataSigChanIndex OBJECT-TYPE
   SYNTAX     Integer32 (1..255)
   ACCESS     not-accessible
   STATUS     mandatory
   DESCRIPTION
     "This variable represents the index for the mscDataSigChan tables."
::= { mscDataSigChanRowStatusEntry 10 }

mscDataSigChanProvTable OBJECT-TYPE
   SYNTAX     SEQUENCE OF MscDataSigChanProvEntry
   ACCESS     not-accessible
   STATUS     mandatory
   DESCRIPTION
     "This group represents the provisionable attributes of a 
      DataSigChan."
::= { mscDataSigChan 100 }

mscDataSigChanProvEntry OBJECT-TYPE
   SYNTAX     MscDataSigChanProvEntry
   ACCESS     not-accessible
   STATUS     mandatory
   DESCRIPTION
     "An entry in the mscDataSigChanProvTable."
   INDEX {
      mscDataSigChanIndex }
::= { mscDataSigChanProvTable 1 }

MscDataSigChanProvEntry ::= SEQUENCE {
   mscDataSigChanCommentText
      AsciiString }

mscDataSigChanCommentText OBJECT-TYPE
   SYNTAX     AsciiString (SIZE (0..40))
   ACCESS     read-write
   STATUS     mandatory
   DESCRIPTION
     "This attribute specifies the name of the customer that is using this 
      DataSigChan. Typical use of this attribute is to store customer 
      name."
::= { mscDataSigChanProvEntry 1 }

mscDataSigChanCidDataTable OBJECT-TYPE
   SYNTAX     SEQUENCE OF MscDataSigChanCidDataEntry
   ACCESS     not-accessible
   STATUS     mandatory
   DESCRIPTION
     "This group contains the attribute for a component's Customer 
      Identifier (CID). Refer to the attribute description for a detailed 
      explanation of CIDs."
::= { mscDataSigChan 101 }

mscDataSigChanCidDataEntry OBJECT-TYPE
   SYNTAX     MscDataSigChanCidDataEntry
   ACCESS     not-accessible
   STATUS     mandatory
   DESCRIPTION
     "An entry in the mscDataSigChanCidDataTable."
   INDEX {
      mscDataSigChanIndex }
::= { mscDataSigChanCidDataTable 1 }

MscDataSigChanCidDataEntry ::= SEQUENCE {
   mscDataSigChanCustomerIdentifier
      Unsigned32 }

mscDataSigChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscDataSigChanCidDataEntry 1 }

mscDataSigChanIfEntryTable OBJECT-TYPE
   SYNTAX     SEQUENCE OF MscDataSigChanIfEntryEntry
   ACCESS     not-accessible
   STATUS     mandatory
   DESCRIPTION
     "This group contains the provisionable attributes for the ifEntry."
::= { mscDataSigChan 102 }

mscDataSigChanIfEntryEntry OBJECT-TYPE
   SYNTAX     MscDataSigChanIfEntryEntry
   ACCESS     not-accessible
   STATUS     mandatory
   DESCRIPTION
     "An entry in the mscDataSigChanIfEntryTable."
   INDEX {
      mscDataSigChanIndex }
::= { mscDataSigChanIfEntryTable 1 }

MscDataSigChanIfEntryEntry ::= SEQUENCE {
   mscDataSigChanIfAdminStatus
      INTEGER,
   mscDataSigChanIfIndex
      InterfaceIndex }

mscDataSigChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscDataSigChanIfEntryEntry 1 }

mscDataSigChanIfIndex OBJECT-TYPE
   SYNTAX     InterfaceIndex (1..65535)
   ACCESS     read-only
   STATUS     mandatory
   DESCRIPTION
     "This is the index for the IfEntry. Its value is automatically initialized 
      during the provisioning process."
::= { mscDataSigChanIfEntryEntry 2 }

mscDataSigChanStateTable OBJECT-TYPE
   SYNTAX     SEQUENCE OF MscDataSigChanStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscDataSigChan 103 }

mscDataSigChanStateEntry OBJECT-TYPE
   SYNTAX     MscDataSigChanStateEntry
   ACCESS     not-accessible
   STATUS     mandatory
   DESCRIPTION
     "An entry in the mscDataSigChanStateTable."
   INDEX {
      mscDataSigChanIndex }
::= { mscDataSigChanStateTable 1 }

MscDataSigChanStateEntry ::= SEQUENCE {
   mscDataSigChanAdminState
      INTEGER,
   mscDataSigChanOperationalState
      INTEGER,
   mscDataSigChanUsageState
      INTEGER }

mscDataSigChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscDataSigChanStateEntry 1 }

mscDataSigChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscDataSigChanStateEntry 2 }

mscDataSigChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscDataSigChanStateEntry 3 }

mscDataSigChanOperStatusTable OBJECT-TYPE
   SYNTAX     SEQUENCE OF MscDataSigChanOperStatusEntry
   ACCESS     not-accessible
   STATUS     mandatory
   DESCRIPTION
     "This group includes the Operational Status attribute. This attribute 
      defines the current operational state of this component."
::= { mscDataSigChan 104 }

mscDataSigChanOperStatusEntry OBJECT-TYPE
   SYNTAX     MscDataSigChanOperStatusEntry
   ACCESS     not-accessible
   STATUS     mandatory
   DESCRIPTION
     "An entry in the mscDataSigChanOperStatusTable."
   INDEX {
      mscDataSigChanIndex }
::= { mscDataSigChanOperStatusTable 1 }

MscDataSigChanOperStatusEntry ::= SEQUENCE {
   mscDataSigChanSnmpOperStatus
      INTEGER }

mscDataSigChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscDataSigChanOperStatusEntry 1 }


-- DataSigChan/n CallControl
-- This component defines the Call Control parameters and displays 
-- the statistics of the D-channel.

mscDataSigChanCc OBJECT IDENTIFIER ::= { mscDataSigChan 2 }



mscDataSigChanCcRowStatusTable OBJECT-TYPE
   SYNTAX     SEQUENCE OF MscDataSigChanCcRowStatusEntry
   ACCESS     not-accessible
   STATUS     mandatory
   DESCRIPTION
     "This entry controls the addition and deletion of 
      mscDataSigChanCc components."
::= { mscDataSigChanCc 1 }

mscDataSigChanCcRowStatusEntry OBJECT-TYPE
   SYNTAX     MscDataSigChanCcRowStatusEntry
   ACCESS     not-accessible
   STATUS     mandatory
   DESCRIPTION
     "A single entry in the table represents a single 
      mscDataSigChanCc component."
   INDEX {
      mscDataSigChanIndex,
      mscDataSigChanCcIndex }
::= { mscDataSigChanCcRowStatusTable 1 }

MscDataSigChanCcRowStatusEntry ::= SEQUENCE {
   mscDataSigChanCcRowStatus
      RowStatus,
   mscDataSigChanCcComponentName
      DisplayString,
   mscDataSigChanCcStorageType
      StorageType,
   mscDataSigChanCcIndex
      NonReplicated }

mscDataSigChanCcRowStatus OBJECT-TYPE
   SYNTAX     RowStatus 
   ACCESS     read-only
   STATUS     mandatory
   DESCRIPTION
     "This variable is used as the basis for SNMP naming of
      mscDataSigChanCc components.
      These components cannot be added nor deleted."
::= { mscDataSigChanCcRowStatusEntry 1 }

mscDataSigChanCcComponentName OBJECT-TYPE
   SYNTAX     DisplayString 
   ACCESS     read-only
   STATUS     mandatory
   DESCRIPTION
     "This variable provides the component's string name for
      use with the ASCII Console Interface"
::= { mscDataSigChanCcRowStatusEntry 2 }

mscDataSigChanCcStorageType OBJECT-TYPE
   SYNTAX     StorageType 
   ACCESS     read-only
   STATUS     mandatory
   DESCRIPTION
     "This variable represents the storage type value for the
      mscDataSigChanCc tables."
::= { mscDataSigChanCcRowStatusEntry 4 }

mscDataSigChanCcIndex OBJECT-TYPE
   SYNTAX     NonReplicated 
   ACCESS     not-accessible
   STATUS     mandatory
   DESCRIPTION
     "This variable represents the index for the mscDataSigChanCc tables."
::= { mscDataSigChanCcRowStatusEntry 10 }

mscDataSigChanCcStatsTable OBJECT-TYPE
   SYNTAX     SEQUENCE OF MscDataSigChanCcStatsEntry
   ACCESS     not-accessible
   STATUS     mandatory
   DESCRIPTION
     "This group contains the statistics of the CallControl"
::= { mscDataSigChanCc 10 }

mscDataSigChanCcStatsEntry OBJECT-TYPE
   SYNTAX     MscDataSigChanCcStatsEntry
   ACCESS     not-accessible
   STATUS     mandatory
   DESCRIPTION
     "An entry in the mscDataSigChanCcStatsTable."
   INDEX {
      mscDataSigChanIndex,
      mscDataSigChanCcIndex }
::= { mscDataSigChanCcStatsTable 1 }

MscDataSigChanCcStatsEntry ::= SEQUENCE {
   mscDataSigChanCcTotalValidInCalls
      Unsigned32,
   mscDataSigChanCcSuccessfullInCalls
      Unsigned32,
   mscDataSigChanCcInInvalidCapability
      Unsigned32,
   mscDataSigChanCcInInvalidScreen
      Unsigned32,
   mscDataSigChanCcInInvalidCgpn
      Unsigned32,
   mscDataSigChanCcInChannelBusy
      Unsigned32,
   mscDataSigChanCcLastClearCause
      INTEGER,
   mscDataSigChanCcLastClearedCallingPartyNumber
      DigitString }

mscDataSigChanCcTotalValidInCalls OBJECT-TYPE
   SYNTAX     Unsigned32 (0..4294967295)
   ACCESS     read-only
   STATUS     mandatory
   DESCRIPTION
     "This attribute counts the total number of incoming calls (with valid 
      mandatory IE contents and received in a valid ISDN state) from the 
      interface. This counter wraps to zero after reaching its maximum 
      value."
   DEFVAL     { 0 }
::= { mscDataSigChanCcStatsEntry 1 }

mscDataSigChanCcSuccessfullInCalls OBJECT-TYPE
   SYNTAX     Unsigned32 (0..4294967295)
   ACCESS     read-only
   STATUS     mandatory
   DESCRIPTION
     "This attribute counts the total number of successfull valid incoming 
      calls from the interface. Unsuccessful calls include those that have 
      disallowed Capability (BC, LLC), screening indicator, or calling 
      party number, and calls that are rejected due to requested channel 
      busy. This counter wraps to zero after reaching its maximum value."
   DEFVAL     { 0 }
::= { mscDataSigChanCcStatsEntry 2 }

mscDataSigChanCcInInvalidCapability OBJECT-TYPE
   SYNTAX     Unsigned32 (0..4294967295)
   ACCESS     read-only
   STATUS     mandatory
   DESCRIPTION
     "This attribute counts the number of valid incoming calls rejected 
      due to an unsupported service capability, such as Information 
      Transfer Rate, Class of Service, Protocol Standard. This counter 
      wraps to zero after reaching its maximum value."
   DEFVAL     { 0 }
::= { mscDataSigChanCcStatsEntry 3 }

mscDataSigChanCcInInvalidScreen OBJECT-TYPE
   SYNTAX     Unsigned32 (0..4294967295)
   ACCESS     read-only
   STATUS     mandatory
   DESCRIPTION
     "This attribute counts the number of valid incoming calls rejected 
      due to a screening indicator value not provisioned in the channel 
      group's screeningIndicator attribute. This counter wraps to zero 
      after reaching its maximum value."
   DEFVAL     { 0 }
::= { mscDataSigChanCcStatsEntry 4 }

mscDataSigChanCcInInvalidCgpn OBJECT-TYPE
   SYNTAX     Unsigned32 (0..4294967295)
   ACCESS     read-only
   STATUS     mandatory
   DESCRIPTION
     "This attribute counts the number of valid incoming calls rejected 
      due to the calling party number not beeing provisioned in any 
      channelGroup component of this call control. This counter wraps to 
      zero after reaching its maximum value."
   DEFVAL     { 0 }
::= { mscDataSigChanCcStatsEntry 5 }

mscDataSigChanCcInChannelBusy OBJECT-TYPE
   SYNTAX     Unsigned32 (0..4294967295)
   ACCESS     read-only
   STATUS     mandatory
   DESCRIPTION
     "This attribute counts the number of valid incoming calls rejected 
      due to no available B-Channels. This counter wraps to zero after 
      reaching its maximum value."
   DEFVAL     { 0 }
::= { mscDataSigChanCcStatsEntry 6 }

mscDataSigChanCcLastClearCause OBJECT-TYPE
   SYNTAX     INTEGER (0..255)
   ACCESS     read-only
   STATUS     mandatory
   DESCRIPTION
     "This attribute indicates the Q931 clear cause of the last valid call 
      that is rejected or cleared."
::= { mscDataSigChanCcStatsEntry 7 }

mscDataSigChanCcLastClearedCallingPartyNumber OBJECT-TYPE
   SYNTAX     DigitString (SIZE (1..14))
   ACCESS     read-only
   STATUS     mandatory
   DESCRIPTION
     "This attribute shows the calling party number of the last valid call 
      that is rejected or cleared."
::= { mscDataSigChanCcStatsEntry 8 }


-- DataSigChan/n Cc ChannelGroup/n
-- A ChannelGroup defines the call allocation parameters and the 
-- channel list for a subgroup of users.

mscDataSigChanCcCg OBJECT IDENTIFIER ::= { mscDataSigChanCc 2 }



mscDataSigChanCcCgRowStatusTable OBJECT-TYPE
   SYNTAX     SEQUENCE OF MscDataSigChanCcCgRowStatusEntry
   ACCESS     not-accessible
   STATUS     mandatory
   DESCRIPTION
     "This entry controls the addition and deletion of 
      mscDataSigChanCcCg components."
::= { mscDataSigChanCcCg 1 }

mscDataSigChanCcCgRowStatusEntry OBJECT-TYPE
   SYNTAX     MscDataSigChanCcCgRowStatusEntry
   ACCESS     not-accessible
   STATUS     mandatory
   DESCRIPTION
     "A single entry in the table represents a single 
      mscDataSigChanCcCg component."
   INDEX {
      mscDataSigChanIndex,
      mscDataSigChanCcIndex,
      mscDataSigChanCcCgIndex }
::= { mscDataSigChanCcCgRowStatusTable 1 }

MscDataSigChanCcCgRowStatusEntry ::= SEQUENCE {
   mscDataSigChanCcCgRowStatus
      RowStatus,
   mscDataSigChanCcCgComponentName
      DisplayString,
   mscDataSigChanCcCgStorageType
      StorageType,
   mscDataSigChanCcCgIndex
      Integer32 }

mscDataSigChanCcCgRowStatus OBJECT-TYPE
   SYNTAX     RowStatus 
   ACCESS     read-write
   STATUS     mandatory
   DESCRIPTION
     "This variable is used as the basis for SNMP naming of
      mscDataSigChanCcCg components.
      These components can be added and deleted."
::= { mscDataSigChanCcCgRowStatusEntry 1 }

mscDataSigChanCcCgComponentName OBJECT-TYPE
   SYNTAX     DisplayString 
   ACCESS     read-only
   STATUS     mandatory
   DESCRIPTION
     "This variable provides the component's string name for
      use with the ASCII Console Interface"
::= { mscDataSigChanCcCgRowStatusEntry 2 }

mscDataSigChanCcCgStorageType OBJECT-TYPE
   SYNTAX     StorageType 
   ACCESS     read-only
   STATUS     mandatory
   DESCRIPTION
     "This variable represents the storage type value for the
      mscDataSigChanCcCg tables."
::= { mscDataSigChanCcCgRowStatusEntry 4 }

mscDataSigChanCcCgIndex OBJECT-TYPE
   SYNTAX     Integer32 (1..31)
   ACCESS     not-accessible
   STATUS     mandatory
   DESCRIPTION
     "This variable represents the index for the mscDataSigChanCcCg tables."
::= { mscDataSigChanCcCgRowStatusEntry 10 }

mscDataSigChanCcCgCidDataTable OBJECT-TYPE
   SYNTAX     SEQUENCE OF MscDataSigChanCcCgCidDataEntry
   ACCESS     not-accessible
   STATUS     mandatory
   DESCRIPTION
     "This group contains the attribute for a component's Customer 
      Identifier (CID). Refer to the attribute description for a detailed 
      explanation of CIDs."
::= { mscDataSigChanCcCg 10 }

mscDataSigChanCcCgCidDataEntry OBJECT-TYPE
   SYNTAX     MscDataSigChanCcCgCidDataEntry
   ACCESS     not-accessible
   STATUS     mandatory
   DESCRIPTION
     "An entry in the mscDataSigChanCcCgCidDataTable."
   INDEX {
      mscDataSigChanIndex,
      mscDataSigChanCcIndex,
      mscDataSigChanCcCgIndex }
::= { mscDataSigChanCcCgCidDataTable 1 }

MscDataSigChanCcCgCidDataEntry ::= SEQUENCE {
   mscDataSigChanCcCgCustomerIdentifier
      Unsigned32 }

mscDataSigChanCcCgCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscDataSigChanCcCgCidDataEntry 1 }

mscDataSigChanCcCgProvTable OBJECT-TYPE
   SYNTAX     SEQUENCE OF MscDataSigChanCcCgProvEntry
   ACCESS     not-accessible
   STATUS     mandatory
   DESCRIPTION
     "This group defines the call admission parameters applied to the 
      group of B-Channels."
::= { mscDataSigChanCcCg 11 }

mscDataSigChanCcCgProvEntry OBJECT-TYPE
   SYNTAX     MscDataSigChanCcCgProvEntry
   ACCESS     not-accessible
   STATUS     mandatory
   DESCRIPTION
     "An entry in the mscDataSigChanCcCgProvTable."
   INDEX {
      mscDataSigChanIndex,
      mscDataSigChanCcIndex,
      mscDataSigChanCcCgIndex }
::= { mscDataSigChanCcCgProvTable 1 }

MscDataSigChanCcCgProvEntry ::= SEQUENCE {
   mscDataSigChanCcCgCommentText
      AsciiString,
   mscDataSigChanCcCgScreeningIndicator
      OCTET STRING,
   mscDataSigChanCcCgChannelAssignmentOrder
      INTEGER,
   mscDataSigChanCcCgChannelList
      OCTET STRING }

mscDataSigChanCcCgCommentText OBJECT-TYPE
   SYNTAX     AsciiString (SIZE (0..40))
   ACCESS     read-write
   STATUS     mandatory
   DESCRIPTION
     "This attribute specifies the name of the customer that is using this 
      ChannelGroup. Typical use of this attribute is to store customer 
      name."
::= { mscDataSigChanCcCgProvEntry 1 }

mscDataSigChanCcCgScreeningIndicator OBJECT-TYPE
   SYNTAX     OCTET STRING (SIZE (1))
   ACCESS     read-write
   STATUS     mandatory
   DESCRIPTION
     "This attribute defines the acceptable set of screening modes. The 
      screening mode is carried by the Calling Party Number information 
      element (IE) of the B-Channel request packet. There are four types 
      of mode:
      upns - User provided, not screened
      upvp - User provided, verified and passed
      upvf - User provided, verified and failed
      np - Network provided
      When a call is received with a screening indicator not provisioned 
      in the list, the call is cleared.

      Description of bits:
      upns(0)
      upvp(1)
      upvf(2)
      np(3)"
   DEFVAL     { '50'H }
::= { mscDataSigChanCcCgProvEntry 2 }

mscDataSigChanCcCgChannelAssignmentOrder OBJECT-TYPE
   SYNTAX     INTEGER  {
                 ascending(0),
                 descending(1) }
   ACCESS     read-write
   STATUS     mandatory
   DESCRIPTION
     "This attribute defines the order (ascending or descending) in which 
      the B-Channels are allocated. This attribute is used only when it is 
      not signalled in the call setup message."
   DEFVAL     { ascending }
::= { mscDataSigChanCcCgProvEntry 3 }

mscDataSigChanCcCgChannelList OBJECT-TYPE
   SYNTAX     OCTET STRING (SIZE (4))
   ACCESS     read-write
   STATUS     mandatory
   DESCRIPTION
     "This attribute contains the list of B-Channel numbers forming the 
      channel group. At least one channel must be specified.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { mscDataSigChanCcCgProvEntry 4 }

mscDataSigChanCcCgStatsTable OBJECT-TYPE
   SYNTAX     SEQUENCE OF MscDataSigChanCcCgStatsEntry
   ACCESS     not-accessible
   STATUS     mandatory
   DESCRIPTION
     "This group contains the statistics for a ChannelGroup"
::= { mscDataSigChanCcCg 12 }

mscDataSigChanCcCgStatsEntry OBJECT-TYPE
   SYNTAX     MscDataSigChanCcCgStatsEntry
   ACCESS     not-accessible
   STATUS     mandatory
   DESCRIPTION
     "An entry in the mscDataSigChanCcCgStatsTable."
   INDEX {
      mscDataSigChanIndex,
      mscDataSigChanCcIndex,
      mscDataSigChanCcCgIndex }
::= { mscDataSigChanCcCgStatsTable 1 }

MscDataSigChanCcCgStatsEntry ::= SEQUENCE {
   mscDataSigChanCcCgTotalInCalls
      Unsigned32,
   mscDataSigChanCcCgSuccessfullInCalls
      Unsigned32,
   mscDataSigChanCcCgRejectedNoChanAvail
      Unsigned32,
   mscDataSigChanCcCgIdleChannelCount
      INTEGER,
   mscDataSigChanCcCgBusyChannelCount
      INTEGER }

mscDataSigChanCcCgTotalInCalls OBJECT-TYPE
   SYNTAX     Unsigned32 (0..4294967295)
   ACCESS     read-only
   STATUS     mandatory
   DESCRIPTION
     "This attribute counts the total number of incoming calls (with valid 
      mandatory IE contents and received in a valid ISDN state) from the 
      interface for this channelGroup. This counter wraps to zero after 
      reaching its maximum value."
   DEFVAL     { 0 }
::= { mscDataSigChanCcCgStatsEntry 1 }

mscDataSigChanCcCgSuccessfullInCalls OBJECT-TYPE
   SYNTAX     Unsigned32 (0..4294967295)
   ACCESS     read-only
   STATUS     mandatory
   DESCRIPTION
     "This attribute counts the number of valid incoming calls for this 
      channelGroup. This counter wraps to zero after reaching its 
      maximum value.
      DESCRIPTION"
   DEFVAL     { 0 }
::= { mscDataSigChanCcCgStatsEntry 2 }

mscDataSigChanCcCgRejectedNoChanAvail OBJECT-TYPE
   SYNTAX     Unsigned32 (0..4294967295)
   ACCESS     read-only
   STATUS     mandatory
   DESCRIPTION
     "This attribute counts the number of rejected call because no channel 
      were available under the selected channel group. This counter wraps 
      to zero after reaching its maximum value.
      DESCRIPTION"
   DEFVAL     { 0 }
::= { mscDataSigChanCcCgStatsEntry 3 }

mscDataSigChanCcCgIdleChannelCount OBJECT-TYPE
   SYNTAX     INTEGER (0..255)
   ACCESS     read-only
   STATUS     mandatory
   DESCRIPTION
     "This attribute shows the number of B-channels in the channel group 
      that are in idle state."
   DEFVAL     { 0 }
::= { mscDataSigChanCcCgStatsEntry 4 }

mscDataSigChanCcCgBusyChannelCount OBJECT-TYPE
   SYNTAX     INTEGER (0..255)
   ACCESS     read-only
   STATUS     mandatory
   DESCRIPTION
     "This attribute shows the number of B-Channels in this channel 
      group that are in busy state."
   DEFVAL     { 0 }
::= { mscDataSigChanCcCgStatsEntry 5 }


-- DataIsdn/n Cc Cg/n Cgpn/n
-- This component identifies the acceptable calling party number by its 
-- instance number, which can consist up to a maximum of 14 decimal 
-- digits. These are the numbers that are allowed to use the channels of 
-- this ChannelGroup.

mscDataSigChanCcCgCgpn OBJECT IDENTIFIER ::= { mscDataSigChanCcCg 2 }



mscDataSigChanCcCgCgpnRowStatusTable OBJECT-TYPE
   SYNTAX     SEQUENCE OF MscDataSigChanCcCgCgpnRowStatusEntry
   ACCESS     not-accessible
   STATUS     mandatory
   DESCRIPTION
     "This entry controls the addition and deletion of 
      mscDataSigChanCcCgCgpn components."
::= { mscDataSigChanCcCgCgpn 1 }

mscDataSigChanCcCgCgpnRowStatusEntry OBJECT-TYPE
   SYNTAX     MscDataSigChanCcCgCgpnRowStatusEntry
   ACCESS     not-accessible
   STATUS     mandatory
   DESCRIPTION
     "A single entry in the table represents a single 
      mscDataSigChanCcCgCgpn component."
   INDEX {
      mscDataSigChanIndex,
      mscDataSigChanCcIndex,
      mscDataSigChanCcCgIndex,
      mscDataSigChanCcCgCgpnIndex }
::= { mscDataSigChanCcCgCgpnRowStatusTable 1 }

MscDataSigChanCcCgCgpnRowStatusEntry ::= SEQUENCE {
   mscDataSigChanCcCgCgpnRowStatus
      RowStatus,
   mscDataSigChanCcCgCgpnComponentName
      DisplayString,
   mscDataSigChanCcCgCgpnStorageType
      StorageType,
   mscDataSigChanCcCgCgpnIndex
      DigitString }

mscDataSigChanCcCgCgpnRowStatus OBJECT-TYPE
   SYNTAX     RowStatus 
   ACCESS     read-write
   STATUS     mandatory
   DESCRIPTION
     "This variable is used as the basis for SNMP naming of
      mscDataSigChanCcCgCgpn components.
      These components can be added and deleted."
::= { mscDataSigChanCcCgCgpnRowStatusEntry 1 }

mscDataSigChanCcCgCgpnComponentName OBJECT-TYPE
   SYNTAX     DisplayString 
   ACCESS     read-only
   STATUS     mandatory
   DESCRIPTION
     "This variable provides the component's string name for
      use with the ASCII Console Interface"
::= { mscDataSigChanCcCgCgpnRowStatusEntry 2 }

mscDataSigChanCcCgCgpnStorageType OBJECT-TYPE
   SYNTAX     StorageType 
   ACCESS     read-only
   STATUS     mandatory
   DESCRIPTION
     "This variable represents the storage type value for the
      mscDataSigChanCcCgCgpn tables."
::= { mscDataSigChanCcCgCgpnRowStatusEntry 4 }

mscDataSigChanCcCgCgpnIndex OBJECT-TYPE
   SYNTAX     DigitString (SIZE (1..14))
   ACCESS     not-accessible
   STATUS     mandatory
   DESCRIPTION
     "This variable represents the index for the mscDataSigChanCcCgCgpn tables."
::= { mscDataSigChanCcCgCgpnRowStatusEntry 10 }

-- 
-- *** THIS SUBTREE CURRENTLY NOT IMPLEMENTED ***
-- 

-- DataSigChan/n Cc Bchannel/n
-- DataSigChan/n Cc Cg/n Bchannel/n
-- This component identifies the B-channels associated with a 
-- CallControl or a ChannelGroup.

mscDataSigChanCcCgBch OBJECT IDENTIFIER ::= { mscDataSigChanCcCg 3 }



mscDataSigChanCcCgBchRowStatusTable OBJECT-TYPE
   SYNTAX     SEQUENCE OF MscDataSigChanCcCgBchRowStatusEntry
   ACCESS     not-accessible
   STATUS     mandatory
   DESCRIPTION
     "*** THIS TABLE CURRENTLY NOT IMPLEMENTED ***

      This entry controls the addition and deletion of 
      mscDataSigChanCcCgBch components."
::= { mscDataSigChanCcCgBch 1 }

mscDataSigChanCcCgBchRowStatusEntry OBJECT-TYPE
   SYNTAX     MscDataSigChanCcCgBchRowStatusEntry
   ACCESS     not-accessible
   STATUS     mandatory
   DESCRIPTION
     "A single entry in the table represents a single 
      mscDataSigChanCcCgBch component."
   INDEX {
      mscDataSigChanIndex,
      mscDataSigChanCcIndex,
      mscDataSigChanCcCgIndex,
      mscDataSigChanCcCgBchIndex }
::= { mscDataSigChanCcCgBchRowStatusTable 1 }

MscDataSigChanCcCgBchRowStatusEntry ::= SEQUENCE {
   mscDataSigChanCcCgBchRowStatus
      RowStatus,
   mscDataSigChanCcCgBchComponentName
      DisplayString,
   mscDataSigChanCcCgBchStorageType
      StorageType,
   mscDataSigChanCcCgBchIndex
      Integer32 }

mscDataSigChanCcCgBchRowStatus OBJECT-TYPE
   SYNTAX     RowStatus 
   ACCESS     read-only
   STATUS     mandatory
   DESCRIPTION
     "This variable is used as the basis for SNMP naming of
      mscDataSigChanCcCgBch components.
      These components cannot be added nor deleted."
::= { mscDataSigChanCcCgBchRowStatusEntry 1 }

mscDataSigChanCcCgBchComponentName OBJECT-TYPE
   SYNTAX     DisplayString 
   ACCESS     read-only
   STATUS     mandatory
   DESCRIPTION
     "This variable provides the component's string name for
      use with the ASCII Console Interface"
::= { mscDataSigChanCcCgBchRowStatusEntry 2 }

mscDataSigChanCcCgBchStorageType OBJECT-TYPE
   SYNTAX     StorageType 
   ACCESS     read-only
   STATUS     mandatory
   DESCRIPTION
     "This variable represents the storage type value for the
      mscDataSigChanCcCgBch tables."
::= { mscDataSigChanCcCgBchRowStatusEntry 4 }

mscDataSigChanCcCgBchIndex OBJECT-TYPE
   SYNTAX     Integer32 (1..31)
   ACCESS     not-accessible
   STATUS     mandatory
   DESCRIPTION
     "This variable represents the index for the mscDataSigChanCcCgBch tables."
::= { mscDataSigChanCcCgBchRowStatusEntry 10 }

mscDataSigChanCcCgBchBchanOpDataTable OBJECT-TYPE
   SYNTAX     SEQUENCE OF MscDataSigChanCcCgBchBchanOpDataEntry
   ACCESS     not-accessible
   STATUS     mandatory
   DESCRIPTION
     "*** THIS TABLE CURRENTLY NOT IMPLEMENTED ***

      This group contains the operational data of a B-Channel."
::= { mscDataSigChanCcCgBch 2 }

mscDataSigChanCcCgBchBchanOpDataEntry OBJECT-TYPE
   SYNTAX     MscDataSigChanCcCgBchBchanOpDataEntry
   ACCESS     not-accessible
   STATUS     mandatory
   DESCRIPTION
     "An entry in the mscDataSigChanCcCgBchBchanOpDataTable."
   INDEX {
      mscDataSigChanIndex,
      mscDataSigChanCcIndex,
      mscDataSigChanCcCgIndex,
      mscDataSigChanCcCgBchIndex }
::= { mscDataSigChanCcCgBchBchanOpDataTable 1 }

MscDataSigChanCcCgBchBchanOpDataEntry ::= SEQUENCE {
   mscDataSigChanCcCgBchState
      INTEGER,
   mscDataSigChanCcCgBchCallingPartyNumber
      DigitString,
   mscDataSigChanCcCgBchLastQ931ClearCause
      INTEGER,
   mscDataSigChanCcCgBchRunningApplication
      AsciiString }

mscDataSigChanCcCgBchState OBJECT-TYPE
   SYNTAX     INTEGER  {
                 idle(0),
                 busy(1),
                 disabled(2),
                 noProtocolProvisioned(3) }
   ACCESS     read-only
   STATUS     mandatory
   DESCRIPTION
     "This attribute indicates the state of the B-channel. A B-channel is in 
      idle state when it is available for a call. The busy state indicate that 
      the B-channel is presently in use. The disabled state means that the 
      access service is not enabled because it is locked or the port is 
      down. The state noProtocolProvisioned means that the call control 
      did not yet received the registration for this B-channel."
::= { mscDataSigChanCcCgBchBchanOpDataEntry 1 }

mscDataSigChanCcCgBchCallingPartyNumber OBJECT-TYPE
   SYNTAX     DigitString (SIZE (1..14))
   ACCESS     read-only
   STATUS     mandatory
   DESCRIPTION
     "This attribute indicates the calling party number of the last valid call 
      request for this channel."
::= { mscDataSigChanCcCgBchBchanOpDataEntry 2 }

mscDataSigChanCcCgBchLastQ931ClearCause OBJECT-TYPE
   SYNTAX     INTEGER (0..255)
   ACCESS     read-only
   STATUS     mandatory
   DESCRIPTION
     "The clear cause of the last call on this B-channel."
::= { mscDataSigChanCcCgBchBchanOpDataEntry 3 }

mscDataSigChanCcCgBchRunningApplication OBJECT-TYPE
   SYNTAX     AsciiString (SIZE (0..20))
   ACCESS     read-only
   STATUS     mandatory
   DESCRIPTION
     "The name of the application running on this B-channel."
   DEFVAL     { ''H }  -- ""
::= { mscDataSigChanCcCgBchBchanOpDataEntry 4 }


-- DataIsdn/n CallControl Trace
-- This component defines the Call Control trace component for the 
-- dataIsdn. It consists of the Pri/n subcomponent.

mscDataSigChanCcTr OBJECT IDENTIFIER ::= { mscDataSigChanCc 3 }



mscDataSigChanCcTrRowStatusTable OBJECT-TYPE
   SYNTAX     SEQUENCE OF MscDataSigChanCcTrRowStatusEntry
   ACCESS     not-accessible
   STATUS     mandatory
   DESCRIPTION
     "This entry controls the addition and deletion of 
      mscDataSigChanCcTr components."
::= { mscDataSigChanCcTr 1 }

mscDataSigChanCcTrRowStatusEntry OBJECT-TYPE
   SYNTAX     MscDataSigChanCcTrRowStatusEntry
   ACCESS     not-accessible
   STATUS     mandatory
   DESCRIPTION
     "A single entry in the table represents a single 
      mscDataSigChanCcTr component."
   INDEX {
      mscDataSigChanIndex,
      mscDataSigChanCcIndex,
      mscDataSigChanCcTrIndex }
::= { mscDataSigChanCcTrRowStatusTable 1 }

MscDataSigChanCcTrRowStatusEntry ::= SEQUENCE {
   mscDataSigChanCcTrRowStatus
      RowStatus,
   mscDataSigChanCcTrComponentName
      DisplayString,
   mscDataSigChanCcTrStorageType
      StorageType,
   mscDataSigChanCcTrIndex
      NonReplicated }

mscDataSigChanCcTrRowStatus OBJECT-TYPE
   SYNTAX     RowStatus 
   ACCESS     read-write
   STATUS     mandatory
   DESCRIPTION
     "This variable is used as the basis for SNMP naming of
      mscDataSigChanCcTr components.
      These components can be added and deleted."
::= { mscDataSigChanCcTrRowStatusEntry 1 }

mscDataSigChanCcTrComponentName OBJECT-TYPE
   SYNTAX     DisplayString 
   ACCESS     read-only
   STATUS     mandatory
   DESCRIPTION
     "This variable provides the component's string name for
      use with the ASCII Console Interface"
::= { mscDataSigChanCcTrRowStatusEntry 2 }

mscDataSigChanCcTrStorageType OBJECT-TYPE
   SYNTAX     StorageType 
   ACCESS     read-only
   STATUS     mandatory
   DESCRIPTION
     "This variable represents the storage type value for the
      mscDataSigChanCcTr tables."
::= { mscDataSigChanCcTrRowStatusEntry 4 }

mscDataSigChanCcTrIndex OBJECT-TYPE
   SYNTAX     NonReplicated 
   ACCESS     not-accessible
   STATUS     mandatory
   DESCRIPTION
     "This variable represents the index for the mscDataSigChanCcTr tables."
::= { mscDataSigChanCcTrRowStatusEntry 10 }

-- 
-- *** THIS SUBTREE CURRENTLY NOT IMPLEMENTED ***
-- 

-- DataIsdn/n CallControl Trace Pri/n
-- The component displays the class data members of the isdn Pri/n 
-- class.

mscDataSigChanCcTrPri OBJECT IDENTIFIER ::= { mscDataSigChanCcTr 2 }



mscDataSigChanCcTrPriRowStatusTable OBJECT-TYPE
   SYNTAX     SEQUENCE OF MscDataSigChanCcTrPriRowStatusEntry
   ACCESS     not-accessible
   STATUS     mandatory
   DESCRIPTION
     "*** THIS TABLE CURRENTLY NOT IMPLEMENTED ***

      This entry controls the addition and deletion of 
      mscDataSigChanCcTrPri components."
::= { mscDataSigChanCcTrPri 1 }

mscDataSigChanCcTrPriRowStatusEntry OBJECT-TYPE
   SYNTAX     MscDataSigChanCcTrPriRowStatusEntry
   ACCESS     not-accessible
   STATUS     mandatory
   DESCRIPTION
     "A single entry in the table represents a single 
      mscDataSigChanCcTrPri component."
   INDEX {
      mscDataSigChanIndex,
      mscDataSigChanCcIndex,
      mscDataSigChanCcTrIndex,
      mscDataSigChanCcTrPriIndex }
::= { mscDataSigChanCcTrPriRowStatusTable 1 }

MscDataSigChanCcTrPriRowStatusEntry ::= SEQUENCE {
   mscDataSigChanCcTrPriRowStatus
      RowStatus,
   mscDataSigChanCcTrPriComponentName
      DisplayString,
   mscDataSigChanCcTrPriStorageType
      StorageType,
   mscDataSigChanCcTrPriIndex
      Integer32 }

mscDataSigChanCcTrPriRowStatus OBJECT-TYPE
   SYNTAX     RowStatus 
   ACCESS     read-only
   STATUS     mandatory
   DESCRIPTION
     "This variable is used as the basis for SNMP naming of
      mscDataSigChanCcTrPri components.
      These components cannot be added nor deleted."
::= { mscDataSigChanCcTrPriRowStatusEntry 1 }

mscDataSigChanCcTrPriComponentName OBJECT-TYPE
   SYNTAX     DisplayString 
   ACCESS     read-only
   STATUS     mandatory
   DESCRIPTION
     "This variable provides the component's string name for
      use with the ASCII Console Interface"
::= { mscDataSigChanCcTrPriRowStatusEntry 2 }

mscDataSigChanCcTrPriStorageType OBJECT-TYPE
   SYNTAX     StorageType 
   ACCESS     read-only
   STATUS     mandatory
   DESCRIPTION
     "This variable represents the storage type value for the
      mscDataSigChanCcTrPri tables."
::= { mscDataSigChanCcTrPriRowStatusEntry 4 }

mscDataSigChanCcTrPriIndex OBJECT-TYPE
   SYNTAX     Integer32 (0..3)
   ACCESS     not-accessible
   STATUS     mandatory
   DESCRIPTION
     "This variable represents the index for the mscDataSigChanCcTrPri tables."
::= { mscDataSigChanCcTrPriRowStatusEntry 10 }

-- 
-- *** THIS SUBTREE CURRENTLY NOT IMPLEMENTED ***
-- 

-- DataIsdn/n CallControl Trace Pri/n Bch/m
-- The component displays the class data members of the isdn Pri/n 
-- Bch/m class.

mscDataSigChanCcTrPriBch OBJECT IDENTIFIER ::= { mscDataSigChanCcTrPri 2 }



mscDataSigChanCcTrPriBchRowStatusTable OBJECT-TYPE
   SYNTAX     SEQUENCE OF MscDataSigChanCcTrPriBchRowStatusEntry
   ACCESS     not-accessible
   STATUS     mandatory
   DESCRIPTION
     "*** THIS TABLE CURRENTLY NOT IMPLEMENTED ***

      This entry controls the addition and deletion of 
      mscDataSigChanCcTrPriBch components."
::= { mscDataSigChanCcTrPriBch 1 }

mscDataSigChanCcTrPriBchRowStatusEntry OBJECT-TYPE
   SYNTAX     MscDataSigChanCcTrPriBchRowStatusEntry
   ACCESS     not-accessible
   STATUS     mandatory
   DESCRIPTION
     "A single entry in the table represents a single 
      mscDataSigChanCcTrPriBch component."
   INDEX {
      mscDataSigChanIndex,
      mscDataSigChanCcIndex,
      mscDataSigChanCcTrIndex,
      mscDataSigChanCcTrPriIndex,
      mscDataSigChanCcTrPriBchIndex }
::= { mscDataSigChanCcTrPriBchRowStatusTable 1 }

MscDataSigChanCcTrPriBchRowStatusEntry ::= SEQUENCE {
   mscDataSigChanCcTrPriBchRowStatus
      RowStatus,
   mscDataSigChanCcTrPriBchComponentName
      DisplayString,
   mscDataSigChanCcTrPriBchStorageType
      StorageType,
   mscDataSigChanCcTrPriBchIndex
      Integer32 }

mscDataSigChanCcTrPriBchRowStatus OBJECT-TYPE
   SYNTAX     RowStatus 
   ACCESS     read-only
   STATUS     mandatory
   DESCRIPTION
     "This variable is used as the basis for SNMP naming of
      mscDataSigChanCcTrPriBch components.
      These components cannot be added nor deleted."
::= { mscDataSigChanCcTrPriBchRowStatusEntry 1 }

mscDataSigChanCcTrPriBchComponentName OBJECT-TYPE
   SYNTAX     DisplayString 
   ACCESS     read-only
   STATUS     mandatory
   DESCRIPTION
     "This variable provides the component's string name for
      use with the ASCII Console Interface"
::= { mscDataSigChanCcTrPriBchRowStatusEntry 2 }

mscDataSigChanCcTrPriBchStorageType OBJECT-TYPE
   SYNTAX     StorageType 
   ACCESS     read-only
   STATUS     mandatory
   DESCRIPTION
     "This variable represents the storage type value for the
      mscDataSigChanCcTrPriBch tables."
::= { mscDataSigChanCcTrPriBchRowStatusEntry 4 }

mscDataSigChanCcTrPriBchIndex OBJECT-TYPE
   SYNTAX     Integer32 (1..31)
   ACCESS     not-accessible
   STATUS     mandatory
   DESCRIPTION
     "This variable represents the index for the mscDataSigChanCcTrPriBch tables."
::= { mscDataSigChanCcTrPriBchRowStatusEntry 10 }

-- 
-- *** THIS SUBTREE CURRENTLY NOT IMPLEMENTED ***
-- 

-- DataSigChan/n Cc Bchannel/n
-- DataSigChan/n Cc Cg/n Bchannel/n
-- This component identifies the B-channels associated with a 
-- CallControl or a ChannelGroup.

mscDataSigChanCcBch OBJECT IDENTIFIER ::= { mscDataSigChanCc 4 }



mscDataSigChanCcBchRowStatusTable OBJECT-TYPE
   SYNTAX     SEQUENCE OF MscDataSigChanCcBchRowStatusEntry
   ACCESS     not-accessible
   STATUS     mandatory
   DESCRIPTION
     "*** THIS TABLE CURRENTLY NOT IMPLEMENTED ***

      This entry controls the addition and deletion of 
      mscDataSigChanCcBch components."
::= { mscDataSigChanCcBch 1 }

mscDataSigChanCcBchRowStatusEntry OBJECT-TYPE
   SYNTAX     MscDataSigChanCcBchRowStatusEntry
   ACCESS     not-accessible
   STATUS     mandatory
   DESCRIPTION
     "A single entry in the table represents a single 
      mscDataSigChanCcBch component."
   INDEX {
      mscDataSigChanIndex,
      mscDataSigChanCcIndex,
      mscDataSigChanCcBchIndex }
::= { mscDataSigChanCcBchRowStatusTable 1 }

MscDataSigChanCcBchRowStatusEntry ::= SEQUENCE {
   mscDataSigChanCcBchRowStatus
      RowStatus,
   mscDataSigChanCcBchComponentName
      DisplayString,
   mscDataSigChanCcBchStorageType
      StorageType,
   mscDataSigChanCcBchIndex
      Integer32 }

mscDataSigChanCcBchRowStatus OBJECT-TYPE
   SYNTAX     RowStatus 
   ACCESS     read-only
   STATUS     mandatory
   DESCRIPTION
     "This variable is used as the basis for SNMP naming of
      mscDataSigChanCcBch components.
      These components cannot be added nor deleted."
::= { mscDataSigChanCcBchRowStatusEntry 1 }

mscDataSigChanCcBchComponentName OBJECT-TYPE
   SYNTAX     DisplayString 
   ACCESS     read-only
   STATUS     mandatory
   DESCRIPTION
     "This variable provides the component's string name for
      use with the ASCII Console Interface"
::= { mscDataSigChanCcBchRowStatusEntry 2 }

mscDataSigChanCcBchStorageType OBJECT-TYPE
   SYNTAX     StorageType 
   ACCESS     read-only
   STATUS     mandatory
   DESCRIPTION
     "This variable represents the storage type value for the
      mscDataSigChanCcBch tables."
::= { mscDataSigChanCcBchRowStatusEntry 4 }

mscDataSigChanCcBchIndex OBJECT-TYPE
   SYNTAX     Integer32 (1..31)
   ACCESS     not-accessible
   STATUS     mandatory
   DESCRIPTION
     "This variable represents the index for the mscDataSigChanCcBch tables."
::= { mscDataSigChanCcBchRowStatusEntry 10 }

mscDataSigChanCcBchBchanOpDataTable OBJECT-TYPE
   SYNTAX     SEQUENCE OF MscDataSigChanCcBchBchanOpDataEntry
   ACCESS     not-accessible
   STATUS     mandatory
   DESCRIPTION
     "*** THIS TABLE CURRENTLY NOT IMPLEMENTED ***

      This group contains the operational data of a B-Channel."
::= { mscDataSigChanCcBch 2 }

mscDataSigChanCcBchBchanOpDataEntry OBJECT-TYPE
   SYNTAX     MscDataSigChanCcBchBchanOpDataEntry
   ACCESS     not-accessible
   STATUS     mandatory
   DESCRIPTION
     "An entry in the mscDataSigChanCcBchBchanOpDataTable."
   INDEX {
      mscDataSigChanIndex,
      mscDataSigChanCcIndex,
      mscDataSigChanCcBchIndex }
::= { mscDataSigChanCcBchBchanOpDataTable 1 }

MscDataSigChanCcBchBchanOpDataEntry ::= SEQUENCE {
   mscDataSigChanCcBchState
      INTEGER,
   mscDataSigChanCcBchCallingPartyNumber
      DigitString,
   mscDataSigChanCcBchLastQ931ClearCause
      INTEGER,
   mscDataSigChanCcBchRunningApplication
      AsciiString }

mscDataSigChanCcBchState OBJECT-TYPE
   SYNTAX     INTEGER  {
                 idle(0),
                 busy(1),
                 disabled(2),
                 noProtocolProvisioned(3) }
   ACCESS     read-only
   STATUS     mandatory
   DESCRIPTION
     "This attribute indicates the state of the B-channel. A B-channel is in 
      idle state when it is available for a call. The busy state indicate that 
      the B-channel is presently in use. The disabled state means that the 
      access service is not enabled because it is locked or the port is 
      down. The state noProtocolProvisioned means that the call control 
      did not yet received the registration for this B-channel."
::= { mscDataSigChanCcBchBchanOpDataEntry 1 }

mscDataSigChanCcBchCallingPartyNumber OBJECT-TYPE
   SYNTAX     DigitString (SIZE (1..14))
   ACCESS     read-only
   STATUS     mandatory
   DESCRIPTION
     "This attribute indicates the calling party number of the last valid call 
      request for this channel."
::= { mscDataSigChanCcBchBchanOpDataEntry 2 }

mscDataSigChanCcBchLastQ931ClearCause OBJECT-TYPE
   SYNTAX     INTEGER (0..255)
   ACCESS     read-only
   STATUS     mandatory
   DESCRIPTION
     "The clear cause of the last call on this B-channel."
::= { mscDataSigChanCcBchBchanOpDataEntry 3 }

mscDataSigChanCcBchRunningApplication OBJECT-TYPE
   SYNTAX     AsciiString (SIZE (0..20))
   ACCESS     read-only
   STATUS     mandatory
   DESCRIPTION
     "The name of the application running on this B-channel."
   DEFVAL     { ''H }  -- ""
::= { mscDataSigChanCcBchBchanOpDataEntry 4 }




-- 
-- Version and Compliance statements
-- 



-- Object-Group Statement:
-- A list of all current accessible leaf objects.

-- OBJECTS { mscDataSigChanCcInInvalidCapability,
--           mscDataSigChanCcTrPriComponentName,
--           mscDataSigChanCcCgTotalInCalls,
--           mscDataSigChanCcInInvalidScreen,
--           mscDataSigChanCcStorageType,
--           mscDataSigChanCcBchComponentName,
--           mscDataSigChanCcCgCgpnComponentName,
--           mscDataSigChanCcTrPriBchStorageType,
--           mscDataSigChanAdminState,
--           mscDataSigChanCcCgBchStorageType,
--           mscDataSigChanCcCgChannelAssignmentOrder,
--           mscDataSigChanCcLastClearCause,
--           mscDataSigChanCcCgBchLastQ931ClearCause,
--           mscDataSigChanIfAdminStatus,
--           mscDataSigChanCcBchCallingPartyNumber,
--           mscDataSigChanRowStatus,
--           mscDataSigChanCcCgBusyChannelCount,
--           mscDataSigChanSnmpOperStatus,
--           mscDataSigChanCcCgComponentName,
--           mscDataSigChanCcLastClearedCallingPartyNumber,
--           mscDataSigChanCcRowStatus,
--           mscDataSigChanCommentText,
--           mscDataSigChanUsageState,
--           mscDataSigChanCcTrPriBchRowStatus,
--           mscDataSigChanCcCgBchCallingPartyNumber,
--           mscDataSigChanCcCgSuccessfullInCalls,
--           mscDataSigChanComponentName,
--           mscDataSigChanCcCgBchRowStatus,
--           mscDataSigChanCcTrStorageType,
--           mscDataSigChanCcCgCommentText,
--           mscDataSigChanCcCgBchRunningApplication,
--           mscDataSigChanCcBchState,
--           mscDataSigChanCcComponentName,
--           mscDataSigChanOperationalState,
--           mscDataSigChanCcBchLastQ931ClearCause,
--           mscDataSigChanCcTrPriStorageType,
--           mscDataSigChanCcTrPriBchComponentName,
--           mscDataSigChanCcCgStorageType,
--           mscDataSigChanCcInInvalidCgpn,
--           mscDataSigChanCcCgBchComponentName,
--           mscDataSigChanCcCgChannelList,
--           mscDataSigChanCcBchStorageType,
--           mscDataSigChanCcCgCgpnStorageType,
--           mscDataSigChanCcInChannelBusy,
--           mscDataSigChanCcTrRowStatus,
--           mscDataSigChanCcTotalValidInCalls,
--           mscDataSigChanCcCgScreeningIndicator,
--           mscDataSigChanCcCgIdleChannelCount,
--           mscDataSigChanCcCgRejectedNoChanAvail,
--           mscDataSigChanCustomerIdentifier,
--           mscDataSigChanCcTrPriRowStatus,
--           mscDataSigChanCcSuccessfullInCalls,
--           mscDataSigChanIfIndex,
--           mscDataSigChanCcCgRowStatus,
--           mscDataSigChanCcTrComponentName,
--           mscDataSigChanCcCgCustomerIdentifier,
--           mscDataSigChanCcBchRowStatus,
--           mscDataSigChanCcCgCgpnRowStatus,
--           mscDataSigChanCcCgBchState,
--           mscDataSigChanCcBchRunningApplication,
--           mscDataSigChanStorageType }
-- STATUS  mandatory
-- DESCRIPTION
--   "A list of all current accessible leaf objects."

dataIsdnGroup OBJECT IDENTIFIER ::= { dataIsdnMIB 1 }
dataIsdnGroupCA OBJECT IDENTIFIER ::= { dataIsdnGroup 1 }
dataIsdnGroupCA02 OBJECT IDENTIFIER ::= { dataIsdnGroupCA 3 }
dataIsdnGroupCA02A OBJECT IDENTIFIER ::= { dataIsdnGroupCA02 2 }



-- Agent-Capabilities Statement:

-- PRODUCT-RELEASE "MscPassport Release 1.2 DataIsdn."
-- STATUS          mandatory
-- DESCRIPTION     "Carrier Passport DataIsdn MIB: MIB Version CA02A,
--                  Software Version CA02S9C."
-- SUPPORTS        Nortel-MsCarrier-MscPassport-DataIsdnMIB
--    INCLUDES     { dataIsdnGroupCA02A }

dataIsdnCapabilities OBJECT IDENTIFIER ::= { dataIsdnMIB 3 }
dataIsdnCapabilitiesCA OBJECT IDENTIFIER ::= { dataIsdnCapabilities 1 }
dataIsdnCapabilitiesCA02 OBJECT IDENTIFIER ::= { dataIsdnCapabilitiesCA 3 }
dataIsdnCapabilitiesCA02A OBJECT IDENTIFIER ::= { dataIsdnCapabilitiesCA02 2 }





END
