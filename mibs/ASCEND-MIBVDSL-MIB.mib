--			Ascend mibvdsl MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBVDSL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibvdslLineStatus  OBJECT IDENTIFIER ::= { configuration 161}

	-- The mibvdslLineStatus table
	--
	-- This table contains parameters for the mibvdslLineStatus profile
	--

    mibvdslLineStatusTable	OBJECT-TYPE
	SYNTAX		SEQUENCE OF MibvdslLineStatusEntry
	ACCESS		not-accessible
	STATUS		mandatory
	DESCRIPTION	"A list of mibvdslLineStatus profile entries."
	::= { mibvdslLineStatus 1 }

    mibvdslLineStatusEntry	OBJECT-TYPE
	SYNTAX		MibvdslLineStatusEntry
	ACCESS		not-accessible
	STATUS		mandatory
	DESCRIPTION	"A mibvdslLineStatus entry containing objects that
			 maps to the parameters of mibvdslLineStatus profile."
	INDEX		{ vdslLineStatus-Shelf-o, vdslLineStatus-Slot-o, vdslLineStatus-Item-o }
	::= { mibvdslLineStatusTable 1 }

    MibvdslLineStatusEntry ::=
	SEQUENCE {
	    vdslLineStatus-Shelf-o
		INTEGER,
	    vdslLineStatus-Slot-o
		INTEGER,
	    vdslLineStatus-Item-o
		INTEGER,
	    vdslLineStatus-PhysicalAddress-Shelf
		INTEGER,
	    vdslLineStatus-PhysicalAddress-Slot
		INTEGER,
	    vdslLineStatus-PhysicalAddress-ItemNumber
		INTEGER,
	    vdslLineStatus-LineState
		INTEGER,
	    vdslLineStatus-SparePhysicalAddress-Shelf
		INTEGER,
	    vdslLineStatus-SparePhysicalAddress-Slot
		INTEGER,
	    vdslLineStatus-SparePhysicalAddress-ItemNumber
		INTEGER,
	    vdslLineStatus-SparingState
		INTEGER,
	    vdslLineStatus-SparingChangeReason
		INTEGER,
	    vdslLineStatus-SparingChangeTime
		INTEGER,
	    vdslLineStatus-SparingChangeCounter
		INTEGER,
	    vdslLineStatus-VpiVciRange
		INTEGER,
	    vdslLineStatus-VpSwitchingVpi
		INTEGER,
	    vdslLineStatus-PhysicalStatus-IfGroupIndex
		INTEGER,
	    vdslLineStatus-PhysicalStatus-UnitType
		INTEGER,
	    vdslLineStatus-PhysicalStatus-DevLineState
		INTEGER,
	    vdslLineStatus-PhysicalStatus-OpUpRates
		INTEGER,
	    vdslLineStatus-PhysicalStatus-OpDownRates
		INTEGER,
	    vdslLineStatus-PhysicalStatus-FirmwareVer
		DisplayString,
	    vdslLineStatus-PhysicalStatistic-LineUpTimer-Days
		INTEGER,
	    vdslLineStatus-PhysicalStatistic-LineUpTimer-Hours
		INTEGER,
	    vdslLineStatus-PhysicalStatistic-LineUpTimer-Minutes
		INTEGER,
	    vdslLineStatus-PhysicalStatistic-RxSignalPresent
		INTEGER,
	    vdslLineStatus-PhysicalStatistic-UpDwnCntr
		INTEGER,
	    vdslLineStatus-PhysicalStatistic-SelfTest
		INTEGER,
	    vdslLineStatus-Action-o
		INTEGER
	}

    vdslLineStatus-Shelf-o	OBJECT-TYPE
	SYNTAX	INTEGER
	ACCESS	read-only
	STATUS	mandatory
	DESCRIPTION	""
	::= { mibvdslLineStatusEntry 1 }

    vdslLineStatus-Slot-o	OBJECT-TYPE
	SYNTAX	INTEGER
	ACCESS	read-only
	STATUS	mandatory
	DESCRIPTION	""
	::= { mibvdslLineStatusEntry 2 }

    vdslLineStatus-Item-o	OBJECT-TYPE
	SYNTAX	INTEGER
	ACCESS	read-only
	STATUS	mandatory
	DESCRIPTION	""
	::= { mibvdslLineStatusEntry 3 }

    vdslLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibvdslLineStatusEntry 4 }

    vdslLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibvdslLineStatusEntry 5 }

    vdslLineStatus-PhysicalAddress-ItemNumber	OBJECT-TYPE
	SYNTAX	INTEGER
	ACCESS	read-write
	STATUS	mandatory
	DESCRIPTION	"A number that specifies an addressable entity within the context of shelf and slot."
	::= { mibvdslLineStatusEntry 6 }

    vdslLineStatus-LineState	OBJECT-TYPE
	SYNTAX	INTEGER {
		    doesNotExist (1),
		    disabled (2),
		    active (3)
		}
	ACCESS	read-only
	STATUS	mandatory
	DESCRIPTION	"The overall state of the line."
	::= { mibvdslLineStatusEntry 7 }

    vdslLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibvdslLineStatusEntry 8 }

    vdslLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibvdslLineStatusEntry 9 }

    vdslLineStatus-SparePhysicalAddress-ItemNumber	OBJECT-TYPE
	SYNTAX	INTEGER
	ACCESS	read-write
	STATUS	mandatory
	DESCRIPTION	"A number that specifies an addressable entity within the context of shelf and slot."
	::= { mibvdslLineStatusEntry 10 }

    vdslLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibvdslLineStatusEntry 11 }

    vdslLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { mibvdslLineStatusEntry 12 }

    vdslLineStatus-SparingChangeTime	OBJECT-TYPE
	SYNTAX	INTEGER
	ACCESS	read-only
	STATUS	mandatory
	DESCRIPTION	"The time of the last sparing state change."
	::= { mibvdslLineStatusEntry 13 }

    vdslLineStatus-SparingChangeCounter	OBJECT-TYPE
	SYNTAX	INTEGER
	ACCESS	read-only
	STATUS	mandatory
	DESCRIPTION	"The number of sparing state changes."
	::= { mibvdslLineStatusEntry 14 }

    vdslLineStatus-VpiVciRange	OBJECT-TYPE
	SYNTAX	INTEGER {
		    vpi01Vci321023 (6),
		    vpi03Vci32511 (1),
		    vpi07Vci32255 (2),
		    vpi015Vci32127 (3),
		    vpi031Vci3263 (4),
		    notApplicable (5)
		}
	ACCESS	read-only
	STATUS	mandatory
	DESCRIPTION	"The valid range of vpi and vci for the circuits established for the line. This range can change only after LIM reboot."
	::= { mibvdslLineStatusEntry 15 }

    vdslLineStatus-VpSwitchingVpi	OBJECT-TYPE
	SYNTAX	INTEGER
	ACCESS	read-only
	STATUS	mandatory
	DESCRIPTION	"VPI to be used for the VP switching. Rest of the VPIs will be used for the VC switching."
	::= { mibvdslLineStatusEntry 16 }

    vdslLineStatus-PhysicalStatus-IfGroupIndex	OBJECT-TYPE
	SYNTAX	INTEGER
	ACCESS	read-only
	STATUS	mandatory
	DESCRIPTION	"Interface groups index assigned to this physical port."
	::= { mibvdslLineStatusEntry 17 }

    vdslLineStatus-PhysicalStatus-UnitType	OBJECT-TYPE
	SYNTAX	INTEGER {
		    dslCoe (2),
		    dslCpe (3)
		}
	ACCESS	read-only
	STATUS	mandatory
	DESCRIPTION	"Unit types defines if the node is operating Central Office or Customer Premise equipment software."
	::= { mibvdslLineStatusEntry 18 }

    vdslLineStatus-PhysicalStatus-DevLineState	OBJECT-TYPE
	SYNTAX	INTEGER {
		    dslStatDwnInd (2),
		    dslStatWaitInit (3),
		    dslStatInit (4),
		    dslStatUpInd (5),
		    dslStatFailInd (6),
		    dslStatLback (7),
		    dslStatTest (8),
		    dslStatDownload (9),
		    dslStatNumberStates (10)
		}
	ACCESS	read-only
	STATUS	mandatory
	DESCRIPTION	"Display of current interface state."
	::= { mibvdslLineStatusEntry 19 }

    vdslLineStatus-PhysicalStatus-OpUpRates	OBJECT-TYPE
	SYNTAX	INTEGER
	ACCESS	read-only
	STATUS	mandatory
	DESCRIPTION	"Display operational up rate."
	::= { mibvdslLineStatusEntry 27 }

    vdslLineStatus-PhysicalStatus-OpDownRates	OBJECT-TYPE
	SYNTAX	INTEGER
	ACCESS	read-only
	STATUS	mandatory
	DESCRIPTION	"Display operational down rate."
	::= { mibvdslLineStatusEntry 28 }

    vdslLineStatus-PhysicalStatus-FirmwareVer	OBJECT-TYPE
	SYNTAX	DisplayString
	ACCESS	read-only
	STATUS	mandatory
	DESCRIPTION	"Firmware version ID."
	::= { mibvdslLineStatusEntry 29 }

    vdslLineStatus-PhysicalStatistic-LineUpTimer-Days	OBJECT-TYPE
	SYNTAX	INTEGER
	ACCESS	read-only
	STATUS	mandatory
	DESCRIPTION	"Number of days that the DSL line has been up."
	::= { mibvdslLineStatusEntry 20 }

    vdslLineStatus-PhysicalStatistic-LineUpTimer-Hours	OBJECT-TYPE
	SYNTAX	INTEGER
	ACCESS	read-only
	STATUS	mandatory
	DESCRIPTION	"Number of hours that the DSL line has been up."
	::= { mibvdslLineStatusEntry 21 }

    vdslLineStatus-PhysicalStatistic-LineUpTimer-Minutes	OBJECT-TYPE
	SYNTAX	INTEGER
	ACCESS	read-only
	STATUS	mandatory
	DESCRIPTION	"Number of minutes that the DSL line has been up."
	::= { mibvdslLineStatusEntry 22 }

    vdslLineStatus-PhysicalStatistic-RxSignalPresent	OBJECT-TYPE
	SYNTAX	INTEGER {
		    yes (3),
		    no (2)
		}
	ACCESS	read-only
	STATUS	mandatory
	DESCRIPTION	"State if the receive signal is present or not."
	::= { mibvdslLineStatusEntry 23 }

    vdslLineStatus-PhysicalStatistic-UpDwnCntr	OBJECT-TYPE
	SYNTAX	INTEGER
	ACCESS	read-only
	STATUS	mandatory
	DESCRIPTION	"Interface Up Down counter value displays the number of times the interface trasitions from a down to up state."
	::= { mibvdslLineStatusEntry 24 }

    vdslLineStatus-PhysicalStatistic-SelfTest	OBJECT-TYPE
	SYNTAX	INTEGER {
		    dslSelfTestNone (2),
		    dslSelfTestFailed (3),
		    dslSelfTestPassed (4)
		}
	ACCESS	read-only
	STATUS	mandatory
	DESCRIPTION	"Hardware/firmware self test results."
	::= { mibvdslLineStatusEntry 25 }

    vdslLineStatus-Action-o	OBJECT-TYPE
	SYNTAX	INTEGER {
		    noAction (1),
		    createProfile (2),
		    deleteProfile (3)
		}
	ACCESS	read-write
	STATUS	mandatory
	DESCRIPTION	""
	::= { mibvdslLineStatusEntry 26 }

END
