Nortel-Magellan-Passport-PorsTrunksMIB
DEFINITIONS ::= BEGIN



IMPORTS

      OBJECT-TYPE
   FROM RFC-1212

      passportMIBs
   FROM Nortel-Magellan-Passport-UsefulDefinitionsMIB

      RowPointer,
      DisplayString,
      StorageType,
      RowStatus,
      Integer32,
      Unsigned32
   FROM Nortel-Magellan-Passport-StandardTextualConventionsMIB

      AsciiString,
      NonReplicated
   FROM Nortel-Magellan-Passport-TextualConventionsMIB

      trkIndex,
      trk
   FROM Nortel-Magellan-Passport-TrunksMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     PorsTrunks Enterprise MIB."

porsTrunksMIB OBJECT IDENTIFIER ::= { passportMIBs 39 }










-- Trunk/n PathAdmin
-- This component manages all path related activities on behalf of the 
-- trunk. This component is provisioned with a maximum count of 
-- LogicalChannels that it is allowed to create and a maximum percent 
-- of the trunk's outgoing bandwidth that it is permitted to allocate to 
-- these LogicalChannels.

trkPa OBJECT IDENTIFIER ::= { trk 4 }



trkPaRowStatusTable OBJECT-TYPE
   SYNTAX     SEQUENCE OF TrkPaRowStatusEntry
   ACCESS     not-accessible
   STATUS     mandatory
   DESCRIPTION
     "This entry controls the addition and deletion of 
      trkPa components."
::= { trkPa 1 }

trkPaRowStatusEntry OBJECT-TYPE
   SYNTAX     TrkPaRowStatusEntry
   ACCESS     not-accessible
   STATUS     mandatory
   DESCRIPTION
     "A single entry in the table represents a single 
      trkPa component."
   INDEX {
      trkIndex,
      trkPaIndex }
::= { trkPaRowStatusTable 1 }

TrkPaRowStatusEntry ::= SEQUENCE {
   trkPaRowStatus
      RowStatus,
   trkPaComponentName
      DisplayString,
   trkPaStorageType
      StorageType,
   trkPaIndex
      NonReplicated }

trkPaRowStatus OBJECT-TYPE
   SYNTAX     RowStatus 
   ACCESS     read-write
   STATUS     mandatory
   DESCRIPTION
     "This variable is used as the basis for SNMP naming of
      trkPa components.
      These components can be added and deleted."
::= { trkPaRowStatusEntry 1 }

trkPaComponentName OBJECT-TYPE
   SYNTAX     DisplayString 
   ACCESS     read-only
   STATUS     mandatory
   DESCRIPTION
     "This variable provides the component's string name for
      use with the ASCII Console Interface"
::= { trkPaRowStatusEntry 2 }

trkPaStorageType OBJECT-TYPE
   SYNTAX     StorageType 
   ACCESS     read-only
   STATUS     mandatory
   DESCRIPTION
     "This variable represents the storage type value for the
      trkPa tables."
::= { trkPaRowStatusEntry 4 }

trkPaIndex OBJECT-TYPE
   SYNTAX     NonReplicated 
   ACCESS     not-accessible
   STATUS     mandatory
   DESCRIPTION
     "This variable represents the index for the trkPa tables."
::= { trkPaRowStatusEntry 10 }

trkPaProvTable OBJECT-TYPE
   SYNTAX     SEQUENCE OF TrkPaProvEntry
   ACCESS     not-accessible
   STATUS     mandatory
   DESCRIPTION
     "This group contains all provisionable attributes relevant to path 
      oriented traffic on a trunk. These attributes provide the maximum 
      number of Logical Channels that are permitted under a Trunk/n and 
      the maximum total bandwidth they are allowed to occupy as a 
      percentage of the outgoing trunk bandwidth."
::= { trkPa 10 }

trkPaProvEntry OBJECT-TYPE
   SYNTAX     TrkPaProvEntry
   ACCESS     not-accessible
   STATUS     mandatory
   DESCRIPTION
     "An entry in the trkPaProvTable."
   INDEX {
      trkIndex,
      trkPaIndex }
::= { trkPaProvTable 1 }

TrkPaProvEntry ::= SEQUENCE {
   trkPaMaxLc
      Unsigned32,
   trkPaMaxReservedBwOut
      Unsigned32,
   trkPaTrunkSecurity
      Unsigned32,
   trkPaSupportedTrafficTypes
      OCTET STRING,
   trkPaTrunkType
      INTEGER,
   trkPaCustomerParameter
      Unsigned32,
   trkPaTrunkCost
      Unsigned32,
   trkPaOverrideTrunkDelay
      Unsigned32 }

trkPaMaxLc OBJECT-TYPE
   SYNTAX     Unsigned32 (0..65435)
   ACCESS     read-write
   STATUS     mandatory
   DESCRIPTION
     "This attribute indicates the number of Logical Channels (LCh/n) 
      supported on this trunk. This attribute is used to allocate memory on 
      the trunk FP for the PORS forwarding tables.Unless running in 
      mapped mode on ATM hardware, the PathAdmin will add 100 
      channels to maxLc to reduce the chances of allocation clashes. 
      However, you should never see more than maxLc channels in use 
      for any extended period of time. On ATM hardware in mapped 
      mode the PathAdmin will only add 10 channels to maxLc to permit 
      more efficient use of the available VCC space.
      
      The PathAdmin may not be able to honor a request for maxLc 
      channels. This will happen when the neighbor PathAdmin asks for 
      less channels than this PathAdmin. To resolve the conflict the 
      PathAdmin will always pick the minimum of the two maxLc values. 
      This minimum value is called the negotiatedMaxLc and can be 
      viewed as an operational parameter of the PathAdmin.
      
      Note that in mapped mode on ATM hardware, the value of this 
      attribute provides an upper bound to the number of VCCs that this 
      Trunk/n PathAdmin can occupy. It is not a guarantee that maxLc 
      VCCs will be available to this PathAdmin because the VCC space is 
      a shared resource on the card or port."
   DEFVAL     { 512 }
::= { trkPaProvEntry 1 }

trkPaMaxReservedBwOut OBJECT-TYPE
   SYNTAX     Unsigned32 (0..200)
   ACCESS     read-write
   STATUS     mandatory
   DESCRIPTION
     "This attribute controls the percentage of trunk bandwidth which 
      may be reserved by outgoing path oriented traffic on the trunk. The 
      sum of requiredBandwidth attributes for all paths on this trunk must 
      not exceed this attribute. Setting this attribute to zero (0) prevents 
      paths from being established on this trunk. The limit of reserved 
      bandwidth for incoming path oriented traffic is set using the same 
      attribute on the trunk component on the other end of the trunk.This 
      attribute may be changed without the trunk being restaged. If the 
      value is decreased, calls may be bumped as necessary to free up 
      bandwidth. Increasing the value has no impact on existing calls and 
      new calls are able to use the new bandwidth.
      If this attribute is set to greater than 100%, connectionless traffic is 
      given a minimum of 1Kbit per second for administrative traffic. A 
      value greater than 100% overbooks the trunk bandwidth. By 
      overbooking bandwidth, more calls are able to be established using 
      the unused bandwidth reserved by idle PLCs."
   DEFVAL     { 50 }
::= { trkPaProvEntry 2 }

trkPaTrunkSecurity OBJECT-TYPE
   SYNTAX     Unsigned32 (0..7)
   ACCESS     read-write
   STATUS     mandatory
   DESCRIPTION
     "This attribute indicates the security level of the trunk. Zero(0) 
      represents the most secure trunk and seven(7) represents the least 
      secure. The path's minimum security requirement is indicated by 
      the Plc requiredSecurity attribute, with values identical in range and 
      meaning to this attribute. PORS ensures that the route selected does 
      not contain a trunk whose PathAdmin trunkSecurity attribute is 
      numerically greater than the path's requiredSecurity."
   DEFVAL     { 0 }
::= { trkPaProvEntry 3 }

trkPaSupportedTrafficTypes OBJECT-TYPE
   SYNTAX     OCTET STRING (SIZE (1))
   ACCESS     read-write
   STATUS     mandatory
   DESCRIPTION
     "This attribute indicates the type of traffic that can be transmitted on 
      the trunk. There are eight(8) possible traffic types, and the trunk can 
      transmit all of them if desired. The voice, data and video traffic 
      types are defined, and five(5) other traffic types can be defined by 
      the network administration. This attribute is used in the route 
      selection process to limit the route to trunks that support the traffic 
      type carried by the path. The requiredTrafficType attribute of the 
      PLC indicates the type of traffic carried on the path.

      Description of bits:
      voice(0)
      data(1)
      video(2)
      trafficType1(3)
      trafficType2(4)
      trafficType3(5)
      trafficType4(6)
      trafficType5(7)"
   DEFVAL     { 'f8'H }
::= { trkPaProvEntry 4 }

trkPaTrunkType OBJECT-TYPE
   SYNTAX     INTEGER  {
                 terrestrial(0),
                 satellite(1),
                 trunkType1(2),
                 trunkType2(3),
                 trunkType3(4),
                 trunkType4(5),
                 trunkType5(6),
                 trunkType6(7) }
   ACCESS     read-write
   STATUS     mandatory
   DESCRIPTION
     "This attribute lists the type of the trunk. There can be up to eight(8) 
      types of trunks. The terrestrial and satellite trunk types have been 
      defined, leaving six(6) remaining types that can be defined by the 
      network administration. The set of allowed trunk types for a path is 
      indicated in the permittedTrunkType attribute of the PLC. When 
      selecting a route, PORS only chooses trunks whose PathAdmin 
      trunkType are in the permittedTrunkTypes set of the path."
   DEFVAL     { terrestrial }
::= { trkPaProvEntry 5 }

trkPaCustomerParameter OBJECT-TYPE
   SYNTAX     Unsigned32 (0..7)
   ACCESS     read-write
   STATUS     mandatory
   DESCRIPTION
     "This attribute indicates the customer defined parameter for the 
      trunk. Its value, a number from zero(0) to seven(7), is chosen by a 
      network administration to have a meaning specific to their network, 
      thus allowing them to customize the use of their trunks. A 
      complementary PLC attribute, requiredCustomerParameter, also 
      has a value from zero(0) to seven(7). The Route Selector does not 
      consider trunks whose PathAdmin customerParameter is greater 
      than the requiredCustomerParameter of the path."
   DEFVAL     { 0 }
::= { trkPaProvEntry 6 }

trkPaTrunkCost OBJECT-TYPE
   SYNTAX     Unsigned32 (1..255)
   ACCESS     read-write
   STATUS     mandatory
   DESCRIPTION
     "This attribute is the cost metric for the trunk. This value is assigned 
      by the network administration to represent the network cost of using 
      this trunk. It can be related to distance, speed, dollars, or any other 
      factor that could be taken into consideration. If the 
      trunkAttributeToMinimize is set to trunkCost, PORS finds a route 
      with the smallest sum of the PathAdmin trunkCost attribute over all 
      trunks. The trunk cost can be increased or decreased without 
      disrupting the service to the link. If it is increased and the PORS 
      optimization feature is enabled calls will move off this link to lower 
      cost links when possible. If the cost is decreased new calls will be 
      attracted to this link."
   DEFVAL     { 128 }
::= { trkPaProvEntry 7 }

trkPaOverrideTrunkDelay OBJECT-TYPE
   SYNTAX     Unsigned32 (0..1500)
   ACCESS     read-write
   STATUS     mandatory
   DESCRIPTION
     "This attribute specifies the override value of parent trunk's half 
      round trip delay (propagation delay), which is used by the 
      PathAdmin to negotiate the value of negotiatedTrunkDelay. A value 
      of zero indicates that an override value has not been provided, and 
      that the measured propagation delay value is used for negotiation."
   DEFVAL     { 0 }
::= { trkPaProvEntry 8 }

trkPaOperTable OBJECT-TYPE
   SYNTAX     SEQUENCE OF TrkPaOperEntry
   ACCESS     not-accessible
   STATUS     mandatory
   DESCRIPTION
     "This group contains all operational attributes relevant to path 
      oriented and connectionless bandwidth utilization and path activity 
      on a trunk."
::= { trkPa 11 }

trkPaOperEntry OBJECT-TYPE
   SYNTAX     TrkPaOperEntry
   ACCESS     not-accessible
   STATUS     mandatory
   DESCRIPTION
     "An entry in the trkPaOperTable."
   INDEX {
      trkIndex,
      trkPaIndex }
::= { trkPaOperTable 1 }

TrkPaOperEntry ::= SEQUENCE {
   trkPaState
      AsciiString,
   trkPaUsedLc
      Unsigned32,
   trkPaNegotiatedMaxLc
      Unsigned32,
   trkPaMaxReservableBwOut
      Unsigned32,
   trkPaOverReservedBwOut
      Unsigned32,
   trkPaUnreservedBwOut
      Unsigned32,
   trkPaClashCount
      Unsigned32,
   trkPaNegotiatedSupportedTrafficTypes
      OCTET STRING,
   trkPaNegotiatedTrunkSecurity
      Unsigned32,
   trkPaNegotiatedCustomerParameter
      Unsigned32,
   trkPaNegotiatedTrunkCost
      Unsigned32,
   trkPaNegotiatedAtmMode
      INTEGER,
   trkPaNegotiatedTrunkDelay
      Unsigned32,
   trkPaNegotiatedTrunkType
      INTEGER,
   trkPaAdaptationLevel
      Unsigned32 }

trkPaState OBJECT-TYPE
   SYNTAX     AsciiString (SIZE (1..80))
   ACCESS     read-only
   STATUS     mandatory
   DESCRIPTION
     "This attribute gives the operational state of the PathAdmin 
      component. The PathAdmin may be up, down, goingDown, staging 
      or downWaitingRestage."
::= { trkPaOperEntry 1 }

trkPaUsedLc OBJECT-TYPE
   SYNTAX     Unsigned32 (0..4294967295)
   ACCESS     read-only
   STATUS     mandatory
   DESCRIPTION
     "This attribute gives the total number of Logical Channels currently 
      busy on the trunk. When this number reaches maxLc, no more paths 
      are allowed to instantiate through this trunk. Note that it is possible 
      for usedLc to be less than maxLc but for there to be no currently 
      free LogicalChannels. This is because a LogicalChannel can be in 
      one of several intermediate states between free and busy."
::= { trkPaOperEntry 2 }

trkPaNegotiatedMaxLc OBJECT-TYPE
   SYNTAX     Unsigned32 (0..4294967295)
   ACCESS     read-only
   STATUS     mandatory
   DESCRIPTION
     "This attribute gives the actual value of maxLc that the PathAdmin 
      has decided on after negotiation with the far end PathAdmin. If 
      there is disagreement between the two PathAdmin's maxLc 
      provisionable attributes the smaller of the two is chosen on both 
      sides. This attribute reflects the minimum of these two maxLc's."
::= { trkPaOperEntry 3 }

trkPaMaxReservableBwOut OBJECT-TYPE
   SYNTAX     Unsigned32 (0..4294967295)
   ACCESS     read-only
   STATUS     mandatory
   DESCRIPTION
     "This attribute gives the total bandwidth that this PathAdmin is 
      allowed to reserve. This number is computed by multiplying the 
      parent trunk's measuredSpeedToIf attribute by the 
      maxReservedBwOut provisionable attribute of this PathAdmin."
::= { trkPaOperEntry 4 }

trkPaOverReservedBwOut OBJECT-TYPE
   SYNTAX     Unsigned32 (0..4294967295)
   ACCESS     read-only
   STATUS     mandatory
   DESCRIPTION
     "When bumping is required to free up enough bandwidth for a new 
      path there exists a short period of time when both the new path and 
      the soon to be bumped path are occupying the same bandwidth. 
      This means that the total amount of reserved bandwidth will exceed 
      maxReservableBwOut. When this happens the unreservedBwOut 
      attribute will be 0 and the overReservedBwOut attribute will be non-
      zero to indicate by how much we are currently overcommitted. This 
      value should quickly drop back to zero as the bumping starts to 
      clear the lower holdingPriority calls."
::= { trkPaOperEntry 5 }

trkPaUnreservedBwOut OBJECT-TYPE
   SYNTAX     Unsigned32 (0..4294967295)
   ACCESS     read-only
   STATUS     mandatory
   DESCRIPTION
     "This attribute gives the total of amount of bandwidth that is still 
      available for reservation by new connections. When this number 
      reaches 0 the PathAdmin will no longer admit new connections to 
      the trunk. This number represents available bandwidth in the 
      outward going direction. To determine the inward available 
      bandwidth you must query the PathAdmin at the other end of this 
      Trunk."
::= { trkPaOperEntry 6 }

trkPaClashCount OBJECT-TYPE
   SYNTAX     Unsigned32 (0..4294967295)
   ACCESS     read-only
   STATUS     mandatory
   DESCRIPTION
     "This attribute gives the total number of path setup requests that 
      resulted in an LCh/n or Vcc/x.y clash. A large value for this number 
      is an indicator of poor performance by the PathAdmin in its 
      allocation of LCh/n or Vcc/x.y components. In general the channels 
      will be allocated in opposite orders at each end of the Trunk but this 
      may not always be the case. Note that as the PathAdmin runs out of 
      LCh/n or Vcc/x.y components the number of clashes will increase."
::= { trkPaOperEntry 7 }

trkPaNegotiatedSupportedTrafficTypes OBJECT-TYPE
   SYNTAX     OCTET STRING (SIZE (1))
   ACCESS     read-only
   STATUS     mandatory
   DESCRIPTION
     "This attribute gives the actual value of supportedTrafficTypes that 
      the PathAdmin has decided on after negotiation with the far end 
      PathAdmin. If there is disagreement between the two PathAdmin's 
      supportedTrafficTypes provisionable attributes the union of the two 
      is chosen on both sides. This attribute reflects the union of these two 
      supportedTrafficTypes 's. It is this union that is advertised to all 
      other nodes in the network and which is used for routing decisions.

      Description of bits:
      voice(0)
      data(1)
      video(2)
      trafficType1(3)
      trafficType2(4)
      trafficType3(5)
      trafficType4(6)
      trafficType5(7)"
::= { trkPaOperEntry 9 }

trkPaNegotiatedTrunkSecurity OBJECT-TYPE
   SYNTAX     Unsigned32 (0..7)
   ACCESS     read-only
   STATUS     mandatory
   DESCRIPTION
     "This attribute gives the actual value of the trunkSecurity that the 
      PathAdmin has decided on after negotiation with the far end 
      PathAdmin. If there is disagreement between the two PathAdmin's 
      trunkSecurity provisionable attributes the larger of the two is chosen 
      on both sides. This attribute reflects the maximum of these two 
      trunkSecurity's."
::= { trkPaOperEntry 10 }

trkPaNegotiatedCustomerParameter OBJECT-TYPE
   SYNTAX     Unsigned32 (0..7)
   ACCESS     read-only
   STATUS     mandatory
   DESCRIPTION
     "This attribute gives the actual value of customerParameter that the 
      PathAdmin has decided on after negotiation with the far end 
      PathAdmin. If there is disagreement between the two PathAdmin's 
      customerParameter provisionable attributes the larger of the two is 
      chosen on both sides. This attribute reflects the maximum of these 
      two customerParameter's."
::= { trkPaOperEntry 11 }

trkPaNegotiatedTrunkCost OBJECT-TYPE
   SYNTAX     Unsigned32 (1..255)
   ACCESS     read-only
   STATUS     mandatory
   DESCRIPTION
     "This attribute gives the actual value of trunkCost that the 
      PathAdmin has decided on after negotiation with the far end 
      PathAdmin. If there is disagreement between the two PathAdmin's 
      trunkCost provisionable attributes the larger of the two is chosen on 
      both sides. This attribute reflects the maximum of these two 
      trunkCost's."
::= { trkPaOperEntry 12 }

trkPaNegotiatedAtmMode OBJECT-TYPE
   SYNTAX     INTEGER  {
                 multiplexing(0),
                 mapping(1),
                 notApplicable(2) }
   ACCESS     read-only
   STATUS     mandatory
   DESCRIPTION
     "This attribute gives the actual value of PathAdmin Atm mode that 
      the PathAdmin has decided on after negotiation with the far end 
      PathAdmin. This is only applicable to ATM cards since the mode on 
      non ATM hardware is not specified. The multiplexing mode implies 
      that all voice traffic will be multiplexed onto the Atm 
      atmConnection Vcc and all data will be multiplexed onto the Trunk 
      Atm atmConnection Vcc. The mapping mode implies that each 
      unique logical channel will be allocated its own Vcc. The mode 
      notApplicable implies either this is not ATM hardware or that no 
      Atm subcomponent exists under this or the peer PathAdmin."
::= { trkPaOperEntry 13 }

trkPaNegotiatedTrunkDelay OBJECT-TYPE
   SYNTAX     Unsigned32 (0..1500)
   ACCESS     read-only
   STATUS     mandatory
   DESCRIPTION
     "This attribute gives the actual value of parent trunk's half round trip 
      delay (propagation delay) that the PathAdmin has decided on after 
      negotiation with the far end PathAdmin. If there is disagreement 
      between the two PathAdmins the larger of the two propagation 
      delays is chosen on both sides. This attribute reflects the maximum 
      of these two propagation delays."
::= { trkPaOperEntry 14 }

trkPaNegotiatedTrunkType OBJECT-TYPE
   SYNTAX     INTEGER  {
                 terrestrial(0),
                 satellite(1),
                 trunkType1(2),
                 trunkType2(3),
                 trunkType3(4),
                 trunkType4(5),
                 trunkType5(6),
                 trunkType6(7) }
   ACCESS     read-only
   STATUS     mandatory
   DESCRIPTION
     "This attribute gives the actual value of trunkType that the 
      PathAdmin has decided on after negotiation with the far end 
      PathAdmin. If there is disagreement between the two PathAdmin's 
      trunkType provisionable attributes the provisioned values are used 
      on both sides. That is, both sides maintain their provisioned value.."
::= { trkPaOperEntry 15 }

trkPaAdaptationLevel OBJECT-TYPE
   SYNTAX     Unsigned32 (0..3)
   ACCESS     read-only
   STATUS     mandatory
   DESCRIPTION
     "This attribute indicates the current PORS adaptation level of the 
      parent trunk. The adaptation mechanism is controlled by Adaptation 
      group, which is used to alleviate the high utilization condition on 
      the parent trunk.
      0 - adaptation is not active.
      1 - new calls are prevented from being established over the parent 
      trunk. 
      2 - some connections starting from the lowest holdingPriority 
      attempt to reroute their paths using alternate trunks.
      3 - some connections starting from the lowest holdingPriority are 
      bumped away from the parent trunk."
::= { trkPaOperEntry 16 }

trkPaAdaptationTable OBJECT-TYPE
   SYNTAX     SEQUENCE OF TrkPaAdaptationEntry
   ACCESS     not-accessible
   STATUS     mandatory
   DESCRIPTION
     "This group of provisionable attributes controls the PORS adaptive 
      routing mechanism. Adaptation is triggered by high trunk 
      utilization, and is used to alleviate the high utilization condition on 
      the parent Trunk/n component.
      
      For a Trunk/n with an Unack subcomponent, the link receive 
      utilization (indicated by utilization of Trunk/n) is used for triggering 
      adaptation. 
      
      For a Trunk/n with an AtmAccess subcomponent, the aggregation of 
      the transmit VCCs utilization (indicated by utilization of Trunk/n), 
      VP utilization, and PORT utilization (normal port or IMA port if 
      Ima is used) is used for triggering adaptation."
::= { trkPa 12 }

trkPaAdaptationEntry OBJECT-TYPE
   SYNTAX     TrkPaAdaptationEntry
   ACCESS     not-accessible
   STATUS     mandatory
   DESCRIPTION
     "An entry in the trkPaAdaptationTable."
   INDEX {
      trkIndex,
      trkPaIndex }
::= { trkPaAdaptationTable 1 }

TrkPaAdaptationEntry ::= SEQUENCE {
   trkPaMaxAdaptationLevel
      Unsigned32,
   trkPaAdaptationBandwidth
      Unsigned32 }

trkPaMaxAdaptationLevel OBJECT-TYPE
   SYNTAX     Unsigned32 (0..3)
   ACCESS     read-write
   STATUS     mandatory
   DESCRIPTION
     "This attribute specifies the maximum adaptation level that the parent 
      trunk can reach. It determines the highest degree of adaptation that 
      can be triggered by high trunk utilization.
      
      When the first degree of adaptation is triggered, new calls are 
      prevented from being established over the parent trunk, and the 
      adaptationLevel changes to level one (1). 
      
      When the second degree of adaptation is triggered, some 
      connections starting from the lowest holdingPriority attempt to 
      reroute their paths using alternate trunks, and the adaptationLevel 
      changes to level two (2). 
      
      When the third degree of adaptation is triggered, some connections 
      starting from the lowest holdingPriority are bumped away from the 
      parent trunk, and the adaptationLevel changes to level three (3).
      
      The configurable values are:
      0 - The adapation mechanism is disabled.
      1 - Only the first degree of adaptation can be triggered.
      2 - Up to two degrees of adaptation can be triggered.
      3 - Up to three degrees of adaptation can be triggered. 
      
      Regardless of its value, the operator command CLEAR -hotSwap or 
      CLEAR (without an option) can always be issued on a particular 
      LCh/n to cause the entire path to be rerouted if possible or bumped."
   DEFVAL     { 0 }
::= { trkPaAdaptationEntry 1 }

trkPaAdaptationBandwidth OBJECT-TYPE
   SYNTAX     Unsigned32 (0..4294967295)
   ACCESS     read-write
   STATUS     mandatory
   DESCRIPTION
     "This attribute specifies the amount of bandwidth to be potentially 
      freed up by rerouting connections if possible or freed up by 
      bumping connections on the trunk when the second or third degree 
      of adaptation is triggered.
      
      The adaptationBandwidth value is used to determine the number of 
      connections to be rerouted or bumped starting from the lowest 
      holdingPriority, such that the total of the chosen connections 
      reserved outgoing bandwidth requiredTxBandwidth reaches this 
      adaptationBandwidth value.
      
      If its value is greater than the maxReservableBwOut of Trunk/n Pa, 
      the maxReservableBwOut amount of bandwidth is used for 
      rerouting or bumping."
   DEFVAL     { 64000 }
::= { trkPaAdaptationEntry 2 }

trkPaRbwTable OBJECT-TYPE
   SYNTAX     SEQUENCE OF TrkPaRbwEntry
   ACCESS     not-accessible
   STATUS     mandatory
   DESCRIPTION
     "This attribute gives the total bandwidth reserved by paths for each 
      of five (5) holding priorities. For example the bandwidth used by 
      holdingPriority 0 paths is shown in the left most value."
::= { trkPa 214 }

trkPaRbwEntry OBJECT-TYPE
   SYNTAX     TrkPaRbwEntry
   ACCESS     not-accessible
   STATUS     mandatory
   DESCRIPTION
     "An entry in the trkPaRbwTable."
   INDEX {
      trkIndex,
      trkPaIndex,
      trkPaRbwIndex }
::= { trkPaRbwTable 1 }

TrkPaRbwEntry ::= SEQUENCE {
   trkPaRbwIndex
      Integer32,
   trkPaRbwValue
      Unsigned32 }

trkPaRbwIndex OBJECT-TYPE
   SYNTAX     Integer32 (0..4)
   ACCESS     not-accessible
   STATUS     mandatory
   DESCRIPTION
     "This variable represents the index for the trkPaRbwTable."
::= { trkPaRbwEntry 1 }

trkPaRbwValue OBJECT-TYPE
   SYNTAX     Unsigned32 (0..4294967295)
   ACCESS     read-only
   STATUS     mandatory
   DESCRIPTION
     "This variable represents an individual value for the
      trkPaRbwTable."
::= { trkPaRbwEntry 2 }

trkPaPacntTable OBJECT-TYPE
   SYNTAX     SEQUENCE OF TrkPaPacntEntry
   ACCESS     not-accessible
   STATUS     mandatory
   DESCRIPTION
     "This attribute gives the total number of path instantiation attempts 
      this trunk has processed since its creation. This number includes 
      successful and unsuccessful attempts. This attribute provides five 
      (5) values of this count, one for each path holdingPriority."
::= { trkPa 215 }

trkPaPacntEntry OBJECT-TYPE
   SYNTAX     TrkPaPacntEntry
   ACCESS     not-accessible
   STATUS     mandatory
   DESCRIPTION
     "An entry in the trkPaPacntTable."
   INDEX {
      trkIndex,
      trkPaIndex,
      trkPaPacntIndex }
::= { trkPaPacntTable 1 }

TrkPaPacntEntry ::= SEQUENCE {
   trkPaPacntIndex
      Integer32,
   trkPaPacntValue
      Unsigned32 }

trkPaPacntIndex OBJECT-TYPE
   SYNTAX     Integer32 (0..4)
   ACCESS     not-accessible
   STATUS     mandatory
   DESCRIPTION
     "This variable represents the index for the trkPaPacntTable."
::= { trkPaPacntEntry 1 }

trkPaPacntValue OBJECT-TYPE
   SYNTAX     Unsigned32 (0..4294967295)
   ACCESS     read-only
   STATUS     mandatory
   DESCRIPTION
     "This variable represents an individual value for the
      trkPaPacntTable."
::= { trkPaPacntEntry 2 }

trkPaPfcntTable OBJECT-TYPE
   SYNTAX     SEQUENCE OF TrkPaPfcntEntry
   ACCESS     not-accessible
   STATUS     mandatory
   DESCRIPTION
     "This attribute gives the total number of path instantiation failures 
      that have happened since the creation of this trunk. This attribute 
      provides five (5) values of this count, one for each path 
      holdingPriority."
::= { trkPa 216 }

trkPaPfcntEntry OBJECT-TYPE
   SYNTAX     TrkPaPfcntEntry
   ACCESS     not-accessible
   STATUS     mandatory
   DESCRIPTION
     "An entry in the trkPaPfcntTable."
   INDEX {
      trkIndex,
      trkPaIndex,
      trkPaPfcntIndex }
::= { trkPaPfcntTable 1 }

TrkPaPfcntEntry ::= SEQUENCE {
   trkPaPfcntIndex
      Integer32,
   trkPaPfcntValue
      Unsigned32 }

trkPaPfcntIndex OBJECT-TYPE
   SYNTAX     Integer32 (0..4)
   ACCESS     not-accessible
   STATUS     mandatory
   DESCRIPTION
     "This variable represents the index for the trkPaPfcntTable."
::= { trkPaPfcntEntry 1 }

trkPaPfcntValue OBJECT-TYPE
   SYNTAX     Unsigned32 (0..4294967295)
   ACCESS     read-only
   STATUS     mandatory
   DESCRIPTION
     "This variable represents an individual value for the
      trkPaPfcntTable."
::= { trkPaPfcntEntry 2 }

trkPaPccntTable OBJECT-TYPE
   SYNTAX     SEQUENCE OF TrkPaPccntEntry
   ACCESS     not-accessible
   STATUS     mandatory
   DESCRIPTION
     "This attribute gives the total number of path clear requests this trunk 
      has processed since its creation. This attribute provides five (5) 
      values of this count, one for each path holdingPriority."
::= { trkPa 217 }

trkPaPccntEntry OBJECT-TYPE
   SYNTAX     TrkPaPccntEntry
   ACCESS     not-accessible
   STATUS     mandatory
   DESCRIPTION
     "An entry in the trkPaPccntTable."
   INDEX {
      trkIndex,
      trkPaIndex,
      trkPaPccntIndex }
::= { trkPaPccntTable 1 }

TrkPaPccntEntry ::= SEQUENCE {
   trkPaPccntIndex
      Integer32,
   trkPaPccntValue
      Unsigned32 }

trkPaPccntIndex OBJECT-TYPE
   SYNTAX     Integer32 (0..4)
   ACCESS     not-accessible
   STATUS     mandatory
   DESCRIPTION
     "This variable represents the index for the trkPaPccntTable."
::= { trkPaPccntEntry 1 }

trkPaPccntValue OBJECT-TYPE
   SYNTAX     Unsigned32 (0..4294967295)
   ACCESS     read-only
   STATUS     mandatory
   DESCRIPTION
     "This variable represents an individual value for the
      trkPaPccntTable."
::= { trkPaPccntEntry 2 }

trkPaPbcntTable OBJECT-TYPE
   SYNTAX     SEQUENCE OF TrkPaPbcntEntry
   ACCESS     not-accessible
   STATUS     mandatory
   DESCRIPTION
     "This attribute gives the total number of path bumping requests this 
      trunk has processed since its creation. This attribute provides 5 
      values of this count, one for each path holdingPriority."
::= { trkPa 218 }

trkPaPbcntEntry OBJECT-TYPE
   SYNTAX     TrkPaPbcntEntry
   ACCESS     not-accessible
   STATUS     mandatory
   DESCRIPTION
     "An entry in the trkPaPbcntTable."
   INDEX {
      trkIndex,
      trkPaIndex,
      trkPaPbcntIndex }
::= { trkPaPbcntTable 1 }

TrkPaPbcntEntry ::= SEQUENCE {
   trkPaPbcntIndex
      Integer32,
   trkPaPbcntValue
      Unsigned32 }

trkPaPbcntIndex OBJECT-TYPE
   SYNTAX     Integer32 (0..4)
   ACCESS     not-accessible
   STATUS     mandatory
   DESCRIPTION
     "This variable represents the index for the trkPaPbcntTable."
::= { trkPaPbcntEntry 1 }

trkPaPbcntValue OBJECT-TYPE
   SYNTAX     Unsigned32 (0..4294967295)
   ACCESS     read-only
   STATUS     mandatory
   DESCRIPTION
     "This variable represents an individual value for the
      trkPaPbcntTable."
::= { trkPaPbcntEntry 2 }

trkPaAdpthTable OBJECT-TYPE
   SYNTAX     SEQUENCE OF TrkPaAdpthEntry
   ACCESS     not-accessible
   STATUS     mandatory
   DESCRIPTION
     "This attribute specifies three utilization thresholds used to trigger 
      the three degrees of adaptation. It is a vector indexed by (level1, 
      level2, and level3).
      
      While the PORS adaptationLevel is zero (0), 
      - if the trunk utilization has exceeded the level1 value for the period 
      of time specified by the set value of adaptationHoldOffTime, the 
      first degree of adaptation is triggered. Meanwhile, the Trunk/n Pa 
      component generates a SET alarm indicating that the PORS 
      adaptation mechanism is active. The PORS adaptationLevel 
      increases to level one (1).
      
      While the PORS adaptationLevel is one (1),
      - if the trunk utilization has exceeded the level2 value for the period 
      of time specified by the set value of adaptationHoldOffTime, the 
      second degree of adaptation is triggered. The PORS 
      adaptationLevel increases to level two (2).
      - Otherwise, if the trunk utilization has exceeded the level1 value 
      for an additional period of time specified by the set value of 
      adaptationHoldOffTime, the PORS adaptationLevel remains 
      unchanged.
      - Otherwise, if the trunk utilization has subsequently fallen back to 
      a level at or below the level1 value for the period of time specified 
      by the clear value of adaptationHoldOffTime, new calls are allowed 
      to be established over the parent trunk. Meanwhile, the Trunk/n Pa 
      component generates a CLEAR alarm indicating that the PORS 
      adaptation mechanism is no longer active. The PORS 
      adaptationLevel decreases to level zero (0).
      
      While the PORS adaptationLevel is two (2),
      - if the trunk utilization has exceeded the level3 value for the period 
      of time specified by the set value of adaptationHoldOffTime, the 
      third degree of adaptation is triggered. The PORS adaptationLevel 
      increases to level three (3).
      - Otherwise, if the trunk utilization has exceeded the level2 value 
      for an additional period of time specified by the set value of 
      adaptationHoldOffTime, the second degree of adaptation is 
      triggered again, and the PORS adaptationLevel remains unchanged.
      - Otherwise, if the trunk utilization has subsequently fallen back to 
      a level at or below the level2 value for the period of time specified 
      by the clear value of adaptationHoldOffTime, the PORS 
      adaptationLevel decreases to level one (1).
      
      While the PORS adaptationLevel is three (3), 
      - if the trunk utilization has exceeded the level3 value for an 
      additional period of time specified by the set value of 
      adaptationHoldOffTime, the third degree of adaptation is triggered 
      again, and the PORS adaptationLevel remains unchanged.
      - Otherwise, if the trunk utilization has subsequently fallen back to 
      a level at or below the level3 value for the period of time specified 
      by the clear value of adaptationHoldOffTime, the PORS 
      adaptationLevel decreases to level two (2).
      
      For a Trunk/n with an Unack subcomponent, the link receive 
      utilization (indicated by utilization of Trunk/n) is monitored against 
      the thresholds. Since the trunk application solely owns the physical 
      link, the maximum link receive utilization is 100%. The restrictions 
      on the setting of the three thresholds are:
      - when maxAdaptationLevel is 1, the value of (level1) must be in the 
      range of 0% to 100%.
      - when maxAdaptationLevel is 2, the values of (level1 and level2) 
      must be the range of 0% to 100%, and the value of level1 must be 
      less than or equal to the value of level2.
      - when maxAdaptationLevel is 3, the values of (level1, level2, and 
      level3) must be in the range of 0% to 100%, and the value of level1 
      must be less than or equal to the value of level2, which must be less 
      than or equal to the value of level3.
      
      For a Trunk/n with an AtmAccess subcomponent, the aggregation of 
      transmit VCCs utilization (indicated by utilization of Trunk/n), VP 
      utilization, and PORT utilization (normal port or IMA port if Ima is 
      used) is monitored against the thresholds. Since the trunk 
      application shares a physical link with other applications, both the 
      VCCs and VP utilizations can exceed 100%, and the value 200% is 
      chosen as the maximum calculated utilization for VCCs and VP, so 
      all thresholds can take on any value in the range of 0% to 200%. 
      The restrictions on the setting of the three thresholds are:
      - when maxAdaptationLevel is 2, the value of level1 must be less 
      than or equal to the value of level2.
      - when maxAdaptationLevel is 3, the value of level1 must be less 
      than or equal to the value of level2, which must be less than or 
      equal to the value of level3."
::= { trkPa 653 }

trkPaAdpthEntry OBJECT-TYPE
   SYNTAX     TrkPaAdpthEntry
   ACCESS     not-accessible
   STATUS     mandatory
   DESCRIPTION
     "An entry in the trkPaAdpthTable."
   INDEX {
      trkIndex,
      trkPaIndex,
      trkPaAdpthIndex }
::= { trkPaAdpthTable 1 }

TrkPaAdpthEntry ::= SEQUENCE {
   trkPaAdpthIndex
      INTEGER,
   trkPaAdpthValue
      Unsigned32 }

trkPaAdpthIndex OBJECT-TYPE
   SYNTAX     INTEGER  {
                 level1(0),
                 level2(1),
                 level3(2) }
   ACCESS     not-accessible
   STATUS     mandatory
   DESCRIPTION
     "This variable represents the trkPaAdpthTable
      specific index for the trkPaAdpthTable."
::= { trkPaAdpthEntry 1 }

trkPaAdpthValue OBJECT-TYPE
   SYNTAX     Unsigned32 (0..200)
   ACCESS     read-write
   STATUS     mandatory
   DESCRIPTION
     "This variable represents an individual value for the
      trkPaAdpthTable."
::= { trkPaAdpthEntry 2 }

trkPaAdphoTable OBJECT-TYPE
   SYNTAX     SEQUENCE OF TrkPaAdphoEntry
   ACCESS     not-accessible
   STATUS     mandatory
   DESCRIPTION
     "This attribute specifies two interval times. It is a vector indexed by 
      (set clear). The set value specifies the period of time for which the 
      trunk utilization must be above the utilization threshold specified by 
      adaptationThreshold before the corresponding degree of adaptation 
      is triggered. The clear value specifies the period of time for which 
      the trunk utilization must be at or below the utilization threshold 
      specified by adaptationThreshold before the PORS adaptationLevel 
      is decreased by one (1)."
::= { trkPa 654 }

trkPaAdphoEntry OBJECT-TYPE
   SYNTAX     TrkPaAdphoEntry
   ACCESS     not-accessible
   STATUS     mandatory
   DESCRIPTION
     "An entry in the trkPaAdphoTable."
   INDEX {
      trkIndex,
      trkPaIndex,
      trkPaAdphoIndex }
::= { trkPaAdphoTable 1 }

TrkPaAdphoEntry ::= SEQUENCE {
   trkPaAdphoIndex
      INTEGER,
   trkPaAdphoValue
      Unsigned32 }

trkPaAdphoIndex OBJECT-TYPE
   SYNTAX     INTEGER  {
                 set(0),
                 clear(1) }
   ACCESS     not-accessible
   STATUS     mandatory
   DESCRIPTION
     "This variable represents the trkPaAdphoTable
      specific index for the trkPaAdphoTable."
::= { trkPaAdphoEntry 1 }

trkPaAdphoValue OBJECT-TYPE
   SYNTAX     Unsigned32 (5..60)
   ACCESS     read-write
   STATUS     mandatory
   DESCRIPTION
     "This variable represents an individual value for the
      trkPaAdphoTable."
::= { trkPaAdphoEntry 2 }

-- 
-- *** THIS SUBTREE CURRENTLY NOT IMPLEMENTED ***
-- 

-- Trunk/n LogicalChannel/n
-- This component is automatically created when a new path sets up 
-- over the Trunk and is deleted when that path terminates. An 
-- application component name followed by a series of 
-- LogicalChannel component names followed by an application 
-- component name serve to uniquely identify a path. Issuing a clear 
-- to this component will cause the entire path to collapse and all 
-- resources to be freed. Normally the end point components will 
-- attempt to reroute after a clear and may even reroute over this same 
-- trunk.

trkLCh OBJECT IDENTIFIER ::= { trk 5 }



trkLChRowStatusTable OBJECT-TYPE
   SYNTAX     SEQUENCE OF TrkLChRowStatusEntry
   ACCESS     not-accessible
   STATUS     mandatory
   DESCRIPTION
     "*** THIS TABLE CURRENTLY NOT IMPLEMENTED ***

      This entry controls the addition and deletion of 
      trkLCh components."
::= { trkLCh 1 }

trkLChRowStatusEntry OBJECT-TYPE
   SYNTAX     TrkLChRowStatusEntry
   ACCESS     not-accessible
   STATUS     mandatory
   DESCRIPTION
     "A single entry in the table represents a single 
      trkLCh component."
   INDEX {
      trkIndex,
      trkLChIndex }
::= { trkLChRowStatusTable 1 }

TrkLChRowStatusEntry ::= SEQUENCE {
   trkLChRowStatus
      RowStatus,
   trkLChComponentName
      DisplayString,
   trkLChStorageType
      StorageType,
   trkLChIndex
      Integer32 }

trkLChRowStatus OBJECT-TYPE
   SYNTAX     RowStatus 
   ACCESS     read-only
   STATUS     mandatory
   DESCRIPTION
     "This variable is used as the basis for SNMP naming of
      trkLCh components.
      These components cannot be added nor deleted."
::= { trkLChRowStatusEntry 1 }

trkLChComponentName OBJECT-TYPE
   SYNTAX     DisplayString 
   ACCESS     read-only
   STATUS     mandatory
   DESCRIPTION
     "This variable provides the component's string name for
      use with the ASCII Console Interface"
::= { trkLChRowStatusEntry 2 }

trkLChStorageType OBJECT-TYPE
   SYNTAX     StorageType 
   ACCESS     read-only
   STATUS     mandatory
   DESCRIPTION
     "This variable represents the storage type value for the
      trkLCh tables."
::= { trkLChRowStatusEntry 4 }

trkLChIndex OBJECT-TYPE
   SYNTAX     Integer32 (1..65535)
   ACCESS     not-accessible
   STATUS     mandatory
   DESCRIPTION
     "This variable represents the index for the trkLCh tables."
::= { trkLChRowStatusEntry 10 }

trkLChOperTable OBJECT-TYPE
   SYNTAX     SEQUENCE OF TrkLChOperEntry
   ACCESS     not-accessible
   STATUS     mandatory
   DESCRIPTION
     "*** THIS TABLE CURRENTLY NOT IMPLEMENTED ***

      This group contains all operational attributes pertaining to the 
      Logical Channel component owned by this trunk."
::= { trkLCh 10 }

trkLChOperEntry OBJECT-TYPE
   SYNTAX     TrkLChOperEntry
   ACCESS     not-accessible
   STATUS     mandatory
   DESCRIPTION
     "An entry in the trkLChOperTable."
   INDEX {
      trkIndex,
      trkLChIndex }
::= { trkLChOperTable 1 }

TrkLChOperEntry ::= SEQUENCE {
   trkLChNextHop
      RowPointer,
   trkLChSetupPriority
      Unsigned32,
   trkLChHoldingPriority
      Unsigned32,
   trkLChEmissionPriority
      Unsigned32,
   trkLChDiscardPriority
      Unsigned32,
   trkLChRequiredTxBandwidth
      Unsigned32,
   trkLChRequiredRxBandwidth
      Unsigned32,
   trkLChMode
      INTEGER,
   trkLChMaximumTransmissionUnit
      Unsigned32,
   trkLChLocalConnection
      RowPointer }

trkLChNextHop OBJECT-TYPE
   SYNTAX     RowPointer 
   ACCESS     read-only
   STATUS     mandatory
   DESCRIPTION
     "The nextHop is the name of the component across the bus which is 
      forwarding packets to us. Inversely the nextHop of our nextHop 
      component is us. More precisely, LCh/n components point to each 
      other across the bus via their nextHop attributes. In the case where 
      the next hop is an application the nextHop attribute will indicate the 
      component name of this application."
::= { trkLChOperEntry 2 }

trkLChSetupPriority OBJECT-TYPE
   SYNTAX     Unsigned32 (0..4)
   ACCESS     read-only
   STATUS     mandatory
   DESCRIPTION
     "This attribute gives the priority at which a path is established. Zero 
      (0) is the highest priority and four (4) is the lowest. When PORS 
      establishes a path through the network, it uses the setupPriority 
      attribute to determine its potential for bumping established paths to 
      acquire their bandwidth. The holdingPriority, a complementary 
      attribute of this component, indicates the priority a path maintains 
      once it is established. A new path can bump an existing path if the 
      new path's setupPriority is higher (or numerically less) than the 
      existing path's holdingPriority."
::= { trkLChOperEntry 3 }

trkLChHoldingPriority OBJECT-TYPE
   SYNTAX     Unsigned32 (0..4)
   ACCESS     read-only
   STATUS     mandatory
   DESCRIPTION
     "This attribute gives the priority that a path holds once it is 
      established. Zero (0) is the highest priority and four (4) is the 
      lowest. A path's holdingPriority determines its likelihood of being 
      bumped by a new path to acquire its bandwidth. The setupPriority, a 
      complementary attribute, indicates the priority of a path at 
      establishment time. A new path can bump an existing path if the 
      new path's setupPriority is higher (or numerically less) than the 
      existing path's holdingPriority."
::= { trkLChOperEntry 4 }

trkLChEmissionPriority OBJECT-TYPE
   SYNTAX     Unsigned32 (0..3)
   ACCESS     read-only
   STATUS     mandatory
   DESCRIPTION
     "This attribute indicates the urgency with which packets on the 
      LCh's path are emitted by this trunk. The emissionPriority 
      translates into the trunk's emission queue. Zero (0) indicates the 
      highest emissionPriority, while three (3) indicates the lowest. 
      Packets with a higher emissionPriority (or numerically less) are put 
      on an emission queue which is serviced before a queue which 
      accepts packets of a lower emissionPriority and hence experience 
      smaller delays traversing congested trunks."
::= { trkLChOperEntry 5 }

trkLChDiscardPriority OBJECT-TYPE
   SYNTAX     Unsigned32 (0..3)
   ACCESS     read-only
   STATUS     mandatory
   DESCRIPTION
     "This attribute indicates the importance of the packets on the path. 
      Zero (0) is used for paths carrying the most important traffic, and 
      two (3) is used for paths carrying the least important traffic. In times 
      of congestion, the discardPriority is used by packet forwarding on 
      the trunk to determine which packets are discarded first to reduce 
      the load. Packets with a higher discardPriority (or numerically less) 
      are discarded after packets with a lower discardPriority (or 
      numerically higher)."
::= { trkLChOperEntry 6 }

trkLChRequiredTxBandwidth OBJECT-TYPE
   SYNTAX     Unsigned32 (0..4294967295)
   ACCESS     read-only
   STATUS     mandatory
   DESCRIPTION
     "This attribute gives the bandwidth (in bits per second units) 
      reserved by this LCh/n for emitting packets on the trunk."
::= { trkLChOperEntry 7 }

trkLChRequiredRxBandwidth OBJECT-TYPE
   SYNTAX     Unsigned32 (0..4294967295)
   ACCESS     read-only
   STATUS     mandatory
   DESCRIPTION
     "This attribute gives the bandwidth (in bits per second units) 
      reserved by this LCh/n for receiving packets on the trunk."
::= { trkLChOperEntry 8 }

trkLChMode OBJECT-TYPE
   SYNTAX     INTEGER  {
                 unknown(0),
                 hdlcFrmMux(1),
                 aal5FrmMux(2),
                 spoFrmMux(3),
                 spoFrmMap(4),
                 aal5FrmMap(5),
                 cellMap(6) }
   ACCESS     read-only
   STATUS     mandatory
   DESCRIPTION
     "This attribute gives the operational mode of the LogicalChannel 
      component. It indicates what kind of transport is being performed 
      on the packets in the channel. There are 7 possible values of this 
      attribute as follows:
      
      unknown - not currently in busy state, type of forwarding not 
      determined yet.
      
      hdlcFrmMux - frames are being multiplexed (multiple LCh/n on 
      same port or channel) using HDLC encapsulation.
      
      aal5FrmMux - frames are being multiplexed (multiple LCh/n on 
      same ATM VCC) using the AAL5 segmentation and recombination 
      protocol. 
      
      spoFrmMux - frames are being multiplexed (multiple LCh/n on 
      same ATM VCC) using the Short Path Oriented segmentation and 
      recombination protocol. This is a proprietary protocol which 
      encapsulates voice frames into a single ATM cell unlike AAL5 
      which would require two cells to transport the 45 byte voice frames.
      
      aal5FrmMap - frames are being mapped (a single LCh/n per ATM 
      VCC) using the AAL5 segmentation and recombination protocol. 
      AAL5 mapped frames are forwarded by hardware in both directions 
      and require no CPU intervention.
      
      spoFrmMap - frames are being mapped (a single LCh/n per ATM 
      VCC) using the Short Path Oriented segmentation and 
      recombination protocol. SPO mapped frames are forwarded by 
      hardware in both directions and require no CPU intervention in all 
      but one special case. In particular CPU is required only if frames 
      are being forwarded to an LCh/n whose mode is spoFrmMux.
      
      cellMap - ATM cells are being relayed directly over the bus with no 
      segmentation and recombination protocol. The segmentation and 
      recombination is only done at transition points between frame based 
      cards and ATM cell based cards so this hop represents a pure 
      tandem cell hop, ATM card to ATM card. No CPU is required to 
      process these cells."
::= { trkLChOperEntry 9 }

trkLChMaximumTransmissionUnit OBJECT-TYPE
   SYNTAX     Unsigned32 (0..4294967295)
   ACCESS     read-only
   STATUS     mandatory
   DESCRIPTION
     "This attribute gives the size of the largest frame this service will 
      send. A value of 0 means that the Mtu is unknown. A value of 45 or 
      less (but non zero) means that ATM single cell transport will be 
      used wherever possible. Otherwise ATM AAL5 adaption layer 
      transport will be required to handle all frames."
::= { trkLChOperEntry 10 }

trkLChLocalConnection OBJECT-TYPE
   SYNTAX     RowPointer 
   ACCESS     read-only
   STATUS     mandatory
   DESCRIPTION
     "The localConnection attribute specifies the name of the connection 
      on the local interface. On ATM hardware this is in the form AtmIf/n 
      Vcc/x.y. On non ATM hardware this attribute is empty."
::= { trkLChOperEntry 11 }




-- 
-- Version and Compliance statements
-- 



-- Object-Group Statement:
-- A list of all current accessible leaf objects.

-- OBJECTS { trkPaNegotiatedSupportedTrafficTypes,
--           trkPaOverrideTrunkDelay,
--           trkLChNextHop,
--           trkPaOverReservedBwOut,
--           trkPaNegotiatedCustomerParameter,
--           trkPaRowStatus,
--           trkPaState,
--           trkPaMaxReservedBwOut,
--           trkPaNegotiatedTrunkSecurity,
--           trkPaNegotiatedTrunkType,
--           trkLChEmissionPriority,
--           trkPaAdphoValue,
--           trkLChMaximumTransmissionUnit,
--           trkPaPacntValue,
--           trkPaAdpthValue,
--           trkPaMaxReservableBwOut,
--           trkLChRequiredTxBandwidth,
--           trkLChRowStatus,
--           trkLChComponentName,
--           trkPaUsedLc,
--           trkLChHoldingPriority,
--           trkPaComponentName,
--           trkPaUnreservedBwOut,
--           trkPaAdaptationBandwidth,
--           trkPaMaxAdaptationLevel,
--           trkPaRbwValue,
--           trkPaTrunkCost,
--           trkPaPccntValue,
--           trkPaStorageType,
--           trkLChMode,
--           trkPaNegotiatedAtmMode,
--           trkPaMaxLc,
--           trkPaSupportedTrafficTypes,
--           trkPaPbcntValue,
--           trkPaCustomerParameter,
--           trkPaPfcntValue,
--           trkPaAdaptationLevel,
--           trkLChDiscardPriority,
--           trkPaNegotiatedTrunkDelay,
--           trkPaTrunkSecurity,
--           trkPaNegotiatedTrunkCost,
--           trkPaTrunkType,
--           trkLChLocalConnection,
--           trkLChRequiredRxBandwidth,
--           trkLChSetupPriority,
--           trkLChStorageType,
--           trkPaClashCount,
--           trkPaNegotiatedMaxLc }
-- STATUS  mandatory
-- DESCRIPTION
--   "A list of all current accessible leaf objects."

porsTrunksGroup OBJECT IDENTIFIER ::= { porsTrunksMIB 1 }
porsTrunksGroupBE OBJECT IDENTIFIER ::= { porsTrunksGroup 5 }
porsTrunksGroupBE00 OBJECT IDENTIFIER ::= { porsTrunksGroupBE 1 }
porsTrunksGroupBE00A OBJECT IDENTIFIER ::= { porsTrunksGroupBE00 2 }



-- Agent-Capabilities Statement:

-- PRODUCT-RELEASE "Passport Release 7.0 PorsTrunks."
-- STATUS          mandatory
-- DESCRIPTION     "PorsTrunks MIB: MIB Version BE00A,
--                  Software Version BG00S4C."
-- SUPPORTS        Nortel-Magellan-Passport-PorsTrunksMIB
--    INCLUDES     { porsTrunksGroupBE00A }

porsTrunksCapabilities OBJECT IDENTIFIER ::= { porsTrunksMIB 3 }
porsTrunksCapabilitiesBE OBJECT IDENTIFIER ::= { porsTrunksCapabilities 5 }
porsTrunksCapabilitiesBE00 OBJECT IDENTIFIER ::= { porsTrunksCapabilitiesBE 1 }
porsTrunksCapabilitiesBE00A OBJECT IDENTIFIER ::= { porsTrunksCapabilitiesBE00 2 }





END
