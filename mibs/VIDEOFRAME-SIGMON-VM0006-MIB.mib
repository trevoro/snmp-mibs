VIDEOFRAME-SIGMON-VM0006-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                      vfProducts(4)
	--							  |
	--						vfSigmonFrame(2)
	--							  |
	--					  vfSigmonFrameModules(1)
	--							  |
	--					  vm0006GPIInterface(6)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1).
	--          videoframe(4596).vfProducts(4).vfSigmonFrame(2).
	--			vfSigmonFrameModuleTypes(1)
	--	
	--  or, 1.3.6.1.4.1.4596.4.2.1
	--
	--
	--  Object Name                               Object Id         
	--  --------------------------------          --------------
	--
	--	vm0006GPIInterface							p.6
	--		vm0006Table								p.6.1
	--		vm0006TableEntry						p.6.1.1
	--			vm0006SlotNumber					p.6.1.1.1.m		m = slot #
	--			vm0006Active						p.6.1.1.2.m
	--			vm0006Locate						p.6.1.1.3.m
	--		vm0006GPISignalTable					p.6.2
	--		vm0006GPISignalEntry					p.6.2.1
	--			vm0006GPISignalSlotNumber			p.6.2.1.1.m.n	m = slot #, n = signal #
	--			vm0006GPISignalNumber				p.6.2.1.2.m.n
	--			vm0006GPISignalState				p.6.2.1.3.m.n
	--			vm0007GPIChandedAck					p.6.2.1.4.m.n
	--			vm0006GPISignalName					p.6.2.1.5.m.n
	--			vm0006GPISignalDescription			p.6.2.1.6.m.n
	--			vm0006GPISignalTrapEnable			p.6.2.1.7.m.n
	--		vm0006GPIInterfaceEvents				p.6.3
	--			vm0006GPIInterfaceEventsV2			p.6.3.0
	--				gpiChanged						p.6.3.0.1
	--    

	IMPORTS
		OBJECT-TYPE FROM RFC1155-SMI
		MODULE-IDENTITY, OBJECT-IDENTITY, NOTIFICATION-TYPE,
		IpAddress
			FROM SNMPv2-SMI
		DisplayString, RowStatus
			FROM SNMPv2-TC
		MODULE-COMPLIANCE, OBJECT-GROUP
			FROM SNMPv2-CONF
		vfMIBModules
			FROM VIDEOFRAME-REGISTRATIONS-MIB
		vfBoxId
			FROM VIDEOFRAME-GENERIC-MIB
		vfSigmonFrameModuleTypes, vfProductsVF200Reg, vfFrameSlotNumber
			FROM VIDEOFRAME-SIGMON-MIB;

	videoframeSigmonVm0006MIB MODULE-IDENTITY
		LAST-UPDATED "0109110000Z"
		ORGANIZATION "Videoframe Systems"
		CONTACT-INFO
			"Videoframe Systems
			P.O. Box 1991,
			Grass Valley, CA 95945, USA.

			+1 (530) 477-2000

			http://www.videoframesystems.com"
	DESCRIPTION
		"This MIB describes the device specific objects of the VM0006
		GPI Interface Module, and augments MIB-2, VF-GENERIC, and VF-SIGMON
		in the identification of this Videoframe Systems managed device.

		This module will be extended or modified as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0109110000Z"
	DESCRIPTION
		"First release."
	::= { vfMIBModules 6 }

	--
	-- VM0006, VM0010, and VM0011 product registration. vfProductsVF200Reg is from
	-- vf-sigmon
	--

	vfProductsVM0006 OBJECT-IDENTITY
		STATUS	current
		DESCRIPTION
			"Videoframe VM0006 GPO Interface (Relay) Module."
	::= { vfProductsVF200Reg 6 }

	--
	--  The VM0006 MIB top-level groups
	--

	-- root of this MIB module
vm0006GPIInterface		OBJECT IDENTIFIER ::= { vfSigmonFrameModuleTypes 6 }

	--
	-- Other signal monitoring modules, whose management information is defined in
	-- other MIB modules.
	--
	--		vm0001AnalogAudio		OBJECT IDENTIFIER ::= { vfSigmonFrameModuleTypes 1 }
	--		vm0002AnalogVideo		OBJECT IDENTIFIER ::= { vfSigmonFrameModuleTypes 2 }
	--		vm0003AESEBUAudio		OBJECT IDENTIFIER ::= { vfSigmonFrameModuleTypes 3 }
	--		vm0004SDIVideo			OBJECT IDENTIFIER ::= { vfSigmonFrameModuleTypes 4 }
	--		vm0005SerialIO			OBJECT IDENTIFIER ::= { vfSigmonFrameModuleTypes 5 }
	--		vm0007TransferSwitch	OBJECT IDENTIFIER ::= { vfSigmonFrameModuleTypes 7 }
	--		vm0008CPU				OBJECT IDENTIFIER ::= { vfSigmonFrameModuleTypes 8 }
	--		vm0009DTMFTransceiver	OBJECT IDENTIFIER ::= { vfSigmonFrameModuleTypes 9 }
	--		vm0010GPOInterface		OBJECT IDENTIFIER ::= { vfSigmonFrameModuleTypes 10 }
	--		vm0011GPIOInterface		OBJECT IDENTIFIER ::= { vfSigmonFrameModuleTypes 11 }
	--

vm0006Table	OBJECT-TYPE
	SYNTAX	SEQUENCE OF Vm0006Entry
	MAX-ACCESS	not-accessible
	STATUS	current
	DESCRIPTION
		"Each row contains information about one VM0006 GPI Interface
		 module in the managed VF200 frame."

	::=	{ vm0006GPIInterface 1}


vm0006Entry	OBJECT-TYPE
	SYNTAX	Vm0006Entry
    MAX-ACCESS not-accessible
    STATUS     current
    DESCRIPTION
        "A GPI Interface module entry."
	INDEX { vfFrameSlotNumber }
    ::= { vm0006Table 1 } 
		
Vm0006Entry   ::= 
    SEQUENCE	{
		vm0006SlotNumber					INTEGER,
		vm0006Active						INTEGER,
		vm0006Locate						INTEGER
				}	

vm0006SlotNumber OBJECT-TYPE
		SYNTAX	INTEGER (1..12)				
		MAX-ACCESS	read-only
		STATUS		current
		DESCRIPTION
			"The slot that this entry represents."
	::= { vm0006Entry 1 }

vm0006Active OBJECT-TYPE
		SYNTAX	INTEGER
					{
						active(1),
						inactive(2)
					}				
		MAX-ACCESS	read-only
		STATUS		current
		DESCRIPTION
			"Indicates whether this entry is active (this module is in
			 this slot)."
	::= { vm0006Entry 2 }

vm0006Locate OBJECT-TYPE
		SYNTAX	INTEGER
					{
						flash(1),
						off(2)
					}				
		MAX-ACCESS	read-write
		STATUS		current
		DESCRIPTION
			"Controls the locate indicator on the module and indicates its
			 current state.  Set to flash (1) to cause the locate LED on the
			 front of the module to begin flashing.  Set to off to stop flashing."
	::= { vm0006Entry 3 }

vm0006GPISignalTable	OBJECT-TYPE
	SYNTAX	SEQUENCE OF Vm0006GPISignalEntry
	MAX-ACCESS	not-accessible
	STATUS	current
	DESCRIPTION
		"Each row contains information about one GPI signal of one
		 VM0006 GPI Interface module in the managed VF200 frame."

	::=	{ vm0006GPIInterface 2}

vm0006GPISignalEntry	OBJECT-TYPE
	SYNTAX	Vm0006GPISignalEntry
    MAX-ACCESS not-accessible
    STATUS     current
    DESCRIPTION
        "A GPI Interface module GPI signal entry."
	INDEX { vfFrameSlotNumber, vm0006GPISignalNumber }
    ::= { vm0006GPISignalTable 1 } 
		
Vm0006GPISignalEntry   ::= 
    SEQUENCE	{
		vm0006GPISignalSlotNumber			INTEGER,
		vm0006GPISignalNumber				INTEGER,
		vm0006GPISignalState				INTEGER,
		vm0007GPIChandedAck					INTEGER,
		vm0006GPISignalName					DisplayString,
		vm0006GPISignalDescription			DisplayString,
		vm0006GPISignalTrapEnable			INTEGER
		}

vm0006GPISignalSlotNumber OBJECT-TYPE
		SYNTAX	INTEGER (1..12)				
		MAX-ACCESS	read-only
		STATUS		current
		DESCRIPTION
			"The frame slot number that this entry represents."
	::= { vm0006GPISignalEntry 1 }

vm0006GPISignalNumber OBJECT-TYPE
		SYNTAX		INTEGER(1..16)
		MAX-ACCESS	read-only
		STATUS		current
		DESCRIPTION
			"The GPI number within the module."
	::= { vm0006GPISignalEntry 2 }

vm0006GPISignalState OBJECT-TYPE
		SYNTAX	INTEGER
					{
						high(1),
						low(2)
					}				
		MAX-ACCESS	read-only
		STATUS		current
		DESCRIPTION
			"Indicates the current state of this GPI signal."
	::= { vm0006GPISignalEntry 3 }

vm0007GPIChandedAck	OBJECT-TYPE
		SYNTAX	INTEGER
				{
					idle(1),
					unacknowledged(2),
					acknowledge(3)
				}
		MAX-ACCESS	read-write
		STATUS		current
		DESCRIPTION
			"When Auto Re-Arm is set to off, set to acknowledge (3) to acknowledge
			 a triggered gpiChanged notification."
	::= { vm0006GPISignalEntry 4 }

vm0006GPISignalName OBJECT-TYPE
		SYNTAX		DisplayString (SIZE(0..20))
		MAX-ACCESS	read-write
		STATUS		current
		DESCRIPTION
			"The name of this GPI signal."
	::= { vm0006GPISignalEntry 5 }

vm0006GPISignalDescription OBJECT-TYPE
		SYNTAX		DisplayString (SIZE(0..120))
		MAX-ACCESS	read-write
		STATUS		current
		DESCRIPTION
			"Descriptive identification of this GPI signal."
	::= { vm0006GPISignalEntry 6 }

vm0006GPISignalTrapEnable OBJECT-TYPE
		SYNTAX	INTEGER
					{
						enabled(1),
						disabled(2)
					}				
		MAX-ACCESS	read-write
		STATUS		current
		DESCRIPTION
			"Enables or disables trap generation from this GPI signal."
	::= { vm0006GPISignalEntry 7 }


	--
	-- VM0006 Events
	--

vm0006GPIInterfaceEvents		OBJECT IDENTIFIER ::= { vm0006GPIInterface 3 }
vm0006GPIInterfaceEventsV2		OBJECT IDENTIFIER ::= { vm0006GPIInterfaceEvents 0 }

gpiChanged	NOTIFICATION-TYPE
		OBJECTS
			{
				vfBoxId,
				vm0006SlotNumber,
				vm0006GPISignalNumber,
				vm0006GPISignalName,
				vm0006GPISignalDescription
			}
		STATUS	current
		DESCRIPTION
			"One or more GPIs, for which traps are enabled, has changed state."
		::= { vm0006GPIInterfaceEventsV2 1 }

END
