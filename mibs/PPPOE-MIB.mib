-- extracted from draft-wheeler-info-pppoe-mib-01.txt
-- at Thu Oct 19 07:11:20 2000

PPPOE-MIB DEFINITIONS ::= BEGIN

    IMPORTS
        MODULE-IDENTITY, experimental, OBJECT-TYPE,
        Integer32, Counter32, Gauge32
            FROM SNMPv2-SMI
        InterfaceIndex
            FROM IF-MIB
        RowStatus, TruthValue, DisplayString
            FROM SNMPv2-TC
        MODULE-COMPLIANCE, OBJECT-GROUP
            FROM SNMPv2-CONF
        ;

-- Begin managed object definitions here...

pPPoE   MODULE-IDENTITY
           LAST-UPDATED    "0010012000Z" -- October 01, 2000
           ORGANIZATION    "IETF Network Working Group"
           CONTACT-INFO
              "J Senthilnathan
              Postal: 3Com Corporation
                      1800 W. Central Road
                      Mount Prospect
                      Illinois 60056
              Tel:    +1 847342 6954
              Email:  jsenthil@mw.3com.com

              Rohit Verma
              Postal: Deloitte Consultin
                      180, N. Stetson Avenue
                      Chicago, 
                      Illinois 60601
              Tel:    +1 312374 2475
              Email:  Rohit_Verma@mw.3com.com

              Bill Vroman
              Postal: 3Com Corporation
                      1800 W. Central Road
                      Mount Prospect
                      Illinois 60056
              Tel:    +1 847222 2008
              Email:  Bill_Vroman@mw.3com.com

              Ross Wheeler
              Postal: Wind River
                      17771 Cowan Ave
                      Irvine, CA 92614
              Tel:    +1 949442 0770
              Email:  ross@windriver.com"

           DESCRIPTION
        "The MIB module that describes managed objects of
        general use by the PPP over Ethernet Protocol."

           ::= { experimental 9999 1 }

-- Top level MIB structure

   pPPoEObjects      OBJECT IDENTIFIER ::= { pPPoE 1 }
   pPPoEConformance  OBJECT IDENTIFIER ::= { pPPoE 2 }

-- MIB Groups

   pPPoEConfig       OBJECT IDENTIFIER ::= { pPPoEObjects 1 }
   pPPoEBindings     OBJECT IDENTIFIER ::= { pPPoEObjects 2 }
   pPPoESession      OBJECT IDENTIFIER ::= { pPPoEObjects 3 }

-- MIB Objects

pPPoEConfigMaxTotalSessions   OBJECT-TYPE
    SYNTAX  Integer32
    MAX-ACCESS  read-write
    STATUS  current
    DESCRIPTION
        "The number of maximum allowed PPPoE sessions"
    ::= { pPPoEConfig 1 }

pPPoEConfigMaxSessionsPerHost   OBJECT-TYPE
    SYNTAX  Integer32
    MAX-ACCESS  read-write
    STATUS  current
    DESCRIPTION
        "The number of maximum allowed PPPoE sessions from a
        peer"
    ::= { pPPoEConfig 2 }

pPPoEConfigPADITxInterval   OBJECT-TYPE
    SYNTAX  Integer32 (1..60)
    MAX-ACCESS  read-write
    STATUS  current
    DESCRIPTION
        "The time n seconds between PADI retries from the
        Host"
    DEFVAL    { 5 }
    ::= { pPPoEConfig 3 }

pPPoEConfigPADIMaxNumberOfRetries   OBJECT-TYPE
    SYNTAX  Integer32 (1..10)
    MAX-ACCESS  read-write
    STATUS  current
    DESCRIPTION
        "The number of times the Host sends a PADI"
    DEFVAL    { 5 }
    ::= { pPPoEConfig 4 }

-- The PPPoE service names table

pPPoEConfigServiceNameTable OBJECT-TYPE
    SYNTAX     SEQUENCE OF PPPoEConfigServiceNameEntry
    MAX-ACCESS not-accessible
    STATUS     current
    DESCRIPTION
        "The table listing the service names configured for
        PPPoE."
    ::= { pPPoEConfig 5 }

pPPoEConfigServiceNameEntry OBJECT-TYPE
    SYNTAX     PPPoEConfigServiceNameEntry
    MAX-ACCESS not-accessible
    STATUS     current
    DESCRIPTION
        "An entry representing service name enabled for
        PPPoE"
    INDEX      { pPPoEConfigServiceName }
    ::= { pPPoEConfigServiceNameTable 1 }

PPPoEConfigServiceNameEntry ::= SEQUENCE {
    pPPoEConfigServiceName       DisplayString,
    pPPoEConfigServiceRowStatus   RowStatus }

pPPoEConfigServiceName OBJECT-TYPE
    SYNTAX     DisplayString (SIZE (1..32))
    MAX-ACCESS read-create
    STATUS     current
    DESCRIPTION
        "The service name enabled for PPPoE."
::= { pPPoEConfigServiceNameEntry 1 }

pPPoEConfigServiceRowStatus   OBJECT-TYPE
    SYNTAX      RowStatus
    MAX-ACCESS  read-create
    STATUS      current
    DESCRIPTION
        "This object is used to create and delete rows from
        the pPPoEServiceTable.  It can be set only to the
        value of createAndGo and destroy.  It returns only
        the value of active."
::= { pPPoEConfigServiceNameEntry 2 }


-- The PPPoE Bindings Table

pPPoEBindingsTable OBJECT-TYPE
    SYNTAX     SEQUENCE OF PPPoEBindingsEntry
    MAX-ACCESS not-accessible
    STATUS     current
    DESCRIPTION
        "The table listing the Ethernet interfaces on which
        PPPoE is bound."
    ::= { pPPoEBindings 1 }

pPPoEBindingsEntry OBJECT-TYPE
    SYNTAX     PPPoEBindingsEntry
    MAX-ACCESS not-accessible
    STATUS     current
    DESCRIPTION
        "An entry representing an interface on which PPPoE is
        bound."
    INDEX      { pPPoEBindingsIndex }
    ::= { pPPoEBindingsTable 1 }


PPPoEBindingsEntry ::= SEQUENCE {
    pPPoEBindingsIndex        InterfaceIndex,
    pPPoEBindingsEnabled    TruthValue,
    pPPoEBindingsNumberActiveSessions   Gauge32,
    pPPoEBindingsTotalNumberSessions   Counter32,
    pPPoEBindingsNumberPADIRejected   Counter32,
    pPPoEBindingsNumberPADIReceived   Counter32,
    pPPoEBindingsNumberPADRRejected   Counter32,
    pPPoEBindingsNumberPADRReceived   Counter32,
    pPPoEBindingsNumberPADOTransmitted   Counter32,
    pPPoEBindingsNumberPADSTransmitted   Counter32,
    pPPoEBindingsNumberPADTReceived   Counter32,
    pPPoEBindingsNumberPADTTransmitted   Counter32,
    pPPoEBindingsNumberServiceNameErrors   Counter32,
    pPPoEBindingsNumberACSystemErrors   Counter32,
    pPPoEBindingsNumberGenericErrorsReceived   Counter32,
    pPPoEBindingsNumberGenericErrorsTransmitted   Counter32,
    pPPoEBindingsNumberMalformedPackets   Counter32,
    pPPoEBindingsNumberPADITimeouts   Counter32,
    pPPoEBindingsNumberMultiplePADOReceived   Counter32 }

pPPoEBindingsIndex OBJECT-TYPE
    SYNTAX          InterfaceIndex
    MAX-ACCESS      read-only
    STATUS          current
    DESCRIPTION
        "This value for this object is equal to the value of
        ifIndex of the Interfaces MIB for the Ethernet
        interfaces."
    ::= { pPPoEBindingsEntry 1 }

pPPoEBindingsEnabled OBJECT-TYPE
    SYNTAX     TruthValue
    MAX-ACCESS read-write
    STATUS     current
    DESCRIPTION
        "Whether pppoe is enabled or not."
    DEFVAL    { false } ::= { pPPoEBindingsEntry 2 }


pPPoEBindingsNumberActiveSessions   OBJECT-TYPE
    SYNTAX  Gauge32
    MAX-ACCESS  read-only
    STATUS  current
    DESCRIPTION
        "The number of Active PPPoE Sessions"
    ::= { pPPoEBindingsEntry 3 }

pPPoEBindingsTotalNumberSessions   OBJECT-TYPE
    SYNTAX  Counter32
    MAX-ACCESS  read-only
    STATUS  current
    DESCRIPTION
        "The total number of PPPoE Sessions since last
        counter reset"
    ::= { pPPoEBindingsEntry 4 }

pPPoEBindingsNumberPADIRejected   OBJECT-TYPE
    SYNTAX  Counter32
    MAX-ACCESS  read-only
    STATUS  current
    DESCRIPTION
        "The number of PADI discarded"
    ::= { pPPoEBindingsEntry 5 }

pPPoEBindingsNumberPADIReceived   OBJECT-TYPE
    SYNTAX  Counter32
    MAX-ACCESS  read-only
    STATUS  current
    DESCRIPTION
        "The number of PPPoE PADI received"
    ::= { pPPoEBindingsEntry 6 }

pPPoEBindingsNumberPADRRejected   OBJECT-TYPE
    SYNTAX  Counter32
    MAX-ACCESS  read-only
    STATUS  current
    DESCRIPTION
        "The number of PPPoE PADR discarded"
    ::= { pPPoEBindingsEntry 7 }

pPPoEBindingsNumberPADRReceived   OBJECT-TYPE
    SYNTAX  Counter32
    MAX-ACCESS  read-only
    STATUS  current
    DESCRIPTION
        "The number of PPPoE PADR received"
    ::= { pPPoEBindingsEntry 8 }

pPPoEBindingsNumberPADOTransmitted   OBJECT-TYPE
    SYNTAX  Counter32
    MAX-ACCESS  read-only
    STATUS  current
    DESCRIPTION
        "The number of PPPoE PADO transmitted"
    ::= { pPPoEBindingsEntry 9 }

pPPoEBindingsNumberPADSTransmitted   OBJECT-TYPE
    SYNTAX  Counter32
    MAX-ACCESS  read-only
    STATUS  current
    DESCRIPTION
        "The number of PPPoE PADS transmitted"
    ::= { pPPoEBindingsEntry 10 }

pPPoEBindingsNumberPADTReceived   OBJECT-TYPE
    SYNTAX  Counter32
    MAX-ACCESS  read-only
    STATUS  current
    DESCRIPTION
        "The number of PPPoE PADT received"
    ::= { pPPoEBindingsEntry 11 }

pPPoEBindingsNumberPADTTransmitted   OBJECT-TYPE
    SYNTAX  Counter32
    MAX-ACCESS  read-only
    STATUS  current
    DESCRIPTION
        "The number of PPPoE PADT transmitted"
    ::= { pPPoEBindingsEntry 12 }

pPPoEBindingsNumberServiceNameErrors   OBJECT-TYPE
    SYNTAX  Counter32
    MAX-ACCESS  read-only
    STATUS  current
    DESCRIPTION
        "The number of PPPoE Service-Name-Error tags
        received/transmitted"
    ::= { pPPoEBindingsEntry 13 }

pPPoEBindingsNumberACSystemErrors   OBJECT-TYPE
    SYNTAX  Counter32
    MAX-ACCESS  read-only
    STATUS  current
    DESCRIPTION
        "The number of PPPoE AC-System-Error tags
        received/transmitted"
    ::= { pPPoEBindingsEntry 14 }

pPPoEBindingsNumberGenericErrorsReceived   OBJECT-TYPE
    SYNTAX  Counter32
    MAX-ACCESS  read-only
    STATUS  current
    DESCRIPTION
        "The number of PPPoE Generic-Error tags received"
    ::= { pPPoEBindingsEntry 15 }

pPPoEBindingsNumberGenericErrorsTransmitted   OBJECT-TYPE
    SYNTAX  Counter32
    MAX-ACCESS  read-only
    STATUS  current
    DESCRIPTION
        "The number of PPPoE Generic-Error tags transmitted"
    ::= { pPPoEBindingsEntry 16 }

pPPoEBindingsNumberMalformedPackets   OBJECT-TYPE
    SYNTAX  Counter32
    MAX-ACCESS  read-only
    STATUS  current
    DESCRIPTION
        "The number of malformed PPPoE packets received"
    ::= { pPPoEBindingsEntry 17 }

pPPoEBindingsNumberPADITimeouts   OBJECT-TYPE
    SYNTAX  Counter32
    MAX-ACCESS  read-only
    STATUS  current
    DESCRIPTION
        "The number of PPPoE timeouts waiting for a response
        to a PADI"
    ::= { pPPoEBindingsEntry 18 }

pPPoEBindingsNumberMultiplePADOReceived   OBJECT-TYPE
    SYNTAX  Counter32
    MAX-ACCESS  read-only
    STATUS  current
    DESCRIPTION
        "The number of PPPoE multiple PADO's received after a
        PADI request"
    ::= { pPPoEBindingsEntry 19 }



-- The PPPoE sessions table

pPPoESessionTable OBJECT-TYPE
    SYNTAX    SEQUENCE OF PPPoESessionEntry
    MAX-ACCESS not-accessible
    STATUS current
    DESCRIPTION
        "This table lists the PPPoE sessions established in
        the device"
    ::= { pPPoESession 1 }

pPPoESessionEntry OBJECT-TYPE
    SYNTAX          PPPoESessionEntry
    MAX-ACCESS      not-accessible
    STATUS          current
    DESCRIPTION
        "Table of PPPoE sessions in the device"
    INDEX           { pPPoESessionIfIndex}
    ::= { pPPoESessionTable 1 }

PPPoESessionEntry ::= SEQUENCE {
    pPPoESessionIfIndex InterfaceIndex,
    pPPoESessionID Integer32,
    pPPoESessionPeerAddress DisplayString,
    pPPoESessionState INTEGER }

pPPoESessionIfIndex OBJECT-TYPE
    SYNTAX          InterfaceIndex
    MAX-ACCESS      read-only
    STATUS          current
    DESCRIPTION
        "The value for this object is equal to the value of
        ifIndex of the Interfaces MIB for the PPPoE interface
        instantiated for this session."
    ::= { pPPoESessionEntry 1 }

pPPoESessionID OBJECT-TYPE
    SYNTAX          Integer32
    MAX-ACCESS      read-only
    STATUS          current
    DESCRIPTION
        "This object contains the session identifier for this
        session as assigned by the AC in the PADS message."
    ::= { pPPoESessionEntry 2 }

pPPoESessionPeerAddress  OBJECT-TYPE
    SYNTAX          DisplayString
    MAX-ACCESS      read-only
    STATUS          current
    DESCRIPTION
        "This object contains the MAC address for the session
        peer."
    ::= { pPPoESessionEntry 3 }

pPPoESessionState OBJECT-TYPE
    SYNTAX          INTEGER {
                            noState(1),
                            pADISent(2),
                            pADIRcvd(3),
                            pADOSent(4),
                            pADORcvd(5),
                            pADRSent(6),
                            pADRRcvd(7),
                            pADSSent(8),
                            pADSRcvd(9),
                            sessionStage(10) }
    MAX-ACCESS      read-only
    STATUS          current
    DESCRIPTION
        "This object contains the session state for this
        session"
    ::= { pPPoESessionEntry 4 }

-- Conformance Definitions

pPPoEConformanceGroups         OBJECT IDENTIFIER
    ::= { pPPoEConformance 1 }
pPPoECompliances               OBJECT IDENTIFIER
    ::= { pPPoEConformance 2 }

  -- compliance statements

pPPoECompliance MODULE-COMPLIANCE
      STATUS  current
      DESCRIPTION
        "The compliance statement for agents that support the
        PPPOE-MIB."
      MODULE -- this module

      MANDATORY-GROUPS { pPPoEGeneralConformanceGroup }

      GROUP pPPoEHostConformanceGroup
      DESCRIPTION
        "This group of objects is mandatory for the Host side
        implementation of PPPoE."

      GROUP pPPoEACConformanceGroup
      DESCRIPTION
        "This group of objects is mandatory for the AC side
        implementation of PPPoE."

      OBJECT  pPPoEConfigMaxTotalSessions
      MIN-ACCESS  read-only
      DESCRIPTION
        " The agent is not required to allow the user to
        change the quantity of the maximum quantity of
        allowed sessions.  This may be due to the
        implementation of the system.
        The agent is not required to support a SET operation
        to this object in the absence of adequate security."

      OBJECT        pPPoEConfigMaxSessionsPerHost
      MIN-ACCESS    read-only
      DESCRIPTION
        " The agent is not required to allow the user to
        change the quantity of the maximum quantity of
        allowed sessions.  This may be due to the
        implementation of the system.
        The agent is not required to support a SET operation
        to this object in the absence of adequate security."

      OBJECT    pPPoEConfigPADITxInterval
      MIN-ACCESS  read-only
      DESCRIPTION
        " The agent is not required to allow the user to
        change the quantity of the maximum quantity of
        allowed sessions.  This may be due to the
        implementation of the system.
        The agent is not required to support a SET operation
        to this object in the absence of adequate security."

      OBJECT    pPPoEConfigPADIMaxNumberOfRetries
      MIN-ACCESS read-only
      DESCRIPTION
        "The agent is not required to support a SET operation
        to this object in the absence of adequate security."

      OBJECT pPPoEConfigServiceName
      MIN-ACCESS read-only
      DESCRIPTION
        "The agent is not required to support a SET operation
        to this object in the absence of adequate security."

      OBJECT pPPoEConfigServiceRowStatus
      MIN-ACCESS read-only
      DESCRIPTION
        "The agent is not required to support a SET operation
        to this object in the absence of adequate security."

      OBJECT pPPoEBindingsEnabled
      MIN-ACCESS read-only
      DESCRIPTION
        "The agent is not required to support a SET operation
        to this object in the absence of adequate security."
      ::= { pPPoECompliances 1 }

-- units of conformance

pPPoEGeneralConformanceGroup OBJECT-GROUP
      OBJECTS {
      pPPoEBindingsEnabled,
      pPPoEBindingsNumberActiveSessions,
      pPPoEBindingsTotalNumberSessions,
      pPPoEBindingsNumberPADTReceived,
      pPPoEBindingsNumberPADTTransmitted,
      pPPoEBindingsNumberGenericErrorsReceived,
      pPPoEBindingsNumberGenericErrorsTransmitted,
      pPPoEBindingsNumberMalformedPackets,
      pPPoESessionID,
      pPPoESessionPeerAddress,
      pPPoESessionState,
      pPPoEConfigServiceName,
      pPPoEConfigServiceRowStatus }
      STATUS current
      DESCRIPTION
        "This group is mandatory for all PPPoE entities."
              ::= { pPPoEConformanceGroups 1 }

pPPoEHostConformanceGroup OBJECT-GROUP
      OBJECTS {
      pPPoEBindingsNumberPADITimeouts,
      pPPoEBindingsNumberMultiplePADOReceived
      }
      STATUS  current
      DESCRIPTION

        "This group is mandatory for all Host entities."
      ::= { pPPoEConformanceGroups 2 }

pPPoEACConformanceGroup OBJECT-GROUP
      OBJECTS {
      pPPoEBindingsNumberPADIRejected,
      pPPoEBindingsNumberPADIReceived,
      pPPoEBindingsNumberPADRRejected,
      pPPoEBindingsNumberPADRReceived,
      pPPoEBindingsNumberPADOTransmitted,
      pPPoEBindingsNumberPADSTransmitted,
      pPPoEBindingsNumberServiceNameErrors,
      pPPoEBindingsNumberACSystemErrors }
      STATUS current
      DESCRIPTION

        "This group is mandatory for all AC entities."
      ::= { pPPoEConformanceGroups 3 }

END         -- End Template MIB definitions 4.0 References
