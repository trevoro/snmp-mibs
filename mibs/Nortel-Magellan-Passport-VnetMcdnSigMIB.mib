Nortel-Magellan-Passport-VnetMcdnSigMIB
DEFINITIONS ::= BEGIN



IMPORTS

      OBJECT-TYPE
   FROM RFC-1212

      passportMIBs
   FROM Nortel-Magellan-Passport-UsefulDefinitionsMIB

      Counter32,
      DisplayString,
      StorageType,
      RowStatus,
      Unsigned32
   FROM Nortel-Magellan-Passport-StandardTextualConventionsMIB

      NonReplicated,
      Link
   FROM Nortel-Magellan-Passport-TextualConventionsMIB

      sigChanIndex,
      sigChan
   FROM Nortel-Magellan-Passport-VoiceNetworkingMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VnetMcdnSig Enterprise MIB."

vnetMcdnSigMIB OBJECT IDENTIFIER ::= { passportMIBs 142 }










-- SigChan/n McdnSig
-- The McdnSig component defines the operational characteristics of 
-- the signalling channel's connection to the external equipment. This 
-- is the proprietary MCDN protocol as based on Nortel specification 
-- TR-88-5003.

sigChanMcdn OBJECT IDENTIFIER ::= { sigChan 17 }



sigChanMcdnRowStatusTable OBJECT-TYPE
   SYNTAX     SEQUENCE OF SigChanMcdnRowStatusEntry
   ACCESS     not-accessible
   STATUS     mandatory
   DESCRIPTION
     "This entry controls the addition and deletion of 
      sigChanMcdn components."
::= { sigChanMcdn 1 }

sigChanMcdnRowStatusEntry OBJECT-TYPE
   SYNTAX     SigChanMcdnRowStatusEntry
   ACCESS     not-accessible
   STATUS     mandatory
   DESCRIPTION
     "A single entry in the table represents a single 
      sigChanMcdn component."
   INDEX {
      sigChanIndex,
      sigChanMcdnIndex }
::= { sigChanMcdnRowStatusTable 1 }

SigChanMcdnRowStatusEntry ::= SEQUENCE {
   sigChanMcdnRowStatus
      RowStatus,
   sigChanMcdnComponentName
      DisplayString,
   sigChanMcdnStorageType
      StorageType,
   sigChanMcdnIndex
      NonReplicated }

sigChanMcdnRowStatus OBJECT-TYPE
   SYNTAX     RowStatus 
   ACCESS     read-write
   STATUS     mandatory
   DESCRIPTION
     "This variable is used as the basis for SNMP naming of
      sigChanMcdn components.
      These components can be added and deleted."
::= { sigChanMcdnRowStatusEntry 1 }

sigChanMcdnComponentName OBJECT-TYPE
   SYNTAX     DisplayString 
   ACCESS     read-only
   STATUS     mandatory
   DESCRIPTION
     "This variable provides the component's string name for
      use with the ASCII Console Interface"
::= { sigChanMcdnRowStatusEntry 2 }

sigChanMcdnStorageType OBJECT-TYPE
   SYNTAX     StorageType 
   ACCESS     read-only
   STATUS     mandatory
   DESCRIPTION
     "This variable represents the storage type value for the
      sigChanMcdn tables."
::= { sigChanMcdnRowStatusEntry 4 }

sigChanMcdnIndex OBJECT-TYPE
   SYNTAX     NonReplicated 
   ACCESS     not-accessible
   STATUS     mandatory
   DESCRIPTION
     "This variable represents the index for the sigChanMcdn tables."
::= { sigChanMcdnRowStatusEntry 10 }

sigChanMcdnL2Table OBJECT-TYPE
   SYNTAX     SEQUENCE OF SigChanMcdnL2Entry
   ACCESS     not-accessible
   STATUS     mandatory
   DESCRIPTION
     "This group specifies the provisionable layer 2 attributes of the 
      Q.931 ITU-T protocol."
::= { sigChanMcdn 11 }

sigChanMcdnL2Entry OBJECT-TYPE
   SYNTAX     SigChanMcdnL2Entry
   ACCESS     not-accessible
   STATUS     mandatory
   DESCRIPTION
     "An entry in the sigChanMcdnL2Table."
   INDEX {
      sigChanIndex,
      sigChanMcdnIndex }
::= { sigChanMcdnL2Table 1 }

SigChanMcdnL2Entry ::= SEQUENCE {
   sigChanMcdnT23
      Unsigned32,
   sigChanMcdnT200
      Unsigned32,
   sigChanMcdnN200
      Unsigned32,
   sigChanMcdnT203
      Unsigned32,
   sigChanMcdnCircuitSwitchedK
      Unsigned32 }

sigChanMcdnT23 OBJECT-TYPE
   SYNTAX     Unsigned32 (1..15)
   ACCESS     read-write
   STATUS     mandatory
   DESCRIPTION
     "This attribute specifies the layer 2 enable request timer."
   DEFVAL     { 10 }
::= { sigChanMcdnL2Entry 1 }

sigChanMcdnT200 OBJECT-TYPE
   SYNTAX     Unsigned32 (1..20)
   ACCESS     read-write
   STATUS     mandatory
   DESCRIPTION
     "This attribute specifies the maximum time between a layer 2 frame 
      and its acknowledgment."
   DEFVAL     { 1 }
::= { sigChanMcdnL2Entry 2 }

sigChanMcdnN200 OBJECT-TYPE
   SYNTAX     Unsigned32 (1..8)
   ACCESS     read-write
   STATUS     mandatory
   DESCRIPTION
     "This attribute specifies the maximum number of re-transmissions of 
      a layer 2 frame."
   DEFVAL     { 3 }
::= { sigChanMcdnL2Entry 3 }

sigChanMcdnT203 OBJECT-TYPE
   SYNTAX     Unsigned32 (2..40)
   ACCESS     read-write
   STATUS     mandatory
   DESCRIPTION
     "This attribute specifies the maximum time for which layer 2 frames 
      may be absent. Expiry triggers a check on whether the far end is 
      alive."
   DEFVAL     { 10 }
::= { sigChanMcdnL2Entry 4 }

sigChanMcdnCircuitSwitchedK OBJECT-TYPE
   SYNTAX     Unsigned32 (1..127)
   ACCESS     read-write
   STATUS     mandatory
   DESCRIPTION
     "This attribute specifies the maximum number of sequentially 
      numbered I frames (that is, window size (k)) that may be 
      unacknowledged at any given time for a SAP supporting primary 
      rate (64kbit/sec) signalling."
   DEFVAL     { 7 }
::= { sigChanMcdnL2Entry 6 }

sigChanMcdnL3Table OBJECT-TYPE
   SYNTAX     SEQUENCE OF SigChanMcdnL3Entry
   ACCESS     not-accessible
   STATUS     mandatory
   DESCRIPTION
     "This group represents the provisionable Layer 3 timer attributes of 
      the MCDN signalling protocol."
::= { sigChanMcdn 12 }

sigChanMcdnL3Entry OBJECT-TYPE
   SYNTAX     SigChanMcdnL3Entry
   ACCESS     not-accessible
   STATUS     mandatory
   DESCRIPTION
     "An entry in the sigChanMcdnL3Table."
   INDEX {
      sigChanIndex,
      sigChanMcdnIndex }
::= { sigChanMcdnL3Table 1 }

SigChanMcdnL3Entry ::= SEQUENCE {
   sigChanMcdnT302
      Unsigned32,
   sigChanMcdnT304
      Unsigned32,
   sigChanMcdnT309
      Unsigned32,
   sigChanMcdnT310
      Unsigned32,
   sigChanMcdnT316
      Unsigned32,
   sigChanMcdnT317
      Unsigned32 }

sigChanMcdnT302 OBJECT-TYPE
   SYNTAX     Unsigned32 (10..30)
   ACCESS     read-write
   STATUS     mandatory
   DESCRIPTION
     "This attribute specifies the overlap receiving timer; in a UNI, this is 
      network to user, but for Peer to Peer it is all incoming calls. This 
      attribute is ignored if overlap signalling is disabled."
   DEFVAL     { 15 }
::= { sigChanMcdnL3Entry 1 }

sigChanMcdnT304 OBJECT-TYPE
   SYNTAX     Unsigned32 (10..30)
   ACCESS     read-write
   STATUS     mandatory
   DESCRIPTION
     "This attribute specifies the overlap sending timer; in a UNI, this is 
      user to network, but for Peer to Peer it is all outgoing calls. This 
      attribute is ignored if overlap signalling is disabled."
   DEFVAL     { 10 }
::= { sigChanMcdnL3Entry 2 }

sigChanMcdnT309 OBJECT-TYPE
   SYNTAX     Unsigned32 (15..120)
   ACCESS     read-write
   STATUS     mandatory
   DESCRIPTION
     "This attribute specifies the data link disconnect timer; used to ride 
      out temporary failures."
   DEFVAL     { 90 }
::= { sigChanMcdnL3Entry 3 }

sigChanMcdnT310 OBJECT-TYPE
   SYNTAX     Unsigned32 (10..120)
   ACCESS     read-write
   STATUS     mandatory
   DESCRIPTION
     "This attribute specifies the call proceeding state timer."
   DEFVAL     { 10 }
::= { sigChanMcdnL3Entry 4 }

sigChanMcdnT316 OBJECT-TYPE
   SYNTAX     Unsigned32 (31..180)
   ACCESS     read-write
   STATUS     mandatory
   DESCRIPTION
     "This attribute specifies the restart request response timer.
      It must be set greater than t317."
   DEFVAL     { 120 }
::= { sigChanMcdnL3Entry 5 }

sigChanMcdnT317 OBJECT-TYPE
   SYNTAX     Unsigned32 (30..179)
   ACCESS     read-only
   STATUS     mandatory
   DESCRIPTION
     "This attribute specifies the restart operation timer, used when a 
      RESTART was received."
   DEFVAL     { 30 }
::= { sigChanMcdnL3Entry 6 }

sigChanMcdnProvTable OBJECT-TYPE
   SYNTAX     SEQUENCE OF SigChanMcdnProvEntry
   ACCESS     not-accessible
   STATUS     mandatory
   DESCRIPTION
     "This group defines the general options of the D-channel signalling 
      link."
::= { sigChanMcdn 13 }

sigChanMcdnProvEntry OBJECT-TYPE
   SYNTAX     SigChanMcdnProvEntry
   ACCESS     not-accessible
   STATUS     mandatory
   DESCRIPTION
     "An entry in the sigChanMcdnProvTable."
   INDEX {
      sigChanIndex,
      sigChanMcdnIndex }
::= { sigChanMcdnProvTable 1 }

SigChanMcdnProvEntry ::= SEQUENCE {
   sigChanMcdnSide
      INTEGER,
   sigChanMcdnMaxNonCallConcurrent
      Unsigned32,
   sigChanMcdnOverlapSending
      INTEGER,
   sigChanMcdnOverlapReceiving
      INTEGER,
   sigChanMcdnChanMaintenanceHandling
      INTEGER }

sigChanMcdnSide OBJECT-TYPE
   SYNTAX     INTEGER  {
                 network(1),
                 user(2) }
   ACCESS     read-write
   STATUS     mandatory
   DESCRIPTION
     "This attribute specifies whether the interface provides layer 2 and 3 
      services equivalent to the ITU-T network or user side of the 
      connection. If this attribute is set to network, then the interface is 
      master during channel negotiation, and uses network side layer 2 
      command/response bits. If this attribute is set to user, then the 
      interface is slave during channel negotiation, and uses user side 
      layer 2 command/response bits.
      Note that although a peer to peer protocol has no true network or 
      user side, for channel negotiation and layer 2 handling the peer to 
      peer and UNI protocols have identical function. A true UNI may 
      also have uni-directional messages and/or message elements; the 
      peer to peer has all elements bidirectional."
   DEFVAL     { network }
::= { sigChanMcdnProvEntry 1 }

sigChanMcdnMaxNonCallConcurrent OBJECT-TYPE
   SYNTAX     Unsigned32 (1..30)
   ACCESS     read-write
   STATUS     mandatory
   DESCRIPTION
     "This attribute specifies the maximum number of simultaneous active 
      non-call transactions that are allowed."
   DEFVAL     { 30 }
::= { sigChanMcdnProvEntry 2 }

sigChanMcdnOverlapSending OBJECT-TYPE
   SYNTAX     INTEGER  {
                 enabled(0),
                 disabled(1) }
   ACCESS     read-write
   STATUS     mandatory
   DESCRIPTION
     "This attribute specifies whether overlap sending to the PBX is 
      enabled."
   DEFVAL     { enabled }
::= { sigChanMcdnProvEntry 3 }

sigChanMcdnOverlapReceiving OBJECT-TYPE
   SYNTAX     INTEGER  {
                 enabled(0),
                 disabled(1) }
   ACCESS     read-write
   STATUS     mandatory
   DESCRIPTION
     "This attribute specifies whether overlap receiving from the PBX is 
      enabled."
   DEFVAL     { enabled }
::= { sigChanMcdnProvEntry 4 }

sigChanMcdnChanMaintenanceHandling OBJECT-TYPE
   SYNTAX     INTEGER  {
                 globalOnStartup(0),
                 serviceMessage(1),
                 restartMessage(2) }
   ACCESS     read-write
   STATUS     mandatory
   DESCRIPTION
     "This attribute specifies handling of channel maintenance events 
      such as locking and unlocking a channel or channel registration on 
      start-up. The decision here is whether to send individual channel 
      RESTART messages, SERVICE messages, or nothing. Note that 
      channel registration only occurs after the global interface restart at 
      startup.
      
      The attribute controls start-up handling absolutely, and channel lock 
      and unlock conditionally. That is, setting this to enable SERVICE 
      messages ensures SERVICE messages at start-up and whenever a 
      channel goes into or out of service. However, if this is not set to 
      enable SERVICE messaging, a RESTART is always sent on 
      unlocking a channel. 
      
      globalOnStartup provides the minimum required function at start-
      up, without any individual channel confirmation. Note that when 
      this is set, channel RESTART is still used for channel unlock. 
      globalOnStartup applies to SigChan start-up only.
      
      serviceMessage enables sending and receiving SERVICE messages. 
      If enabled, SERVICE messages are always used for channel 
      maintenance on channel lock, channel unlock and start-up.
      
      restartMessage provides individual channel RESTARTs when a 
      SigChan starts up. If enabled, the RESTART is used at start-up and 
      channel unlock. However, if both SERVICE and RESTART 
      messages are disabled, the RESTART will still be used when a 
      channel unlocks."
   DEFVAL     { restartMessage }
::= { sigChanMcdnProvEntry 5 }

sigChanMcdnStateTable OBJECT-TYPE
   SYNTAX     SEQUENCE OF SigChanMcdnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanMcdn 14 }

sigChanMcdnStateEntry OBJECT-TYPE
   SYNTAX     SigChanMcdnStateEntry
   ACCESS     not-accessible
   STATUS     mandatory
   DESCRIPTION
     "An entry in the sigChanMcdnStateTable."
   INDEX {
      sigChanIndex,
      sigChanMcdnIndex }
::= { sigChanMcdnStateTable 1 }

SigChanMcdnStateEntry ::= SEQUENCE {
   sigChanMcdnAdminState
      INTEGER,
   sigChanMcdnOperationalState
      INTEGER,
   sigChanMcdnUsageState
      INTEGER }

sigChanMcdnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanMcdnStateEntry 1 }

sigChanMcdnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanMcdnStateEntry 2 }

sigChanMcdnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanMcdnStateEntry 3 }

sigChanMcdnStatsTable OBJECT-TYPE
   SYNTAX     SEQUENCE OF SigChanMcdnStatsEntry
   ACCESS     not-accessible
   STATUS     mandatory
   DESCRIPTION
     "This group provides the operational components for the McdnSig 
      component."
::= { sigChanMcdn 15 }

sigChanMcdnStatsEntry OBJECT-TYPE
   SYNTAX     SigChanMcdnStatsEntry
   ACCESS     not-accessible
   STATUS     mandatory
   DESCRIPTION
     "An entry in the sigChanMcdnStatsTable."
   INDEX {
      sigChanIndex,
      sigChanMcdnIndex }
::= { sigChanMcdnStatsTable 1 }

SigChanMcdnStatsEntry ::= SEQUENCE {
   sigChanMcdnTotalCallsToIf
      Counter32,
   sigChanMcdnTotalCallsFromIf
      Counter32,
   sigChanMcdnNonCallAssocSessionsToIf
      Counter32,
   sigChanMcdnNonCallAssocSessionsFromIf
      Counter32 }

sigChanMcdnTotalCallsToIf OBJECT-TYPE
   SYNTAX     Counter32 
   ACCESS     read-only
   STATUS     mandatory
   DESCRIPTION
     "This attribute counts the total number of calls that have been made 
      to the interface. The value wraps when it reaches its maximum."
::= { sigChanMcdnStatsEntry 2 }

sigChanMcdnTotalCallsFromIf OBJECT-TYPE
   SYNTAX     Counter32 
   ACCESS     read-only
   STATUS     mandatory
   DESCRIPTION
     "This attribute counts the total number of calls from the interface. 
      The value wraps when it reaches its maximum."
::= { sigChanMcdnStatsEntry 3 }

sigChanMcdnNonCallAssocSessionsToIf OBJECT-TYPE
   SYNTAX     Counter32 
   ACCESS     read-only
   STATUS     mandatory
   DESCRIPTION
     "This attribute counts the total number of non-call associated 
      sessions to the interface. The value wraps when it reaches its 
      maximum."
::= { sigChanMcdnStatsEntry 4 }

sigChanMcdnNonCallAssocSessionsFromIf OBJECT-TYPE
   SYNTAX     Counter32 
   ACCESS     read-only
   STATUS     mandatory
   DESCRIPTION
     "This attribute counts the total number of non-call associated 
      sessions from the interface. The value wraps when it reaches its 
      maximum."
::= { sigChanMcdnStatsEntry 5 }

sigChanMcdnOperTable OBJECT-TYPE
   SYNTAX     SEQUENCE OF SigChanMcdnOperEntry
   ACCESS     not-accessible
   STATUS     mandatory
   DESCRIPTION
     "This group provides the operational attributes for the MCDN 
      signalling."
::= { sigChanMcdn 16 }

sigChanMcdnOperEntry OBJECT-TYPE
   SYNTAX     SigChanMcdnOperEntry
   ACCESS     not-accessible
   STATUS     mandatory
   DESCRIPTION
     "An entry in the sigChanMcdnOperTable."
   INDEX {
      sigChanIndex,
      sigChanMcdnIndex }
::= { sigChanMcdnOperTable 1 }

SigChanMcdnOperEntry ::= SEQUENCE {
   sigChanMcdnActiveChannels
      Unsigned32,
   sigChanMcdnActiveVoiceChannels
      Unsigned32,
   sigChanMcdnActiveDataChannels
      Unsigned32,
   sigChanMcdnPeakActiveChannels
      Unsigned32,
   sigChanMcdnPeakActiveVoiceChannels
      Unsigned32,
   sigChanMcdnPeakActiveDataChannels
      Unsigned32,
   sigChanMcdnDChanStatus
      INTEGER }

sigChanMcdnActiveChannels OBJECT-TYPE
   SYNTAX     Unsigned32 (0..128)
   ACCESS     read-only
   STATUS     mandatory
   DESCRIPTION
     "This attribute indicates the number of currently active channels. 
      This includes data and voice channels."
   DEFVAL     { 0 }
::= { sigChanMcdnOperEntry 1 }

sigChanMcdnActiveVoiceChannels OBJECT-TYPE
   SYNTAX     Unsigned32 (0..128)
   ACCESS     read-only
   STATUS     mandatory
   DESCRIPTION
     "This attribute indicates the number of channels that are currently 
      carrying voice."
   DEFVAL     { 0 }
::= { sigChanMcdnOperEntry 2 }

sigChanMcdnActiveDataChannels OBJECT-TYPE
   SYNTAX     Unsigned32 (0..128)
   ACCESS     read-only
   STATUS     mandatory
   DESCRIPTION
     "This attribute indicates the number of channels that are currently 
      carrying data. This does not include modem data."
   DEFVAL     { 0 }
::= { sigChanMcdnOperEntry 3 }

sigChanMcdnPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { sigChanMcdnOperEntry 4 }

sigChanMcdnPeakActiveVoiceChannels OBJECT-TYPE
   SYNTAX     Unsigned32 (0..128)
   ACCESS     read-only
   STATUS     mandatory
   DESCRIPTION
     "This attribute indicates the maximum number of voice channels that 
      have been active on this signalling channel during the last polling 
      period."
   DEFVAL     { 0 }
::= { sigChanMcdnOperEntry 5 }

sigChanMcdnPeakActiveDataChannels OBJECT-TYPE
   SYNTAX     Unsigned32 (0..128)
   ACCESS     read-only
   STATUS     mandatory
   DESCRIPTION
     "This attribute indicates the maximum number of data channels that 
      have been active on this signalling channel during the last polling 
      period."
   DEFVAL     { 0 }
::= { sigChanMcdnOperEntry 6 }

sigChanMcdnDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { sigChanMcdnOperEntry 7 }

sigChanMcdnToolsTable OBJECT-TYPE
   SYNTAX     SEQUENCE OF SigChanMcdnToolsEntry
   ACCESS     not-accessible
   STATUS     mandatory
   DESCRIPTION
     "This contains a series of operational attributes which turn on and off 
      several kinds of tracing."
::= { sigChanMcdn 17 }

sigChanMcdnToolsEntry OBJECT-TYPE
   SYNTAX     SigChanMcdnToolsEntry
   ACCESS     not-accessible
   STATUS     mandatory
   DESCRIPTION
     "An entry in the sigChanMcdnToolsTable."
   INDEX {
      sigChanIndex,
      sigChanMcdnIndex }
::= { sigChanMcdnToolsTable 1 }

SigChanMcdnToolsEntry ::= SEQUENCE {
   sigChanMcdnTracing
      OCTET STRING,
   sigChanMcdnMessageTraced
      OCTET STRING,
   sigChanMcdnDirectionTraced
      OCTET STRING }

sigChanMcdnTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously.  
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { sigChanMcdnToolsEntry 1 }

sigChanMcdnMessageTraced OBJECT-TYPE
   SYNTAX     OCTET STRING (SIZE (4))
   ACCESS     read-write
   STATUS     mandatory
   DESCRIPTION
     "This attribute specifies the type of ISDN messages that are to be 
      traced.

      Description of bits:
      alerting(0)
      callProceeding(1)
      connectionlessFacility(2)
      congestionControl(3)
      connect(4)
      connectAcknowledge(5)
      disconnect(6)
      facility(7)
      facilityAcknowledge(8)
      facilityReject(9)
      information(10)
      notify(11)
      progress(12)
      register(13)
      releaseComp(14)
      release(15)
      restart(16)
      restartAcknowledge(17)
      service(18)
      serviceAcknowledge(19)
      setup(20)
      setupAcknowledge(21)
      status(22)
      statusEnquiry(23)
      userInformation(24)
      all(25)"
   DEFVAL     { 'ffffff80'H }
::= { sigChanMcdnToolsEntry 2 }

sigChanMcdnDirectionTraced OBJECT-TYPE
   SYNTAX     OCTET STRING (SIZE (1))
   ACCESS     read-write
   STATUS     mandatory
   DESCRIPTION
     "This attribute indicates whether the incoming (from PBX), outgoing 
      (to PBX), or both incoming and outgoing messages are traced.

      Description of bits:
      incoming(0)
      outgoing(1)"
   DEFVAL     { 'c0'H }
::= { sigChanMcdnToolsEntry 3 }

sigChanMcdnClsTable OBJECT-TYPE
   SYNTAX     SEQUENCE OF SigChanMcdnClsEntry
   ACCESS     not-accessible
   STATUS     mandatory
   DESCRIPTION
     "This group enables and disables the support of the MCDN 
      proprietary signalling for connectionless features on the local 
      signalling channel."
::= { sigChanMcdn 18 }

sigChanMcdnClsEntry OBJECT-TYPE
   SYNTAX     SigChanMcdnClsEntry
   ACCESS     not-accessible
   STATUS     mandatory
   DESCRIPTION
     "An entry in the sigChanMcdnClsTable."
   INDEX {
      sigChanIndex,
      sigChanMcdnIndex }
::= { sigChanMcdnClsTable 1 }

SigChanMcdnClsEntry ::= SEQUENCE {
   sigChanMcdnClsFeaturesSupported
      OCTET STRING }

sigChanMcdnClsFeaturesSupported OBJECT-TYPE
   SYNTAX     OCTET STRING (SIZE (2))
   ACCESS     read-write
   STATUS     mandatory
   DESCRIPTION
     "This attribute specifies the features to be supported by MCDN 
      'TCAP' connectionless messaging. Note that some features such as 
      Network ACD combine connectionless and connection oriented. In 
      the NACD case, the connectionless messaging enables the source 
      and target PBXs to establish the networked relationship, and calls 
      sent across the network (connection oriented) will contain basic 
      information relating the call to the feature.
      
      Feature Definitions:
      networkAcd: transfer of a call from a pool of agents to a second 
      pool of agents across the network.
      networkMessageService: message waiting capability (for example, 
      lamps on sets). Also includes signalling for voice mail, but is not 
      limited to voice mail.
      networkVoiceMail: a specific subset of Network Message Service, 
      separated functionally as it always terminates on an interactive 
      voice response mailbox application.
      networkRingAgain: ring again to remote sets.
      electronicLock: change of set capabilities by a remote user dialling 
      the applicable code and password.
      remoteCallForward: call forwarding a phone via applicable code 
      and password.
      callPickupNetworkWide (call pickup world wide): scan for a 
      ringing call on another node, to enable the scanning set to pick up 
      the call.
      networkPackage1: a collection of other features including but not 
      limited to network clock synchronization. Note that on the Meridian 
      1, this is a general purpose group used for very small features not 
      requiring a new ISDN Facility feature type.
      isdnApplicationInterface: network wide support of a number of 
      Meridian 1 Application Module Link features.
      mobilityMultisiteNetworking: the capability to use a wireless phone 
      in multiple sites, by having the phone register on arrival at the new 
      site, and having the PBX at the new site negotiate the set 
      'relocation' with the base PBX.
      miscellaneous: Any feature that is not listed above.

      Description of bits:
      networkAcd(0)
      networkMessageService(1)
      networkRingAgain(2)
      networkVoiceMail(3)
      electronicLock(4)
      remoteCallForward(5)
      callPickupWorldWide(6)
      networkPackage1(7)
      isdnApplicationInterface(8)
      mobilityMultisiteNetworking(9)
      notused10(10)
      notused11(11)
      notused12(12)
      notused13(13)
      notused14(14)
      miscellaneous(15)"
   DEFVAL     { 'ffc1'H }
::= { sigChanMcdnClsEntry 2 }

sigChanMcdnCoTable OBJECT-TYPE
   SYNTAX     SEQUENCE OF SigChanMcdnCoEntry
   ACCESS     not-accessible
   STATUS     mandatory
   DESCRIPTION
     "This group enables and disables the support of the MCDN 
      proprietary signalling for the listed features on the local signalling 
      channel."
::= { sigChanMcdn 19 }

sigChanMcdnCoEntry OBJECT-TYPE
   SYNTAX     SigChanMcdnCoEntry
   ACCESS     not-accessible
   STATUS     mandatory
   DESCRIPTION
     "An entry in the sigChanMcdnCoTable."
   INDEX {
      sigChanIndex,
      sigChanMcdnIndex }
::= { sigChanMcdnCoTable 1 }

SigChanMcdnCoEntry ::= SEQUENCE {
   sigChanMcdnDropBackCongestion
      INTEGER,
   sigChanMcdnNetworkNameDisplay
      OCTET STRING,
   sigChanMcdnMultisiteBusinessGroup
      INTEGER,
   sigChanMcdnConOrFeaturesSupported
      OCTET STRING }

sigChanMcdnDropBackCongestion OBJECT-TYPE
   SYNTAX     INTEGER  {
                 noDropBackAllowed(0),
                 dropBackToOriginator(1),
                 dropBackToPriorNode(2) }
   ACCESS     read-write
   STATUS     mandatory
   DESCRIPTION
     "This attribute specifies if the Meridian 1 Drop Back Congestion 
      Handling for trunks is enabled, and what type is being supported."
   DEFVAL     { noDropBackAllowed }
::= { sigChanMcdnCoEntry 1 }

sigChanMcdnNetworkNameDisplay OBJECT-TYPE
   SYNTAX     OCTET STRING (SIZE (1))
   ACCESS     read-write
   STATUS     mandatory
   DESCRIPTION
     "This attribute specifies what Name Display is supported.
      
      nd1 corresponds to the Meridian 1 RCAP (Remote CAPability) 
      nd1. This translates as caller provides name info in SETUP, ringing 
      party name in ALERTING, redirection name in NOTIFY, and 
      answering party name in CONNECT (as applicable, and if the name 
      changes).
      
      nd2 corresponds to the Meridian 1 RCAP (Remote CAPability) 
      nd2. This translates as caller provides name info in SETUP, 
      answering party provides name in NOTIFY on answer.
      
      nd3 corresponds to the Meridian 1 RCAP (Remote CAPability) 
      nd3, which is nd1 plus name information in call clearing messages 
      (busy user, etc.) where a specific user was found but either could not 
      answer or cleared the call. This corresponds to the QSIG name 
      display.

      Description of bits:
      nameDisplay1(0)
      nameDisplay2(1)
      nameDisplay3(2)"
::= { sigChanMcdnCoEntry 4 }

sigChanMcdnMultisiteBusinessGroup OBJECT-TYPE
   SYNTAX     INTEGER  {
                 transport(0),
                 discard(1) }
   ACCESS     read-write
   STATUS     mandatory
   DESCRIPTION
     "This attribute specifies whether to enable transport for the 
      Meridian 1 Multisite Business Group IE. The Meridian 1 allows 
      multiple 'Tenants' to exist on a single PBX. These Tenants have 
      limited access to each other and to system resources.   That is, users 
      associated with 'Tenant group one' cannot use trunks, attendants, 
      and features from another group, and so forth. The Multi-Site 
      Business Group is a single Tenant existing on more than one PBX.   
      As an example, 'tenant one' on a PBX may 'own' resources 
      belonging to 'tenant one' on another PBX.   The Multi-Site 
      Business Group IE as used in the Meridian 1 Network Tenant 
      Services feature enables linking the two tenants together."
   DEFVAL     { transport }
::= { sigChanMcdnCoEntry 7 }

sigChanMcdnConOrFeaturesSupported OBJECT-TYPE
   SYNTAX     OCTET STRING (SIZE (2))
   ACCESS     read-write
   STATUS     mandatory
   DESCRIPTION
     "This attribute indicates the features to be supported by MCDN 
      'ROSE' connection oriented messaging. 
      
      Feature Definitions:
      networkAttendantService: network wide support of Attendant 
      ('operator') services.
      classOfServiceTransport: this is not a ROSE feature. Class of 
      Service transport takes place in the called party number when 
      provisioned on the Meridian 1 to use an ESN signalling type.
      trunkRouteOptimization: dropping of redundant links in a call, 
      when a set call forwards a call prior to answer.
      remoteVirtualQueuing: queuing at a remote node without requiring 
      a B channel to be kept up.
      offHookQueuing: Queuing by maintaining the speech path to the 
      queuing node.
      networkCallTrace: call progress tracing across a network (that is, 
      call reached node a, node b, terminated at c,...).
      networkIntercom: network wide access to an intercom system onm 
      a Meridian 1.
      callPickupNetworkWide: connection oriented messages associated 
      with the TCAP call pickup scan operation. The messages that 
      actually pick up the ringing call.
      radioPaging: access to a radio paging system network wide, 
      allowing single radio paging facilities in a relatively dense local 
      PBX network.
      networkAccess: information to enable access to PBX features from 
      outside the network. Additional data is provided to identify access 
      capabilities for a spoecific call. (Similar to transmittiong 
      authorization code capabilities network wide.)
      antiTromboning: actually includes two capabilities - NAS 
      (Network Attendant Setvice) and Trunk Anti-Tromboning. Calls 
      that exit the subnet to a PBX and are transferred back to a network 
      number via the same D channel can be optimized. If PBX A 
      (Passport A) calls across the subnet to Passport B, D channel Z, to 
      PBX B, and PBX B transfers across D channel Z to Passport B and 
      therefore to PBX C/Passport C, this allows tha call to simplify to 
      PBX/Passport A to PBX/Passport C.
      miscellaneous: Any feature that is not listed above.

      Description of bits:
      networkAttendantService(0)
      classOfServiceTransport(1)
      trunkRouteOptimization(2)
      remoteVirtualQueuing(3)
      networkCallId(4)
      offHookQueuing(5)
      networkCallTrace(6)
      networkIntercom(7)
      callPickupNetworkWide(8)
      radioPaging(9)
      networkAccess(10)
      antiTromboning(11)
      miscellaneous(12)"
   DEFVAL     { 'fff8'H }
::= { sigChanMcdnCoEntry 8 }


-- SigChan/n Mcdn Framer
-- 
-- The Framer component controls link layer framing for application 
-- components sending and receiving data on a link interface. It is also 
-- through Framer, that an application component is associated with a 
-- specific hardware link interface.
-- 
-- The Framer component provides provisionable attributes related to 
-- data path aspects of the hardware interface (such as crc and frame 
-- length). The Framer component also provides a provisionable 
-- attribute which binds the application component to a specific 
-- hardware component.
-- 
-- The Framer component contains operational attributes for link 
-- interface data path statistics (such as frame counts and aborts).
-- 

sigChanMcdnFramer OBJECT IDENTIFIER ::= { sigChanMcdn 2 }



sigChanMcdnFramerRowStatusTable OBJECT-TYPE
   SYNTAX     SEQUENCE OF SigChanMcdnFramerRowStatusEntry
   ACCESS     not-accessible
   STATUS     mandatory
   DESCRIPTION
     "This entry controls the addition and deletion of 
      sigChanMcdnFramer components."
::= { sigChanMcdnFramer 1 }

sigChanMcdnFramerRowStatusEntry OBJECT-TYPE
   SYNTAX     SigChanMcdnFramerRowStatusEntry
   ACCESS     not-accessible
   STATUS     mandatory
   DESCRIPTION
     "A single entry in the table represents a single 
      sigChanMcdnFramer component."
   INDEX {
      sigChanIndex,
      sigChanMcdnIndex,
      sigChanMcdnFramerIndex }
::= { sigChanMcdnFramerRowStatusTable 1 }

SigChanMcdnFramerRowStatusEntry ::= SEQUENCE {
   sigChanMcdnFramerRowStatus
      RowStatus,
   sigChanMcdnFramerComponentName
      DisplayString,
   sigChanMcdnFramerStorageType
      StorageType,
   sigChanMcdnFramerIndex
      NonReplicated }

sigChanMcdnFramerRowStatus OBJECT-TYPE
   SYNTAX     RowStatus 
   ACCESS     read-only
   STATUS     mandatory
   DESCRIPTION
     "This variable is used as the basis for SNMP naming of
      sigChanMcdnFramer components.
      These components cannot be added nor deleted."
::= { sigChanMcdnFramerRowStatusEntry 1 }

sigChanMcdnFramerComponentName OBJECT-TYPE
   SYNTAX     DisplayString 
   ACCESS     read-only
   STATUS     mandatory
   DESCRIPTION
     "This variable provides the component's string name for
      use with the ASCII Console Interface"
::= { sigChanMcdnFramerRowStatusEntry 2 }

sigChanMcdnFramerStorageType OBJECT-TYPE
   SYNTAX     StorageType 
   ACCESS     read-only
   STATUS     mandatory
   DESCRIPTION
     "This variable represents the storage type value for the
      sigChanMcdnFramer tables."
::= { sigChanMcdnFramerRowStatusEntry 4 }

sigChanMcdnFramerIndex OBJECT-TYPE
   SYNTAX     NonReplicated 
   ACCESS     not-accessible
   STATUS     mandatory
   DESCRIPTION
     "This variable represents the index for the sigChanMcdnFramer tables."
::= { sigChanMcdnFramerRowStatusEntry 10 }

sigChanMcdnFramerProvTable OBJECT-TYPE
   SYNTAX     SEQUENCE OF SigChanMcdnFramerProvEntry
   ACCESS     not-accessible
   STATUS     mandatory
   DESCRIPTION
     "This group contains the base provisioning data for the Framer 
      component. Application or hardware interface specific provisioning 
      data is contained in other provisionable Framer groups."
::= { sigChanMcdnFramer 10 }

sigChanMcdnFramerProvEntry OBJECT-TYPE
   SYNTAX     SigChanMcdnFramerProvEntry
   ACCESS     not-accessible
   STATUS     mandatory
   DESCRIPTION
     "An entry in the sigChanMcdnFramerProvTable."
   INDEX {
      sigChanIndex,
      sigChanMcdnIndex,
      sigChanMcdnFramerIndex }
::= { sigChanMcdnFramerProvTable 1 }

SigChanMcdnFramerProvEntry ::= SEQUENCE {
   sigChanMcdnFramerInterfaceName
      Link }

sigChanMcdnFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { sigChanMcdnFramerProvEntry 1 }

sigChanMcdnFramerStateTable OBJECT-TYPE
   SYNTAX     SEQUENCE OF SigChanMcdnFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { sigChanMcdnFramer 12 }

sigChanMcdnFramerStateEntry OBJECT-TYPE
   SYNTAX     SigChanMcdnFramerStateEntry
   ACCESS     not-accessible
   STATUS     mandatory
   DESCRIPTION
     "An entry in the sigChanMcdnFramerStateTable."
   INDEX {
      sigChanIndex,
      sigChanMcdnIndex,
      sigChanMcdnFramerIndex }
::= { sigChanMcdnFramerStateTable 1 }

SigChanMcdnFramerStateEntry ::= SEQUENCE {
   sigChanMcdnFramerAdminState
      INTEGER,
   sigChanMcdnFramerOperationalState
      INTEGER,
   sigChanMcdnFramerUsageState
      INTEGER }

sigChanMcdnFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { sigChanMcdnFramerStateEntry 1 }

sigChanMcdnFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { sigChanMcdnFramerStateEntry 2 }

sigChanMcdnFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { sigChanMcdnFramerStateEntry 3 }

sigChanMcdnFramerStatsTable OBJECT-TYPE
   SYNTAX     SEQUENCE OF SigChanMcdnFramerStatsEntry
   ACCESS     not-accessible
   STATUS     mandatory
   DESCRIPTION
     "This group contains the operational statistics data for a Framer 
      component."
::= { sigChanMcdnFramer 13 }

sigChanMcdnFramerStatsEntry OBJECT-TYPE
   SYNTAX     SigChanMcdnFramerStatsEntry
   ACCESS     not-accessible
   STATUS     mandatory
   DESCRIPTION
     "An entry in the sigChanMcdnFramerStatsTable."
   INDEX {
      sigChanIndex,
      sigChanMcdnIndex,
      sigChanMcdnFramerIndex }
::= { sigChanMcdnFramerStatsTable 1 }

SigChanMcdnFramerStatsEntry ::= SEQUENCE {
   sigChanMcdnFramerFrmToIf
      Counter32,
   sigChanMcdnFramerFrmFromIf
      Counter32,
   sigChanMcdnFramerOctetFromIf
      Counter32,
   sigChanMcdnFramerAborts
      Counter32,
   sigChanMcdnFramerCrcErrors
      Counter32,
   sigChanMcdnFramerLrcErrors
      Counter32,
   sigChanMcdnFramerNonOctetErrors
      Counter32,
   sigChanMcdnFramerOverruns
      Counter32,
   sigChanMcdnFramerUnderruns
      Counter32,
   sigChanMcdnFramerLargeFrmErrors
      Counter32 }

sigChanMcdnFramerFrmToIf OBJECT-TYPE
   SYNTAX     Counter32 
   ACCESS     read-only
   STATUS     mandatory
   DESCRIPTION
     "This attribute counts the number of frames transmitted to the link 
      interface by Framer.
      This count wraps to zero after reaching its maximum value."
::= { sigChanMcdnFramerStatsEntry 1 }

sigChanMcdnFramerFrmFromIf OBJECT-TYPE
   SYNTAX     Counter32 
   ACCESS     read-only
   STATUS     mandatory
   DESCRIPTION
     "This attribute counts the number of frames received from the link 
      interface by Framer.
      This count wraps to zero after reaching its maximum value."
::= { sigChanMcdnFramerStatsEntry 2 }

sigChanMcdnFramerOctetFromIf OBJECT-TYPE
   SYNTAX     Counter32 
   ACCESS     read-only
   STATUS     mandatory
   DESCRIPTION
     "This attribute counts the number of bytes received from the link 
      interface by Framer. This count wraps to zero when it exceeds its 
      maximum value."
::= { sigChanMcdnFramerStatsEntry 3 }

sigChanMcdnFramerAborts OBJECT-TYPE
   SYNTAX     Counter32 
   ACCESS     read-only
   STATUS     mandatory
   DESCRIPTION
     "This attribute counts the total number of aborts received.
      This count wraps to zero after reaching its maximum value."
::= { sigChanMcdnFramerStatsEntry 4 }

sigChanMcdnFramerCrcErrors OBJECT-TYPE
   SYNTAX     Counter32 
   ACCESS     read-only
   STATUS     mandatory
   DESCRIPTION
     "This attribute counts the total number of frames with CRC errors.
      This count wraps to zero after reaching its maximum value."
::= { sigChanMcdnFramerStatsEntry 5 }

sigChanMcdnFramerLrcErrors OBJECT-TYPE
   SYNTAX     Counter32 
   ACCESS     read-only
   STATUS     mandatory
   DESCRIPTION
     "This attribute counts the total number of frames with LRC errors.
      This count wraps to zero after reaching its maximum value."
::= { sigChanMcdnFramerStatsEntry 6 }

sigChanMcdnFramerNonOctetErrors OBJECT-TYPE
   SYNTAX     Counter32 
   ACCESS     read-only
   STATUS     mandatory
   DESCRIPTION
     "This attribute counts the total number of frames that were non octet 
      aligned.
      This count wraps to zero after reaching its maximum value."
::= { sigChanMcdnFramerStatsEntry 7 }

sigChanMcdnFramerOverruns OBJECT-TYPE
   SYNTAX     Counter32 
   ACCESS     read-only
   STATUS     mandatory
   DESCRIPTION
     "This attribute counts the total number of frames received from the 
      link for which overruns occurred.
      This count wraps to zero after reaching its maximum value."
::= { sigChanMcdnFramerStatsEntry 8 }

sigChanMcdnFramerUnderruns OBJECT-TYPE
   SYNTAX     Counter32 
   ACCESS     read-only
   STATUS     mandatory
   DESCRIPTION
     "This attribute counts the total number of frames transmitted to the 
      link for which underruns occurred.
      This count wraps to zero after reaching its maximum value."
::= { sigChanMcdnFramerStatsEntry 9 }

sigChanMcdnFramerLargeFrmErrors OBJECT-TYPE
   SYNTAX     Counter32 
   ACCESS     read-only
   STATUS     mandatory
   DESCRIPTION
     "This attribute counts the total number of frames received which 
      were too large (longer than 500 bytes).
      This count wraps to zero after reaching its maximum value."
::= { sigChanMcdnFramerStatsEntry 10 }




-- 
-- Version and Compliance statements
-- 



-- Object-Group Statement:
-- A list of all current accessible leaf objects.

-- OBJECTS { sigChanMcdnNetworkNameDisplay,
--           sigChanMcdnT309,
--           sigChanMcdnOperationalState,
--           sigChanMcdnT203,
--           sigChanMcdnComponentName,
--           sigChanMcdnMessageTraced,
--           sigChanMcdnChanMaintenanceHandling,
--           sigChanMcdnFramerFrmToIf,
--           sigChanMcdnT302,
--           sigChanMcdnT317,
--           sigChanMcdnSide,
--           sigChanMcdnFramerAborts,
--           sigChanMcdnT310,
--           sigChanMcdnPeakActiveChannels,
--           sigChanMcdnT316,
--           sigChanMcdnActiveChannels,
--           sigChanMcdnFramerLargeFrmErrors,
--           sigChanMcdnActiveDataChannels,
--           sigChanMcdnClsFeaturesSupported,
--           sigChanMcdnNonCallAssocSessionsToIf,
--           sigChanMcdnTotalCallsFromIf,
--           sigChanMcdnN200,
--           sigChanMcdnFramerFrmFromIf,
--           sigChanMcdnFramerStorageType,
--           sigChanMcdnT23,
--           sigChanMcdnPeakActiveDataChannels,
--           sigChanMcdnFramerCrcErrors,
--           sigChanMcdnStorageType,
--           sigChanMcdnOverlapSending,
--           sigChanMcdnT200,
--           sigChanMcdnDropBackCongestion,
--           sigChanMcdnOverlapReceiving,
--           sigChanMcdnFramerOctetFromIf,
--           sigChanMcdnDChanStatus,
--           sigChanMcdnFramerAdminState,
--           sigChanMcdnFramerLrcErrors,
--           sigChanMcdnAdminState,
--           sigChanMcdnFramerRowStatus,
--           sigChanMcdnActiveVoiceChannels,
--           sigChanMcdnTracing,
--           sigChanMcdnRowStatus,
--           sigChanMcdnFramerOverruns,
--           sigChanMcdnConOrFeaturesSupported,
--           sigChanMcdnT304,
--           sigChanMcdnMaxNonCallConcurrent,
--           sigChanMcdnNonCallAssocSessionsFromIf,
--           sigChanMcdnPeakActiveVoiceChannels,
--           sigChanMcdnFramerNonOctetErrors,
--           sigChanMcdnFramerUsageState,
--           sigChanMcdnMultisiteBusinessGroup,
--           sigChanMcdnFramerComponentName,
--           sigChanMcdnUsageState,
--           sigChanMcdnTotalCallsToIf,
--           sigChanMcdnFramerInterfaceName,
--           sigChanMcdnDirectionTraced,
--           sigChanMcdnCircuitSwitchedK,
--           sigChanMcdnFramerUnderruns,
--           sigChanMcdnFramerOperationalState }
-- STATUS  mandatory
-- DESCRIPTION
--   "A list of all current accessible leaf objects."

vnetMcdnSigGroup OBJECT IDENTIFIER ::= { vnetMcdnSigMIB 1 }
vnetMcdnSigGroupBE OBJECT IDENTIFIER ::= { vnetMcdnSigGroup 5 }
vnetMcdnSigGroupBE01 OBJECT IDENTIFIER ::= { vnetMcdnSigGroupBE 2 }
vnetMcdnSigGroupBE01A OBJECT IDENTIFIER ::= { vnetMcdnSigGroupBE01 2 }



-- Agent-Capabilities Statement:

-- PRODUCT-RELEASE "Passport Release 7.0 VnetMcdnSig."
-- STATUS          mandatory
-- DESCRIPTION     "VnetMcdnSig MIB: MIB Version BE01A,
--                  Software Version BG00S4C."
-- SUPPORTS        Nortel-Magellan-Passport-VnetMcdnSigMIB
--    INCLUDES     { vnetMcdnSigGroupBE01A }

vnetMcdnSigCapabilities OBJECT IDENTIFIER ::= { vnetMcdnSigMIB 3 }
vnetMcdnSigCapabilitiesBE OBJECT IDENTIFIER ::= { vnetMcdnSigCapabilities 5 }
vnetMcdnSigCapabilitiesBE01 OBJECT IDENTIFIER ::= { vnetMcdnSigCapabilitiesBE 2 }
vnetMcdnSigCapabilitiesBE01A OBJECT IDENTIFIER ::= { vnetMcdnSigCapabilitiesBE01 2 }





END
