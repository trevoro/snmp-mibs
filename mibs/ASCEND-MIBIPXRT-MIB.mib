--			Ascend mibipxrt MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPXRT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibipxRouteProfile  OBJECT IDENTIFIER ::= { configuration 89}

	-- The mibipxRouteProfile table
	--
	-- This table contains parameters for the mibipxRouteProfile profile
	--

    mibipxRouteProfileTable	OBJECT-TYPE
	SYNTAX		SEQUENCE OF MibipxRouteProfileEntry
	ACCESS		not-accessible
	STATUS		mandatory
	DESCRIPTION	"A list of mibipxRouteProfile profile entries."
	::= { mibipxRouteProfile 1 }

    mibipxRouteProfileEntry	OBJECT-TYPE
	SYNTAX		MibipxRouteProfileEntry
	ACCESS		not-accessible
	STATUS		mandatory
	DESCRIPTION	"A mibipxRouteProfile entry containing objects that
			 maps to the parameters of mibipxRouteProfile profile."
	INDEX		{ ipxRouteProfile-Name }
	::= { mibipxRouteProfileTable 1 }

    MibipxRouteProfileEntry ::=
	SEQUENCE {
	    ipxRouteProfile-Index
		INTEGER,
	    ipxRouteProfile-Name
		DisplayString,
	    ipxRouteProfile-ServerType
		DisplayString,
	    ipxRouteProfile-DestNetwork
		DisplayString,
	    ipxRouteProfile-ServerNode
		DisplayString,
	    ipxRouteProfile-ServerSocket
		DisplayString,
	    ipxRouteProfile-Hops
		INTEGER,
	    ipxRouteProfile-Ticks
		INTEGER,
	    ipxRouteProfile-ProfileNumber
		INTEGER,
	    ipxRouteProfile-ProfileName
		DisplayString,
	    ipxRouteProfile-ActiveRoute
		INTEGER,
	    ipxRouteProfile-Action-o
		INTEGER
	}

    ipxRouteProfile-Index	OBJECT-TYPE
	SYNTAX	INTEGER
	ACCESS	read-write
	STATUS	mandatory
	DESCRIPTION	"PROFACCE index"
	::= { mibipxRouteProfileEntry 1 }

    ipxRouteProfile-Name	OBJECT-TYPE
	SYNTAX	DisplayString
	ACCESS	read-only
	STATUS	mandatory
	DESCRIPTION	"SAP name of the server."
	::= { mibipxRouteProfileEntry 2 }

    ipxRouteProfile-ServerType	OBJECT-TYPE
	SYNTAX	DisplayString
	ACCESS	read-write
	STATUS	mandatory
	DESCRIPTION	"SAP type."
	::= { mibipxRouteProfileEntry 3 }

    ipxRouteProfile-DestNetwork	OBJECT-TYPE
	SYNTAX	DisplayString
	ACCESS	read-write
	STATUS	mandatory
	DESCRIPTION	"The IPX network number of the destination network in 4 bytes."
	::= { mibipxRouteProfileEntry 4 }

    ipxRouteProfile-ServerNode	OBJECT-TYPE
	SYNTAX	DisplayString
	ACCESS	read-write
	STATUS	mandatory
	DESCRIPTION	"The node address of the server. For NetWare servers 3.0 and beyond, this is 1."
	::= { mibipxRouteProfileEntry 5 }

    ipxRouteProfile-ServerSocket	OBJECT-TYPE
	SYNTAX	DisplayString
	ACCESS	read-write
	STATUS	mandatory
	DESCRIPTION	"The advertising socket number for the server."
	::= { mibipxRouteProfileEntry 6 }

    ipxRouteProfile-Hops	OBJECT-TYPE
	SYNTAX	INTEGER
	ACCESS	read-write
	STATUS	mandatory
	DESCRIPTION	"The distance in hops to the network."
	::= { mibipxRouteProfileEntry 7 }

    ipxRouteProfile-Ticks	OBJECT-TYPE
	SYNTAX	INTEGER
	ACCESS	read-write
	STATUS	mandatory
	DESCRIPTION	"The distance in ticks to the network."
	::= { mibipxRouteProfileEntry 8 }

    ipxRouteProfile-ProfileNumber	OBJECT-TYPE
	SYNTAX	INTEGER
	ACCESS	read-write
	STATUS	mandatory
	DESCRIPTION	"The profile through which we reach the net."
	::= { mibipxRouteProfileEntry 9 }

    ipxRouteProfile-ProfileName	OBJECT-TYPE
	SYNTAX	DisplayString
	ACCESS	read-write
	STATUS	mandatory
	DESCRIPTION	"The connection through which we reach the net."
	::= { mibipxRouteProfileEntry 10 }

    ipxRouteProfile-ActiveRoute	OBJECT-TYPE
	SYNTAX	INTEGER {
		    no (1),
		    yes (2)
		}
	ACCESS	read-write
	STATUS	mandatory
	DESCRIPTION	"TRUE if this route is active.Inactive routes are not placed in the routing tables."
	::= { mibipxRouteProfileEntry 11 }

    ipxRouteProfile-Action-o	OBJECT-TYPE
	SYNTAX	INTEGER {
		    noAction (1),
		    createProfile (2),
		    deleteProfile (3)
		}
	ACCESS	read-write
	STATUS	mandatory
	DESCRIPTION	""
	::= { mibipxRouteProfileEntry 12 }

END
