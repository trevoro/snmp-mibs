--
--	Aptis Enterprise MIB
--	Monitoring Module (V2 SMI)
-- 
--	Nortel Networks
--	11 Elizabeth Drive
--	Chelmsford, MA 01824
--
--	NOTE: this MIB is programmatically generated and should not
--	be modified by hand.
--
--	Copyright (c) 1997-2000 Nortel Networks
--	All Rights Reserved.

APTIS-MONITOR-MIB DEFINITIONS ::= BEGIN

    IMPORTS
        aptis-monitoring, Boolean
            FROM APTIS-MIB
	aptis-modules
 	    FROM APTIS-REG-MIB
        MODULE-IDENTITY, OBJECT-TYPE, IpAddress
            FROM SNMPv2-SMI
        DisplayString, RowStatus
            FROM SNMPv2-TC;

    aptisMonitorModule MODULE-IDENTITY
        LAST-UPDATED "0004140000Z"
        ORGANIZATION "Nortel Networks"
        CONTACT-INFO
            "   Technical Support/Customer Service
                Nortel Networks

                Postal: 11 Elizabeth Drive
                        Chelmsford, MA 01824

                Tel:
                In the USA: Dial 1-800-758-4827 to contact a Technical Support engineer.
                Outside the USA:  Contact your Regional Nortel Networks Support Prime.

                For information about the Nortel Networks Network Access Division,
                go to the World Wide Web (WWW) site at http://www.nortelnetworks.com."

        DESCRIPTION
            "The following tables describe the variables that allow 
	     monitoring of an Aptis box."

    ::= { aptis-modules 4 }

-- This file generated from  clocking.cml by smog.
-- date: Thu Jun 29 01:11:25  2000

	clockStatusTable	OBJECT-TYPE
		SYNTAX		SEQUENCE OF ClockStatusEntry
		MAX-ACCESS	not-accessible
		STATUS		current
		DESCRIPTION
			"Clock Status."

	::= { aptis-monitoring 2901 }

	clockStatusEntry	OBJECT-TYPE
		SYNTAX		ClockStatusEntry
		MAX-ACCESS	not-accessible
		STATUS		current
		DESCRIPTION
			"This is the structure of entries in the
			 clockStatusTable."
		INDEX		{ clockStatusCurrentSource }
	::= { clockStatusTable 1 }

	ClockStatusEntry ::= SEQUENCE {
		clockStatusCurrentSource	INTEGER
	}

	clockStatusCurrentSource	OBJECT-TYPE
		SYNTAX		INTEGER {
				    internal(0),
				    primary(1),
				    secondary(2)
				}
		MAX-ACCESS	read-only
		STATUS		current
		DESCRIPTION
			"Current Clock Source."

	::= { clockStatusEntry 1 }

-- This file generated from  ds0.cml by smog.
-- date: Thu Jun 29 01:11:25  2000

	ds0StatsTable	OBJECT-TYPE
		SYNTAX		SEQUENCE OF Ds0StatsEntry
		MAX-ACCESS	not-accessible
		STATUS		current
		DESCRIPTION
			"DS0 Stats."

	::= { aptis-monitoring 2112 }

	ds0StatsEntry	OBJECT-TYPE
		SYNTAX		Ds0StatsEntry
		MAX-ACCESS	not-accessible
		STATUS		current
		DESCRIPTION
			"This is the structure of entries in the
			 ds0StatsTable."
		INDEX		{ ds0StatsSlotIndex, ds0StatsLineNumber, ds0StatsDs0Index }
	::= { ds0StatsTable 1 }

	Ds0StatsEntry ::= SEQUENCE {
		ds0StatsInCalls			INTEGER,
		ds0StatsInConnected		INTEGER,
		ds0StatsOutCalls		INTEGER,
		ds0StatsOutConnected		INTEGER,
		ds0StatsInCleared		INTEGER,
		ds0StatsOutCleared		INTEGER,
		ds0StatsSlotIndex		INTEGER,
		ds0StatsLineNumber		INTEGER,
		ds0StatsDs0Index		INTEGER
	}

	ds0StatsInCalls	OBJECT-TYPE
		SYNTAX		INTEGER
		MAX-ACCESS	read-only
		STATUS		current
		DESCRIPTION
			"Number of attempted incoming calls."

	::= { ds0StatsEntry 1 }

	ds0StatsInConnected	OBJECT-TYPE
		SYNTAX		INTEGER
		MAX-ACCESS	read-only
		STATUS		current
		DESCRIPTION
			"Number of connected incoming calls."

	::= { ds0StatsEntry 2 }

	ds0StatsOutCalls	OBJECT-TYPE
		SYNTAX		INTEGER
		MAX-ACCESS	read-only
		STATUS		current
		DESCRIPTION
			"Number of attempted outgoing calls."

	::= { ds0StatsEntry 3 }

	ds0StatsOutConnected	OBJECT-TYPE
		SYNTAX		INTEGER
		MAX-ACCESS	read-only
		STATUS		current
		DESCRIPTION
			"Number of connected outgoing calls."

	::= { ds0StatsEntry 4 }

	ds0StatsInCleared	OBJECT-TYPE
		SYNTAX		INTEGER
		MAX-ACCESS	read-only
		STATUS		current
		DESCRIPTION
			"Number of calls disconnected from CVX Access Switch.
			It is possible that the number of calls cleared may
			total higher than the number of calls attempted. This
			can occur if the user and the switch disconnect
			simultaneously."

	::= { ds0StatsEntry 5 }

	ds0StatsOutCleared	OBJECT-TYPE
		SYNTAX		INTEGER
		MAX-ACCESS	read-only
		STATUS		current
		DESCRIPTION
			"Number of calls disconnected remotely."

	::= { ds0StatsEntry 6 }

	ds0StatsSlotIndex	OBJECT-TYPE
		SYNTAX		INTEGER (1..32)
		MAX-ACCESS	read-only
		STATUS		current
		DESCRIPTION
			"The physical slot number associated with this line."

	::= { ds0StatsEntry 7 }

	ds0StatsLineNumber	OBJECT-TYPE
		SYNTAX		INTEGER (1..56)
		MAX-ACCESS	read-only
		STATUS		current
		DESCRIPTION
			"The line number of the line to which the stats
			apply."

	::= { ds0StatsEntry 8 }

	ds0StatsDs0Index	OBJECT-TYPE
		SYNTAX		INTEGER (1..32)
		MAX-ACCESS	read-only
		STATUS		current
		DESCRIPTION
			"The DS0 time slot for which the stats apply."

	::= { ds0StatsEntry 9 }

-- This file generated from  e1.cml by smog.
-- date: Thu Jun 29 01:11:25  2000

	e1StatsTable	OBJECT-TYPE
		SYNTAX		SEQUENCE OF E1StatsEntry
		MAX-ACCESS	not-accessible
		STATUS		current
		DESCRIPTION
			"E1 stats."

	::= { aptis-monitoring 2502 }

	e1StatsEntry	OBJECT-TYPE
		SYNTAX		E1StatsEntry
		MAX-ACCESS	not-accessible
		STATUS		current
		DESCRIPTION
			"This is the structure of entries in the
			 e1StatsTable."
		INDEX		{ e1StatsSlotIndex, e1StatsLineNumber }
	::= { e1StatsTable 1 }

	E1StatsEntry ::= SEQUENCE {
		e1StatsAlarmStatus		INTEGER,
		e1StatsSlotIndex		INTEGER,
		e1StatsLineNumber		INTEGER
	}

	e1StatsAlarmStatus	OBJECT-TYPE
		SYNTAX		INTEGER {
				    f1(0),
				    f2(1),
				    f3(2),
				    f4(3),
				    f5(4),
				    f6(5)
				}
		MAX-ACCESS	read-only
		STATUS		current
		DESCRIPTION
			"E1 layer 1 state."

	::= { e1StatsEntry 1 }

	e1StatsSlotIndex	OBJECT-TYPE
		SYNTAX		INTEGER (1..32)
		MAX-ACCESS	read-only
		STATUS		current
		DESCRIPTION
			"The physical slot number associated with this line."

	::= { e1StatsEntry 2 }

	e1StatsLineNumber	OBJECT-TYPE
		SYNTAX		INTEGER (1..32)
		MAX-ACCESS	read-only
		STATUS		current
		DESCRIPTION
			"The line number of the line to which the status
			applies."

	::= { e1StatsEntry 3 }


	e1CountsTable	OBJECT-TYPE
		SYNTAX		SEQUENCE OF E1CountsEntry
		MAX-ACCESS	not-accessible
		STATUS		current
		DESCRIPTION
			"E1_counts."

	::= { aptis-monitoring 2503 }

	e1CountsEntry	OBJECT-TYPE
		SYNTAX		E1CountsEntry
		MAX-ACCESS	not-accessible
		STATUS		current
		DESCRIPTION
			"This is the structure of entries in the
			 e1CountsTable."
		INDEX		{ e1CountsSlotIndex, e1CountsLineNumber }
	::= { e1CountsTable 1 }

	E1CountsEntry ::= SEQUENCE {
		e1CountsChannelCount		INTEGER,
		e1CountsChannelsInUse		INTEGER,
		e1CountsIncomingCallAttempts	INTEGER,
		e1CountsIncomingConnects	INTEGER,
		e1CountsIncomingDisconnects	INTEGER,
		e1CountsOutgoingCallAttempts	INTEGER,
		e1CountsOutgoingConnects	INTEGER,
		e1CountsOutgoingDisconnects	INTEGER,
		e1CountsSessionAbortMessages	INTEGER,
		e1CountsSlotIndex		INTEGER,
		e1CountsLineNumber		INTEGER
	}

	e1CountsChannelCount	OBJECT-TYPE
		SYNTAX		INTEGER
		MAX-ACCESS	read-only
		STATUS		current
		DESCRIPTION
			"DS0s (B-channels) on this interface."

	::= { e1CountsEntry 1 }

	e1CountsChannelsInUse	OBJECT-TYPE
		SYNTAX		INTEGER
		MAX-ACCESS	read-only
		STATUS		current
		DESCRIPTION
			"DS0s (B-channels) in use."

	::= { e1CountsEntry 2 }

	e1CountsIncomingCallAttempts	OBJECT-TYPE
		SYNTAX		INTEGER
		MAX-ACCESS	read-only
		STATUS		current
		DESCRIPTION
			"Incoming call attempts on this E1."

	::= { e1CountsEntry 3 }

	e1CountsIncomingConnects	OBJECT-TYPE
		SYNTAX		INTEGER
		MAX-ACCESS	read-only
		STATUS		current
		DESCRIPTION
			"Incoming connect messages."

	::= { e1CountsEntry 4 }

	e1CountsIncomingDisconnects	OBJECT-TYPE
		SYNTAX		INTEGER
		MAX-ACCESS	read-only
		STATUS		current
		DESCRIPTION
			"Incoming disconnect messages."

	::= { e1CountsEntry 5 }

	e1CountsOutgoingCallAttempts	OBJECT-TYPE
		SYNTAX		INTEGER
		MAX-ACCESS	read-only
		STATUS		current
		DESCRIPTION
			"Outgoing call attempts on this E1."

	::= { e1CountsEntry 6 }

	e1CountsOutgoingConnects	OBJECT-TYPE
		SYNTAX		INTEGER
		MAX-ACCESS	read-only
		STATUS		current
		DESCRIPTION
			"Outgoing connect messages."

	::= { e1CountsEntry 7 }

	e1CountsOutgoingDisconnects	OBJECT-TYPE
		SYNTAX		INTEGER
		MAX-ACCESS	read-only
		STATUS		current
		DESCRIPTION
			"Outgoing disconnect messages."

	::= { e1CountsEntry 8 }

	e1CountsSessionAbortMessages	OBJECT-TYPE
		SYNTAX		INTEGER
		MAX-ACCESS	read-only
		STATUS		current
		DESCRIPTION
			"Abort messages from the session manager."

	::= { e1CountsEntry 9 }

	e1CountsSlotIndex	OBJECT-TYPE
		SYNTAX		INTEGER (1..32)
		MAX-ACCESS	read-only
		STATUS		current
		DESCRIPTION
			"The physical slot number associated with this line."

	::= { e1CountsEntry 10 }

	e1CountsLineNumber	OBJECT-TYPE
		SYNTAX		INTEGER (1..32)
		MAX-ACCESS	read-only
		STATUS		current
		DESCRIPTION
			"The line number of the line to which the status
			applies."

	::= { e1CountsEntry 11 }


	e1SummaryStatsTable	OBJECT-TYPE
		SYNTAX		SEQUENCE OF E1SummaryStatsEntry
		MAX-ACCESS	not-accessible
		STATUS		current
		DESCRIPTION
			"E1 Summary Stats."

	::= { aptis-monitoring 2504 }

	e1SummaryStatsEntry	OBJECT-TYPE
		SYNTAX		E1SummaryStatsEntry
		MAX-ACCESS	not-accessible
		STATUS		current
		DESCRIPTION
			"This is the structure of entries in the
			 e1SummaryStatsTable."
		INDEX		{ e1SummaryStatsSlotIndex, e1SummaryStatsLineNumber }
	::= { e1SummaryStatsTable 1 }

	E1SummaryStatsEntry ::= SEQUENCE {
		e1SummaryStatsRingingChannels	INTEGER,
		e1SummaryStatsConnectedChannels	INTEGER,
		e1SummaryStatsClearingChannels	INTEGER,
		e1SummaryStatsSlotIndex		INTEGER,
		e1SummaryStatsLineNumber	INTEGER,
		e1SummaryStatsFunctionalChannels INTEGER,
		e1SummaryStatsIdleChannels	INTEGER
	}

	e1SummaryStatsRingingChannels	OBJECT-TYPE
		SYNTAX		INTEGER
		MAX-ACCESS	read-only
		STATUS		current
		DESCRIPTION
			"Bit mask of b-channels that have calls coming up,
			with b-channel 1 at 0x02, 2 at 0x04, etc."

	::= { e1SummaryStatsEntry 1 }

	e1SummaryStatsConnectedChannels	OBJECT-TYPE
		SYNTAX		INTEGER
		MAX-ACCESS	read-only
		STATUS		current
		DESCRIPTION
			"Bit mask of b-channels that have calls connected,
			with b-channel 1 at 0x02, 2 at 0x04, etc."

	::= { e1SummaryStatsEntry 2 }

	e1SummaryStatsClearingChannels	OBJECT-TYPE
		SYNTAX		INTEGER
		MAX-ACCESS	read-only
		STATUS		current
		DESCRIPTION
			"Bit mask of b-channels that have calls going down,
			with b-channel 1 at 0x02, 2 at 0x04, etc."

	::= { e1SummaryStatsEntry 3 }

	e1SummaryStatsSlotIndex	OBJECT-TYPE
		SYNTAX		INTEGER (1..32)
		MAX-ACCESS	read-only
		STATUS		current
		DESCRIPTION
			"The physical slot number associated with this line."

	::= { e1SummaryStatsEntry 4 }

	e1SummaryStatsLineNumber	OBJECT-TYPE
		SYNTAX		INTEGER (1..32)
		MAX-ACCESS	read-only
		STATUS		current
		DESCRIPTION
			"The line number of the line to which the status
			applies."

	::= { e1SummaryStatsEntry 5 }

	e1SummaryStatsFunctionalChannels	OBJECT-TYPE
		SYNTAX		INTEGER
		MAX-ACCESS	read-only
		STATUS		current
		DESCRIPTION
			"Bit mask of b-channels that are in the functional
			state."

	::= { e1SummaryStatsEntry 6 }

	e1SummaryStatsIdleChannels	OBJECT-TYPE
		SYNTAX		INTEGER
		MAX-ACCESS	read-only
		STATUS		current
		DESCRIPTION
			"Bit mask of b-channels that are in the idle state."

	::= { e1SummaryStatsEntry 7 }

-- This file generated from  ipchdlc.cml by smog.
-- date: Thu Jun 29 01:11:26  2000

	cHdlcStatsTable	OBJECT-TYPE
		SYNTAX		SEQUENCE OF CHdlcStatsEntry
		MAX-ACCESS	not-accessible
		STATUS		current
		DESCRIPTION
			"Cisco High Level Data Link Control Status
			Information."

	::= { aptis-monitoring 1211 }

	cHdlcStatsEntry	OBJECT-TYPE
		SYNTAX		CHdlcStatsEntry
		MAX-ACCESS	not-accessible
		STATUS		current
		DESCRIPTION
			"This is the structure of entries in the
			 cHdlcStatsTable."
		INDEX		{ cHdlcStatsNohdrspaceOut }
	::= { cHdlcStatsTable 1 }

	CHdlcStatsEntry ::= SEQUENCE {
		cHdlcStatsNohdrspaceOut		INTEGER,
		cHdlcStatsNomemoryOut		INTEGER,
		cHdlcStatsCiscoFramesOut	INTEGER,
		cHdlcStatsKeepalivesIn		INTEGER,
		cHdlcStatsUnknownProtocolIn	INTEGER,
		cHdlcStatsShortFramesIn		INTEGER,
		cHdlcStatsPppFramesIn		INTEGER,
		cHdlcStatsUnknownFramesIn	INTEGER,
		cHdlcStatsUnknownCiscoTypeIn	INTEGER,
		cHdlcStatsCiscoFramesIn		INTEGER
	}

	cHdlcStatsNohdrspaceOut	OBJECT-TYPE
		SYNTAX		INTEGER
		MAX-ACCESS	read-only
		STATUS		current
		DESCRIPTION
			"Packet dropped due to lack of header space."

	::= { cHdlcStatsEntry 1 }

	cHdlcStatsNomemoryOut	OBJECT-TYPE
		SYNTAX		INTEGER
		MAX-ACCESS	read-only
		STATUS		current
		DESCRIPTION
			"Packet dropped due to lack of memory."

	::= { cHdlcStatsEntry 2 }

	cHdlcStatsCiscoFramesOut	OBJECT-TYPE
		SYNTAX		INTEGER
		MAX-ACCESS	read-only
		STATUS		current
		DESCRIPTION
			"Count of frames output."

	::= { cHdlcStatsEntry 3 }

	cHdlcStatsKeepalivesIn	OBJECT-TYPE
		SYNTAX		INTEGER
		MAX-ACCESS	read-only
		STATUS		current
		DESCRIPTION
			"Count of keep-alives received."

	::= { cHdlcStatsEntry 4 }

	cHdlcStatsUnknownProtocolIn	OBJECT-TYPE
		SYNTAX		INTEGER
		MAX-ACCESS	read-only
		STATUS		current
		DESCRIPTION
			"Count of unknown protocols received."

	::= { cHdlcStatsEntry 5 }

	cHdlcStatsShortFramesIn	OBJECT-TYPE
		SYNTAX		INTEGER
		MAX-ACCESS	read-only
		STATUS		current
		DESCRIPTION
			"Count of too-short frames received."

	::= { cHdlcStatsEntry 6 }

	cHdlcStatsPppFramesIn	OBJECT-TYPE
		SYNTAX		INTEGER
		MAX-ACCESS	read-only
		STATUS		current
		DESCRIPTION
			"Count of PPP frames received."

	::= { cHdlcStatsEntry 7 }

	cHdlcStatsUnknownFramesIn	OBJECT-TYPE
		SYNTAX		INTEGER
		MAX-ACCESS	read-only
		STATUS		current
		DESCRIPTION
			"Count of unknown frames received."

	::= { cHdlcStatsEntry 8 }

	cHdlcStatsUnknownCiscoTypeIn	OBJECT-TYPE
		SYNTAX		INTEGER
		MAX-ACCESS	read-only
		STATUS		current
		DESCRIPTION
			"Count of unknown Cisco control frames received."

	::= { cHdlcStatsEntry 9 }

	cHdlcStatsCiscoFramesIn	OBJECT-TYPE
		SYNTAX		INTEGER
		MAX-ACCESS	read-only
		STATUS		current
		DESCRIPTION
			"Count of Cisco control frames received."

	::= { cHdlcStatsEntry 10 }

-- This file generated from  ipcleartcp.cml by smog.
-- date: Thu Jun 29 01:11:26  2000

	ipCleartcpStatsTable	OBJECT-TYPE
		SYNTAX		SEQUENCE OF IpCleartcpStatsEntry
		MAX-ACCESS	not-accessible
		STATUS		current
		DESCRIPTION
			"ClearTCP Statistics."

	::= { aptis-monitoring 1231 }

	ipCleartcpStatsEntry	OBJECT-TYPE
		SYNTAX		IpCleartcpStatsEntry
		MAX-ACCESS	not-accessible
		STATUS		current
		DESCRIPTION
			"This is the structure of entries in the
			 ipCleartcpStatsTable."
		INDEX		{ ipCleartcpStatsInputQfull }
	::= { ipCleartcpStatsTable 1 }

	IpCleartcpStatsEntry ::= SEQUENCE {
		ipCleartcpStatsInputQfull	INTEGER,
		ipCleartcpStatsInputTcpfull	INTEGER,
		ipCleartcpStatsInputDroppedBytes INTEGER,
		ipCleartcpStatsInputBytes	INTEGER,
		ipCleartcpStatsOutputQfull	INTEGER,
		ipCleartcpStatsOutputDroppedBytes INTEGER,
		ipCleartcpStatsOutputBytes	INTEGER
	}

	ipCleartcpStatsInputQfull	OBJECT-TYPE
		SYNTAX		INTEGER
		MAX-ACCESS	read-only
		STATUS		current
		DESCRIPTION
			"Number of pbufs dropped because input queue was
			full."

	::= { ipCleartcpStatsEntry 1 }

	ipCleartcpStatsInputTcpfull	OBJECT-TYPE
		SYNTAX		INTEGER
		MAX-ACCESS	read-only
		STATUS		current
		DESCRIPTION
			"Number of pbufs dropped because TCP input queue was
			full."

	::= { ipCleartcpStatsEntry 2 }

	ipCleartcpStatsInputDroppedBytes	OBJECT-TYPE
		SYNTAX		INTEGER
		MAX-ACCESS	read-only
		STATUS		current
		DESCRIPTION
			"Total number of input bytes dropped (all causes)."

	::= { ipCleartcpStatsEntry 3 }

	ipCleartcpStatsInputBytes	OBJECT-TYPE
		SYNTAX		INTEGER
		MAX-ACCESS	read-only
		STATUS		current
		DESCRIPTION
			"Total number of input bytes."

	::= { ipCleartcpStatsEntry 4 }

	ipCleartcpStatsOutputQfull	OBJECT-TYPE
		SYNTAX		INTEGER
		MAX-ACCESS	read-only
		STATUS		current
		DESCRIPTION
			"Number of pbufs dropped because output queue was
			full."

	::= { ipCleartcpStatsEntry 5 }

	ipCleartcpStatsOutputDroppedBytes	OBJECT-TYPE
		SYNTAX		INTEGER
		MAX-ACCESS	read-only
		STATUS		current
		DESCRIPTION
			"Total number of output bytes dropped (all causes)."

	::= { ipCleartcpStatsEntry 6 }

	ipCleartcpStatsOutputBytes	OBJECT-TYPE
		SYNTAX		INTEGER
		MAX-ACCESS	read-only
		STATUS		current
		DESCRIPTION
			"Total number of output bytes."

	::= { ipCleartcpStatsEntry 7 }

-- This file generated from  ipservices.cml by smog.
-- date: Thu Jun 29 01:11:26  2000

	ipSvcMonitoringTable	OBJECT-TYPE
		SYNTAX		SEQUENCE OF IpSvcMonitoringEntry
		MAX-ACCESS	not-accessible
		STATUS		current
		DESCRIPTION
			"IP services monitoring table."

	::= { aptis-monitoring 1102 }

	ipSvcMonitoringEntry	OBJECT-TYPE
		SYNTAX		IpSvcMonitoringEntry
		MAX-ACCESS	not-accessible
		STATUS		current
		DESCRIPTION
			"This is the structure of entries in the
			 ipSvcMonitoringTable."
		INDEX		{ ipSvcMonitoringServiceName }
	::= { ipSvcMonitoringTable 1 }

	IpSvcMonitoringEntry ::= SEQUENCE {
		ipSvcMonitoringServiceName	DisplayString,
		ipSvcMonitoringState		INTEGER,
		ipSvcMonitoringUptime		INTEGER,
		ipSvcMonitoringRequestsIn	INTEGER,
		ipSvcMonitoringResponsesOut	INTEGER,
		ipSvcMonitoringRequestsOut	INTEGER,
		ipSvcMonitoringResponsesIn	INTEGER,
		ipSvcMonitoringRequestsInProgress INTEGER,
		ipSvcMonitoringRequestsInError	INTEGER,
		ipSvcMonitoringResponsesInError	INTEGER
	}

	ipSvcMonitoringServiceName	OBJECT-TYPE
		SYNTAX		DisplayString (SIZE (0..32))
		MAX-ACCESS	read-only
		STATUS		current
		DESCRIPTION
			"Name of IP service."

	::= { ipSvcMonitoringEntry 1 }

	ipSvcMonitoringState	OBJECT-TYPE
		SYNTAX		INTEGER {
				    stopped(1),
				    stopping(2),
				    starting(3),
				    running(4)
				}
		MAX-ACCESS	read-only
		STATUS		current
		DESCRIPTION
			"Current state of the IP service."

	::= { ipSvcMonitoringEntry 2 }

	ipSvcMonitoringUptime	OBJECT-TYPE
		SYNTAX		INTEGER
		MAX-ACCESS	read-only
		STATUS		current
		DESCRIPTION
			"Uptime of the IP service."

	::= { ipSvcMonitoringEntry 3 }

	ipSvcMonitoringRequestsIn	OBJECT-TYPE
		SYNTAX		INTEGER
		MAX-ACCESS	read-only
		STATUS		current
		DESCRIPTION
			"Number of service requests received."

	::= { ipSvcMonitoringEntry 10 }

	ipSvcMonitoringResponsesOut	OBJECT-TYPE
		SYNTAX		INTEGER
		MAX-ACCESS	read-only
		STATUS		current
		DESCRIPTION
			"Number of service responses issued."

	::= { ipSvcMonitoringEntry 11 }

	ipSvcMonitoringRequestsOut	OBJECT-TYPE
		SYNTAX		INTEGER
		MAX-ACCESS	read-only
		STATUS		current
		DESCRIPTION
			"Number of service requests issued."

	::= { ipSvcMonitoringEntry 12 }

	ipSvcMonitoringResponsesIn	OBJECT-TYPE
		SYNTAX		INTEGER
		MAX-ACCESS	read-only
		STATUS		current
		DESCRIPTION
			"Number of service responses received."

	::= { ipSvcMonitoringEntry 13 }

	ipSvcMonitoringRequestsInProgress	OBJECT-TYPE
		SYNTAX		INTEGER
		MAX-ACCESS	read-only
		STATUS		current
		DESCRIPTION
			"Number of service requests in progress."

	::= { ipSvcMonitoringEntry 14 }

	ipSvcMonitoringRequestsInError	OBJECT-TYPE
		SYNTAX		INTEGER
		MAX-ACCESS	read-only
		STATUS		current
		DESCRIPTION
			"Number of service requests in error."

	::= { ipSvcMonitoringEntry 15 }

	ipSvcMonitoringResponsesInError	OBJECT-TYPE
		SYNTAX		INTEGER
		MAX-ACCESS	read-only
		STATUS		current
		DESCRIPTION
			"Number of service responses in error."

	::= { ipSvcMonitoringEntry 16 }


	ipAlarmEntryTable	OBJECT-TYPE
		SYNTAX		SEQUENCE OF IpAlarmEntryEntry
		MAX-ACCESS	not-accessible
		STATUS		current
		DESCRIPTION
			"IP alarm entry table."

	::= { aptis-monitoring 1196 }

	ipAlarmEntryEntry	OBJECT-TYPE
		SYNTAX		IpAlarmEntryEntry
		MAX-ACCESS	not-accessible
		STATUS		current
		DESCRIPTION
			"This is the structure of entries in the
			 ipAlarmEntryTable."
		INDEX		{ ipAlarmEntryTrapGenNum }
	::= { ipAlarmEntryTable 1 }

	IpAlarmEntryEntry ::= SEQUENCE {
		ipAlarmEntryAlarmType		INTEGER,
		ipAlarmEntryTrapGenNum		INTEGER,
		ipAlarmEntryTrapType		INTEGER,
		ipAlarmEntryTrapOID		OCTET STRING,
		ipAlarmEntryTrapOIDLen		INTEGER,
		ipAlarmEntryTrapSeverity	INTEGER,
		ipAlarmEntryTrapTimeticks	INTEGER,
		ipAlarmEntryTrapPath		DisplayString,
		ipAlarmEntryTrapArg1		DisplayString,
		ipAlarmEntryTrapArg2		DisplayString,
		ipAlarmEntryTrapArg3		DisplayString,
		ipAlarmEntryTrapGroup		INTEGER
	}

	ipAlarmEntryAlarmType	OBJECT-TYPE
		SYNTAX		INTEGER {
				    other(1),
				    flashAlarm(2),
				    ds1Alarm(3),
				    ds3Alarm(4),
				    linkAlarm(5),
				    isdnLinkAlarm(6),
				    hssiPortAlarm(7),
				    enetPortAlarm(8),
				    tunnelAlarm(9),
				    ss7Alarm(10),
				    macModemsAlarm(11),
				    totalModemsAlarm(12),
				    slotAlarm(13),
				    fanAlarm(14),
				    powerAlarm(15),
				    dhcpAlarm(16),
				    slotTempAlarm(17),
				    slaveSccFlashAlarm(18),
				    slaveSccAlarm(19)
				}
		MAX-ACCESS	read-only
		STATUS		current
		DESCRIPTION
			"Type of this alarm."

	::= { ipAlarmEntryEntry 1 }

	ipAlarmEntryTrapGenNum	OBJECT-TYPE
		SYNTAX		INTEGER (0..2147483647)
		MAX-ACCESS	read-only
		STATUS		current
		DESCRIPTION
			"trapGen sent in onset trap PDU."

	::= { ipAlarmEntryEntry 2 }

	ipAlarmEntryTrapType	OBJECT-TYPE
		SYNTAX		INTEGER
		MAX-ACCESS	read-only
		STATUS		current
		DESCRIPTION
			"trapType sent in onset trap PDU."

	::= { ipAlarmEntryEntry 3 }

	ipAlarmEntryTrapOID	OBJECT-TYPE
		SYNTAX		OCTET STRING (SIZE (0..256))
		MAX-ACCESS	read-only
		STATUS		current
		DESCRIPTION
			"trap object id sent in onset trap PDU."

	::= { ipAlarmEntryEntry 4 }

	ipAlarmEntryTrapOIDLen	OBJECT-TYPE
		SYNTAX		INTEGER
		MAX-ACCESS	read-only
		STATUS		current
		DESCRIPTION
			"trap object id length sent in onset trap PDU."

	::= { ipAlarmEntryEntry 5 }

	ipAlarmEntryTrapSeverity	OBJECT-TYPE
		SYNTAX		INTEGER {
				    fatal(7),
				    emerg(6),
				    alert(5),
				    crit(4),
				    err(3),
				    warning(2),
				    notice(1),
				    info(0)
				}
		MAX-ACCESS	read-only
		STATUS		current
		DESCRIPTION
			"trapSeverity sent in onset trap PDU."

	::= { ipAlarmEntryEntry 6 }

	ipAlarmEntryTrapTimeticks	OBJECT-TYPE
		SYNTAX		INTEGER
		MAX-ACCESS	read-only
		STATUS		current
		DESCRIPTION
			"sysuptime when onset trap PDU was sent."

	::= { ipAlarmEntryEntry 7 }

	ipAlarmEntryTrapPath	OBJECT-TYPE
		SYNTAX		DisplayString (SIZE (0..200))
		MAX-ACCESS	read-only
		STATUS		current
		DESCRIPTION
			"trapPath sent in onset trap PDU."

	::= { ipAlarmEntryEntry 8 }

	ipAlarmEntryTrapArg1	OBJECT-TYPE
		SYNTAX		DisplayString (SIZE (0..200))
		MAX-ACCESS	read-only
		STATUS		current
		DESCRIPTION
			"first trap specific variable sent in onset trap PDU."

	::= { ipAlarmEntryEntry 11 }

	ipAlarmEntryTrapArg2	OBJECT-TYPE
		SYNTAX		DisplayString (SIZE (0..200))
		MAX-ACCESS	read-only
		STATUS		current
		DESCRIPTION
			"second trap specific variable sent in onset trap
			PDU."

	::= { ipAlarmEntryEntry 12 }

	ipAlarmEntryTrapArg3	OBJECT-TYPE
		SYNTAX		DisplayString (SIZE (0..200))
		MAX-ACCESS	read-only
		STATUS		current
		DESCRIPTION
			"third trap specific variable sent in onset trap PDU."

	::= { ipAlarmEntryEntry 13 }

	ipAlarmEntryTrapGroup	OBJECT-TYPE
		SYNTAX		INTEGER {
				    cvx(1),
				    mib2(2)
				}
		MAX-ACCESS	read-only
		STATUS		current
		DESCRIPTION
			"Notes whether this trap is a standard defined trap,
			or CVX proprietary"

	::= { ipAlarmEntryEntry 14 }

-- This file generated from  ipsecsrv.cml by smog.
-- date: Thu Jun 29 01:11:26  2000

	ipsecCountersTable	OBJECT-TYPE
		SYNTAX		SEQUENCE OF IpsecCountersEntry
		MAX-ACCESS	not-accessible
		STATUS		current
		DESCRIPTION
			"IPSec Statistics Counters"

	::= { aptis-monitoring 1612 }

	ipsecCountersEntry	OBJECT-TYPE
		SYNTAX		IpsecCountersEntry
		MAX-ACCESS	not-accessible
		STATUS		current
		DESCRIPTION
			"This is the structure of entries in the
			 ipsecCountersTable."
		INDEX		{ ipsecCountersOutboundCounter }
	::= { ipsecCountersTable 1 }

	IpsecCountersEntry ::= SEQUENCE {
		ipsecCountersOutboundCounter	INTEGER,
		ipsecCountersInboundCounter	INTEGER,
		ipsecCountersOutboundDropCounter INTEGER,
		ipsecCountersInboundDropCounter	INTEGER
	}

	ipsecCountersOutboundCounter	OBJECT-TYPE
		SYNTAX		INTEGER
		MAX-ACCESS	read-only
		STATUS		current
		DESCRIPTION
			"Specifies number of the outbound packets processed by
			the IPSec module."

	::= { ipsecCountersEntry 1 }

	ipsecCountersInboundCounter	OBJECT-TYPE
		SYNTAX		INTEGER
		MAX-ACCESS	read-only
		STATUS		current
		DESCRIPTION
			"Specifies number of the inbound packets processed by
			the IPSec module."

	::= { ipsecCountersEntry 2 }

	ipsecCountersOutboundDropCounter	OBJECT-TYPE
		SYNTAX		INTEGER
		MAX-ACCESS	read-only
		STATUS		current
		DESCRIPTION
			"Specifies number of the outbound packets dropped by
			the IPSec module."

	::= { ipsecCountersEntry 3 }

	ipsecCountersInboundDropCounter	OBJECT-TYPE
		SYNTAX		INTEGER
		MAX-ACCESS	read-only
		STATUS		current
		DESCRIPTION
			"Specifies number of the inbound packets dropped by
			the IPSec module."

	::= { ipsecCountersEntry 4 }

-- This file generated from  ipstub.cml by smog.
-- date: Thu Jun 29 01:11:27  2000

	ipStubStatsTable	OBJECT-TYPE
		SYNTAX		SEQUENCE OF IpStubStatsEntry
		MAX-ACCESS	not-accessible
		STATUS		current
		DESCRIPTION
			"IP Stub Stats Information."

	::= { aptis-monitoring 1221 }

	ipStubStatsEntry	OBJECT-TYPE
		SYNTAX		IpStubStatsEntry
		MAX-ACCESS	not-accessible
		STATUS		current
		DESCRIPTION
			"This is the structure of entries in the
			 ipStubStatsTable."
		INDEX		{ ipStubStatsIgmpInMsgs }
	::= { ipStubStatsTable 1 }

	IpStubStatsEntry ::= SEQUENCE {
		ipStubStatsIgmpInMsgs		INTEGER,
		ipStubStatsIgmpInErrors		INTEGER,
		ipStubStatsIgmpInReports	INTEGER,
		ipStubStatsIgmpInQueries	INTEGER,
		ipStubStatsIgmpUnknownType	INTEGER,
		ipStubStatsIgmpOutMsgs		INTEGER,
		ipStubStatsNomemoryOut		INTEGER
	}

	ipStubStatsIgmpInMsgs	OBJECT-TYPE
		SYNTAX		INTEGER
		MAX-ACCESS	read-only
		STATUS		current
		DESCRIPTION
			"number of IGMP packets received"

	::= { ipStubStatsEntry 1 }

	ipStubStatsIgmpInErrors	OBJECT-TYPE
		SYNTAX		INTEGER
		MAX-ACCESS	read-only
		STATUS		current
		DESCRIPTION
			"number of times IGMP packets received in error"

	::= { ipStubStatsEntry 2 }

	ipStubStatsIgmpInReports	OBJECT-TYPE
		SYNTAX		INTEGER
		MAX-ACCESS	read-only
		STATUS		current
		DESCRIPTION
			"number of IGMP report packets received"

	::= { ipStubStatsEntry 3 }

	ipStubStatsIgmpInQueries	OBJECT-TYPE
		SYNTAX		INTEGER
		MAX-ACCESS	read-only
		STATUS		current
		DESCRIPTION
			"number of IGMP query packets received"

	::= { ipStubStatsEntry 4 }

	ipStubStatsIgmpUnknownType	OBJECT-TYPE
		SYNTAX		INTEGER
		MAX-ACCESS	read-only
		STATUS		current
		DESCRIPTION
			"number of IGMP packets of unknown type received"

	::= { ipStubStatsEntry 5 }

	ipStubStatsIgmpOutMsgs	OBJECT-TYPE
		SYNTAX		INTEGER
		MAX-ACCESS	read-only
		STATUS		current
		DESCRIPTION
			"number of IGMP packets sent"

	::= { ipStubStatsEntry 6 }

	ipStubStatsNomemoryOut	OBJECT-TYPE
		SYNTAX		INTEGER
		MAX-ACCESS	read-only
		STATUS		current
		DESCRIPTION
			"number of times IGMP not sent due to no memory"

	::= { ipStubStatsEntry 7 }

-- This file generated from  isdn.cml by smog.
-- date: Thu Jun 29 01:11:27  2000

	iSDNStatsTable	OBJECT-TYPE
		SYNTAX		SEQUENCE OF ISDNStatsEntry
		MAX-ACCESS	not-accessible
		STATUS		current
		DESCRIPTION
			"ISDN Stats Information."

	::= { aptis-monitoring 2208 }

	iSDNStatsEntry	OBJECT-TYPE
		SYNTAX		ISDNStatsEntry
		MAX-ACCESS	not-accessible
		STATUS		current
		DESCRIPTION
			"This is the structure of entries in the
			 iSDNStatsTable."
		INDEX		{ iSDNStatsInCalls }
	::= { iSDNStatsTable 1 }

	ISDNStatsEntry ::= SEQUENCE {
		iSDNStatsInCalls		INTEGER,
		iSDNStatsInConnected		INTEGER,
		iSDNStatsOutCalls		INTEGER,
		iSDNStatsOutConnected		INTEGER,
		iSDNStatsChargedUnits		INTEGER
	}

	iSDNStatsInCalls	OBJECT-TYPE
		SYNTAX		INTEGER
		MAX-ACCESS	read-only
		STATUS		current
		DESCRIPTION
			"Number of attempted incoming calls"

	::= { iSDNStatsEntry 1 }

	iSDNStatsInConnected	OBJECT-TYPE
		SYNTAX		INTEGER
		MAX-ACCESS	read-only
		STATUS		current
		DESCRIPTION
			"Number of completed incoming calls"

	::= { iSDNStatsEntry 2 }

	iSDNStatsOutCalls	OBJECT-TYPE
		SYNTAX		INTEGER
		MAX-ACCESS	read-only
		STATUS		current
		DESCRIPTION
			"Number of attempted outgoing calls"

	::= { iSDNStatsEntry 3 }

	iSDNStatsOutConnected	OBJECT-TYPE
		SYNTAX		INTEGER
		MAX-ACCESS	read-only
		STATUS		current
		DESCRIPTION
			"Number of completed outgoing calls"

	::= { iSDNStatsEntry 4 }

	iSDNStatsChargedUnits	OBJECT-TYPE
		SYNTAX		INTEGER
		MAX-ACCESS	read-only
		STATUS		current
		DESCRIPTION
			"Number of calls charged to this line (outgoing calls,
			plus reverse-billed incoming calls)"

	::= { iSDNStatsEntry 5 }


	iSDNLayer2StatsTable	OBJECT-TYPE
		SYNTAX		SEQUENCE OF ISDNLayer2StatsEntry
		MAX-ACCESS	not-accessible
		STATUS		current
		DESCRIPTION
			"ISDN Layer-2 Stats Information."

	::= { aptis-monitoring 2209 }

	iSDNLayer2StatsEntry	OBJECT-TYPE
		SYNTAX		ISDNLayer2StatsEntry
		MAX-ACCESS	not-accessible
		STATUS		current
		DESCRIPTION
			"This is the structure of entries in the
			 iSDNLayer2StatsTable."
		INDEX		{ iSDNLayer2StatsLapdPeerSabme }
	::= { iSDNLayer2StatsTable 1 }

	ISDNLayer2StatsEntry ::= SEQUENCE {
		iSDNLayer2StatsLapdPeerSabme	INTEGER,
		iSDNLayer2StatsLapdRcvdFrmr	INTEGER,
		iSDNLayer2StatsLapdState	INTEGER
	}

	iSDNLayer2StatsLapdPeerSabme	OBJECT-TYPE
		SYNTAX		INTEGER
		MAX-ACCESS	read-only
		STATUS		current
		DESCRIPTION
			"Number of SABME frames received on this interface"

	::= { iSDNLayer2StatsEntry 1 }

	iSDNLayer2StatsLapdRcvdFrmr	OBJECT-TYPE
		SYNTAX		INTEGER
		MAX-ACCESS	read-only
		STATUS		current
		DESCRIPTION
			"Number of FRMR response frames received. (Indicates
			number of framing errors on this interface)"

	::= { iSDNLayer2StatsEntry 2 }

	iSDNLayer2StatsLapdState	OBJECT-TYPE
		SYNTAX		INTEGER {
				    down(0),
				    up(1)
				}
		MAX-ACCESS	read-only
		STATUS		current
		DESCRIPTION
			"Current state of the ISDN LAPD link"

	::= { iSDNLayer2StatsEntry 3 }


	iSDNHDLCFrameTable	OBJECT-TYPE
		SYNTAX		SEQUENCE OF ISDNHDLCFrameEntry
		MAX-ACCESS	not-accessible
		STATUS		current
		DESCRIPTION
			"ISDN HDLC Frame Information."

	::= { aptis-monitoring 2210 }

	iSDNHDLCFrameEntry	OBJECT-TYPE
		SYNTAX		ISDNHDLCFrameEntry
		MAX-ACCESS	not-accessible
		STATUS		current
		DESCRIPTION
			"This is the structure of entries in the
			 iSDNHDLCFrameTable."
		INDEX		{ iSDNHDLCFrameIndex }
	::= { iSDNHDLCFrameTable 1 }

	ISDNHDLCFrameEntry ::= SEQUENCE {
		iSDNHDLCFrameIndex		INTEGER,
		iSDNHDLCFrameNextIndex		INTEGER,
		iSDNHDLCFrameMaxIndex		INTEGER,
		iSDNHDLCFrameTimestamp		INTEGER,
		iSDNHDLCFrameDirection		INTEGER,
		iSDNHDLCFrameLength		INTEGER,
		iSDNHDLCFrameMessage		OCTET STRING
	}

	iSDNHDLCFrameIndex	OBJECT-TYPE
		SYNTAX		INTEGER
		MAX-ACCESS	read-only
		STATUS		current
		DESCRIPTION
			"Index of this message"

	::= { iSDNHDLCFrameEntry 1 }

	iSDNHDLCFrameNextIndex	OBJECT-TYPE
		SYNTAX		INTEGER
		MAX-ACCESS	read-only
		STATUS		current
		DESCRIPTION
			"next available log"

	::= { iSDNHDLCFrameEntry 2 }

	iSDNHDLCFrameMaxIndex	OBJECT-TYPE
		SYNTAX		INTEGER
		MAX-ACCESS	read-only
		STATUS		current
		DESCRIPTION
			"last saved log"

	::= { iSDNHDLCFrameEntry 3 }

	iSDNHDLCFrameTimestamp	OBJECT-TYPE
		SYNTAX		INTEGER
		MAX-ACCESS	read-only
		STATUS		current
		DESCRIPTION
			"timestamp"

	::= { iSDNHDLCFrameEntry 4 }

	iSDNHDLCFrameDirection	OBJECT-TYPE
		SYNTAX		INTEGER {
				    transmit(1),
				    receive(2)
				}
		MAX-ACCESS	read-only
		STATUS		current
		DESCRIPTION
			"transmit or receive"

	::= { iSDNHDLCFrameEntry 5 }

	iSDNHDLCFrameLength	OBJECT-TYPE
		SYNTAX		INTEGER
		MAX-ACCESS	read-only
		STATUS		current
		DESCRIPTION
			"length of HDLC frame"

	::= { iSDNHDLCFrameEntry 6 }

	iSDNHDLCFrameMessage	OBJECT-TYPE
		SYNTAX		OCTET STRING (SIZE (0..260))
		MAX-ACCESS	read-only
		STATUS		current
		DESCRIPTION
			"contents of HDLC frame"

	::= { iSDNHDLCFrameEntry 7 }

-- This file generated from  l2f.cml by smog.
-- date: Thu Jun 29 01:11:27  2000

	l2FTunnelStatusActiveTable	OBJECT-TYPE
		SYNTAX		SEQUENCE OF L2FTunnelStatusActiveEntry
		MAX-ACCESS	not-accessible
		STATUS		current
		DESCRIPTION
			"Layer-2 Forwarding Active Tunnel Status."

	::= { aptis-monitoring 1351 }

	l2FTunnelStatusActiveEntry	OBJECT-TYPE
		SYNTAX		L2FTunnelStatusActiveEntry
		MAX-ACCESS	not-accessible
		STATUS		current
		DESCRIPTION
			"This is the structure of entries in the
			 l2FTunnelStatusActiveTable."
		INDEX		{ l2FTunnelStatusActiveLocalCLID }
	::= { l2FTunnelStatusActiveTable 1 }

	L2FTunnelStatusActiveEntry ::= SEQUENCE {
		l2FTunnelStatusActiveLocalCLID	INTEGER,
		l2FTunnelStatusActiveRemoteCLID	INTEGER,
		l2FTunnelStatusActiveLocalAddress IpAddress,
		l2FTunnelStatusActiveRemoteAddress IpAddress,
		l2FTunnelStatusActiveState	INTEGER,
		l2FTunnelStatusActiveUpTime	INTEGER,
		l2FTunnelStatusActiveActiveLinks INTEGER,
		l2FTunnelStatusActiveMaxActiveLinks INTEGER,
		l2FTunnelStatusActivePendingLinks INTEGER,
		l2FTunnelStatusActiveLinksAdded	INTEGER,
		l2FTunnelStatusActiveLinksAddedSuccessfully INTEGER,
		l2FTunnelStatusActiveLinksAddedUnsuccessfully INTEGER,
		l2FTunnelStatusActiveLinksRemoved INTEGER,
		l2FTunnelStatusActiveGotOpened	Boolean,
		l2FTunnelStatusActiveVPOP	INTEGER,
		l2FTunnelStatusActiveL2FTermationCause INTEGER
	}

	l2FTunnelStatusActiveLocalCLID	OBJECT-TYPE
		SYNTAX		INTEGER
		MAX-ACCESS	read-only
		STATUS		current
		DESCRIPTION
			"Local CLID for this tunnel"

	::= { l2FTunnelStatusActiveEntry 1 }

	l2FTunnelStatusActiveRemoteCLID	OBJECT-TYPE
		SYNTAX		INTEGER
		MAX-ACCESS	read-only
		STATUS		current
		DESCRIPTION
			"Remote CLID for this tunnel (0 = not known yet)"

	::= { l2FTunnelStatusActiveEntry 2 }

	l2FTunnelStatusActiveLocalAddress	OBJECT-TYPE
		SYNTAX		IpAddress
		MAX-ACCESS	read-only
		STATUS		current
		DESCRIPTION
			"IP address used by CVX"

	::= { l2FTunnelStatusActiveEntry 3 }

	l2FTunnelStatusActiveRemoteAddress	OBJECT-TYPE
		SYNTAX		IpAddress
		MAX-ACCESS	read-only
		STATUS		current
		DESCRIPTION
			"IP address of home gateway"

	::= { l2FTunnelStatusActiveEntry 4 }

	l2FTunnelStatusActiveState	OBJECT-TYPE
		SYNTAX		INTEGER {
				    idle(0),
				    start1(1),
				    start2(2),
				    opened(3),
				    close1(4),
				    close2(5)
				}
		MAX-ACCESS	read-only
		STATUS		current
		DESCRIPTION
			"Current state of this tunnel"

	::= { l2FTunnelStatusActiveEntry 5 }

	l2FTunnelStatusActiveUpTime	OBJECT-TYPE
		SYNTAX		INTEGER
		MAX-ACCESS	read-only
		STATUS		current
		DESCRIPTION
			"Time this tunnel has been active"

	::= { l2FTunnelStatusActiveEntry 6 }

	l2FTunnelStatusActiveActiveLinks	OBJECT-TYPE
		SYNTAX		INTEGER
		MAX-ACCESS	read-only
		STATUS		current
		DESCRIPTION
			"Current number of active links"

	::= { l2FTunnelStatusActiveEntry 7 }

	l2FTunnelStatusActiveMaxActiveLinks	OBJECT-TYPE
		SYNTAX		INTEGER
		MAX-ACCESS	read-only
		STATUS		current
		DESCRIPTION
			"Highest number of links"

	::= { l2FTunnelStatusActiveEntry 8 }

	l2FTunnelStatusActivePendingLinks	OBJECT-TYPE
		SYNTAX		INTEGER
		MAX-ACCESS	read-only
		STATUS		current
		DESCRIPTION
			"Current number of pending links"

	::= { l2FTunnelStatusActiveEntry 9 }

	l2FTunnelStatusActiveLinksAdded	OBJECT-TYPE
		SYNTAX		INTEGER
		MAX-ACCESS	read-only
		STATUS		current
		DESCRIPTION
			"Total number of links added to this tunnel"

	::= { l2FTunnelStatusActiveEntry 10 }

	l2FTunnelStatusActiveLinksAddedSuccessfully	OBJECT-TYPE
		SYNTAX		INTEGER
		MAX-ACCESS	read-only
		STATUS		current
		DESCRIPTION
			"Total number of links added successfully"

	::= { l2FTunnelStatusActiveEntry 11 }

	l2FTunnelStatusActiveLinksAddedUnsuccessfully	OBJECT-TYPE
		SYNTAX		INTEGER
		MAX-ACCESS	read-only
		STATUS		current
		DESCRIPTION
			"Total number of links added unsuccessfully"

	::= { l2FTunnelStatusActiveEntry 12 }

	l2FTunnelStatusActiveLinksRemoved	OBJECT-TYPE
		SYNTAX		INTEGER
		MAX-ACCESS	read-only
		STATUS		current
		DESCRIPTION
			"Total number of links removed"

	::= { l2FTunnelStatusActiveEntry 13 }

	l2FTunnelStatusActiveGotOpened	OBJECT-TYPE
		SYNTAX		Boolean
		MAX-ACCESS	read-only
		STATUS		current
		DESCRIPTION
			"Specifies whether tunnel was opened successfully"

	::= { l2FTunnelStatusActiveEntry 14 }

	l2FTunnelStatusActiveVPOP	OBJECT-TYPE
		SYNTAX		INTEGER
		MAX-ACCESS	read-only
		STATUS		current
		DESCRIPTION
			"VPOP of first link added to this tunnel"

	::= { l2FTunnelStatusActiveEntry 15 }

	l2FTunnelStatusActiveL2FTermationCause	OBJECT-TYPE
		SYNTAX		INTEGER
		MAX-ACCESS	read-only
		STATUS		current
		DESCRIPTION
			"L2F termination cause"

	::= { l2FTunnelStatusActiveEntry 16 }


	l2FTunnelStatusInactiveTable	OBJECT-TYPE
		SYNTAX		SEQUENCE OF L2FTunnelStatusInactiveEntry
		MAX-ACCESS	not-accessible
		STATUS		current
		DESCRIPTION
			"Layer-2 Forwarding Inactive Tunnel Status."

	::= { aptis-monitoring 1352 }

	l2FTunnelStatusInactiveEntry	OBJECT-TYPE
		SYNTAX		L2FTunnelStatusInactiveEntry
		MAX-ACCESS	not-accessible
		STATUS		current
		DESCRIPTION
			"This is the structure of entries in the
			 l2FTunnelStatusInactiveTable."
		INDEX		{ l2FTunnelStatusInactiveLocalCLID }
	::= { l2FTunnelStatusInactiveTable 1 }

	L2FTunnelStatusInactiveEntry ::= SEQUENCE {
		l2FTunnelStatusInactiveLocalCLID INTEGER,
		l2FTunnelStatusInactiveRemoteCLID INTEGER,
		l2FTunnelStatusInactiveLocalAddress IpAddress,
		l2FTunnelStatusInactiveRemoteAddress IpAddress,
		l2FTunnelStatusInactiveState	INTEGER,
		l2FTunnelStatusInactiveUpTime	INTEGER,
		l2FTunnelStatusInactiveActiveLinks INTEGER,
		l2FTunnelStatusInactiveMaxActiveLinks INTEGER,
		l2FTunnelStatusInactivePendingLinks INTEGER,
		l2FTunnelStatusInactiveLinksAdded INTEGER,
		l2FTunnelStatusInactiveLinksAddedSuccessfully INTEGER,
		l2FTunnelStatusInactiveLinksAddedUnsuccessfully INTEGER,
		l2FTunnelStatusInactiveLinksRemoved INTEGER,
		l2FTunnelStatusInactiveGotOpened Boolean,
		l2FTunnelStatusInactiveVPOP	INTEGER,
		l2FTunnelStatusInactiveL2FTermationCause INTEGER
	}

	l2FTunnelStatusInactiveLocalCLID	OBJECT-TYPE
		SYNTAX		INTEGER
		MAX-ACCESS	read-only
		STATUS		current
		DESCRIPTION
			"Local CLID for this tunnel"

	::= { l2FTunnelStatusInactiveEntry 1 }

	l2FTunnelStatusInactiveRemoteCLID	OBJECT-TYPE
		SYNTAX		INTEGER
		MAX-ACCESS	read-only
		STATUS		current
		DESCRIPTION
			"Remote CLID for this tunnel (0 = not known yet)"

	::= { l2FTunnelStatusInactiveEntry 2 }

	l2FTunnelStatusInactiveLocalAddress	OBJECT-TYPE
		SYNTAX		IpAddress
		MAX-ACCESS	read-only
		STATUS		current
		DESCRIPTION
			"IP address used by CVX"

	::= { l2FTunnelStatusInactiveEntry 3 }

	l2FTunnelStatusInactiveRemoteAddress	OBJECT-TYPE
		SYNTAX		IpAddress
		MAX-ACCESS	read-only
		STATUS		current
		DESCRIPTION
			"IP address of home gateway"

	::= { l2FTunnelStatusInactiveEntry 4 }

	l2FTunnelStatusInactiveState	OBJECT-TYPE
		SYNTAX		INTEGER {
				    idle(0),
				    start1(1),
				    start2(2),
				    opened(3),
				    close1(4),
				    close2(5)
				}
		MAX-ACCESS	read-only
		STATUS		current
		DESCRIPTION
			"Current state of this tunnel"

	::= { l2FTunnelStatusInactiveEntry 5 }

	l2FTunnelStatusInactiveUpTime	OBJECT-TYPE
		SYNTAX		INTEGER
		MAX-ACCESS	read-only
		STATUS		current
		DESCRIPTION
			"Time this tunnel has been active"

	::= { l2FTunnelStatusInactiveEntry 6 }

	l2FTunnelStatusInactiveActiveLinks	OBJECT-TYPE
		SYNTAX		INTEGER
		MAX-ACCESS	read-only
		STATUS		current
		DESCRIPTION
			"Current number of active links"

	::= { l2FTunnelStatusInactiveEntry 7 }

	l2FTunnelStatusInactiveMaxActiveLinks	OBJECT-TYPE
		SYNTAX		INTEGER
		MAX-ACCESS	read-only
		STATUS		current
		DESCRIPTION
			"Highest number of links"

	::= { l2FTunnelStatusInactiveEntry 8 }

	l2FTunnelStatusInactivePendingLinks	OBJECT-TYPE
		SYNTAX		INTEGER
		MAX-ACCESS	read-only
		STATUS		current
		DESCRIPTION
			"Current number of pending links"

	::= { l2FTunnelStatusInactiveEntry 9 }

	l2FTunnelStatusInactiveLinksAdded	OBJECT-TYPE
		SYNTAX		INTEGER
		MAX-ACCESS	read-only
		STATUS		current
		DESCRIPTION
			"Total number of links added to this tunnel"

	::= { l2FTunnelStatusInactiveEntry 10 }

	l2FTunnelStatusInactiveLinksAddedSuccessfully	OBJECT-TYPE
		SYNTAX		INTEGER
		MAX-ACCESS	read-only
		STATUS		current
		DESCRIPTION
			"Total number of links added successfully"

	::= { l2FTunnelStatusInactiveEntry 11 }

	l2FTunnelStatusInactiveLinksAddedUnsuccessfully	OBJECT-TYPE
		SYNTAX		INTEGER
		MAX-ACCESS	read-only
		STATUS		current
		DESCRIPTION
			"Total number of links added unsuccessfully"

	::= { l2FTunnelStatusInactiveEntry 12 }

	l2FTunnelStatusInactiveLinksRemoved	OBJECT-TYPE
		SYNTAX		INTEGER
		MAX-ACCESS	read-only
		STATUS		current
		DESCRIPTION
			"Total number of links removed"

	::= { l2FTunnelStatusInactiveEntry 13 }

	l2FTunnelStatusInactiveGotOpened	OBJECT-TYPE
		SYNTAX		Boolean
		MAX-ACCESS	read-only
		STATUS		current
		DESCRIPTION
			"Specifies whether tunnel was opened successfully"

	::= { l2FTunnelStatusInactiveEntry 14 }

	l2FTunnelStatusInactiveVPOP	OBJECT-TYPE
		SYNTAX		INTEGER
		MAX-ACCESS	read-only
		STATUS		current
		DESCRIPTION
			"VPOP of first link added to this tunnel"

	::= { l2FTunnelStatusInactiveEntry 15 }

	l2FTunnelStatusInactiveL2FTermationCause	OBJECT-TYPE
		SYNTAX		INTEGER
		MAX-ACCESS	read-only
		STATUS		current
		DESCRIPTION
			"L2F termination cause"

	::= { l2FTunnelStatusInactiveEntry 16 }


	l2FLinkStatusTable	OBJECT-TYPE
		SYNTAX		SEQUENCE OF L2FLinkStatusEntry
		MAX-ACCESS	not-accessible
		STATUS		current
		DESCRIPTION
			"Layer-2 Forwarding Link Status."

	::= { aptis-monitoring 1353 }

	l2FLinkStatusEntry	OBJECT-TYPE
		SYNTAX		L2FLinkStatusEntry
		MAX-ACCESS	not-accessible
		STATUS		current
		DESCRIPTION
			"This is the structure of entries in the
			 l2FLinkStatusTable."
		INDEX		{ l2FLinkStatusLocalCLID, l2FLinkStatusIndex }
	::= { l2FLinkStatusTable 1 }

	L2FLinkStatusEntry ::= SEQUENCE {
		l2FLinkStatusLocalCLID		INTEGER,
		l2FLinkStatusIndex		INTEGER,
		l2FLinkStatusSessionID		INTEGER,
		l2FLinkStatusVPOP		INTEGER,
		l2FLinkStatusMIDValue		INTEGER,
		l2FLinkStatusState		INTEGER,
		l2FLinkStatusUpTime		INTEGER,
		l2FLinkStatusUserName		DisplayString,
		l2FLinkStatusTxPackets		INTEGER,
		l2FLinkStatusTxBytes		INTEGER,
		l2FLinkStatusRxPackets		INTEGER,
		l2FLinkStatusRxBytes		INTEGER,
		l2FLinkStatusL2FTermationCause	INTEGER
	}

	l2FLinkStatusLocalCLID	OBJECT-TYPE
		SYNTAX		INTEGER
		MAX-ACCESS	read-only
		STATUS		current
		DESCRIPTION
			"Local CLID for this tunnel"

	::= { l2FLinkStatusEntry 1 }

	l2FLinkStatusIndex	OBJECT-TYPE
		SYNTAX		INTEGER
		MAX-ACCESS	read-only
		STATUS		current
		DESCRIPTION
			"Index of this link in the tunnel"

	::= { l2FLinkStatusEntry 2 }

	l2FLinkStatusSessionID	OBJECT-TYPE
		SYNTAX		INTEGER
		MAX-ACCESS	read-only
		STATUS		current
		DESCRIPTION
			"System session ID for this link"

	::= { l2FLinkStatusEntry 3 }

	l2FLinkStatusVPOP	OBJECT-TYPE
		SYNTAX		INTEGER
		MAX-ACCESS	read-only
		STATUS		current
		DESCRIPTION
			"VPOP of first link added to this tunnel"

	::= { l2FLinkStatusEntry 4 }

	l2FLinkStatusMIDValue	OBJECT-TYPE
		SYNTAX		INTEGER
		MAX-ACCESS	read-only
		STATUS		current
		DESCRIPTION
			"MID value for this link"

	::= { l2FLinkStatusEntry 11 }

	l2FLinkStatusState	OBJECT-TYPE
		SYNTAX		INTEGER {
				    idle(0),
				    pending(1),
				    start1(2),
				    opened(3),
				    close1(4),
				    close2(5)
				}
		MAX-ACCESS	read-only
		STATUS		current
		DESCRIPTION
			"Current state of this link"

	::= { l2FLinkStatusEntry 12 }

	l2FLinkStatusUpTime	OBJECT-TYPE
		SYNTAX		INTEGER
		MAX-ACCESS	read-only
		STATUS		current
		DESCRIPTION
			"Time this link has been active"

	::= { l2FLinkStatusEntry 13 }

	l2FLinkStatusUserName	OBJECT-TYPE
		SYNTAX		DisplayString (SIZE (0..64))
		MAX-ACCESS	read-only
		STATUS		current
		DESCRIPTION
			"Remote user name"

	::= { l2FLinkStatusEntry 14 }

	l2FLinkStatusTxPackets	OBJECT-TYPE
		SYNTAX		INTEGER
		MAX-ACCESS	read-only
		STATUS		current
		DESCRIPTION
			"Number of packets transmitted to remote user"

	::= { l2FLinkStatusEntry 21 }

	l2FLinkStatusTxBytes	OBJECT-TYPE
		SYNTAX		INTEGER
		MAX-ACCESS	read-only
		STATUS		current
		DESCRIPTION
			"Number of bytes transmitted to remote user"

	::= { l2FLinkStatusEntry 22 }

	l2FLinkStatusRxPackets	OBJECT-TYPE
		SYNTAX		INTEGER
		MAX-ACCESS	read-only
		STATUS		current
		DESCRIPTION
			"Number of packets received from remote user"

	::= { l2FLinkStatusEntry 23 }

	l2FLinkStatusRxBytes	OBJECT-TYPE
		SYNTAX		INTEGER
		MAX-ACCESS	read-only
		STATUS		current
		DESCRIPTION
			"Number of bytes received from remote user"

	::= { l2FLinkStatusEntry 24 }

	l2FLinkStatusL2FTermationCause	OBJECT-TYPE
		SYNTAX		INTEGER
		MAX-ACCESS	read-only
		STATUS		current
		DESCRIPTION
			"L2F termination cause"

	::= { l2FLinkStatusEntry 31 }


	l2FLogEntryTable	OBJECT-TYPE
		SYNTAX		SEQUENCE OF L2FLogEntryEntry
		MAX-ACCESS	not-accessible
		STATUS		current
		DESCRIPTION
			"Layer-2 Forwarding Log Entry Information."

	::= { aptis-monitoring 1354 }

	l2FLogEntryEntry	OBJECT-TYPE
		SYNTAX		L2FLogEntryEntry
		MAX-ACCESS	not-accessible
		STATUS		current
		DESCRIPTION
			"This is the structure of entries in the
			 l2FLogEntryTable."
		INDEX		{ l2FLogEntryLocalCLID, l2FLogEntryIndex }
	::= { l2FLogEntryTable 1 }

	L2FLogEntryEntry ::= SEQUENCE {
		l2FLogEntryLocalCLID		INTEGER,
		l2FLogEntryIndex		INTEGER,
		l2FLogEntryMinIndex		INTEGER,
		l2FLogEntryMaxIndex		INTEGER,
		l2FLogEntryUpTime		INTEGER,
		l2FLogEntryEntryText		OCTET STRING
	}

	l2FLogEntryLocalCLID	OBJECT-TYPE
		SYNTAX		INTEGER
		MAX-ACCESS	read-only
		STATUS		current
		DESCRIPTION
			"Local CLID for this tunnel"

	::= { l2FLogEntryEntry 1 }

	l2FLogEntryIndex	OBJECT-TYPE
		SYNTAX		INTEGER
		MAX-ACCESS	read-only
		STATUS		current
		DESCRIPTION
			"Log entry index"

	::= { l2FLogEntryEntry 2 }

	l2FLogEntryMinIndex	OBJECT-TYPE
		SYNTAX		INTEGER
		MAX-ACCESS	read-only
		STATUS		current
		DESCRIPTION
			"Index of oldest event available"

	::= { l2FLogEntryEntry 11 }

	l2FLogEntryMaxIndex	OBJECT-TYPE
		SYNTAX		INTEGER
		MAX-ACCESS	read-only
		STATUS		current
		DESCRIPTION
			"Index of newest event available"

	::= { l2FLogEntryEntry 12 }

	l2FLogEntryUpTime	OBJECT-TYPE
		SYNTAX		INTEGER
		MAX-ACCESS	read-only
		STATUS		current
		DESCRIPTION
			"Time this tunnel has been active"

	::= { l2FLogEntryEntry 13 }

	l2FLogEntryEntryText	OBJECT-TYPE
		SYNTAX		OCTET STRING (SIZE (0..256))
		MAX-ACCESS	read-only
		STATUS		current
		DESCRIPTION
			"Log entry text."

	::= { l2FLogEntryEntry 21 }

-- This file generated from  l2tp.cml by smog.
-- date: Thu Jun 29 01:11:28  2000

	l2TPTunnelStatusActiveTable	OBJECT-TYPE
		SYNTAX		SEQUENCE OF L2TPTunnelStatusActiveEntry
		MAX-ACCESS	not-accessible
		STATUS		current
		DESCRIPTION
			"Layer-2 Tunneling Protocol Active Tunnel Status."

	::= { aptis-monitoring 1507 }

	l2TPTunnelStatusActiveEntry	OBJECT-TYPE
		SYNTAX		L2TPTunnelStatusActiveEntry
		MAX-ACCESS	not-accessible
		STATUS		current
		DESCRIPTION
			"This is the structure of entries in the
			 l2TPTunnelStatusActiveTable."
		INDEX		{ l2TPTunnelStatusActiveLocalID }
	::= { l2TPTunnelStatusActiveTable 1 }

	L2TPTunnelStatusActiveEntry ::= SEQUENCE {
		l2TPTunnelStatusActiveSlot	INTEGER,
		l2TPTunnelStatusActiveLocalID	INTEGER,
		l2TPTunnelStatusActiveRemoteID	INTEGER,
		l2TPTunnelStatusActiveLocalAddress IpAddress,
		l2TPTunnelStatusActiveRemoteAddress IpAddress,
		l2TPTunnelStatusActiveState	INTEGER,
		l2TPTunnelStatusActiveUpTime	INTEGER,
		l2TPTunnelStatusActiveActiveLinks INTEGER,
		l2TPTunnelStatusActiveMaxActiveLinks INTEGER,
		l2TPTunnelStatusActivePendingLinks INTEGER,
		l2TPTunnelStatusActiveLinksAdded INTEGER,
		l2TPTunnelStatusActiveLinksAddedSuccessfully INTEGER,
		l2TPTunnelStatusActiveLinksAddedUnsuccessfully INTEGER,
		l2TPTunnelStatusActiveLinksRemoved INTEGER,
		l2TPTunnelStatusActiveGotOpened	Boolean,
		l2TPTunnelStatusActiveVPOP	INTEGER,
		l2TPTunnelStatusActiveL2TPTermationCause INTEGER
	}

	l2TPTunnelStatusActiveSlot	OBJECT-TYPE
		SYNTAX		INTEGER
		MAX-ACCESS	read-only
		STATUS		current
		DESCRIPTION
			"Slot on which tunnel is terminated"

	::= { l2TPTunnelStatusActiveEntry 1 }

	l2TPTunnelStatusActiveLocalID	OBJECT-TYPE
		SYNTAX		INTEGER
		MAX-ACCESS	read-only
		STATUS		current
		DESCRIPTION
			"Local ID for this tunnel"

	::= { l2TPTunnelStatusActiveEntry 2 }

	l2TPTunnelStatusActiveRemoteID	OBJECT-TYPE
		SYNTAX		INTEGER
		MAX-ACCESS	read-only
		STATUS		current
		DESCRIPTION
			"Remote ID for this tunnel (0 = not known yet)"

	::= { l2TPTunnelStatusActiveEntry 3 }

	l2TPTunnelStatusActiveLocalAddress	OBJECT-TYPE
		SYNTAX		IpAddress
		MAX-ACCESS	read-only
		STATUS		current
		DESCRIPTION
			"IP address used by CVX"

	::= { l2TPTunnelStatusActiveEntry 4 }

	l2TPTunnelStatusActiveRemoteAddress	OBJECT-TYPE
		SYNTAX		IpAddress
		MAX-ACCESS	read-only
		STATUS		current
		DESCRIPTION
			"IP address of LNS"

	::= { l2TPTunnelStatusActiveEntry 5 }

	l2TPTunnelStatusActiveState	OBJECT-TYPE
		SYNTAX		INTEGER {
				    idle(0),
				    waitCtrlReply(1),
				    waitCtrlConn(2),
				    established(3),
				    closed(4)
				}
		MAX-ACCESS	read-only
		STATUS		current
		DESCRIPTION
			"Current state of this tunnel"

	::= { l2TPTunnelStatusActiveEntry 6 }

	l2TPTunnelStatusActiveUpTime	OBJECT-TYPE
		SYNTAX		INTEGER
		MAX-ACCESS	read-only
		STATUS		current
		DESCRIPTION
			"Time this tunnel has been active"

	::= { l2TPTunnelStatusActiveEntry 7 }

	l2TPTunnelStatusActiveActiveLinks	OBJECT-TYPE
		SYNTAX		INTEGER
		MAX-ACCESS	read-only
		STATUS		current
		DESCRIPTION
			"Current number of active links"

	::= { l2TPTunnelStatusActiveEntry 8 }

	l2TPTunnelStatusActiveMaxActiveLinks	OBJECT-TYPE
		SYNTAX		INTEGER
		MAX-ACCESS	read-only
		STATUS		current
		DESCRIPTION
			"Highest number of links"

	::= { l2TPTunnelStatusActiveEntry 9 }

	l2TPTunnelStatusActivePendingLinks	OBJECT-TYPE
		SYNTAX		INTEGER
		MAX-ACCESS	read-only
		STATUS		current
		DESCRIPTION
			"Current number of pending links"

	::= { l2TPTunnelStatusActiveEntry 10 }

	l2TPTunnelStatusActiveLinksAdded	OBJECT-TYPE
		SYNTAX		INTEGER
		MAX-ACCESS	read-only
		STATUS		current
		DESCRIPTION
			"Total number of links added to this tunnel"

	::= { l2TPTunnelStatusActiveEntry 11 }

	l2TPTunnelStatusActiveLinksAddedSuccessfully	OBJECT-TYPE
		SYNTAX		INTEGER
		MAX-ACCESS	read-only
		STATUS		current
		DESCRIPTION
			"Total number of links added successfully"

	::= { l2TPTunnelStatusActiveEntry 12 }

	l2TPTunnelStatusActiveLinksAddedUnsuccessfully	OBJECT-TYPE
		SYNTAX		INTEGER
		MAX-ACCESS	read-only
		STATUS		current
		DESCRIPTION
			"Total number of links added unsuccessfully"

	::= { l2TPTunnelStatusActiveEntry 13 }

	l2TPTunnelStatusActiveLinksRemoved	OBJECT-TYPE
		SYNTAX		INTEGER
		MAX-ACCESS	read-only
		STATUS		current
		DESCRIPTION
			"Total number of links removed"

	::= { l2TPTunnelStatusActiveEntry 14 }

	l2TPTunnelStatusActiveGotOpened	OBJECT-TYPE
		SYNTAX		Boolean
		MAX-ACCESS	read-only
		STATUS		current
		DESCRIPTION
			"Specifies whether tunnel was opened successfully"

	::= { l2TPTunnelStatusActiveEntry 15 }

	l2TPTunnelStatusActiveVPOP	OBJECT-TYPE
		SYNTAX		INTEGER
		MAX-ACCESS	read-only
		STATUS		current
		DESCRIPTION
			"VPOP of first link added to this tunnel"

	::= { l2TPTunnelStatusActiveEntry 16 }

	l2TPTunnelStatusActiveL2TPTermationCause	OBJECT-TYPE
		SYNTAX		INTEGER
		MAX-ACCESS	read-only
		STATUS		current
		DESCRIPTION
			"L2TP termination cause"

	::= { l2TPTunnelStatusActiveEntry 17 }


	l2TPTunnelStatusInactiveTable	OBJECT-TYPE
		SYNTAX		SEQUENCE OF L2TPTunnelStatusInactiveEntry
		MAX-ACCESS	not-accessible
		STATUS		current
		DESCRIPTION
			"Layer-2 Tunneling Protocol Inactive Tunnel Status."

	::= { aptis-monitoring 1508 }

	l2TPTunnelStatusInactiveEntry	OBJECT-TYPE
		SYNTAX		L2TPTunnelStatusInactiveEntry
		MAX-ACCESS	not-accessible
		STATUS		current
		DESCRIPTION
			"This is the structure of entries in the
			 l2TPTunnelStatusInactiveTable."
		INDEX		{ l2TPTunnelStatusInactiveLocalID }
	::= { l2TPTunnelStatusInactiveTable 1 }

	L2TPTunnelStatusInactiveEntry ::= SEQUENCE {
		l2TPTunnelStatusInactiveSlot	INTEGER,
		l2TPTunnelStatusInactiveLocalID	INTEGER,
		l2TPTunnelStatusInactiveRemoteID INTEGER,
		l2TPTunnelStatusInactiveLocalAddress IpAddress,
		l2TPTunnelStatusInactiveRemoteAddress IpAddress,
		l2TPTunnelStatusInactiveState	INTEGER,
		l2TPTunnelStatusInactiveUpTime	INTEGER,
		l2TPTunnelStatusInactiveActiveLinks INTEGER,
		l2TPTunnelStatusInactiveMaxActiveLinks INTEGER,
		l2TPTunnelStatusInactivePendingLinks INTEGER,
		l2TPTunnelStatusInactiveLinksAdded INTEGER,
		l2TPTunnelStatusInactiveLinksAddedSuccessfully INTEGER,
		l2TPTunnelStatusInactiveLinksAddedUnsuccessfully INTEGER,
		l2TPTunnelStatusInactiveLinksRemoved INTEGER,
		l2TPTunnelStatusInactiveGotOpened Boolean,
		l2TPTunnelStatusInactiveVPOP	INTEGER,
		l2TPTunnelStatusInactiveL2TPTermationCause INTEGER
	}

	l2TPTunnelStatusInactiveSlot	OBJECT-TYPE
		SYNTAX		INTEGER
		MAX-ACCESS	read-only
		STATUS		current
		DESCRIPTION
			"Slot on which tunnel is terminated"

	::= { l2TPTunnelStatusInactiveEntry 1 }

	l2TPTunnelStatusInactiveLocalID	OBJECT-TYPE
		SYNTAX		INTEGER
		MAX-ACCESS	read-only
		STATUS		current
		DESCRIPTION
			"Local ID for this tunnel"

	::= { l2TPTunnelStatusInactiveEntry 2 }

	l2TPTunnelStatusInactiveRemoteID	OBJECT-TYPE
		SYNTAX		INTEGER
		MAX-ACCESS	read-only
		STATUS		current
		DESCRIPTION
			"Remote ID for this tunnel (0 = not known yet)"

	::= { l2TPTunnelStatusInactiveEntry 3 }

	l2TPTunnelStatusInactiveLocalAddress	OBJECT-TYPE
		SYNTAX		IpAddress
		MAX-ACCESS	read-only
		STATUS		current
		DESCRIPTION
			"IP address used by CVX"

	::= { l2TPTunnelStatusInactiveEntry 4 }

	l2TPTunnelStatusInactiveRemoteAddress	OBJECT-TYPE
		SYNTAX		IpAddress
		MAX-ACCESS	read-only
		STATUS		current
		DESCRIPTION
			"IP address of LNS"

	::= { l2TPTunnelStatusInactiveEntry 5 }

	l2TPTunnelStatusInactiveState	OBJECT-TYPE
		SYNTAX		INTEGER {
				    idle(0),
				    waitCtrlReply(1),
				    waitCtrlConn(2),
				    established(3),
				    closed(4)
				}
		MAX-ACCESS	read-only
		STATUS		current
		DESCRIPTION
			"Current state of this tunnel"

	::= { l2TPTunnelStatusInactiveEntry 6 }

	l2TPTunnelStatusInactiveUpTime	OBJECT-TYPE
		SYNTAX		INTEGER
		MAX-ACCESS	read-only
		STATUS		current
		DESCRIPTION
			"Time this tunnel has been active"

	::= { l2TPTunnelStatusInactiveEntry 7 }

	l2TPTunnelStatusInactiveActiveLinks	OBJECT-TYPE
		SYNTAX		INTEGER
		MAX-ACCESS	read-only
		STATUS		current
		DESCRIPTION
			"Current number of active links"

	::= { l2TPTunnelStatusInactiveEntry 8 }

	l2TPTunnelStatusInactiveMaxActiveLinks	OBJECT-TYPE
		SYNTAX		INTEGER
		MAX-ACCESS	read-only
		STATUS		current
		DESCRIPTION
			"Highest number of links"

	::= { l2TPTunnelStatusInactiveEntry 9 }

	l2TPTunnelStatusInactivePendingLinks	OBJECT-TYPE
		SYNTAX		INTEGER
		MAX-ACCESS	read-only
		STATUS		current
		DESCRIPTION
			"Current number of pending links"

	::= { l2TPTunnelStatusInactiveEntry 10 }

	l2TPTunnelStatusInactiveLinksAdded	OBJECT-TYPE
		SYNTAX		INTEGER
		MAX-ACCESS	read-only
		STATUS		current
		DESCRIPTION
			"Total number of links added to this tunnel"

	::= { l2TPTunnelStatusInactiveEntry 11 }

	l2TPTunnelStatusInactiveLinksAddedSuccessfully	OBJECT-TYPE
		SYNTAX		INTEGER
		MAX-ACCESS	read-only
		STATUS		current
		DESCRIPTION
			"Total number of links added successfully"

	::= { l2TPTunnelStatusInactiveEntry 12 }

	l2TPTunnelStatusInactiveLinksAddedUnsuccessfully	OBJECT-TYPE
		SYNTAX		INTEGER
		MAX-ACCESS	read-only
		STATUS		current
		DESCRIPTION
			"Total number of links added unsuccessfully"

	::= { l2TPTunnelStatusInactiveEntry 13 }

	l2TPTunnelStatusInactiveLinksRemoved	OBJECT-TYPE
		SYNTAX		INTEGER
		MAX-ACCESS	read-only
		STATUS		current
		DESCRIPTION
			"Total number of links removed"

	::= { l2TPTunnelStatusInactiveEntry 14 }

	l2TPTunnelStatusInactiveGotOpened	OBJECT-TYPE
		SYNTAX		Boolean
		MAX-ACCESS	read-only
		STATUS		current
		DESCRIPTION
			"Specifies whether tunnel was opened successfully"

	::= { l2TPTunnelStatusInactiveEntry 15 }

	l2TPTunnelStatusInactiveVPOP	OBJECT-TYPE
		SYNTAX		INTEGER
		MAX-ACCESS	read-only
		STATUS		current
		DESCRIPTION
			"VPOP of first link added to this tunnel"

	::= { l2TPTunnelStatusInactiveEntry 16 }

	l2TPTunnelStatusInactiveL2TPTermationCause	OBJECT-TYPE
		SYNTAX		INTEGER
		MAX-ACCESS	read-only
		STATUS		current
		DESCRIPTION
			"L2TP termination cause"

	::= { l2TPTunnelStatusInactiveEntry 17 }


	l2TPLinkStatusTable	OBJECT-TYPE
		SYNTAX		SEQUENCE OF L2TPLinkStatusEntry
		MAX-ACCESS	not-accessible
		STATUS		current
		DESCRIPTION
			"Layer-2 Tunneling Protocol Link Status."

	::= { aptis-monitoring 1509 }

	l2TPLinkStatusEntry	OBJECT-TYPE
		SYNTAX		L2TPLinkStatusEntry
		MAX-ACCESS	not-accessible
		STATUS		current
		DESCRIPTION
			"This is the structure of entries in the
			 l2TPLinkStatusTable."
		INDEX		{ l2TPLinkStatusLocalID, l2TPLinkStatusIndex }
	::= { l2TPLinkStatusTable 1 }

	L2TPLinkStatusEntry ::= SEQUENCE {
		l2TPLinkStatusLocalID		INTEGER,
		l2TPLinkStatusRemoteID		INTEGER,
		l2TPLinkStatusIndex		INTEGER,
		l2TPLinkStatusSessionID		INTEGER,
		l2TPLinkStatusVPOP		INTEGER,
		l2TPLinkStatusState		INTEGER,
		l2TPLinkStatusUpTime		INTEGER,
		l2TPLinkStatusUserName		DisplayString,
		l2TPLinkStatusTxPackets		INTEGER,
		l2TPLinkStatusTxBytes		INTEGER,
		l2TPLinkStatusRxPackets		INTEGER,
		l2TPLinkStatusRxBytes		INTEGER,
		l2TPLinkStatusL2TPTermationCause INTEGER
	}

	l2TPLinkStatusLocalID	OBJECT-TYPE
		SYNTAX		INTEGER
		MAX-ACCESS	read-only
		STATUS		current
		DESCRIPTION
			"Local ID for this link"

	::= { l2TPLinkStatusEntry 1 }

	l2TPLinkStatusRemoteID	OBJECT-TYPE
		SYNTAX		INTEGER
		MAX-ACCESS	read-only
		STATUS		current
		DESCRIPTION
			"Local ID for this link"

	::= { l2TPLinkStatusEntry 2 }

	l2TPLinkStatusIndex	OBJECT-TYPE
		SYNTAX		INTEGER
		MAX-ACCESS	read-only
		STATUS		current
		DESCRIPTION
			"Index of this link in the tunnel"

	::= { l2TPLinkStatusEntry 3 }

	l2TPLinkStatusSessionID	OBJECT-TYPE
		SYNTAX		INTEGER
		MAX-ACCESS	read-only
		STATUS		current
		DESCRIPTION
			"System session ID for this link"

	::= { l2TPLinkStatusEntry 4 }

	l2TPLinkStatusVPOP	OBJECT-TYPE
		SYNTAX		INTEGER
		MAX-ACCESS	read-only
		STATUS		current
		DESCRIPTION
			"VPOP of first link added to this tunnel"

	::= { l2TPLinkStatusEntry 5 }

	l2TPLinkStatusState	OBJECT-TYPE
		SYNTAX		INTEGER {
				    idle(0),
				    waitReply(1),
				    connected(2),
				    closed(3)
				}
		MAX-ACCESS	read-only
		STATUS		current
		DESCRIPTION
			"Current state of this link"

	::= { l2TPLinkStatusEntry 11 }

	l2TPLinkStatusUpTime	OBJECT-TYPE
		SYNTAX		INTEGER
		MAX-ACCESS	read-only
		STATUS		current
		DESCRIPTION
			"Time this link has been active"

	::= { l2TPLinkStatusEntry 12 }

	l2TPLinkStatusUserName	OBJECT-TYPE
		SYNTAX		DisplayString (SIZE (0..64))
		MAX-ACCESS	read-only
		STATUS		current
		DESCRIPTION
			"Remote user name"

	::= { l2TPLinkStatusEntry 13 }

	l2TPLinkStatusTxPackets	OBJECT-TYPE
		SYNTAX		INTEGER
		MAX-ACCESS	read-only
		STATUS		current
		DESCRIPTION
			"Number of packets transmitted to remote user"

	::= { l2TPLinkStatusEntry 21 }

	l2TPLinkStatusTxBytes	OBJECT-TYPE
		SYNTAX		INTEGER
		MAX-ACCESS	read-only
		STATUS		current
		DESCRIPTION
			"Number of bytes transmitted to remote user"

	::= { l2TPLinkStatusEntry 22 }

	l2TPLinkStatusRxPackets	OBJECT-TYPE
		SYNTAX		INTEGER
		MAX-ACCESS	read-only
		STATUS		current
		DESCRIPTION
			"Number of packets received from remote user"

	::= { l2TPLinkStatusEntry 23 }

	l2TPLinkStatusRxBytes	OBJECT-TYPE
		SYNTAX		INTEGER
		MAX-ACCESS	read-only
		STATUS		current
		DESCRIPTION
			"Number of bytes received from remote user"

	::= { l2TPLinkStatusEntry 24 }

	l2TPLinkStatusL2TPTermationCause	OBJECT-TYPE
		SYNTAX		INTEGER
		MAX-ACCESS	read-only
		STATUS		current
		DESCRIPTION
			"L2TP termination cause"

	::= { l2TPLinkStatusEntry 31 }


	l2TPLogEntryTable	OBJECT-TYPE
		SYNTAX		SEQUENCE OF L2TPLogEntryEntry
		MAX-ACCESS	not-accessible
		STATUS		current
		DESCRIPTION
			"Layer-2 Tunneling Protocol Log Entry Information."

	::= { aptis-monitoring 1510 }

	l2TPLogEntryEntry	OBJECT-TYPE
		SYNTAX		L2TPLogEntryEntry
		MAX-ACCESS	not-accessible
		STATUS		current
		DESCRIPTION
			"This is the structure of entries in the
			 l2TPLogEntryTable."
		INDEX		{ l2TPLogEntryLocalID, l2TPLogEntryIndex }
	::= { l2TPLogEntryTable 1 }

	L2TPLogEntryEntry ::= SEQUENCE {
		l2TPLogEntryLocalID		INTEGER,
		l2TPLogEntryIndex		INTEGER,
		l2TPLogEntryMinIndex		INTEGER,
		l2TPLogEntryMaxIndex		INTEGER,
		l2TPLogEntryUpTime		INTEGER,
		l2TPLogEntryEntryText		OCTET STRING
	}

	l2TPLogEntryLocalID	OBJECT-TYPE
		SYNTAX		INTEGER
		MAX-ACCESS	read-only
		STATUS		current
		DESCRIPTION
			"Local ID for this tunnel"

	::= { l2TPLogEntryEntry 1 }

	l2TPLogEntryIndex	OBJECT-TYPE
		SYNTAX		INTEGER
		MAX-ACCESS	read-only
		STATUS		current
		DESCRIPTION
			"Log entry index"

	::= { l2TPLogEntryEntry 2 }

	l2TPLogEntryMinIndex	OBJECT-TYPE
		SYNTAX		INTEGER
		MAX-ACCESS	read-only
		STATUS		current
		DESCRIPTION
			"Index of oldest event available"

	::= { l2TPLogEntryEntry 11 }

	l2TPLogEntryMaxIndex	OBJECT-TYPE
		SYNTAX		INTEGER
		MAX-ACCESS	read-only
		STATUS		current
		DESCRIPTION
			"Index of newest event available"

	::= { l2TPLogEntryEntry 12 }

	l2TPLogEntryUpTime	OBJECT-TYPE
		SYNTAX		INTEGER
		MAX-ACCESS	read-only
		STATUS		current
		DESCRIPTION
			"Time this tunnel has been active"

	::= { l2TPLogEntryEntry 13 }

	l2TPLogEntryEntryText	OBJECT-TYPE
		SYNTAX		OCTET STRING (SIZE (0..256))
		MAX-ACCESS	read-only
		STATUS		current
		DESCRIPTION
			"Log entry text."

	::= { l2TPLogEntryEntry 21 }

-- This file generated from  mam.cml by smog.
-- date: Thu Jun 29 01:11:29  2000

	mamLogEntryTable	OBJECT-TYPE
		SYNTAX		SEQUENCE OF MamLogEntryEntry
		MAX-ACCESS	not-accessible
		STATUS		current
		DESCRIPTION
			"MAM Log Table."

	::= { aptis-monitoring 1402 }

	mamLogEntryEntry	OBJECT-TYPE
		SYNTAX		MamLogEntryEntry
		MAX-ACCESS	not-accessible
		STATUS		current
		DESCRIPTION
			"This is the structure of entries in the
			 mamLogEntryTable."
		INDEX		{ mamLogEntryIndex }
	::= { mamLogEntryTable 1 }

	MamLogEntryEntry ::= SEQUENCE {
		mamLogEntryIndex		INTEGER,
		mamLogEntryMinIndex		INTEGER,
		mamLogEntryMaxIndex		INTEGER,
		mamLogEntryEntryText		OCTET STRING
	}

	mamLogEntryIndex	OBJECT-TYPE
		SYNTAX		INTEGER
		MAX-ACCESS	read-only
		STATUS		current
		DESCRIPTION
			"Log entry index"

	::= { mamLogEntryEntry 1 }

	mamLogEntryMinIndex	OBJECT-TYPE
		SYNTAX		INTEGER
		MAX-ACCESS	read-only
		STATUS		current
		DESCRIPTION
			"Index of oldest event available"

	::= { mamLogEntryEntry 2 }

	mamLogEntryMaxIndex	OBJECT-TYPE
		SYNTAX		INTEGER
		MAX-ACCESS	read-only
		STATUS		current
		DESCRIPTION
			"Index of newest event available"

	::= { mamLogEntryEntry 3 }

	mamLogEntryEntryText	OBJECT-TYPE
		SYNTAX		OCTET STRING (SIZE (0..1024))
		MAX-ACCESS	read-only
		STATUS		current
		DESCRIPTION
			"Log entry text."

	::= { mamLogEntryEntry 4 }

-- This file generated from  modem.cml by smog.
-- date: Thu Jun 29 01:11:29  2000

	modemStatsTable	OBJECT-TYPE
		SYNTAX		SEQUENCE OF ModemStatsEntry
		MAX-ACCESS	not-accessible
		STATUS		current
		DESCRIPTION
			"Modem stats table."

	::= { aptis-monitoring 1422 }

	modemStatsEntry	OBJECT-TYPE
		SYNTAX		ModemStatsEntry
		MAX-ACCESS	not-accessible
		STATUS		current
		DESCRIPTION
			"This is the structure of entries in the
			 modemStatsTable."
		INDEX		{ modemStatsSlot, modemStatsModemIndex }
	::= { modemStatsTable 1 }

	ModemStatsEntry ::= SEQUENCE {
		modemStatsState			INTEGER,
		modemStatsSlot			INTEGER,
		modemStatsIOP			INTEGER,
		modemStatsDMM			INTEGER,
		modemStatsPack			INTEGER,
		modemStatsModem			INTEGER,
		modemStatsCurrentSessionID	INTEGER,
		modemStatsModemIndex		INTEGER,
		modemStatsRPI			INTEGER,
		modemStatsTotalCalls		INTEGER,
		modemStatsConnectedCalls	INTEGER,
		modemStatsLast32Calls		INTEGER,
		modemStatsConnectedWin		INTEGER,
		modemStatsConnectedLose		INTEGER,
		modemStatsAuthCalls		INTEGER,
		modemStatsLast32Auth		INTEGER,
		modemStatsAuthWin		INTEGER,
		modemStatsAuthLose		INTEGER,
		modemStatsECCalls		INTEGER,
		modemStatsDCCalls		INTEGER,
		modemStatsK56Calls		INTEGER,
		modemStatsV90Calls		INTEGER,
		modemStatsV34Calls		INTEGER,
		modemStatsV32Calls		INTEGER,
		modemStatsStatsSamples		INTEGER,
		modemStatsInitialTxSum		INTEGER,
		modemStatsMinTxSum		INTEGER,
		modemStatsMaxTxSum		INTEGER,
		modemStatsFinalTxSum		INTEGER,
		modemStatsMinTxSpeed		INTEGER,
		modemStatsMaxTxSpeed		INTEGER,
		modemStatsInitialRxSum		INTEGER,
		modemStatsMinRxSum		INTEGER,
		modemStatsMaxRxSum		INTEGER,
		modemStatsFinalRxSum		INTEGER,
		modemStatsMinRxSpeed		INTEGER,
		modemStatsMaxRxSpeed		INTEGER,
		modemStatsDownloadAttempts	INTEGER,
		modemStatsDownloadSuccesses	INTEGER,
		modemStatsResetFailures		INTEGER,
		modemStatsResetRevivals		INTEGER,
		modemStatsPackCrashes		INTEGER,
		modemStatsPackRevivals		INTEGER
	}

	modemStatsState	OBJECT-TYPE
		SYNTAX		INTEGER {
				    disabled(1),
				    noDownload(2),
				    dead(3),
				    takenOut(4),
				    idle(5),
				    active(6),
				    downloading(7)
				}
		MAX-ACCESS	read-only
		STATUS		current
		DESCRIPTION
			"Modem's current state."

	::= { modemStatsEntry 1 }

	modemStatsSlot	OBJECT-TYPE
		SYNTAX		INTEGER (1..18)
		MAX-ACCESS	read-only
		STATUS		current
		DESCRIPTION
			"The slot that contains this modem"

	::= { modemStatsEntry 2 }

	modemStatsIOP	OBJECT-TYPE
		SYNTAX		INTEGER (1..3)
		MAX-ACCESS	read-only
		STATUS		current
		DESCRIPTION
			"The IOP on the card that controls this modem"

	::= { modemStatsEntry 3 }

	modemStatsDMM	OBJECT-TYPE
		SYNTAX		INTEGER (1..6)
		MAX-ACCESS	read-only
		STATUS		current
		DESCRIPTION
			"The DMM on the card that contains this modem"

	::= { modemStatsEntry 4 }

	modemStatsPack	OBJECT-TYPE
		SYNTAX		INTEGER (1..2)
		MAX-ACCESS	read-only
		STATUS		current
		DESCRIPTION
			"The pack on the DMM that contains this modem"

	::= { modemStatsEntry 5 }

	modemStatsModem	OBJECT-TYPE
		SYNTAX		INTEGER (1..6)
		MAX-ACCESS	read-only
		STATUS		current
		DESCRIPTION
			"The modem's number on the pack"

	::= { modemStatsEntry 6 }

	modemStatsCurrentSessionID	OBJECT-TYPE
		SYNTAX		INTEGER
		MAX-ACCESS	read-only
		STATUS		current
		DESCRIPTION
			"If active, the ID of the modem's session"

	::= { modemStatsEntry 7 }

	modemStatsModemIndex	OBJECT-TYPE
		SYNTAX		INTEGER
		MAX-ACCESS	read-only
		STATUS		current
		DESCRIPTION
			"The modem number associated with this entry"

	::= { modemStatsEntry 8 }

	modemStatsRPI	OBJECT-TYPE
		SYNTAX		INTEGER (0..100)
		MAX-ACCESS	read-only
		STATUS		current
		DESCRIPTION
			"This modem's current rating (0..100). A modem's RPI
			reveals a modem's quality relative to other modems."

	::= { modemStatsEntry 101 }

	modemStatsTotalCalls	OBJECT-TYPE
		SYNTAX		INTEGER
		MAX-ACCESS	read-only
		STATUS		current
		DESCRIPTION
			"The total number of calls assigned to this modem"

	::= { modemStatsEntry 102 }

	modemStatsConnectedCalls	OBJECT-TYPE
		SYNTAX		INTEGER
		MAX-ACCESS	read-only
		STATUS		current
		DESCRIPTION
			"The total numer of calls on which this modem has
			successfully negotiated a connection with the remote
			modem."

	::= { modemStatsEntry 201 }

	modemStatsLast32Calls	OBJECT-TYPE
		SYNTAX		INTEGER
		MAX-ACCESS	read-only
		STATUS		current
		DESCRIPTION
			"A bitmask indicating connection success (bit is set)
			or failure (bit is not set) on the last 32 calls. The
			lowest-order bit represents the most recent call, and
			the highest-order bit represents the oldest call."

	::= { modemStatsEntry 202 }

	modemStatsConnectedWin	OBJECT-TYPE
		SYNTAX		INTEGER
		MAX-ACCESS	read-only
		STATUS		current
		DESCRIPTION
			"The number of consecutive calls assigned to this
			modem that connected successfully. A value of 0
			indicates that the last call did not connect
			successfully."

	::= { modemStatsEntry 203 }

	modemStatsConnectedLose	OBJECT-TYPE
		SYNTAX		INTEGER
		MAX-ACCESS	read-only
		STATUS		current
		DESCRIPTION
			"The number of consecutive calls assigned to this
			modem that did not connect successfully. A value of 0
			indicates that the last call did connect
			successfully."

	::= { modemStatsEntry 204 }

	modemStatsAuthCalls	OBJECT-TYPE
		SYNTAX		INTEGER
		MAX-ACCESS	read-only
		STATUS		current
		DESCRIPTION
			"The total numer of calls on which this modem has
			connected, and which have proceeded to the
			authentication stage. This does not mean that
			authentication was successful, just that it was
			attempted."

	::= { modemStatsEntry 301 }

	modemStatsLast32Auth	OBJECT-TYPE
		SYNTAX		INTEGER
		MAX-ACCESS	read-only
		STATUS		current
		DESCRIPTION
			"A bitmask indicating connection success (bit is set)
			or failure (bit is not set) on the last 32 calls
			reaching the authentication stage. The lowest-order
			bit represents the most recent call, and the
			highest-order bit represents the oldest call."

	::= { modemStatsEntry 302 }

	modemStatsAuthWin	OBJECT-TYPE
		SYNTAX		INTEGER
		MAX-ACCESS	read-only
		STATUS		current
		DESCRIPTION
			"The number of consecutive calls assigned to this
			modem that connected and reached the authentication
			stage. A value of 0 indicates that the last call did
			not reach the authentication stage."

	::= { modemStatsEntry 303 }

	modemStatsAuthLose	OBJECT-TYPE
		SYNTAX		INTEGER
		MAX-ACCESS	read-only
		STATUS		current
		DESCRIPTION
			"The number of consecutive calls assigned to this
			modem that did not reach the authentication stage. A
			value of 0 indicates that the last call did reach the
			authentication stage."

	::= { modemStatsEntry 304 }

	modemStatsECCalls	OBJECT-TYPE
		SYNTAX		INTEGER
		MAX-ACCESS	read-only
		STATUS		current
		DESCRIPTION
			"The total numer of calls on which this modem has
			connected and negotiated an error correction
			protocol."

	::= { modemStatsEntry 401 }

	modemStatsDCCalls	OBJECT-TYPE
		SYNTAX		INTEGER
		MAX-ACCESS	read-only
		STATUS		current
		DESCRIPTION
			"The total numer of calls on which this modem has
			connected and negotiated a data compression protocol."

	::= { modemStatsEntry 402 }

	modemStatsK56Calls	OBJECT-TYPE
		SYNTAX		INTEGER
		MAX-ACCESS	read-only
		STATUS		current
		DESCRIPTION
			"The total numer of calls on which this modem has
			connected and negotiated the K56 Flex modulation
			protocol."

	::= { modemStatsEntry 403 }

	modemStatsV90Calls	OBJECT-TYPE
		SYNTAX		INTEGER
		MAX-ACCESS	read-only
		STATUS		current
		DESCRIPTION
			"The total numer of calls on which this modem has
			connected and negotiated the V.90 modulation
			protocol."

	::= { modemStatsEntry 404 }

	modemStatsV34Calls	OBJECT-TYPE
		SYNTAX		INTEGER
		MAX-ACCESS	read-only
		STATUS		current
		DESCRIPTION
			"The total numer of calls on which this modem has
			connected and negotiated the V.34 modulation
			protocol."

	::= { modemStatsEntry 405 }

	modemStatsV32Calls	OBJECT-TYPE
		SYNTAX		INTEGER
		MAX-ACCESS	read-only
		STATUS		current
		DESCRIPTION
			"The total numer of calls on which this modem has
			connected and negotiated the V.32 or V.32bis
			modulation protocols."

	::= { modemStatsEntry 406 }

	modemStatsStatsSamples	OBJECT-TYPE
		SYNTAX		INTEGER
		MAX-ACCESS	read-only
		STATUS		current
		DESCRIPTION
			"The total numer of calls on which call statistics
			were obtained. These statistics include minimum and
			maximum speeds, retrains and renegotiations, etc."

	::= { modemStatsEntry 501 }

	modemStatsInitialTxSum	OBJECT-TYPE
		SYNTAX		INTEGER
		MAX-ACCESS	read-only
		STATUS		current
		DESCRIPTION
			"The sum of the initial transmit speeds on all calls
			for which call statistics were obtained. This number
			can be divided by the ConnectedCalls value to obtain
			an average initial transmit speed."

	::= { modemStatsEntry 502 }

	modemStatsMinTxSum	OBJECT-TYPE
		SYNTAX		INTEGER
		MAX-ACCESS	read-only
		STATUS		current
		DESCRIPTION
			"The sum of the minimum transmit speeds on all calls
			for which call statistics were obtained. This number
			can be divided by the StatsSamples value to obtain an
			average minimum transmit speed."

	::= { modemStatsEntry 503 }

	modemStatsMaxTxSum	OBJECT-TYPE
		SYNTAX		INTEGER
		MAX-ACCESS	read-only
		STATUS		current
		DESCRIPTION
			"The sum of the maximum transmit speeds on all calls
			for which call statistics were obtained. This number
			can be divided by the StatsSamples value to obtain an
			average maximum transmit speed."

	::= { modemStatsEntry 504 }

	modemStatsFinalTxSum	OBJECT-TYPE
		SYNTAX		INTEGER
		MAX-ACCESS	read-only
		STATUS		current
		DESCRIPTION
			"The sum of the final transmit speeds on all calls for
			which call statistics were obtained. This number can
			be divided by the StatsSamples value to obtain an
			average final transmit speed."

	::= { modemStatsEntry 505 }

	modemStatsMinTxSpeed	OBJECT-TYPE
		SYNTAX		INTEGER
		MAX-ACCESS	read-only
		STATUS		current
		DESCRIPTION
			"The minimum transmit speed negotiated by this modem."

	::= { modemStatsEntry 506 }

	modemStatsMaxTxSpeed	OBJECT-TYPE
		SYNTAX		INTEGER
		MAX-ACCESS	read-only
		STATUS		current
		DESCRIPTION
			"The maximum transmit speed negotiated by this modem."

	::= { modemStatsEntry 507 }

	modemStatsInitialRxSum	OBJECT-TYPE
		SYNTAX		INTEGER
		MAX-ACCESS	read-only
		STATUS		current
		DESCRIPTION
			"The sum of the initial receive speeds on all calls
			for which call statistics were obtained. This number
			can be divided by the ConnectedCalls value to obtain
			an average initial receive speed."

	::= { modemStatsEntry 508 }

	modemStatsMinRxSum	OBJECT-TYPE
		SYNTAX		INTEGER
		MAX-ACCESS	read-only
		STATUS		current
		DESCRIPTION
			"The sum of the minimum receive speeds on all calls
			for which call statistics were obtained. This number
			can be divided by the StatsSamples value to obtain an
			average minimum receive speed."

	::= { modemStatsEntry 509 }

	modemStatsMaxRxSum	OBJECT-TYPE
		SYNTAX		INTEGER
		MAX-ACCESS	read-only
		STATUS		current
		DESCRIPTION
			"The sum of the maximum receive speeds on all calls
			for which call statistics were obtained. This number
			can be divided by the StatsSamples value to obtain an
			average maximum receive speed."

	::= { modemStatsEntry 510 }

	modemStatsFinalRxSum	OBJECT-TYPE
		SYNTAX		INTEGER
		MAX-ACCESS	read-only
		STATUS		current
		DESCRIPTION
			"The sum of the final receive speeds on all calls for
			which call statistics were obtained. This number can
			be divided by the StatsSamples value to obtain an
			average final receive speed."

	::= { modemStatsEntry 511 }

	modemStatsMinRxSpeed	OBJECT-TYPE
		SYNTAX		INTEGER
		MAX-ACCESS	read-only
		STATUS		current
		DESCRIPTION
			"The minimum receive speed negotiated by this modem."

	::= { modemStatsEntry 512 }

	modemStatsMaxRxSpeed	OBJECT-TYPE
		SYNTAX		INTEGER
		MAX-ACCESS	read-only
		STATUS		current
		DESCRIPTION
			"The maximum receive speed negotiated by this modem."

	::= { modemStatsEntry 513 }

	modemStatsDownloadAttempts	OBJECT-TYPE
		SYNTAX		INTEGER
		MAX-ACCESS	read-only
		STATUS		current
		DESCRIPTION
			"Number of times code was downloaded to the modem's
			pack"

	::= { modemStatsEntry 1001 }

	modemStatsDownloadSuccesses	OBJECT-TYPE
		SYNTAX		INTEGER
		MAX-ACCESS	read-only
		STATUS		current
		DESCRIPTION
			"Number of times code downloaded succeeded"

	::= { modemStatsEntry 1002 }

	modemStatsResetFailures	OBJECT-TYPE
		SYNTAX		INTEGER
		MAX-ACCESS	read-only
		STATUS		current
		DESCRIPTION
			"Number of times the modem failed to respond to
			commands"

	::= { modemStatsEntry 1003 }

	modemStatsResetRevivals	OBJECT-TYPE
		SYNTAX		INTEGER
		MAX-ACCESS	read-only
		STATUS		current
		DESCRIPTION
			"Number of times the modem was revived from the
			non-responsive state"

	::= { modemStatsEntry 1004 }

	modemStatsPackCrashes	OBJECT-TYPE
		SYNTAX		INTEGER
		MAX-ACCESS	read-only
		STATUS		current
		DESCRIPTION
			"Number of times the modem's pack seems to have
			crashed"

	::= { modemStatsEntry 1005 }

	modemStatsPackRevivals	OBJECT-TYPE
		SYNTAX		INTEGER
		MAX-ACCESS	read-only
		STATUS		current
		DESCRIPTION
			"Number of times the modem's apparently-crashed pack
			was revived with a download"

	::= { modemStatsEntry 1006 }


	modemCallStatsTable	OBJECT-TYPE
		SYNTAX		SEQUENCE OF ModemCallStatsEntry
		MAX-ACCESS	not-accessible
		STATUS		current
		DESCRIPTION
			"Modem call stats table."

	::= { aptis-monitoring 1423 }

	modemCallStatsEntry	OBJECT-TYPE
		SYNTAX		ModemCallStatsEntry
		MAX-ACCESS	not-accessible
		STATUS		current
		DESCRIPTION
			"This is the structure of entries in the
			 modemCallStatsTable."
		INDEX		{ modemCallStatsSlotIndex, modemCallStatsModemIndex }
	::= { modemCallStatsTable 1 }

	ModemCallStatsEntry ::= SEQUENCE {
		modemCallStatsTxInitialSpeed	INTEGER,
		modemCallStatsTxFinalSpeed	INTEGER,
		modemCallStatsTxMinSpeed	INTEGER,
		modemCallStatsTxMaxSpeed	INTEGER,
		modemCallStatsRxInitialSpeed	INTEGER,
		modemCallStatsRxFinalSpeed	INTEGER,
		modemCallStatsRxMinSpeed	INTEGER,
		modemCallStatsRxMaxSpeed	INTEGER,
		modemCallStatsECProtocol	DisplayString,
		modemCallStatsDCProtocol	DisplayString,
		modemCallStatsModulationType	DisplayString,
		modemCallStatsInitialModulationType DisplayString,
		modemCallStatsSymbolRate	INTEGER,
		modemCallStatsTxCarrierFrequency INTEGER,
		modemCallStatsRxCarrierFrequency INTEGER,
		modemCallStatsLastAGCGainValue	DisplayString,
		modemCallStatsMinAGCGainValue	DisplayString,
		modemCallStatsMaxAGCGainValue	DisplayString,
		modemCallStatsTxLevel		INTEGER,
		modemCallStatsTxLevelReduction	INTEGER,
		modemCallStatsLastEQMValue	INTEGER,
		modemCallStatsMinEQMValue	INTEGER,
		modemCallStatsMaxEQMValue	INTEGER,
		modemCallStatsEQMHits		INTEGER,
		modemCallStatsEQMSumLow		INTEGER,
		modemCallStatsEQMSumMiddle	INTEGER,
		modemCallStatsEQMSumHigh	INTEGER,
		modemCallStatsEQM1Second	INTEGER,
		modemCallStatsEQM2Seconds	INTEGER,
		modemCallStatsEQM3Seconds	INTEGER,
		modemCallStatsEQM4Seconds	INTEGER,
		modemCallStatsEQM5Seconds	INTEGER,
		modemCallStatsEQM6Seconds	INTEGER,
		modemCallStatsEQM7Seconds	INTEGER,
		modemCallStatsEQM8Seconds	INTEGER,
		modemCallStatsEQM9Seconds	INTEGER,
		modemCallStatsEQM10Seconds	INTEGER,
		modemCallStatsSNRRatio		DisplayString,
		modemCallStatsMinSNRValue	INTEGER,
		modemCallStatsMaxSNRValue	INTEGER,
		modemCallStatsLocalRetrains	INTEGER,
		modemCallStatsRemoteRetrains	INTEGER,
		modemCallStatsLocalRateRenegs	INTEGER,
		modemCallStatsRemoteRateRenegs	INTEGER,
		modemCallStatsTxNonlinearEncoding INTEGER,
		modemCallStatsRxNonlinearEncoding INTEGER,
		modemCallStatsTxPrecoding	INTEGER,
		modemCallStatsRxPrecoding	INTEGER,
		modemCallStatsTxShaping		INTEGER,
		modemCallStatsRxShaping		INTEGER,
		modemCallStatsTrellisMapping	DisplayString,
		modemCallStatsPreEmphasis	INTEGER,
		modemCallStatsUpperBandEdge	DisplayString,
		modemCallStatsLowerBandEdge	DisplayString,
		modemCallStatsRTTHigh		INTEGER,
		modemCallStatsRTTLow		INTEGER,
		modemCallStatsInfo0SequenceHigh	INTEGER,
		modemCallStatsInfo0SequenceLow	INTEGER,
		modemCallStatsRxMPSequenceByte1Low INTEGER,
		modemCallStatsRxMPSequenceByte1High INTEGER,
		modemCallStatsRxMPSequenceByte2Low INTEGER,
		modemCallStatsRxMPSequenceByte2High INTEGER,
		modemCallStatsHighestTxState	INTEGER,
		modemCallStatsHighestRxState	INTEGER,
		modemCallStatsLastTransmitState	INTEGER,
		modemCallStatsLastReceiveState	INTEGER,
		modemCallStatsConnectTimeHours	INTEGER,
		modemCallStatsConnectTimeMinutes INTEGER,
		modemCallStatsConnectTimeSeconds INTEGER,
		modemCallStatsAutoGainAmplitude	DisplayString,
		modemCallStatsAutoGainAttenuation DisplayString,
		modemCallStatsDigitalPadDetected DisplayString,
		modemCallStatsRBSPattern	INTEGER,
		modemCallStatsRBSRateDrop	INTEGER,
		modemCallStatsMaxTxRetransmissions INTEGER,
		modemCallStatsTotalTxRetransmissions INTEGER,
		modemCallStatsNumberOfLAPMREJSReceived INTEGER,
		modemCallStatsNumberOfLAPMREJSTransmitted INTEGER,
		modemCallStatsNumberOfTXBlocksHigh INTEGER,
		modemCallStatsNumberOfTXBlocksLow INTEGER,
		modemCallStatsNumberOfRXBlocksHigh INTEGER,
		modemCallStatsNumberOfRXBlocksLow INTEGER,
		modemCallStatsNumberOfTXCharsMSB INTEGER,
		modemCallStatsNumberOfTXChars2ndByte INTEGER,
		modemCallStatsNumberOfTXChars3rdByte INTEGER,
		modemCallStatsNumberOfTXCharsLSB INTEGER,
		modemCallStatsNumberOfRXCharsMSB INTEGER,
		modemCallStatsNumberOfRXChars2ndByte INTEGER,
		modemCallStatsNumberOfRXChars3rdByte INTEGER,
		modemCallStatsNumberOfRXCharsLSB INTEGER,
		modemCallStatsDisconnectReason	DisplayString,
		modemCallStatsRetrainReason	DisplayString,
		modemCallStatsAbortCode		DisplayString,
		modemCallStatsK56Status		DisplayString,
		modemCallStatsV8ManufacturerID	DisplayString,
		modemCallStatsV8LicenseeCode	DisplayString,
		modemCallStatsV8Capabilities	DisplayString,
		modemCallStatsV8FlexVersion	DisplayString,
		modemCallStatsV8DataPumpRev	DisplayString,
		modemCallStatsV8ControllerRev	DisplayString,
		modemCallStatsV8Progress	DisplayString,
		modemCallStatsV90DigitalPadHigh	INTEGER,
		modemCallStatsV90DigitalPadLow	INTEGER,
		modemCallStatsV90IMDRatio	INTEGER,
		modemCallStatsHandshakeTime	INTEGER,
		modemCallStatsNumberOfHandshakeRetries INTEGER,
		modemCallStatsECState1		INTEGER,
		modemCallStatsECState2		INTEGER,
		modemCallStatsFirmwareState	INTEGER,
		modemCallStatsHighAddrOfMEMACCFailure INTEGER,
		modemCallStatsLowAddrOfMEMACCFailure INTEGER,
		modemCallStatsMinutesSinceRetrain INTEGER,
		modemCallStatsWAStatus		INTEGER,
		modemCallStatsRoundTripTime	DisplayString,
		modemCallStatsDataIsValid	INTEGER,
		modemCallStatsSessionID		INTEGER,
		modemCallStatsSlotIndex		INTEGER,
		modemCallStatsModemIndex	INTEGER
	}

	modemCallStatsTxInitialSpeed	OBJECT-TYPE
		SYNTAX		INTEGER
		MAX-ACCESS	read-only
		STATUS		current
		DESCRIPTION
			"Initial transmit speed in bits/second."

	::= { modemCallStatsEntry 1 }

	modemCallStatsTxFinalSpeed	OBJECT-TYPE
		SYNTAX		INTEGER
		MAX-ACCESS	read-only
		STATUS		current
		DESCRIPTION
			"Final transmit speed in bits/second."

	::= { modemCallStatsEntry 2 }

	modemCallStatsTxMinSpeed	OBJECT-TYPE
		SYNTAX		INTEGER
		MAX-ACCESS	read-only
		STATUS		current
		DESCRIPTION
			"Minimum transmit speed in bits/second."

	::= { modemCallStatsEntry 3 }

	modemCallStatsTxMaxSpeed	OBJECT-TYPE
		SYNTAX		INTEGER
		MAX-ACCESS	read-only
		STATUS		current
		DESCRIPTION
			"Maximum transmit speed in bits/second."

	::= { modemCallStatsEntry 4 }

	modemCallStatsRxInitialSpeed	OBJECT-TYPE
		SYNTAX		INTEGER
		MAX-ACCESS	read-only
		STATUS		current
		DESCRIPTION
			"Initial receive speed in bits/second."

	::= { modemCallStatsEntry 5 }

	modemCallStatsRxFinalSpeed	OBJECT-TYPE
		SYNTAX		INTEGER
		MAX-ACCESS	read-only
		STATUS		current
		DESCRIPTION
			"Final receive speed in bits/second."

	::= { modemCallStatsEntry 6 }

	modemCallStatsRxMinSpeed	OBJECT-TYPE
		SYNTAX		INTEGER
		MAX-ACCESS	read-only
		STATUS		current
		DESCRIPTION
			"Minimum receive speed in bits/second."

	::= { modemCallStatsEntry 7 }

	modemCallStatsRxMaxSpeed	OBJECT-TYPE
		SYNTAX		INTEGER
		MAX-ACCESS	read-only
		STATUS		current
		DESCRIPTION
			"Maximum receive speed in bits/second."

	::= { modemCallStatsEntry 8 }

	modemCallStatsECProtocol	OBJECT-TYPE
		SYNTAX		DisplayString (SIZE (0..32))
		MAX-ACCESS	read-only
		STATUS		current
		DESCRIPTION
			"Error-correction protocol negotiated."

	::= { modemCallStatsEntry 9 }

	modemCallStatsDCProtocol	OBJECT-TYPE
		SYNTAX		DisplayString (SIZE (0..32))
		MAX-ACCESS	read-only
		STATUS		current
		DESCRIPTION
			"Data Compression protocol negotiated."

	::= { modemCallStatsEntry 10 }

	modemCallStatsModulationType	OBJECT-TYPE
		SYNTAX		DisplayString (SIZE (0..32))
		MAX-ACCESS	read-only
		STATUS		current
		DESCRIPTION
			"Modulation protocol negotiated."

	::= { modemCallStatsEntry 11 }

	modemCallStatsInitialModulationType	OBJECT-TYPE
		SYNTAX		DisplayString (SIZE (0..32))
		MAX-ACCESS	read-only
		STATUS		current
		DESCRIPTION
			"Initial Modulation protocol."

	::= { modemCallStatsEntry 12 }

	modemCallStatsSymbolRate	OBJECT-TYPE
		SYNTAX		INTEGER
		MAX-ACCESS	read-only
		STATUS		current
		DESCRIPTION
			"Symbol rate."

	::= { modemCallStatsEntry 13 }

	modemCallStatsTxCarrierFrequency	OBJECT-TYPE
		SYNTAX		INTEGER
		MAX-ACCESS	read-only
		STATUS		current
		DESCRIPTION
			"Transmit carrier frequency."

	::= { modemCallStatsEntry 14 }

	modemCallStatsRxCarrierFrequency	OBJECT-TYPE
		SYNTAX		INTEGER
		MAX-ACCESS	read-only
		STATUS		current
		DESCRIPTION
			"Receive carrier frequency."

	::= { modemCallStatsEntry 15 }

	modemCallStatsLastAGCGainValue	OBJECT-TYPE
		SYNTAX		DisplayString (SIZE (0..32))
		MAX-ACCESS	read-only
		STATUS		current
		DESCRIPTION
			"Last AGC gain value."

	::= { modemCallStatsEntry 16 }

	modemCallStatsMinAGCGainValue	OBJECT-TYPE
		SYNTAX		DisplayString (SIZE (0..32))
		MAX-ACCESS	read-only
		STATUS		current
		DESCRIPTION
			"Minimum AGC gain value."

	::= { modemCallStatsEntry 17 }

	modemCallStatsMaxAGCGainValue	OBJECT-TYPE
		SYNTAX		DisplayString (SIZE (0..32))
		MAX-ACCESS	read-only
		STATUS		current
		DESCRIPTION
			"Maximum AGC gain value."

	::= { modemCallStatsEntry 18 }

	modemCallStatsTxLevel	OBJECT-TYPE
		SYNTAX		INTEGER
		MAX-ACCESS	read-only
		STATUS		current
		DESCRIPTION
			"Transmit level in negative dB's."

	::= { modemCallStatsEntry 19 }

	modemCallStatsTxLevelReduction	OBJECT-TYPE
		SYNTAX		INTEGER
		MAX-ACCESS	read-only
		STATUS		current
		DESCRIPTION
			"Transmit level reduction."

	::= { modemCallStatsEntry 20 }

	modemCallStatsLastEQMValue	OBJECT-TYPE
		SYNTAX		INTEGER
		MAX-ACCESS	read-only
		STATUS		current
		DESCRIPTION
			"Last EQM value."

	::= { modemCallStatsEntry 21 }

	modemCallStatsMinEQMValue	OBJECT-TYPE
		SYNTAX		INTEGER
		MAX-ACCESS	read-only
		STATUS		current
		DESCRIPTION
			"Minimum EQM value."

	::= { modemCallStatsEntry 22 }

	modemCallStatsMaxEQMValue	OBJECT-TYPE
		SYNTAX		INTEGER
		MAX-ACCESS	read-only
		STATUS		current
		DESCRIPTION
			"Maximum EQM value."

	::= { modemCallStatsEntry 23 }

	modemCallStatsEQMHits	OBJECT-TYPE
		SYNTAX		INTEGER
		MAX-ACCESS	read-only
		STATUS		current
		DESCRIPTION
			"Number of times EQM values became larger than 127."

	::= { modemCallStatsEntry 24 }

	modemCallStatsEQMSumLow	OBJECT-TYPE
		SYNTAX		INTEGER
		MAX-ACCESS	read-only
		STATUS		current
		DESCRIPTION
			"Low order byte of the EQM sum."

	::= { modemCallStatsEntry 25 }

	modemCallStatsEQMSumMiddle	OBJECT-TYPE
		SYNTAX		INTEGER
		MAX-ACCESS	read-only
		STATUS		current
		DESCRIPTION
			"Middle order bytes of the EQM sum."

	::= { modemCallStatsEntry 26 }

	modemCallStatsEQMSumHigh	OBJECT-TYPE
		SYNTAX		INTEGER
		MAX-ACCESS	read-only
		STATUS		current
		DESCRIPTION
			"High order byte of the EQM sum."

	::= { modemCallStatsEntry 27 }

	modemCallStatsEQM1Second	OBJECT-TYPE
		SYNTAX		INTEGER
		MAX-ACCESS	read-only
		STATUS		current
		DESCRIPTION
			"EQM 1 second before &v2 issued or hangup."

	::= { modemCallStatsEntry 28 }

	modemCallStatsEQM2Seconds	OBJECT-TYPE
		SYNTAX		INTEGER
		MAX-ACCESS	read-only
		STATUS		current
		DESCRIPTION
			"EQM 2 seconds before &v2 issued or hangup."

	::= { modemCallStatsEntry 29 }

	modemCallStatsEQM3Seconds	OBJECT-TYPE
		SYNTAX		INTEGER
		MAX-ACCESS	read-only
		STATUS		current
		DESCRIPTION
			"EQM 3 seconds before &v2 issued or hangup."

	::= { modemCallStatsEntry 30 }

	modemCallStatsEQM4Seconds	OBJECT-TYPE
		SYNTAX		INTEGER
		MAX-ACCESS	read-only
		STATUS		current
		DESCRIPTION
			"EQM 4 seconds before &v2 issued or hangup."

	::= { modemCallStatsEntry 31 }

	modemCallStatsEQM5Seconds	OBJECT-TYPE
		SYNTAX		INTEGER
		MAX-ACCESS	read-only
		STATUS		current
		DESCRIPTION
			"EQM 5 seconds before &v2 issued or hangup."

	::= { modemCallStatsEntry 32 }

	modemCallStatsEQM6Seconds	OBJECT-TYPE
		SYNTAX		INTEGER
		MAX-ACCESS	read-only
		STATUS		current
		DESCRIPTION
			"EQM 6 seconds before &v2 issued or hangup."

	::= { modemCallStatsEntry 33 }

	modemCallStatsEQM7Seconds	OBJECT-TYPE
		SYNTAX		INTEGER
		MAX-ACCESS	read-only
		STATUS		current
		DESCRIPTION
			"EQM 7 seconds before &v2 issued or hangup."

	::= { modemCallStatsEntry 34 }

	modemCallStatsEQM8Seconds	OBJECT-TYPE
		SYNTAX		INTEGER
		MAX-ACCESS	read-only
		STATUS		current
		DESCRIPTION
			"EQM 8 seconds before &v2 issued or hangup."

	::= { modemCallStatsEntry 35 }

	modemCallStatsEQM9Seconds	OBJECT-TYPE
		SYNTAX		INTEGER
		MAX-ACCESS	read-only
		STATUS		current
		DESCRIPTION
			"EQM 9 seconds before &v2 issued or hangup."

	::= { modemCallStatsEntry 36 }

	modemCallStatsEQM10Seconds	OBJECT-TYPE
		SYNTAX		INTEGER
		MAX-ACCESS	read-only
		STATUS		current
		DESCRIPTION
			"EQM 10 seconds before &v2 issued or hangup."

	::= { modemCallStatsEntry 37 }

	modemCallStatsSNRRatio	OBJECT-TYPE
		SYNTAX		DisplayString (SIZE (0..32))
		MAX-ACCESS	read-only
		STATUS		current
		DESCRIPTION
			"SNR ratio."

	::= { modemCallStatsEntry 38 }

	modemCallStatsMinSNRValue	OBJECT-TYPE
		SYNTAX		INTEGER
		MAX-ACCESS	read-only
		STATUS		current
		DESCRIPTION
			"Minimum SNR value."

	::= { modemCallStatsEntry 39 }

	modemCallStatsMaxSNRValue	OBJECT-TYPE
		SYNTAX		INTEGER
		MAX-ACCESS	read-only
		STATUS		current
		DESCRIPTION
			"Maximum SNR value."

	::= { modemCallStatsEntry 40 }

	modemCallStatsLocalRetrains	OBJECT-TYPE
		SYNTAX		INTEGER
		MAX-ACCESS	read-only
		STATUS		current
		DESCRIPTION
			"Number of local retrains."

	::= { modemCallStatsEntry 41 }

	modemCallStatsRemoteRetrains	OBJECT-TYPE
		SYNTAX		INTEGER
		MAX-ACCESS	read-only
		STATUS		current
		DESCRIPTION
			"Number of remote retrains."

	::= { modemCallStatsEntry 42 }

	modemCallStatsLocalRateRenegs	OBJECT-TYPE
		SYNTAX		INTEGER
		MAX-ACCESS	read-only
		STATUS		current
		DESCRIPTION
			"Number of local rate renegotiations."

	::= { modemCallStatsEntry 43 }

	modemCallStatsRemoteRateRenegs	OBJECT-TYPE
		SYNTAX		INTEGER
		MAX-ACCESS	read-only
		STATUS		current
		DESCRIPTION
			"Number of remote rate renegotiations."

	::= { modemCallStatsEntry 44 }

	modemCallStatsTxNonlinearEncoding	OBJECT-TYPE
		SYNTAX		INTEGER
		MAX-ACCESS	read-only
		STATUS		current
		DESCRIPTION
			"Whether non-linear transmit encoding was on."

	::= { modemCallStatsEntry 45 }

	modemCallStatsRxNonlinearEncoding	OBJECT-TYPE
		SYNTAX		INTEGER
		MAX-ACCESS	read-only
		STATUS		current
		DESCRIPTION
			"Whether non-linear receive encoding was on."

	::= { modemCallStatsEntry 46 }

	modemCallStatsTxPrecoding	OBJECT-TYPE
		SYNTAX		INTEGER
		MAX-ACCESS	read-only
		STATUS		current
		DESCRIPTION
			"Whether transmit precoding was on."

	::= { modemCallStatsEntry 47 }

	modemCallStatsRxPrecoding	OBJECT-TYPE
		SYNTAX		INTEGER
		MAX-ACCESS	read-only
		STATUS		current
		DESCRIPTION
			"Whether receive precoding was on."

	::= { modemCallStatsEntry 48 }

	modemCallStatsTxShaping	OBJECT-TYPE
		SYNTAX		INTEGER
		MAX-ACCESS	read-only
		STATUS		current
		DESCRIPTION
			"Whether transmit shaping was on."

	::= { modemCallStatsEntry 49 }

	modemCallStatsRxShaping	OBJECT-TYPE
		SYNTAX		INTEGER
		MAX-ACCESS	read-only
		STATUS		current
		DESCRIPTION
			"Whether receive shaping was on."

	::= { modemCallStatsEntry 50 }

	modemCallStatsTrellisMapping	OBJECT-TYPE
		SYNTAX		DisplayString (SIZE (0..32))
		MAX-ACCESS	read-only
		STATUS		current
		DESCRIPTION
			"Rrellis mapping type."

	::= { modemCallStatsEntry 51 }

	modemCallStatsPreEmphasis	OBJECT-TYPE
		SYNTAX		INTEGER
		MAX-ACCESS	read-only
		STATUS		current
		DESCRIPTION
			"Pre-emphasis filter chosen."

	::= { modemCallStatsEntry 52 }

	modemCallStatsUpperBandEdge	OBJECT-TYPE
		SYNTAX		DisplayString (SIZE (0..32))
		MAX-ACCESS	read-only
		STATUS		current
		DESCRIPTION
			"Upper band edge."

	::= { modemCallStatsEntry 53 }

	modemCallStatsLowerBandEdge	OBJECT-TYPE
		SYNTAX		DisplayString (SIZE (0..32))
		MAX-ACCESS	read-only
		STATUS		current
		DESCRIPTION
			"Lower band edge."

	::= { modemCallStatsEntry 54 }

	modemCallStatsRTTHigh	OBJECT-TYPE
		SYNTAX		INTEGER
		MAX-ACCESS	read-only
		STATUS		current
		DESCRIPTION
			"Round trip delay, high byte."

	::= { modemCallStatsEntry 55 }

	modemCallStatsRTTLow	OBJECT-TYPE
		SYNTAX		INTEGER
		MAX-ACCESS	read-only
		STATUS		current
		DESCRIPTION
			"Round trip delay, low byte."

	::= { modemCallStatsEntry 56 }

	modemCallStatsInfo0SequenceHigh	OBJECT-TYPE
		SYNTAX		INTEGER
		MAX-ACCESS	read-only
		STATUS		current
		DESCRIPTION
			"Info 0 sequence, high byte."

	::= { modemCallStatsEntry 57 }

	modemCallStatsInfo0SequenceLow	OBJECT-TYPE
		SYNTAX		INTEGER
		MAX-ACCESS	read-only
		STATUS		current
		DESCRIPTION
			"Info 0 sequence, low byte."

	::= { modemCallStatsEntry 58 }

	modemCallStatsRxMPSequenceByte1Low	OBJECT-TYPE
		SYNTAX		INTEGER
		MAX-ACCESS	read-only
		STATUS		current
		DESCRIPTION
			"RX MP sequence byte 1, low byte."

	::= { modemCallStatsEntry 59 }

	modemCallStatsRxMPSequenceByte1High	OBJECT-TYPE
		SYNTAX		INTEGER
		MAX-ACCESS	read-only
		STATUS		current
		DESCRIPTION
			"RX MP sequence byte 1, high byte."

	::= { modemCallStatsEntry 60 }

	modemCallStatsRxMPSequenceByte2Low	OBJECT-TYPE
		SYNTAX		INTEGER
		MAX-ACCESS	read-only
		STATUS		current
		DESCRIPTION
			"RX MP sequence byte 2, low byte."

	::= { modemCallStatsEntry 61 }

	modemCallStatsRxMPSequenceByte2High	OBJECT-TYPE
		SYNTAX		INTEGER
		MAX-ACCESS	read-only
		STATUS		current
		DESCRIPTION
			"RX MP sequence byte 2, high byte."

	::= { modemCallStatsEntry 62 }

	modemCallStatsHighestTxState	OBJECT-TYPE
		SYNTAX		INTEGER
		MAX-ACCESS	read-only
		STATUS		current
		DESCRIPTION
			"Highest transmit state."

	::= { modemCallStatsEntry 63 }

	modemCallStatsHighestRxState	OBJECT-TYPE
		SYNTAX		INTEGER
		MAX-ACCESS	read-only
		STATUS		current
		DESCRIPTION
			"Highest receive state."

	::= { modemCallStatsEntry 64 }

	modemCallStatsLastTransmitState	OBJECT-TYPE
		SYNTAX		INTEGER
		MAX-ACCESS	read-only
		STATUS		current
		DESCRIPTION
			"Last transmit state."

	::= { modemCallStatsEntry 65 }

	modemCallStatsLastReceiveState	OBJECT-TYPE
		SYNTAX		INTEGER
		MAX-ACCESS	read-only
		STATUS		current
		DESCRIPTION
			"Last receive state."

	::= { modemCallStatsEntry 66 }

	modemCallStatsConnectTimeHours	OBJECT-TYPE
		SYNTAX		INTEGER
		MAX-ACCESS	read-only
		STATUS		current
		DESCRIPTION
			"Connection time, hours."

	::= { modemCallStatsEntry 67 }

	modemCallStatsConnectTimeMinutes	OBJECT-TYPE
		SYNTAX		INTEGER
		MAX-ACCESS	read-only
		STATUS		current
		DESCRIPTION
			"Connection time, minutes."

	::= { modemCallStatsEntry 68 }

	modemCallStatsConnectTimeSeconds	OBJECT-TYPE
		SYNTAX		INTEGER
		MAX-ACCESS	read-only
		STATUS		current
		DESCRIPTION
			"Connection time, seconds."

	::= { modemCallStatsEntry 69 }

	modemCallStatsAutoGainAmplitude	OBJECT-TYPE
		SYNTAX		DisplayString (SIZE (0..32))
		MAX-ACCESS	read-only
		STATUS		current
		DESCRIPTION
			"Auto gain amplitude."

	::= { modemCallStatsEntry 70 }

	modemCallStatsAutoGainAttenuation	OBJECT-TYPE
		SYNTAX		DisplayString (SIZE (0..32))
		MAX-ACCESS	read-only
		STATUS		current
		DESCRIPTION
			"Auto gain attenuation."

	::= { modemCallStatsEntry 71 }

	modemCallStatsDigitalPadDetected	OBJECT-TYPE
		SYNTAX		DisplayString (SIZE (0..32))
		MAX-ACCESS	read-only
		STATUS		current
		DESCRIPTION
			"Digital pad detected."

	::= { modemCallStatsEntry 72 }

	modemCallStatsRBSPattern	OBJECT-TYPE
		SYNTAX		INTEGER
		MAX-ACCESS	read-only
		STATUS		current
		DESCRIPTION
			"RBS Pattern."

	::= { modemCallStatsEntry 73 }

	modemCallStatsRBSRateDrop	OBJECT-TYPE
		SYNTAX		INTEGER
		MAX-ACCESS	read-only
		STATUS		current
		DESCRIPTION
			"Rate drop due to RBS."

	::= { modemCallStatsEntry 74 }

	modemCallStatsMaxTxRetransmissions	OBJECT-TYPE
		SYNTAX		INTEGER
		MAX-ACCESS	read-only
		STATUS		current
		DESCRIPTION
			"Max number of retransmissions for one frame."

	::= { modemCallStatsEntry 75 }

	modemCallStatsTotalTxRetransmissions	OBJECT-TYPE
		SYNTAX		INTEGER
		MAX-ACCESS	read-only
		STATUS		current
		DESCRIPTION
			"Total number of retransmissions during connection."

	::= { modemCallStatsEntry 76 }

	modemCallStatsNumberOfLAPMREJSReceived	OBJECT-TYPE
		SYNTAX		INTEGER
		MAX-ACCESS	read-only
		STATUS		current
		DESCRIPTION
			"Number of LAPM REJ frames received."

	::= { modemCallStatsEntry 77 }

	modemCallStatsNumberOfLAPMREJSTransmitted	OBJECT-TYPE
		SYNTAX		INTEGER
		MAX-ACCESS	read-only
		STATUS		current
		DESCRIPTION
			"Number of LAPM REJ frames transmitted."

	::= { modemCallStatsEntry 78 }

	modemCallStatsNumberOfTXBlocksHigh	OBJECT-TYPE
		SYNTAX		INTEGER
		MAX-ACCESS	read-only
		STATUS		current
		DESCRIPTION
			"Number of TX blocks, high byte."

	::= { modemCallStatsEntry 79 }

	modemCallStatsNumberOfTXBlocksLow	OBJECT-TYPE
		SYNTAX		INTEGER
		MAX-ACCESS	read-only
		STATUS		current
		DESCRIPTION
			"Number of TX blocks, low byte."

	::= { modemCallStatsEntry 80 }

	modemCallStatsNumberOfRXBlocksHigh	OBJECT-TYPE
		SYNTAX		INTEGER
		MAX-ACCESS	read-only
		STATUS		current
		DESCRIPTION
			"Number of RX blocks, high byte."

	::= { modemCallStatsEntry 81 }

	modemCallStatsNumberOfRXBlocksLow	OBJECT-TYPE
		SYNTAX		INTEGER
		MAX-ACCESS	read-only
		STATUS		current
		DESCRIPTION
			"Number of RX blocks, low byte."

	::= { modemCallStatsEntry 82 }

	modemCallStatsNumberOfTXCharsMSB	OBJECT-TYPE
		SYNTAX		INTEGER
		MAX-ACCESS	read-only
		STATUS		current
		DESCRIPTION
			"Number of TX characters, high byte."

	::= { modemCallStatsEntry 83 }

	modemCallStatsNumberOfTXChars2ndByte	OBJECT-TYPE
		SYNTAX		INTEGER
		MAX-ACCESS	read-only
		STATUS		current
		DESCRIPTION
			"Number of TX characters, 2nd byte."

	::= { modemCallStatsEntry 84 }

	modemCallStatsNumberOfTXChars3rdByte	OBJECT-TYPE
		SYNTAX		INTEGER
		MAX-ACCESS	read-only
		STATUS		current
		DESCRIPTION
			"Number of TX characters, 3rd byte."

	::= { modemCallStatsEntry 85 }

	modemCallStatsNumberOfTXCharsLSB	OBJECT-TYPE
		SYNTAX		INTEGER
		MAX-ACCESS	read-only
		STATUS		current
		DESCRIPTION
			"Number of TX characters, low byte."

	::= { modemCallStatsEntry 86 }

	modemCallStatsNumberOfRXCharsMSB	OBJECT-TYPE
		SYNTAX		INTEGER
		MAX-ACCESS	read-only
		STATUS		current
		DESCRIPTION
			"Number of RX characters, high byte."

	::= { modemCallStatsEntry 87 }

	modemCallStatsNumberOfRXChars2ndByte	OBJECT-TYPE
		SYNTAX		INTEGER
		MAX-ACCESS	read-only
		STATUS		current
		DESCRIPTION
			"Number of RX characters, 2nd byte."

	::= { modemCallStatsEntry 88 }

	modemCallStatsNumberOfRXChars3rdByte	OBJECT-TYPE
		SYNTAX		INTEGER
		MAX-ACCESS	read-only
		STATUS		current
		DESCRIPTION
			"Number of RX characters, 3rd byte."

	::= { modemCallStatsEntry 89 }

	modemCallStatsNumberOfRXCharsLSB	OBJECT-TYPE
		SYNTAX		INTEGER
		MAX-ACCESS	read-only
		STATUS		current
		DESCRIPTION
			"Number of RX characters, low byte."

	::= { modemCallStatsEntry 90 }

	modemCallStatsDisconnectReason	OBJECT-TYPE
		SYNTAX		DisplayString (SIZE (0..64))
		MAX-ACCESS	read-only
		STATUS		current
		DESCRIPTION
			"Disconnect reason."

	::= { modemCallStatsEntry 91 }

	modemCallStatsRetrainReason	OBJECT-TYPE
		SYNTAX		DisplayString (SIZE (0..64))
		MAX-ACCESS	read-only
		STATUS		current
		DESCRIPTION
			"Reason for retrain or rate renegotiation."

	::= { modemCallStatsEntry 92 }

	modemCallStatsAbortCode	OBJECT-TYPE
		SYNTAX		DisplayString (SIZE (0..64))
		MAX-ACCESS	read-only
		STATUS		current
		DESCRIPTION
			"Abort code."

	::= { modemCallStatsEntry 93 }

	modemCallStatsK56Status	OBJECT-TYPE
		SYNTAX		DisplayString (SIZE (0..64))
		MAX-ACCESS	read-only
		STATUS		current
		DESCRIPTION
			"K56flex status."

	::= { modemCallStatsEntry 94 }

	modemCallStatsV8ManufacturerID	OBJECT-TYPE
		SYNTAX		DisplayString (SIZE (0..32))
		MAX-ACCESS	read-only
		STATUS		current
		DESCRIPTION
			"Manufacturer id (V.8bis octet 13)."

	::= { modemCallStatsEntry 95 }

	modemCallStatsV8LicenseeCode	OBJECT-TYPE
		SYNTAX		DisplayString (SIZE (0..32))
		MAX-ACCESS	read-only
		STATUS		current
		DESCRIPTION
			"Licensee code (V.8bis octet 14)."

	::= { modemCallStatsEntry 96 }

	modemCallStatsV8Capabilities	OBJECT-TYPE
		SYNTAX		DisplayString (SIZE (0..32))
		MAX-ACCESS	read-only
		STATUS		current
		DESCRIPTION
			"Manufacturer's product capabilities (V.8bis octet
			15)."

	::= { modemCallStatsEntry 97 }

	modemCallStatsV8FlexVersion	OBJECT-TYPE
		SYNTAX		DisplayString (SIZE (0..64))
		MAX-ACCESS	read-only
		STATUS		current
		DESCRIPTION
			"Flex version number (V.8bis octet 16)."

	::= { modemCallStatsEntry 98 }

	modemCallStatsV8DataPumpRev	OBJECT-TYPE
		SYNTAX		DisplayString (SIZE (0..32))
		MAX-ACCESS	read-only
		STATUS		current
		DESCRIPTION
			"CONEXANT's data pump revision number (V.8bis octet
			17)."

	::= { modemCallStatsEntry 99 }

	modemCallStatsV8ControllerRev	OBJECT-TYPE
		SYNTAX		DisplayString (SIZE (0..32))
		MAX-ACCESS	read-only
		STATUS		current
		DESCRIPTION
			"CONEXANT's controller revision (V.8bis octet 18)."

	::= { modemCallStatsEntry 100 }

	modemCallStatsV8Progress	OBJECT-TYPE
		SYNTAX		DisplayString (SIZE (0..64))
		MAX-ACCESS	read-only
		STATUS		current
		DESCRIPTION
			"Progress."

	::= { modemCallStatsEntry 101 }

	modemCallStatsV90DigitalPadHigh	OBJECT-TYPE
		SYNTAX		INTEGER
		MAX-ACCESS	read-only
		STATUS		current
		DESCRIPTION
			"V.90 Digital pad value, high byte."

	::= { modemCallStatsEntry 102 }

	modemCallStatsV90DigitalPadLow	OBJECT-TYPE
		SYNTAX		INTEGER
		MAX-ACCESS	read-only
		STATUS		current
		DESCRIPTION
			"V.90 Digital pad value, low byte."

	::= { modemCallStatsEntry 103 }

	modemCallStatsV90IMDRatio	OBJECT-TYPE
		SYNTAX		INTEGER
		MAX-ACCESS	read-only
		STATUS		current
		DESCRIPTION
			"V.90 IMD ratio."

	::= { modemCallStatsEntry 104 }

	modemCallStatsHandshakeTime	OBJECT-TYPE
		SYNTAX		INTEGER
		MAX-ACCESS	read-only
		STATUS		current
		DESCRIPTION
			"Handshake time."

	::= { modemCallStatsEntry 105 }

	modemCallStatsNumberOfHandshakeRetries	OBJECT-TYPE
		SYNTAX		INTEGER
		MAX-ACCESS	read-only
		STATUS		current
		DESCRIPTION
			"Number of handshake retries."

	::= { modemCallStatsEntry 106 }

	modemCallStatsECState1	OBJECT-TYPE
		SYNTAX		INTEGER
		MAX-ACCESS	read-only
		STATUS		current
		DESCRIPTION
			"EC state 1."

	::= { modemCallStatsEntry 107 }

	modemCallStatsECState2	OBJECT-TYPE
		SYNTAX		INTEGER
		MAX-ACCESS	read-only
		STATUS		current
		DESCRIPTION
			"EC state 2."

	::= { modemCallStatsEntry 108 }

	modemCallStatsFirmwareState	OBJECT-TYPE
		SYNTAX		INTEGER
		MAX-ACCESS	read-only
		STATUS		current
		DESCRIPTION
			"Firmware state."

	::= { modemCallStatsEntry 109 }

	modemCallStatsHighAddrOfMEMACCFailure	OBJECT-TYPE
		SYNTAX		INTEGER
		MAX-ACCESS	read-only
		STATUS		current
		DESCRIPTION
			"Memory address, high byte."

	::= { modemCallStatsEntry 110 }

	modemCallStatsLowAddrOfMEMACCFailure	OBJECT-TYPE
		SYNTAX		INTEGER
		MAX-ACCESS	read-only
		STATUS		current
		DESCRIPTION
			"Low address of MEMACC failure."

	::= { modemCallStatsEntry 111 }

	modemCallStatsMinutesSinceRetrain	OBJECT-TYPE
		SYNTAX		INTEGER
		MAX-ACCESS	read-only
		STATUS		current
		DESCRIPTION
			"Number of minutes since last retrain or rate
			renogiation."

	::= { modemCallStatsEntry 112 }

	modemCallStatsWAStatus	OBJECT-TYPE
		SYNTAX		INTEGER
		MAX-ACCESS	read-only
		STATUS		current
		DESCRIPTION
			"WA status."

	::= { modemCallStatsEntry 113 }

	modemCallStatsRoundTripTime	OBJECT-TYPE
		SYNTAX		DisplayString (SIZE (0..32))
		MAX-ACCESS	read-only
		STATUS		current
		DESCRIPTION
			"Round trip time."

	::= { modemCallStatsEntry 114 }

	modemCallStatsDataIsValid	OBJECT-TYPE
		SYNTAX		INTEGER
		MAX-ACCESS	read-only
		STATUS		current
		DESCRIPTION
			"Non-zero if data is valid; zero if data is not
			valid."

	::= { modemCallStatsEntry 201 }

	modemCallStatsSessionID	OBJECT-TYPE
		SYNTAX		INTEGER
		MAX-ACCESS	read-only
		STATUS		current
		DESCRIPTION
			"Session ID associated with this data."

	::= { modemCallStatsEntry 202 }

	modemCallStatsSlotIndex	OBJECT-TYPE
		SYNTAX		INTEGER
		MAX-ACCESS	read-only
		STATUS		current
		DESCRIPTION
			"The physical slot number in which this modem
			resides."

	::= { modemCallStatsEntry 203 }

	modemCallStatsModemIndex	OBJECT-TYPE
		SYNTAX		INTEGER
		MAX-ACCESS	read-only
		STATUS		current
		DESCRIPTION
			"The modem number associated with these call
			statistics."

	::= { modemCallStatsEntry 204 }


	modemSummaryStatsTable	OBJECT-TYPE
		SYNTAX		SEQUENCE OF ModemSummaryStatsEntry
		MAX-ACCESS	not-accessible
		STATUS		current
		DESCRIPTION
			"Modem stats summary table."

	::= { aptis-monitoring 1424 }

	modemSummaryStatsEntry	OBJECT-TYPE
		SYNTAX		ModemSummaryStatsEntry
		MAX-ACCESS	not-accessible
		STATUS		current
		DESCRIPTION
			"This is the structure of entries in the
			 modemSummaryStatsTable."
		INDEX		{ modemSummaryStatsSlotNumber }
	::= { modemSummaryStatsTable 1 }

	ModemSummaryStatsEntry ::= SEQUENCE {
		modemSummaryStatsSlotNumber	INTEGER,
		modemSummaryStatsModemCount	INTEGER,
		modemSummaryStatsDisabledCount	INTEGER,
		modemSummaryStatsNoDownloadCount INTEGER,
		modemSummaryStatsDeadCount	INTEGER,
		modemSummaryStatsRemovedCount	INTEGER,
		modemSummaryStatsIdleCount	INTEGER,
		modemSummaryStatsActiveCount	INTEGER,
		modemSummaryStatsDownloadingCount INTEGER,
		modemSummaryStatsTotalCalls	INTEGER,
		modemSummaryStatsConnectedCalls	INTEGER,
		modemSummaryStatsAuthCalls	INTEGER,
		modemSummaryStatsECCalls	INTEGER,
		modemSummaryStatsDCCalls	INTEGER,
		modemSummaryStatsK56Calls	INTEGER,
		modemSummaryStatsV90Calls	INTEGER,
		modemSummaryStatsV34Calls	INTEGER,
		modemSummaryStatsV32Calls	INTEGER,
		modemSummaryStatsReuseSuspectModems Boolean,
		modemSummaryStatsUpTime		INTEGER,
		modemSummaryStatsMaximumCalls	INTEGER
	}

	modemSummaryStatsSlotNumber	OBJECT-TYPE
		SYNTAX		INTEGER
		MAX-ACCESS	read-only
		STATUS		current
		DESCRIPTION
			"Number of slot reporting summary stats"

	::= { modemSummaryStatsEntry 1 }

	modemSummaryStatsModemCount	OBJECT-TYPE
		SYNTAX		INTEGER
		MAX-ACCESS	read-only
		STATUS		current
		DESCRIPTION
			"Total number of modems found on this card"

	::= { modemSummaryStatsEntry 2 }

	modemSummaryStatsDisabledCount	OBJECT-TYPE
		SYNTAX		INTEGER
		MAX-ACCESS	read-only
		STATUS		current
		DESCRIPTION
			"Total number of modems on this card that are disabled
			by config"

	::= { modemSummaryStatsEntry 3 }

	modemSummaryStatsNoDownloadCount	OBJECT-TYPE
		SYNTAX		INTEGER
		MAX-ACCESS	read-only
		STATUS		current
		DESCRIPTION
			"Total number of modems on this card that failed
			download"

	::= { modemSummaryStatsEntry 4 }

	modemSummaryStatsDeadCount	OBJECT-TYPE
		SYNTAX		INTEGER
		MAX-ACCESS	read-only
		STATUS		current
		DESCRIPTION
			"Total number of modems on this card that are not
			responding to commands"

	::= { modemSummaryStatsEntry 5 }

	modemSummaryStatsRemovedCount	OBJECT-TYPE
		SYNTAX		INTEGER
		MAX-ACCESS	read-only
		STATUS		current
		DESCRIPTION
			"Total number of modems on this card that were taken
			out of service due to excessive failures"

	::= { modemSummaryStatsEntry 6 }

	modemSummaryStatsIdleCount	OBJECT-TYPE
		SYNTAX		INTEGER
		MAX-ACCESS	read-only
		STATUS		current
		DESCRIPTION
			"Total number of modems on this card that are
			functional, but not in use"

	::= { modemSummaryStatsEntry 7 }

	modemSummaryStatsActiveCount	OBJECT-TYPE
		SYNTAX		INTEGER
		MAX-ACCESS	read-only
		STATUS		current
		DESCRIPTION
			"Total number of modems on this card that are
			functional and in use"

	::= { modemSummaryStatsEntry 8 }

	modemSummaryStatsDownloadingCount	OBJECT-TYPE
		SYNTAX		INTEGER
		MAX-ACCESS	read-only
		STATUS		current
		DESCRIPTION
			"Total number of modems on this card that are
			currently being downloaded"

	::= { modemSummaryStatsEntry 9 }

	modemSummaryStatsTotalCalls	OBJECT-TYPE
		SYNTAX		INTEGER
		MAX-ACCESS	read-only
		STATUS		current
		DESCRIPTION
			"The total number of calls assigned to modems in this
			slot"

	::= { modemSummaryStatsEntry 101 }

	modemSummaryStatsConnectedCalls	OBJECT-TYPE
		SYNTAX		INTEGER
		MAX-ACCESS	read-only
		STATUS		current
		DESCRIPTION
			"Total number of calls that have connected in this
			slot."

	::= { modemSummaryStatsEntry 102 }

	modemSummaryStatsAuthCalls	OBJECT-TYPE
		SYNTAX		INTEGER
		MAX-ACCESS	read-only
		STATUS		current
		DESCRIPTION
			"Total number of calls that have reached the
			authentication stage in this slot."

	::= { modemSummaryStatsEntry 103 }

	modemSummaryStatsECCalls	OBJECT-TYPE
		SYNTAX		INTEGER
		MAX-ACCESS	read-only
		STATUS		current
		DESCRIPTION
			"Total number of calls that negotiated error
			correction in this slot."

	::= { modemSummaryStatsEntry 104 }

	modemSummaryStatsDCCalls	OBJECT-TYPE
		SYNTAX		INTEGER
		MAX-ACCESS	read-only
		STATUS		current
		DESCRIPTION
			"Total number of calls that negotiated data
			compression in this slot."

	::= { modemSummaryStatsEntry 105 }

	modemSummaryStatsK56Calls	OBJECT-TYPE
		SYNTAX		INTEGER
		MAX-ACCESS	read-only
		STATUS		current
		DESCRIPTION
			"Total number of calls that have connected with K56
			Flex modulation in this slot."

	::= { modemSummaryStatsEntry 106 }

	modemSummaryStatsV90Calls	OBJECT-TYPE
		SYNTAX		INTEGER
		MAX-ACCESS	read-only
		STATUS		current
		DESCRIPTION
			"Total number of calls that have connected with V.90
			modulation in this slot."

	::= { modemSummaryStatsEntry 107 }

	modemSummaryStatsV34Calls	OBJECT-TYPE
		SYNTAX		INTEGER
		MAX-ACCESS	read-only
		STATUS		current
		DESCRIPTION
			"Total number of calls that have connected with V.34
			modulation in this slot."

	::= { modemSummaryStatsEntry 108 }

	modemSummaryStatsV32Calls	OBJECT-TYPE
		SYNTAX		INTEGER
		MAX-ACCESS	read-only
		STATUS		current
		DESCRIPTION
			"Total number of calls that have connected with V.32
			or V.32bis modulation in this slot."

	::= { modemSummaryStatsEntry 109 }

	modemSummaryStatsReuseSuspectModems	OBJECT-TYPE
		SYNTAX		Boolean
		MAX-ACCESS	read-only
		STATUS		current
		DESCRIPTION
			"Specifies whether suspect modems will be used"

	::= { modemSummaryStatsEntry 201 }

	modemSummaryStatsUpTime	OBJECT-TYPE
		SYNTAX		INTEGER
		MAX-ACCESS	read-only
		STATUS		current
		DESCRIPTION
			"The time (in seconds) this card has been active"

	::= { modemSummaryStatsEntry 301 }

	modemSummaryStatsMaximumCalls	OBJECT-TYPE
		SYNTAX		INTEGER
		MAX-ACCESS	read-only
		STATUS		current
		DESCRIPTION
			"The maximum number of simultaneous calls on the
			modems in this slot."

	::= { modemSummaryStatsEntry 401 }


	modemIntervalStatsTable	OBJECT-TYPE
		SYNTAX		SEQUENCE OF ModemIntervalStatsEntry
		MAX-ACCESS	not-accessible
		STATUS		current
		DESCRIPTION
			"Modem interval stats table."

	::= { aptis-monitoring 1425 }

	modemIntervalStatsEntry	OBJECT-TYPE
		SYNTAX		ModemIntervalStatsEntry
		MAX-ACCESS	not-accessible
		STATUS		current
		DESCRIPTION
			"This is the structure of entries in the
			 modemIntervalStatsTable."
		INDEX		{ modemIntervalStatsIndex }
	::= { modemIntervalStatsTable 1 }

	ModemIntervalStatsEntry ::= SEQUENCE {
		modemIntervalStatsIndex		INTEGER,
		modemIntervalStatsStartTime	INTEGER,
		modemIntervalStatsStopTime	INTEGER,
		modemIntervalStatsModemCount	INTEGER,
		modemIntervalStatsDisabledCount	INTEGER,
		modemIntervalStatsNoDownloadCount INTEGER,
		modemIntervalStatsDeadCount	INTEGER,
		modemIntervalStatsRemovedCount	INTEGER,
		modemIntervalStatsIdleCount	INTEGER,
		modemIntervalStatsActiveCount	INTEGER,
		modemIntervalStatsDownloadingCount INTEGER,
		modemIntervalStatsTotalCalls	INTEGER,
		modemIntervalStatsConnectedCalls INTEGER,
		modemIntervalStatsAuthCalls	INTEGER,
		modemIntervalStatsECCalls	INTEGER,
		modemIntervalStatsDCCalls	INTEGER,
		modemIntervalStatsK56Calls	INTEGER,
		modemIntervalStatsV90Calls	INTEGER,
		modemIntervalStatsV34Calls	INTEGER,
		modemIntervalStatsV32Calls	INTEGER,
		modemIntervalStatsOverallTotalCalls INTEGER,
		modemIntervalStatsOverallConnectedCalls INTEGER,
		modemIntervalStatsOverallAuthCalls INTEGER
	}

	modemIntervalStatsIndex	OBJECT-TYPE
		SYNTAX		INTEGER
		MAX-ACCESS	read-only
		STATUS		current
		DESCRIPTION
			"Index of this entry"

	::= { modemIntervalStatsEntry 1 }

	modemIntervalStatsStartTime	OBJECT-TYPE
		SYNTAX		INTEGER
		MAX-ACCESS	read-only
		STATUS		current
		DESCRIPTION
			"Time (in seconds) of start of reporting interval"

	::= { modemIntervalStatsEntry 2 }

	modemIntervalStatsStopTime	OBJECT-TYPE
		SYNTAX		INTEGER
		MAX-ACCESS	read-only
		STATUS		current
		DESCRIPTION
			"Time (in seconds) of start of reporting interval"

	::= { modemIntervalStatsEntry 3 }

	modemIntervalStatsModemCount	OBJECT-TYPE
		SYNTAX		INTEGER
		MAX-ACCESS	read-only
		STATUS		current
		DESCRIPTION
			"Total number of modems found in the system"

	::= { modemIntervalStatsEntry 4 }

	modemIntervalStatsDisabledCount	OBJECT-TYPE
		SYNTAX		INTEGER
		MAX-ACCESS	read-only
		STATUS		current
		DESCRIPTION
			"Total number of modems in the system that are
			disabled by config"

	::= { modemIntervalStatsEntry 5 }

	modemIntervalStatsNoDownloadCount	OBJECT-TYPE
		SYNTAX		INTEGER
		MAX-ACCESS	read-only
		STATUS		current
		DESCRIPTION
			"Total number of modems in the system that failed
			download"

	::= { modemIntervalStatsEntry 6 }

	modemIntervalStatsDeadCount	OBJECT-TYPE
		SYNTAX		INTEGER
		MAX-ACCESS	read-only
		STATUS		current
		DESCRIPTION
			"Total number of modems in the system that are not
			responding to commands"

	::= { modemIntervalStatsEntry 7 }

	modemIntervalStatsRemovedCount	OBJECT-TYPE
		SYNTAX		INTEGER
		MAX-ACCESS	read-only
		STATUS		current
		DESCRIPTION
			"Total number of modems in the system were taken out
			of service due to excessive failures"

	::= { modemIntervalStatsEntry 8 }

	modemIntervalStatsIdleCount	OBJECT-TYPE
		SYNTAX		INTEGER
		MAX-ACCESS	read-only
		STATUS		current
		DESCRIPTION
			"Total number of modems in the system that are
			functional, but not in use"

	::= { modemIntervalStatsEntry 9 }

	modemIntervalStatsActiveCount	OBJECT-TYPE
		SYNTAX		INTEGER
		MAX-ACCESS	read-only
		STATUS		current
		DESCRIPTION
			"Total number of modems in the system that are
			functional and in use"

	::= { modemIntervalStatsEntry 10 }

	modemIntervalStatsDownloadingCount	OBJECT-TYPE
		SYNTAX		INTEGER
		MAX-ACCESS	read-only
		STATUS		current
		DESCRIPTION
			"Total number of modems in the system that are
			currently being downloaded"

	::= { modemIntervalStatsEntry 11 }

	modemIntervalStatsTotalCalls	OBJECT-TYPE
		SYNTAX		INTEGER
		MAX-ACCESS	read-only
		STATUS		current
		DESCRIPTION
			"The total number of calls assigned to modems in the
			system"

	::= { modemIntervalStatsEntry 101 }

	modemIntervalStatsConnectedCalls	OBJECT-TYPE
		SYNTAX		INTEGER
		MAX-ACCESS	read-only
		STATUS		current
		DESCRIPTION
			"Total number of calls that have connected in the
			system"

	::= { modemIntervalStatsEntry 102 }

	modemIntervalStatsAuthCalls	OBJECT-TYPE
		SYNTAX		INTEGER
		MAX-ACCESS	read-only
		STATUS		current
		DESCRIPTION
			"Total number of calls that have reached the
			authentication stage in the system."

	::= { modemIntervalStatsEntry 103 }

	modemIntervalStatsECCalls	OBJECT-TYPE
		SYNTAX		INTEGER
		MAX-ACCESS	read-only
		STATUS		current
		DESCRIPTION
			"Total number of calls that negotiated error
			correction in the system."

	::= { modemIntervalStatsEntry 104 }

	modemIntervalStatsDCCalls	OBJECT-TYPE
		SYNTAX		INTEGER
		MAX-ACCESS	read-only
		STATUS		current
		DESCRIPTION
			"Total number of calls that negotiated data
			compression in the system"

	::= { modemIntervalStatsEntry 105 }

	modemIntervalStatsK56Calls	OBJECT-TYPE
		SYNTAX		INTEGER
		MAX-ACCESS	read-only
		STATUS		current
		DESCRIPTION
			"Total number of calls that have connected with K56
			Flex modulation in the system."

	::= { modemIntervalStatsEntry 106 }

	modemIntervalStatsV90Calls	OBJECT-TYPE
		SYNTAX		INTEGER
		MAX-ACCESS	read-only
		STATUS		current
		DESCRIPTION
			"Total number of calls that have connected with V.90
			modulation in the system."

	::= { modemIntervalStatsEntry 107 }

	modemIntervalStatsV34Calls	OBJECT-TYPE
		SYNTAX		INTEGER
		MAX-ACCESS	read-only
		STATUS		current
		DESCRIPTION
			"Total number of calls that have connected with V.34
			modulation in the system."

	::= { modemIntervalStatsEntry 108 }

	modemIntervalStatsV32Calls	OBJECT-TYPE
		SYNTAX		INTEGER
		MAX-ACCESS	read-only
		STATUS		current
		DESCRIPTION
			"Total number of calls that have connected with V.32
			or V.32bis modulation in the system."

	::= { modemIntervalStatsEntry 109 }

	modemIntervalStatsOverallTotalCalls	OBJECT-TYPE
		SYNTAX		INTEGER
		MAX-ACCESS	read-only
		STATUS		current
		DESCRIPTION
			"The total number of calls assigned to modems in the
			system"

	::= { modemIntervalStatsEntry 201 }

	modemIntervalStatsOverallConnectedCalls	OBJECT-TYPE
		SYNTAX		INTEGER
		MAX-ACCESS	read-only
		STATUS		current
		DESCRIPTION
			"Total number of calls that have connected in the
			system"

	::= { modemIntervalStatsEntry 202 }

	modemIntervalStatsOverallAuthCalls	OBJECT-TYPE
		SYNTAX		INTEGER
		MAX-ACCESS	read-only
		STATUS		current
		DESCRIPTION
			"Total number of calls that have reached the
			authentication stage in the system."

	::= { modemIntervalStatsEntry 203 }


	modemSessionStatsTable	OBJECT-TYPE
		SYNTAX		SEQUENCE OF ModemSessionStatsEntry
		MAX-ACCESS	not-accessible
		STATUS		current
		DESCRIPTION
			"Modem session stats table."

	::= { aptis-monitoring 1426 }

	modemSessionStatsEntry	OBJECT-TYPE
		SYNTAX		ModemSessionStatsEntry
		MAX-ACCESS	not-accessible
		STATUS		current
		DESCRIPTION
			"This is the structure of entries in the
			 modemSessionStatsTable."
		INDEX		{ modemSessionStatsSlotNumber, modemSessionStatsModemIndex }
	::= { modemSessionStatsTable 1 }

	ModemSessionStatsEntry ::= SEQUENCE {
		modemSessionStatsDataValidity	INTEGER,
		modemSessionStatsSessionID	INTEGER,
		modemSessionStatsSlotNumber	INTEGER,
		modemSessionStatsIOPNumber	INTEGER,
		modemSessionStatsDMMNumber	INTEGER,
		modemSessionStatsPackNumber	INTEGER,
		modemSessionStatsModemNumber	INTEGER,
		modemSessionStatsModemIndex	INTEGER,
		modemSessionStatsTDMStream	INTEGER,
		modemSessionStatsTDMSlot	INTEGER,
		modemSessionStatsInitialTxSpeed	INTEGER,
		modemSessionStatsInitialRxSpeed	INTEGER,
		modemSessionStatsConnectString	DisplayString,
		modemSessionStatsAmpV2String	OCTET STRING
	}

	modemSessionStatsDataValidity	OBJECT-TYPE
		SYNTAX		INTEGER {
				    valid(0),
				    notCaptured(1)
				}
		MAX-ACCESS	read-only
		STATUS		current
		DESCRIPTION
			"Specifies whether data is valid"

	::= { modemSessionStatsEntry 1 }

	modemSessionStatsSessionID	OBJECT-TYPE
		SYNTAX		INTEGER
		MAX-ACCESS	read-only
		STATUS		current
		DESCRIPTION
			"Session ID associated with this data"

	::= { modemSessionStatsEntry 2 }

	modemSessionStatsSlotNumber	OBJECT-TYPE
		SYNTAX		INTEGER
		MAX-ACCESS	read-only
		STATUS		current
		DESCRIPTION
			"Modem slot number"

	::= { modemSessionStatsEntry 3 }

	modemSessionStatsIOPNumber	OBJECT-TYPE
		SYNTAX		INTEGER
		MAX-ACCESS	read-only
		STATUS		current
		DESCRIPTION
			"Modem's IOP number"

	::= { modemSessionStatsEntry 4 }

	modemSessionStatsDMMNumber	OBJECT-TYPE
		SYNTAX		INTEGER
		MAX-ACCESS	read-only
		STATUS		current
		DESCRIPTION
			"Modem's DMM number"

	::= { modemSessionStatsEntry 5 }

	modemSessionStatsPackNumber	OBJECT-TYPE
		SYNTAX		INTEGER
		MAX-ACCESS	read-only
		STATUS		current
		DESCRIPTION
			"Modem's Pack number"

	::= { modemSessionStatsEntry 6 }

	modemSessionStatsModemNumber	OBJECT-TYPE
		SYNTAX		INTEGER
		MAX-ACCESS	read-only
		STATUS		current
		DESCRIPTION
			"Modem's index number"

	::= { modemSessionStatsEntry 7 }

	modemSessionStatsModemIndex	OBJECT-TYPE
		SYNTAX		INTEGER
		MAX-ACCESS	read-only
		STATUS		current
		DESCRIPTION
			"Modem's system-wide number"

	::= { modemSessionStatsEntry 8 }

	modemSessionStatsTDMStream	OBJECT-TYPE
		SYNTAX		INTEGER
		MAX-ACCESS	read-only
		STATUS		current
		DESCRIPTION
			"TDM stream used for this session"

	::= { modemSessionStatsEntry 101 }

	modemSessionStatsTDMSlot	OBJECT-TYPE
		SYNTAX		INTEGER
		MAX-ACCESS	read-only
		STATUS		current
		DESCRIPTION
			"TDM slot used for this session"

	::= { modemSessionStatsEntry 102 }

	modemSessionStatsInitialTxSpeed	OBJECT-TYPE
		SYNTAX		INTEGER
		MAX-ACCESS	read-only
		STATUS		current
		DESCRIPTION
			"Initial transmit speed"

	::= { modemSessionStatsEntry 201 }

	modemSessionStatsInitialRxSpeed	OBJECT-TYPE
		SYNTAX		INTEGER
		MAX-ACCESS	read-only
		STATUS		current
		DESCRIPTION
			"Initial transmit speed"

	::= { modemSessionStatsEntry 202 }

	modemSessionStatsConnectString	OBJECT-TYPE
		SYNTAX		DisplayString (SIZE (0..128))
		MAX-ACCESS	read-only
		STATUS		current
		DESCRIPTION
			"CONNECT string from this session"

	::= { modemSessionStatsEntry 301 }

	modemSessionStatsAmpV2String	OBJECT-TYPE
		SYNTAX		OCTET STRING (SIZE (0..1024))
		MAX-ACCESS	read-only
		STATUS		current
		DESCRIPTION
			"&V2 string from this session"

	::= { modemSessionStatsEntry 401 }


	modemSessionStats2Table	OBJECT-TYPE
		SYNTAX		SEQUENCE OF ModemSessionStats2Entry
		MAX-ACCESS	not-accessible
		STATUS		current
		DESCRIPTION
			"Extended modem session stats table."

	::= { aptis-monitoring 1427 }

	modemSessionStats2Entry	OBJECT-TYPE
		SYNTAX		ModemSessionStats2Entry
		MAX-ACCESS	not-accessible
		STATUS		current
		DESCRIPTION
			"This is the structure of entries in the
			 modemSessionStats2Table."
		INDEX		{ modemSessionStats2SessionID }
	::= { modemSessionStats2Table 1 }

	ModemSessionStats2Entry ::= SEQUENCE {
		modemSessionStats2DataValidity	INTEGER,
		modemSessionStats2SessionID	INTEGER,
		modemSessionStats2SlotNumber	INTEGER,
		modemSessionStats2IOPNumber	INTEGER,
		modemSessionStats2DMMNumber	INTEGER,
		modemSessionStats2PackNumber	INTEGER,
		modemSessionStats2ModemNumber	INTEGER,
		modemSessionStats2ModemIndex	INTEGER,
		modemSessionStats2TDMStream	INTEGER,
		modemSessionStats2TDMSlot	INTEGER,
		modemSessionStats2InitialTxSpeed INTEGER,
		modemSessionStats2InitialRxSpeed INTEGER,
		modemSessionStats2ConnectString	DisplayString,
		modemSessionStats2AmpV2String	OCTET STRING
	}

	modemSessionStats2DataValidity	OBJECT-TYPE
		SYNTAX		INTEGER {
				    valid(0),
				    notCaptured(1)
				}
		MAX-ACCESS	read-only
		STATUS		current
		DESCRIPTION
			"Specifies whether data is valid"

	::= { modemSessionStats2Entry 1 }

	modemSessionStats2SessionID	OBJECT-TYPE
		SYNTAX		INTEGER
		MAX-ACCESS	read-only
		STATUS		current
		DESCRIPTION
			"Session ID associated with this data"

	::= { modemSessionStats2Entry 2 }

	modemSessionStats2SlotNumber	OBJECT-TYPE
		SYNTAX		INTEGER
		MAX-ACCESS	read-only
		STATUS		current
		DESCRIPTION
			"Modem slot number"

	::= { modemSessionStats2Entry 3 }

	modemSessionStats2IOPNumber	OBJECT-TYPE
		SYNTAX		INTEGER
		MAX-ACCESS	read-only
		STATUS		current
		DESCRIPTION
			"Modem's IOP number"

	::= { modemSessionStats2Entry 4 }

	modemSessionStats2DMMNumber	OBJECT-TYPE
		SYNTAX		INTEGER
		MAX-ACCESS	read-only
		STATUS		current
		DESCRIPTION
			"Modem's DMM number"

	::= { modemSessionStats2Entry 5 }

	modemSessionStats2PackNumber	OBJECT-TYPE
		SYNTAX		INTEGER
		MAX-ACCESS	read-only
		STATUS		current
		DESCRIPTION
			"Modem's Pack number"

	::= { modemSessionStats2Entry 6 }

	modemSessionStats2ModemNumber	OBJECT-TYPE
		SYNTAX		INTEGER
		MAX-ACCESS	read-only
		STATUS		current
		DESCRIPTION
			"Modem's index number"

	::= { modemSessionStats2Entry 7 }

	modemSessionStats2ModemIndex	OBJECT-TYPE
		SYNTAX		INTEGER
		MAX-ACCESS	read-only
		STATUS		current
		DESCRIPTION
			"Modem's system-wide number"

	::= { modemSessionStats2Entry 8 }

	modemSessionStats2TDMStream	OBJECT-TYPE
		SYNTAX		INTEGER
		MAX-ACCESS	read-only
		STATUS		current
		DESCRIPTION
			"TDM stream used for this session"

	::= { modemSessionStats2Entry 101 }

	modemSessionStats2TDMSlot	OBJECT-TYPE
		SYNTAX		INTEGER
		MAX-ACCESS	read-only
		STATUS		current
		DESCRIPTION
			"TDM slot used for this session"

	::= { modemSessionStats2Entry 102 }

	modemSessionStats2InitialTxSpeed	OBJECT-TYPE
		SYNTAX		INTEGER
		MAX-ACCESS	read-only
		STATUS		current
		DESCRIPTION
			"Initial transmit speed"

	::= { modemSessionStats2Entry 201 }

	modemSessionStats2InitialRxSpeed	OBJECT-TYPE
		SYNTAX		INTEGER
		MAX-ACCESS	read-only
		STATUS		current
		DESCRIPTION
			"Initial transmit speed"

	::= { modemSessionStats2Entry 202 }

	modemSessionStats2ConnectString	OBJECT-TYPE
		SYNTAX		DisplayString (SIZE (0..128))
		MAX-ACCESS	read-only
		STATUS		current
		DESCRIPTION
			"CONNECT string from this session"

	::= { modemSessionStats2Entry 301 }

	modemSessionStats2AmpV2String	OBJECT-TYPE
		SYNTAX		OCTET STRING (SIZE (0..1024))
		MAX-ACCESS	read-only
		STATUS		current
		DESCRIPTION
			"&V2 string from this session"

	::= { modemSessionStats2Entry 401 }

-- This file generated from  ppp.cml by smog.
-- date: Thu Jun 29 01:11:32  2000

	pppLogEntryTable	OBJECT-TYPE
		SYNTAX		SEQUENCE OF PppLogEntryEntry
		MAX-ACCESS	not-accessible
		STATUS		current
		DESCRIPTION
			"PPP log entry table."

	::= { aptis-monitoring 1316 }

	pppLogEntryEntry	OBJECT-TYPE
		SYNTAX		PppLogEntryEntry
		MAX-ACCESS	not-accessible
		STATUS		current
		DESCRIPTION
			"This is the structure of entries in the
			 pppLogEntryTable."
		INDEX		{ pppLogEntrySessionId, pppLogEntryIndex }
	::= { pppLogEntryTable 1 }

	PppLogEntryEntry ::= SEQUENCE {
		pppLogEntrySessionId		INTEGER,
		pppLogEntryIndex		INTEGER,
		pppLogEntryMinIndex		INTEGER,
		pppLogEntryMaxIndex		INTEGER,
		pppLogEntryEntryText		OCTET STRING,
		pppLogEntryRawEntryText		OCTET STRING
	}

	pppLogEntrySessionId	OBJECT-TYPE
		SYNTAX		INTEGER
		MAX-ACCESS	read-only
		STATUS		current
		DESCRIPTION
			"System session ID"

	::= { pppLogEntryEntry 1 }

	pppLogEntryIndex	OBJECT-TYPE
		SYNTAX		INTEGER
		MAX-ACCESS	read-only
		STATUS		current
		DESCRIPTION
			"Log entry index"

	::= { pppLogEntryEntry 2 }

	pppLogEntryMinIndex	OBJECT-TYPE
		SYNTAX		INTEGER
		MAX-ACCESS	read-only
		STATUS		current
		DESCRIPTION
			"Index of oldest event available"

	::= { pppLogEntryEntry 3 }

	pppLogEntryMaxIndex	OBJECT-TYPE
		SYNTAX		INTEGER
		MAX-ACCESS	read-only
		STATUS		current
		DESCRIPTION
			"Index of newest event available"

	::= { pppLogEntryEntry 4 }

	pppLogEntryEntryText	OBJECT-TYPE
		SYNTAX		OCTET STRING (SIZE (0..512))
		MAX-ACCESS	read-only
		STATUS		current
		DESCRIPTION
			"Log entry text."

	::= { pppLogEntryEntry 5 }

	pppLogEntryRawEntryText	OBJECT-TYPE
		SYNTAX		OCTET STRING (SIZE (0..512))
		MAX-ACCESS	read-only
		STATUS		current
		DESCRIPTION
			"Raw entry text, if appropriate for this log type."

	::= { pppLogEntryEntry 6 }


	pppDeadLogEntryTable	OBJECT-TYPE
		SYNTAX		SEQUENCE OF PppDeadLogEntryEntry
		MAX-ACCESS	not-accessible
		STATUS		current
		DESCRIPTION
			"PPP dead log entry table."

	::= { aptis-monitoring 1317 }

	pppDeadLogEntryEntry	OBJECT-TYPE
		SYNTAX		PppDeadLogEntryEntry
		MAX-ACCESS	not-accessible
		STATUS		current
		DESCRIPTION
			"This is the structure of entries in the
			 pppDeadLogEntryTable."
		INDEX		{ pppDeadLogEntryIndex }
	::= { pppDeadLogEntryTable 1 }

	PppDeadLogEntryEntry ::= SEQUENCE {
		pppDeadLogEntrySessionId	INTEGER,
		pppDeadLogEntryIndex		INTEGER,
		pppDeadLogEntryMinIndex		INTEGER,
		pppDeadLogEntryMaxIndex		INTEGER,
		pppDeadLogEntryEntryText	OCTET STRING,
		pppDeadLogEntryRawEntryText	OCTET STRING
	}

	pppDeadLogEntrySessionId	OBJECT-TYPE
		SYNTAX		INTEGER
		MAX-ACCESS	read-only
		STATUS		current
		DESCRIPTION
			"System session ID"

	::= { pppDeadLogEntryEntry 1 }

	pppDeadLogEntryIndex	OBJECT-TYPE
		SYNTAX		INTEGER
		MAX-ACCESS	read-only
		STATUS		current
		DESCRIPTION
			"Log entry index"

	::= { pppDeadLogEntryEntry 2 }

	pppDeadLogEntryMinIndex	OBJECT-TYPE
		SYNTAX		INTEGER
		MAX-ACCESS	read-only
		STATUS		current
		DESCRIPTION
			"Index of oldest event available"

	::= { pppDeadLogEntryEntry 3 }

	pppDeadLogEntryMaxIndex	OBJECT-TYPE
		SYNTAX		INTEGER
		MAX-ACCESS	read-only
		STATUS		current
		DESCRIPTION
			"Index of newest event available"

	::= { pppDeadLogEntryEntry 4 }

	pppDeadLogEntryEntryText	OBJECT-TYPE
		SYNTAX		OCTET STRING (SIZE (0..1024))
		MAX-ACCESS	read-only
		STATUS		current
		DESCRIPTION
			"Log entry text."

	::= { pppDeadLogEntryEntry 5 }

	pppDeadLogEntryRawEntryText	OBJECT-TYPE
		SYNTAX		OCTET STRING (SIZE (0..512))
		MAX-ACCESS	read-only
		STATUS		current
		DESCRIPTION
			"Raw entry text, if appropriate for this log type."

	::= { pppDeadLogEntryEntry 6 }


	pppSessionStatsTable	OBJECT-TYPE
		SYNTAX		SEQUENCE OF PppSessionStatsEntry
		MAX-ACCESS	not-accessible
		STATUS		current
		DESCRIPTION
			"PPP session stats table."

	::= { aptis-monitoring 1318 }

	pppSessionStatsEntry	OBJECT-TYPE
		SYNTAX		PppSessionStatsEntry
		MAX-ACCESS	not-accessible
		STATUS		current
		DESCRIPTION
			"This is the structure of entries in the
			 pppSessionStatsTable."
		INDEX		{ pppSessionStatsSessionID }
	::= { pppSessionStatsTable 1 }

	PppSessionStatsEntry ::= SEQUENCE {
		pppSessionStatsSessionID	INTEGER,
		pppSessionStatsPhase		INTEGER,
		pppSessionStatsUserName		DisplayString,
		pppSessionStatsUpTime		INTEGER,
		pppSessionStatsConnectLimit	INTEGER,
		pppSessionStatsRemainingTime	INTEGER,
		pppSessionStatsInactivityLimit	INTEGER,
		pppSessionStatsInactivityRemaining INTEGER,
		pppSessionStatsDeadSession	Boolean,
		pppSessionStatsInterfaceType	INTEGER,
		pppSessionStatsTxSpeed		INTEGER,
		pppSessionStatsRxSpeed		INTEGER,
		pppSessionStatsLCPState		INTEGER,
		pppSessionStatsLocalMRU		INTEGER,
		pppSessionStatsRemoteMRU	INTEGER,
		pppSessionStatsLocalAuthProtocol INTEGER,
		pppSessionStatsRemoteAuthProtocol INTEGER,
		pppSessionStatsLocalPFC		Boolean,
		pppSessionStatsRemotePFC	Boolean,
		pppSessionStatsLocalACFC	Boolean,
		pppSessionStatsRemoteACFC	Boolean,
		pppSessionStatsLocalACCM	INTEGER,
		pppSessionStatsRemoteACCM	INTEGER,
		pppSessionStatsLocalMRRU	INTEGER,
		pppSessionStatsRemoteMRRU	INTEGER,
		pppSessionStatsLocalShortSeq	Boolean,
		pppSessionStatsRemoteShortSeq	Boolean,
		pppSessionStatsRemoteAuthenticated Boolean,
		pppSessionStatsIPCPState	INTEGER,
		pppSessionStatsLocalIPAddress	INTEGER,
		pppSessionStatsRemoteIPAddress	INTEGER,
		pppSessionStatsDNSAddress1	INTEGER,
		pppSessionStatsDNSAddress2	INTEGER,
		pppSessionStatsNBNSAddress1	INTEGER,
		pppSessionStatsNBNSAddress2	INTEGER,
		pppSessionStatsLocalVJ		Boolean,
		pppSessionStatsLocalVJSlots	INTEGER,
		pppSessionStatsRemoteVJ		Boolean,
		pppSessionStatsRemoteVJSlots	INTEGER,
		pppSessionStatsIPXCPState	INTEGER,
		pppSessionStatsRemoteIPXNetwork	INTEGER,
		pppSessionStatsRemoteIPXNode	DisplayString,
		pppSessionStatsCCPState		INTEGER,
		pppSessionStatsLocalCompressAlgorithm INTEGER,
		pppSessionStatsLocalCompressHistories INTEGER,
		pppSessionStatsRemoteCompressAlgorithm INTEGER,
		pppSessionStatsRemoteCompressHistories INTEGER,
		pppSessionStatsMultilinkActive	Boolean,
		pppSessionStatsMultilinkLinks	INTEGER,
		pppSessionStatsTotalTxSpeed	INTEGER,
		pppSessionStatsTotalRxSpeed	INTEGER,
		pppSessionStatsMLPFragmentsReceived INTEGER,
		pppSessionStatsMLPFragmentsMissing INTEGER,
		pppSessionStatsMLPFragmentsDropped INTEGER,
		pppSessionStatsMLPPacketsReassembled INTEGER,
		pppSessionStatsMLPPacketsNull	INTEGER,
		pppSessionStatsMultilinkLinksAdded INTEGER,
		pppSessionStatsMultilinkLinksRemoved INTEGER,
		pppSessionStatsMultilinkLinksMax INTEGER,
		pppSessionStatsMultilinkLinksMaxConfig INTEGER,
		pppSessionStatsTxPackets	INTEGER,
		pppSessionStatsTxPacketsDropped	INTEGER,
		pppSessionStatsTxBytes		INTEGER,
		pppSessionStatsRxPackets	INTEGER,
		pppSessionStatsRxPacketsDropped	INTEGER,
		pppSessionStatsRxBytes		INTEGER,
		pppSessionStatsTxCompressing	Boolean,
		pppSessionStatsTxBytesBeforeCompress INTEGER,
		pppSessionStatsTxBytesAfterCompress INTEGER,
		pppSessionStatsTxBytesUncompressed INTEGER,
		pppSessionStatsRxBytesBeforeCompress INTEGER,
		pppSessionStatsRxBytesAfterCompress INTEGER,
		pppSessionStatsRxBytesUncompressed INTEGER,
		pppSessionStatsRxCompPacketsDropped INTEGER,
		pppSessionStatsCCPResetsSent	INTEGER,
		pppSessionStatsCCPResetsReceived INTEGER,
		pppSessionStatsRxResourceErrors	INTEGER,
		pppSessionStatsRxQueueErrors	INTEGER,
		pppSessionStatsRxCRCErrors	INTEGER,
		pppSessionStatsRxAbortErrors	INTEGER,
		pppSessionStatsRxOverrunErrors	INTEGER,
		pppSessionStatsRxBigErrors	INTEGER,
		pppSessionStatsRxSmallErrors	INTEGER,
		pppSessionStatsRxAlignErrors	INTEGER,
		pppSessionStatsTxResourceErrors	INTEGER,
		pppSessionStatsTxQueueErrors	INTEGER,
		pppSessionStatsTxBigErrors	INTEGER,
		pppSessionStatsTxUnderrunErrors	INTEGER
	}

	pppSessionStatsSessionID	OBJECT-TYPE
		SYNTAX		INTEGER
		MAX-ACCESS	read-only
		STATUS		current
		DESCRIPTION
			"System session ID"

	::= { pppSessionStatsEntry 1 }

	pppSessionStatsPhase	OBJECT-TYPE
		SYNTAX		INTEGER {
				    idle(0),
				    establish(1),
				    auth(2),
				    network(3),
				    terminate(4)
				}
		MAX-ACCESS	read-only
		STATUS		current
		DESCRIPTION
			"Current PPP phase"

	::= { pppSessionStatsEntry 2 }

	pppSessionStatsUserName	OBJECT-TYPE
		SYNTAX		DisplayString (SIZE (0..64))
		MAX-ACCESS	read-only
		STATUS		current
		DESCRIPTION
			"User name"

	::= { pppSessionStatsEntry 3 }

	pppSessionStatsUpTime	OBJECT-TYPE
		SYNTAX		INTEGER
		MAX-ACCESS	read-only
		STATUS		current
		DESCRIPTION
			"Time (in seconds) session has been connected"

	::= { pppSessionStatsEntry 4 }

	pppSessionStatsConnectLimit	OBJECT-TYPE
		SYNTAX		INTEGER
		MAX-ACCESS	read-only
		STATUS		current
		DESCRIPTION
			"Maximum connect time (in seconds) allowed"

	::= { pppSessionStatsEntry 5 }

	pppSessionStatsRemainingTime	OBJECT-TYPE
		SYNTAX		INTEGER
		MAX-ACCESS	read-only
		STATUS		current
		DESCRIPTION
			"Time (in seconds) remaining. -1 indicates umlimited
			time."

	::= { pppSessionStatsEntry 6 }

	pppSessionStatsInactivityLimit	OBJECT-TYPE
		SYNTAX		INTEGER
		MAX-ACCESS	read-only
		STATUS		current
		DESCRIPTION
			"Inactivity time (in seconds) allowed before
			disconnecting"

	::= { pppSessionStatsEntry 7 }

	pppSessionStatsInactivityRemaining	OBJECT-TYPE
		SYNTAX		INTEGER
		MAX-ACCESS	read-only
		STATUS		current
		DESCRIPTION
			"Time (in seconds) before disconnection due to
			inactivity"

	::= { pppSessionStatsEntry 8 }

	pppSessionStatsDeadSession	OBJECT-TYPE
		SYNTAX		Boolean
		MAX-ACCESS	read-only
		STATUS		current
		DESCRIPTION
			"True if session is dead/disconnected"

	::= { pppSessionStatsEntry 9 }

	pppSessionStatsInterfaceType	OBJECT-TYPE
		SYNTAX		INTEGER {
				    unknown(0),
				    modem(1),
				    isdn(2),
				    leased(3),
				    hssi(4)
				}
		MAX-ACCESS	read-only
		STATUS		current
		DESCRIPTION
			"Interface type (modem, ISDN, etc.)"

	::= { pppSessionStatsEntry 101 }

	pppSessionStatsTxSpeed	OBJECT-TYPE
		SYNTAX		INTEGER
		MAX-ACCESS	read-only
		STATUS		current
		DESCRIPTION
			"Transmit speed in bits per second"

	::= { pppSessionStatsEntry 102 }

	pppSessionStatsRxSpeed	OBJECT-TYPE
		SYNTAX		INTEGER
		MAX-ACCESS	read-only
		STATUS		current
		DESCRIPTION
			"Transmit speed in bits per second"

	::= { pppSessionStatsEntry 103 }

	pppSessionStatsLCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of Link Control Protocol negotiation"

	::= { pppSessionStatsEntry 201 }

	pppSessionStatsLocalMRU	OBJECT-TYPE
		SYNTAX		INTEGER
		MAX-ACCESS	read-only
		STATUS		current
		DESCRIPTION
			"MRU negotiated by local LCP"

	::= { pppSessionStatsEntry 202 }

	pppSessionStatsRemoteMRU	OBJECT-TYPE
		SYNTAX		INTEGER
		MAX-ACCESS	read-only
		STATUS		current
		DESCRIPTION
			"MRU negotiated by remote LCP"

	::= { pppSessionStatsEntry 203 }

	pppSessionStatsLocalAuthProtocol	OBJECT-TYPE
		SYNTAX		INTEGER {
				    none(0),
				    chap(49699),
				    pap(49187)
				}
		MAX-ACCESS	read-only
		STATUS		current
		DESCRIPTION
			"Authentication protocol negotiated by local LCP"

	::= { pppSessionStatsEntry 204 }

	pppSessionStatsRemoteAuthProtocol	OBJECT-TYPE
		SYNTAX		INTEGER {
				    none(0),
				    chap(49699),
				    pap(49187)
				}
		MAX-ACCESS	read-only
		STATUS		current
		DESCRIPTION
			"Authentication protocol negotiated by remote LCP"

	::= { pppSessionStatsEntry 205 }

	pppSessionStatsLocalPFC	OBJECT-TYPE
		SYNTAX		Boolean
		MAX-ACCESS	read-only
		STATUS		current
		DESCRIPTION
			"Protocol Field Compression negotiated by local LCP"

	::= { pppSessionStatsEntry 206 }

	pppSessionStatsRemotePFC	OBJECT-TYPE
		SYNTAX		Boolean
		MAX-ACCESS	read-only
		STATUS		current
		DESCRIPTION
			"Protocol Field Compression negotiated by remote LCP"

	::= { pppSessionStatsEntry 207 }

	pppSessionStatsLocalACFC	OBJECT-TYPE
		SYNTAX		Boolean
		MAX-ACCESS	read-only
		STATUS		current
		DESCRIPTION
			"Address and Control Field Compression negotiated by
			local LCP"

	::= { pppSessionStatsEntry 208 }

	pppSessionStatsRemoteACFC	OBJECT-TYPE
		SYNTAX		Boolean
		MAX-ACCESS	read-only
		STATUS		current
		DESCRIPTION
			"Address and Control Field Compression negotiated by
			remote LCP"

	::= { pppSessionStatsEntry 209 }

	pppSessionStatsLocalACCM	OBJECT-TYPE
		SYNTAX		INTEGER
		MAX-ACCESS	read-only
		STATUS		current
		DESCRIPTION
			"ACCM negotiated by local LCP"

	::= { pppSessionStatsEntry 210 }

	pppSessionStatsRemoteACCM	OBJECT-TYPE
		SYNTAX		INTEGER
		MAX-ACCESS	read-only
		STATUS		current
		DESCRIPTION
			"ACCM negotiated by remote LCP"

	::= { pppSessionStatsEntry 211 }

	pppSessionStatsLocalMRRU	OBJECT-TYPE
		SYNTAX		INTEGER
		MAX-ACCESS	read-only
		STATUS		current
		DESCRIPTION
			"MRRU negotiated by local LCP"

	::= { pppSessionStatsEntry 212 }

	pppSessionStatsRemoteMRRU	OBJECT-TYPE
		SYNTAX		INTEGER
		MAX-ACCESS	read-only
		STATUS		current
		DESCRIPTION
			"MRRU negotiated by remote LCP"

	::= { pppSessionStatsEntry 213 }

	pppSessionStatsLocalShortSeq	OBJECT-TYPE
		SYNTAX		Boolean
		MAX-ACCESS	read-only
		STATUS		current
		DESCRIPTION
			"MLP short sequence numbers negotiated by local LCP"

	::= { pppSessionStatsEntry 214 }

	pppSessionStatsRemoteShortSeq	OBJECT-TYPE
		SYNTAX		Boolean
		MAX-ACCESS	read-only
		STATUS		current
		DESCRIPTION
			"MLP short sequence numbers negotiated by remote LCP"

	::= { pppSessionStatsEntry 215 }

	pppSessionStatsRemoteAuthenticated	OBJECT-TYPE
		SYNTAX		Boolean
		MAX-ACCESS	read-only
		STATUS		current
		DESCRIPTION
			"Remote user has been authenticated"

	::= { pppSessionStatsEntry 301 }

	pppSessionStatsIPCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of IP Control Protocol negotiation"

	::= { pppSessionStatsEntry 401 }

	pppSessionStatsLocalIPAddress	OBJECT-TYPE
		SYNTAX		INTEGER
		MAX-ACCESS	read-only
		STATUS		current
		DESCRIPTION
			"Local IP address"

	::= { pppSessionStatsEntry 402 }

	pppSessionStatsRemoteIPAddress	OBJECT-TYPE
		SYNTAX		INTEGER
		MAX-ACCESS	read-only
		STATUS		current
		DESCRIPTION
			"IP address assigned to remote user"

	::= { pppSessionStatsEntry 403 }

	pppSessionStatsDNSAddress1	OBJECT-TYPE
		SYNTAX		INTEGER
		MAX-ACCESS	read-only
		STATUS		current
		DESCRIPTION
			"First DNS address passed to remote user"

	::= { pppSessionStatsEntry 404 }

	pppSessionStatsDNSAddress2	OBJECT-TYPE
		SYNTAX		INTEGER
		MAX-ACCESS	read-only
		STATUS		current
		DESCRIPTION
			"Second DNS address passed to remote user"

	::= { pppSessionStatsEntry 405 }

	pppSessionStatsNBNSAddress1	OBJECT-TYPE
		SYNTAX		INTEGER
		MAX-ACCESS	read-only
		STATUS		current
		DESCRIPTION
			"First NBNS address passed to remote user"

	::= { pppSessionStatsEntry 406 }

	pppSessionStatsNBNSAddress2	OBJECT-TYPE
		SYNTAX		INTEGER
		MAX-ACCESS	read-only
		STATUS		current
		DESCRIPTION
			"Second NBNS address passed to remote user"

	::= { pppSessionStatsEntry 407 }

	pppSessionStatsLocalVJ	OBJECT-TYPE
		SYNTAX		Boolean
		MAX-ACCESS	read-only
		STATUS		current
		DESCRIPTION
			"VJ header compression negotiated by local IPCP"

	::= { pppSessionStatsEntry 408 }

	pppSessionStatsLocalVJSlots	OBJECT-TYPE
		SYNTAX		INTEGER
		MAX-ACCESS	read-only
		STATUS		current
		DESCRIPTION
			"Number of VJ slots negotiated by local IPCP"

	::= { pppSessionStatsEntry 409 }

	pppSessionStatsRemoteVJ	OBJECT-TYPE
		SYNTAX		Boolean
		MAX-ACCESS	read-only
		STATUS		current
		DESCRIPTION
			"VJ header compression negotiated by remote IPCP"

	::= { pppSessionStatsEntry 410 }

	pppSessionStatsRemoteVJSlots	OBJECT-TYPE
		SYNTAX		INTEGER
		MAX-ACCESS	read-only
		STATUS		current
		DESCRIPTION
			"Number of VJ slots negotiated by remote IPCP"

	::= { pppSessionStatsEntry 411 }

	pppSessionStatsIPXCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of IPX Control Protocol negotiation"

	::= { pppSessionStatsEntry 451 }

	pppSessionStatsRemoteIPXNetwork	OBJECT-TYPE
		SYNTAX		INTEGER
		MAX-ACCESS	read-only
		STATUS		current
		DESCRIPTION
			"Remote IPX Network number"

	::= { pppSessionStatsEntry 452 }

	pppSessionStatsRemoteIPXNode	OBJECT-TYPE
		SYNTAX		DisplayString (SIZE (0..13))
		MAX-ACCESS	read-only
		STATUS		current
		DESCRIPTION
			"Remote IPX Node number"

	::= { pppSessionStatsEntry 453 }

	pppSessionStatsCCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of Compression Control Protocol negotiation"

	::= { pppSessionStatsEntry 501 }

	pppSessionStatsLocalCompressAlgorithm	OBJECT-TYPE
		SYNTAX		INTEGER {
				    none(0),
				    stac4(1),
				    mppc(2),
				    stac3(3)
				}
		MAX-ACCESS	read-only
		STATUS		current
		DESCRIPTION
			"Compression algorithm negotiated by local CCP, and
			thus the algorithm used when the CVX decompresses
			data."

	::= { pppSessionStatsEntry 502 }

	pppSessionStatsLocalCompressHistories	OBJECT-TYPE
		SYNTAX		INTEGER
		MAX-ACCESS	read-only
		STATUS		current
		DESCRIPTION
			"Number of compression histories negotiated by local
			CCP"

	::= { pppSessionStatsEntry 503 }

	pppSessionStatsRemoteCompressAlgorithm	OBJECT-TYPE
		SYNTAX		INTEGER {
				    none(0),
				    stac4(1),
				    mppc(2),
				    stac3(3)
				}
		MAX-ACCESS	read-only
		STATUS		current
		DESCRIPTION
			"Compression algorithm negotiated by remote CCP, and
			thus the algorithm used when the CVX compresses data."

	::= { pppSessionStatsEntry 504 }

	pppSessionStatsRemoteCompressHistories	OBJECT-TYPE
		SYNTAX		INTEGER
		MAX-ACCESS	read-only
		STATUS		current
		DESCRIPTION
			"Number of compression histories negotiated by remote
			CCP"

	::= { pppSessionStatsEntry 505 }

	pppSessionStatsMultilinkActive	OBJECT-TYPE
		SYNTAX		Boolean
		MAX-ACCESS	read-only
		STATUS		current
		DESCRIPTION
			"Multilink active"

	::= { pppSessionStatsEntry 601 }

	pppSessionStatsMultilinkLinks	OBJECT-TYPE
		SYNTAX		INTEGER
		MAX-ACCESS	read-only
		STATUS		current
		DESCRIPTION
			"Number of links in multilink bundle. 0 if multilink
			is not active."

	::= { pppSessionStatsEntry 602 }

	pppSessionStatsTotalTxSpeed	OBJECT-TYPE
		SYNTAX		INTEGER
		MAX-ACCESS	read-only
		STATUS		current
		DESCRIPTION
			"Sum of transmit speeds on all links in multilink
			bundle. 0 if multilink is not active"

	::= { pppSessionStatsEntry 603 }

	pppSessionStatsTotalRxSpeed	OBJECT-TYPE
		SYNTAX		INTEGER
		MAX-ACCESS	read-only
		STATUS		current
		DESCRIPTION
			"Sum of receive speeds on all links in multilink
			bundle. 0 if multilink is not active"

	::= { pppSessionStatsEntry 604 }

	pppSessionStatsMLPFragmentsReceived	OBJECT-TYPE
		SYNTAX		INTEGER
		MAX-ACCESS	read-only
		STATUS		current
		DESCRIPTION
			"Total number of multilink fragments received"

	::= { pppSessionStatsEntry 605 }

	pppSessionStatsMLPFragmentsMissing	OBJECT-TYPE
		SYNTAX		INTEGER
		MAX-ACCESS	read-only
		STATUS		current
		DESCRIPTION
			"Number of times a missing multilink fragment was
			detected."

	::= { pppSessionStatsEntry 606 }

	pppSessionStatsMLPFragmentsDropped	OBJECT-TYPE
		SYNTAX		INTEGER
		MAX-ACCESS	read-only
		STATUS		current
		DESCRIPTION
			"Total number of multilink fragments received, but
			dropped"

	::= { pppSessionStatsEntry 607 }

	pppSessionStatsMLPPacketsReassembled	OBJECT-TYPE
		SYNTAX		INTEGER
		MAX-ACCESS	read-only
		STATUS		current
		DESCRIPTION
			"Total number of packets reassembled from multilink
			fragments"

	::= { pppSessionStatsEntry 608 }

	pppSessionStatsMLPPacketsNull	OBJECT-TYPE
		SYNTAX		INTEGER
		MAX-ACCESS	read-only
		STATUS		current
		DESCRIPTION
			"Total number of 0-length packets reassembled"

	::= { pppSessionStatsEntry 609 }

	pppSessionStatsMultilinkLinksAdded	OBJECT-TYPE
		SYNTAX		INTEGER
		MAX-ACCESS	read-only
		STATUS		current
		DESCRIPTION
			"Number of links added to multilink bundle over the
			bundle's life"

	::= { pppSessionStatsEntry 610 }

	pppSessionStatsMultilinkLinksRemoved	OBJECT-TYPE
		SYNTAX		INTEGER
		MAX-ACCESS	read-only
		STATUS		current
		DESCRIPTION
			"Number of links removed from multilink bundle over
			the bundle's life"

	::= { pppSessionStatsEntry 611 }

	pppSessionStatsMultilinkLinksMax	OBJECT-TYPE
		SYNTAX		INTEGER
		MAX-ACCESS	read-only
		STATUS		current
		DESCRIPTION
			"Maximum number of links ever in multilink bundle"

	::= { pppSessionStatsEntry 612 }

	pppSessionStatsMultilinkLinksMaxConfig	OBJECT-TYPE
		SYNTAX		INTEGER
		MAX-ACCESS	read-only
		STATUS		current
		DESCRIPTION
			"Maximum number of links allowed in multilink bundle"

	::= { pppSessionStatsEntry 613 }

	pppSessionStatsTxPackets	OBJECT-TYPE
		SYNTAX		INTEGER
		MAX-ACCESS	read-only
		STATUS		current
		DESCRIPTION
			"Number of protocol packets transmitted"

	::= { pppSessionStatsEntry 1001 }

	pppSessionStatsTxPacketsDropped	OBJECT-TYPE
		SYNTAX		INTEGER
		MAX-ACCESS	read-only
		STATUS		current
		DESCRIPTION
			"Number of protocol packets not transmitted (out of
			resources, queue limit reached, etc.)"

	::= { pppSessionStatsEntry 1002 }

	pppSessionStatsTxBytes	OBJECT-TYPE
		SYNTAX		INTEGER
		MAX-ACCESS	read-only
		STATUS		current
		DESCRIPTION
			"Total number of protocol bytes transmitted"

	::= { pppSessionStatsEntry 1003 }

	pppSessionStatsRxPackets	OBJECT-TYPE
		SYNTAX		INTEGER
		MAX-ACCESS	read-only
		STATUS		current
		DESCRIPTION
			"Number of protocol packets received"

	::= { pppSessionStatsEntry 1004 }

	pppSessionStatsRxPacketsDropped	OBJECT-TYPE
		SYNTAX		INTEGER
		MAX-ACCESS	read-only
		STATUS		current
		DESCRIPTION
			"Number of protocol packets not received (out of
			resources, queue limit reached, etc.)"

	::= { pppSessionStatsEntry 1005 }

	pppSessionStatsRxBytes	OBJECT-TYPE
		SYNTAX		INTEGER
		MAX-ACCESS	read-only
		STATUS		current
		DESCRIPTION
			"Total number of protocol bytes received"

	::= { pppSessionStatsEntry 1006 }

	pppSessionStatsTxCompressing	OBJECT-TYPE
		SYNTAX		Boolean
		MAX-ACCESS	read-only
		STATUS		current
		DESCRIPTION
			"Compression of transmitted frames is enabled in
			configuration"

	::= { pppSessionStatsEntry 1101 }

	pppSessionStatsTxBytesBeforeCompress	OBJECT-TYPE
		SYNTAX		INTEGER
		MAX-ACCESS	read-only
		STATUS		current
		DESCRIPTION
			"Total number of protocol bytes transmitted before
			compression. 0 if compression was not negotiated"

	::= { pppSessionStatsEntry 1102 }

	pppSessionStatsTxBytesAfterCompress	OBJECT-TYPE
		SYNTAX		INTEGER
		MAX-ACCESS	read-only
		STATUS		current
		DESCRIPTION
			"Total number of protocol bytes transmitted after
			compression. 0 if compression was not negotiated"

	::= { pppSessionStatsEntry 1103 }

	pppSessionStatsTxBytesUncompressed	OBJECT-TYPE
		SYNTAX		INTEGER
		MAX-ACCESS	read-only
		STATUS		current
		DESCRIPTION
			"Total number of protocol bytes transmitted without
			compression. This occurs when compression causes the
			data to grow instead of shrink. 0 if compression was
			not negotiated"

	::= { pppSessionStatsEntry 1104 }

	pppSessionStatsRxBytesBeforeCompress	OBJECT-TYPE
		SYNTAX		INTEGER
		MAX-ACCESS	read-only
		STATUS		current
		DESCRIPTION
			"Total number of protocol bytes received before
			compression. 0 if compression was not negotiated"

	::= { pppSessionStatsEntry 1105 }

	pppSessionStatsRxBytesAfterCompress	OBJECT-TYPE
		SYNTAX		INTEGER
		MAX-ACCESS	read-only
		STATUS		current
		DESCRIPTION
			"Total number of protocol bytes received after
			compression. 0 if compression was not negotiated"

	::= { pppSessionStatsEntry 1106 }

	pppSessionStatsRxBytesUncompressed	OBJECT-TYPE
		SYNTAX		INTEGER
		MAX-ACCESS	read-only
		STATUS		current
		DESCRIPTION
			"Total number of protocol bytes received without
			compression. This occurs when compression causes the
			data to grow instead of shrink. 0 if compression was
			not negotiated"

	::= { pppSessionStatsEntry 1107 }

	pppSessionStatsRxCompPacketsDropped	OBJECT-TYPE
		SYNTAX		INTEGER
		MAX-ACCESS	read-only
		STATUS		current
		DESCRIPTION
			"Number of compressed packets received but dropped
			(due to invalid sequence number, data corruption,
			etc.)"

	::= { pppSessionStatsEntry 1108 }

	pppSessionStatsCCPResetsSent	OBJECT-TYPE
		SYNTAX		INTEGER
		MAX-ACCESS	read-only
		STATUS		current
		DESCRIPTION
			"Total number of CCP Reset-Request frames transmitted.
			Each Reset-Request sent indicates that the CVX
			encountered an error while decompressing data
			transmitted by the remote system."

	::= { pppSessionStatsEntry 1109 }

	pppSessionStatsCCPResetsReceived	OBJECT-TYPE
		SYNTAX		INTEGER
		MAX-ACCESS	read-only
		STATUS		current
		DESCRIPTION
			"Total number of CCP Reset-Request frames received.
			Each Reset-Request received indicates that the remote
			system encountered an error while decompressing data
			transmitted by the CVX."

	::= { pppSessionStatsEntry 1110 }

	pppSessionStatsRxResourceErrors	OBJECT-TYPE
		SYNTAX		INTEGER
		MAX-ACCESS	read-only
		STATUS		current
		DESCRIPTION
			"Total number of receives dropped due to lack of a
			buffer"

	::= { pppSessionStatsEntry 1201 }

	pppSessionStatsRxQueueErrors	OBJECT-TYPE
		SYNTAX		INTEGER
		MAX-ACCESS	read-only
		STATUS		current
		DESCRIPTION
			"Total number of receives dropped due to queue depth"

	::= { pppSessionStatsEntry 1202 }

	pppSessionStatsRxCRCErrors	OBJECT-TYPE
		SYNTAX		INTEGER
		MAX-ACCESS	read-only
		STATUS		current
		DESCRIPTION
			"Total number of receives dropped due to invalid CRC"

	::= { pppSessionStatsEntry 1203 }

	pppSessionStatsRxAbortErrors	OBJECT-TYPE
		SYNTAX		INTEGER
		MAX-ACCESS	read-only
		STATUS		current
		DESCRIPTION
			"Total number of receives aborted"

	::= { pppSessionStatsEntry 1204 }

	pppSessionStatsRxOverrunErrors	OBJECT-TYPE
		SYNTAX		INTEGER
		MAX-ACCESS	read-only
		STATUS		current
		DESCRIPTION
			"Total number of receives dropped due to overruns"

	::= { pppSessionStatsEntry 1205 }

	pppSessionStatsRxBigErrors	OBJECT-TYPE
		SYNTAX		INTEGER
		MAX-ACCESS	read-only
		STATUS		current
		DESCRIPTION
			"Total number of receives that were too large"

	::= { pppSessionStatsEntry 1206 }

	pppSessionStatsRxSmallErrors	OBJECT-TYPE
		SYNTAX		INTEGER
		MAX-ACCESS	read-only
		STATUS		current
		DESCRIPTION
			"Total number of receives that were too small"

	::= { pppSessionStatsEntry 1207 }

	pppSessionStatsRxAlignErrors	OBJECT-TYPE
		SYNTAX		INTEGER
		MAX-ACCESS	read-only
		STATUS		current
		DESCRIPTION
			"Total number of receives dropped due to
			mis-alignment"

	::= { pppSessionStatsEntry 1208 }

	pppSessionStatsTxResourceErrors	OBJECT-TYPE
		SYNTAX		INTEGER
		MAX-ACCESS	read-only
		STATUS		current
		DESCRIPTION
			"Total number of transmits dropped due to lack of a
			buffer"

	::= { pppSessionStatsEntry 1209 }

	pppSessionStatsTxQueueErrors	OBJECT-TYPE
		SYNTAX		INTEGER
		MAX-ACCESS	read-only
		STATUS		current
		DESCRIPTION
			"Total number of transmits dropped due to queue depth"

	::= { pppSessionStatsEntry 1210 }

	pppSessionStatsTxBigErrors	OBJECT-TYPE
		SYNTAX		INTEGER
		MAX-ACCESS	read-only
		STATUS		current
		DESCRIPTION
			"Total number of transmits that were too large"

	::= { pppSessionStatsEntry 1211 }

	pppSessionStatsTxUnderrunErrors	OBJECT-TYPE
		SYNTAX		INTEGER
		MAX-ACCESS	read-only
		STATUS		current
		DESCRIPTION
			"Total number of transmits dropped due to underruns"

	::= { pppSessionStatsEntry 1212 }


	pppDeadSessionStatsTable	OBJECT-TYPE
		SYNTAX		SEQUENCE OF PppDeadSessionStatsEntry
		MAX-ACCESS	not-accessible
		STATUS		current
		DESCRIPTION
			"PPP dead session stats table."

	::= { aptis-monitoring 1320 }

	pppDeadSessionStatsEntry	OBJECT-TYPE
		SYNTAX		PppDeadSessionStatsEntry
		MAX-ACCESS	not-accessible
		STATUS		current
		DESCRIPTION
			"This is the structure of entries in the
			 pppDeadSessionStatsTable."
		INDEX		{ pppDeadSessionStatsSessionID }
	::= { pppDeadSessionStatsTable 1 }

	PppDeadSessionStatsEntry ::= SEQUENCE {
		pppDeadSessionStatsSessionID	INTEGER,
		pppDeadSessionStatsPhase	INTEGER,
		pppDeadSessionStatsUserName	DisplayString,
		pppDeadSessionStatsUpTime	INTEGER,
		pppDeadSessionStatsConnectLimit	INTEGER,
		pppDeadSessionStatsRemainingTime INTEGER,
		pppDeadSessionStatsInactivityLimit INTEGER,
		pppDeadSessionStatsInactivityRemaining INTEGER,
		pppDeadSessionStatsDeadSession	Boolean,
		pppDeadSessionStatsInterfaceType INTEGER,
		pppDeadSessionStatsTxSpeed	INTEGER,
		pppDeadSessionStatsRxSpeed	INTEGER,
		pppDeadSessionStatsLCPState	INTEGER,
		pppDeadSessionStatsLocalMRU	INTEGER,
		pppDeadSessionStatsRemoteMRU	INTEGER,
		pppDeadSessionStatsLocalAuthProtocol INTEGER,
		pppDeadSessionStatsRemoteAuthProtocol INTEGER,
		pppDeadSessionStatsLocalPFC	Boolean,
		pppDeadSessionStatsRemotePFC	Boolean,
		pppDeadSessionStatsLocalACFC	Boolean,
		pppDeadSessionStatsRemoteACFC	Boolean,
		pppDeadSessionStatsLocalACCM	INTEGER,
		pppDeadSessionStatsRemoteACCM	INTEGER,
		pppDeadSessionStatsLocalMRRU	INTEGER,
		pppDeadSessionStatsRemoteMRRU	INTEGER,
		pppDeadSessionStatsLocalShortSeq Boolean,
		pppDeadSessionStatsRemoteShortSeq Boolean,
		pppDeadSessionStatsRemoteAuthenticated Boolean,
		pppDeadSessionStatsIPCPState	INTEGER,
		pppDeadSessionStatsLocalIPAddress INTEGER,
		pppDeadSessionStatsRemoteIPAddress INTEGER,
		pppDeadSessionStatsDNSAddress1	INTEGER,
		pppDeadSessionStatsDNSAddress2	INTEGER,
		pppDeadSessionStatsNBNSAddress1	INTEGER,
		pppDeadSessionStatsNBNSAddress2	INTEGER,
		pppDeadSessionStatsLocalVJ	Boolean,
		pppDeadSessionStatsLocalVJSlots	INTEGER,
		pppDeadSessionStatsRemoteVJ	Boolean,
		pppDeadSessionStatsRemoteVJSlots INTEGER,
		pppDeadSessionStatsIPXCPState	INTEGER,
		pppDeadSessionStatsRemoteIPXNetwork INTEGER,
		pppDeadSessionStatsRemoteIPXNode DisplayString,
		pppDeadSessionStatsCCPState	INTEGER,
		pppDeadSessionStatsLocalCompressAlgorithm INTEGER,
		pppDeadSessionStatsLocalCompressHistories INTEGER,
		pppDeadSessionStatsRemoteCompressAlgorithm INTEGER,
		pppDeadSessionStatsRemoteCompressHistories INTEGER,
		pppDeadSessionStatsMultilinkActive Boolean,
		pppDeadSessionStatsMultilinkLinks INTEGER,
		pppDeadSessionStatsTotalTxSpeed	INTEGER,
		pppDeadSessionStatsTotalRxSpeed	INTEGER,
		pppDeadSessionStatsMLPFragmentsReceived INTEGER,
		pppDeadSessionStatsMLPFragmentsMissing INTEGER,
		pppDeadSessionStatsMLPFragmentsDropped INTEGER,
		pppDeadSessionStatsMLPPacketsReassembled INTEGER,
		pppDeadSessionStatsMLPPacketsNull INTEGER,
		pppDeadSessionStatsMultilinkLinksAdded INTEGER,
		pppDeadSessionStatsMultilinkLinksRemoved INTEGER,
		pppDeadSessionStatsMultilinkLinksMax INTEGER,
		pppDeadSessionStatsMultilinkLinksMaxConfig INTEGER,
		pppDeadSessionStatsTxPackets	INTEGER,
		pppDeadSessionStatsTxPacketsDropped INTEGER,
		pppDeadSessionStatsTxBytes	INTEGER,
		pppDeadSessionStatsRxPackets	INTEGER,
		pppDeadSessionStatsRxPacketsDropped INTEGER,
		pppDeadSessionStatsRxBytes	INTEGER,
		pppDeadSessionStatsTxCompressing Boolean,
		pppDeadSessionStatsTxBytesBeforeCompress INTEGER,
		pppDeadSessionStatsTxBytesAfterCompress INTEGER,
		pppDeadSessionStatsTxBytesUncompressed INTEGER,
		pppDeadSessionStatsRxBytesBeforeCompress INTEGER,
		pppDeadSessionStatsRxBytesAfterCompress INTEGER,
		pppDeadSessionStatsRxBytesUncompressed INTEGER,
		pppDeadSessionStatsRxCompPacketsDropped INTEGER,
		pppDeadSessionStatsCCPResetsSent INTEGER,
		pppDeadSessionStatsCCPResetsReceived INTEGER,
		pppDeadSessionStatsRxResourceErrors INTEGER,
		pppDeadSessionStatsRxQueueErrors INTEGER,
		pppDeadSessionStatsRxCRCErrors	INTEGER,
		pppDeadSessionStatsRxAbortErrors INTEGER,
		pppDeadSessionStatsRxOverrunErrors INTEGER,
		pppDeadSessionStatsRxBigErrors	INTEGER,
		pppDeadSessionStatsRxSmallErrors INTEGER,
		pppDeadSessionStatsRxAlignErrors INTEGER,
		pppDeadSessionStatsTxResourceErrors INTEGER,
		pppDeadSessionStatsTxQueueErrors INTEGER,
		pppDeadSessionStatsTxBigErrors	INTEGER,
		pppDeadSessionStatsTxUnderrunErrors INTEGER
	}

	pppDeadSessionStatsSessionID	OBJECT-TYPE
		SYNTAX		INTEGER
		MAX-ACCESS	read-only
		STATUS		current
		DESCRIPTION
			"System session ID"

	::= { pppDeadSessionStatsEntry 1 }

	pppDeadSessionStatsPhase	OBJECT-TYPE
		SYNTAX		INTEGER {
				    idle(0),
				    establish(1),
				    auth(2),
				    network(3),
				    terminate(4)
				}
		MAX-ACCESS	read-only
		STATUS		current
		DESCRIPTION
			"Current PPP phase"

	::= { pppDeadSessionStatsEntry 2 }

	pppDeadSessionStatsUserName	OBJECT-TYPE
		SYNTAX		DisplayString (SIZE (0..64))
		MAX-ACCESS	read-only
		STATUS		current
		DESCRIPTION
			"User name"

	::= { pppDeadSessionStatsEntry 3 }

	pppDeadSessionStatsUpTime	OBJECT-TYPE
		SYNTAX		INTEGER
		MAX-ACCESS	read-only
		STATUS		current
		DESCRIPTION
			"Time (in seconds) session has been connected"

	::= { pppDeadSessionStatsEntry 4 }

	pppDeadSessionStatsConnectLimit	OBJECT-TYPE
		SYNTAX		INTEGER
		MAX-ACCESS	read-only
		STATUS		current
		DESCRIPTION
			"Maximum connect time (in seconds) allowed"

	::= { pppDeadSessionStatsEntry 5 }

	pppDeadSessionStatsRemainingTime	OBJECT-TYPE
		SYNTAX		INTEGER
		MAX-ACCESS	read-only
		STATUS		current
		DESCRIPTION
			"Time (in seconds) remaining. -1 indicates umlimited
			time."

	::= { pppDeadSessionStatsEntry 6 }

	pppDeadSessionStatsInactivityLimit	OBJECT-TYPE
		SYNTAX		INTEGER
		MAX-ACCESS	read-only
		STATUS		current
		DESCRIPTION
			"Inactivity time (in seconds) allowed before
			disconnecting"

	::= { pppDeadSessionStatsEntry 7 }

	pppDeadSessionStatsInactivityRemaining	OBJECT-TYPE
		SYNTAX		INTEGER
		MAX-ACCESS	read-only
		STATUS		current
		DESCRIPTION
			"Time (in seconds) before disconnection due to
			inactivity"

	::= { pppDeadSessionStatsEntry 8 }

	pppDeadSessionStatsDeadSession	OBJECT-TYPE
		SYNTAX		Boolean
		MAX-ACCESS	read-only
		STATUS		current
		DESCRIPTION
			"True if session is dead/disconnected"

	::= { pppDeadSessionStatsEntry 9 }

	pppDeadSessionStatsInterfaceType	OBJECT-TYPE
		SYNTAX		INTEGER {
				    unknown(0),
				    modem(1),
				    isdn(2),
				    leased(3),
				    hssi(4)
				}
		MAX-ACCESS	read-only
		STATUS		current
		DESCRIPTION
			"Interface type (modem, ISDN, etc.)"

	::= { pppDeadSessionStatsEntry 101 }

	pppDeadSessionStatsTxSpeed	OBJECT-TYPE
		SYNTAX		INTEGER
		MAX-ACCESS	read-only
		STATUS		current
		DESCRIPTION
			"Transmit speed in bits per second"

	::= { pppDeadSessionStatsEntry 102 }

	pppDeadSessionStatsRxSpeed	OBJECT-TYPE
		SYNTAX		INTEGER
		MAX-ACCESS	read-only
		STATUS		current
		DESCRIPTION
			"Transmit speed in bits per second"

	::= { pppDeadSessionStatsEntry 103 }

	pppDeadSessionStatsLCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of Link Control Protocol negotiation"

	::= { pppDeadSessionStatsEntry 201 }

	pppDeadSessionStatsLocalMRU	OBJECT-TYPE
		SYNTAX		INTEGER
		MAX-ACCESS	read-only
		STATUS		current
		DESCRIPTION
			"MRU negotiated by local LCP"

	::= { pppDeadSessionStatsEntry 202 }

	pppDeadSessionStatsRemoteMRU	OBJECT-TYPE
		SYNTAX		INTEGER
		MAX-ACCESS	read-only
		STATUS		current
		DESCRIPTION
			"MRU negotiated by remote LCP"

	::= { pppDeadSessionStatsEntry 203 }

	pppDeadSessionStatsLocalAuthProtocol	OBJECT-TYPE
		SYNTAX		INTEGER {
				    none(0),
				    chap(49699),
				    pap(49187)
				}
		MAX-ACCESS	read-only
		STATUS		current
		DESCRIPTION
			"Authentication protocol negotiated by local LCP"

	::= { pppDeadSessionStatsEntry 204 }

	pppDeadSessionStatsRemoteAuthProtocol	OBJECT-TYPE
		SYNTAX		INTEGER {
				    none(0),
				    chap(49699),
				    pap(49187)
				}
		MAX-ACCESS	read-only
		STATUS		current
		DESCRIPTION
			"Authentication protocol negotiated by remote LCP"

	::= { pppDeadSessionStatsEntry 205 }

	pppDeadSessionStatsLocalPFC	OBJECT-TYPE
		SYNTAX		Boolean
		MAX-ACCESS	read-only
		STATUS		current
		DESCRIPTION
			"Protocol Field Compression negotiated by local LCP"

	::= { pppDeadSessionStatsEntry 206 }

	pppDeadSessionStatsRemotePFC	OBJECT-TYPE
		SYNTAX		Boolean
		MAX-ACCESS	read-only
		STATUS		current
		DESCRIPTION
			"Protocol Field Compression negotiated by remote LCP"

	::= { pppDeadSessionStatsEntry 207 }

	pppDeadSessionStatsLocalACFC	OBJECT-TYPE
		SYNTAX		Boolean
		MAX-ACCESS	read-only
		STATUS		current
		DESCRIPTION
			"Address and Control Field Compression negotiated by
			local LCP"

	::= { pppDeadSessionStatsEntry 208 }

	pppDeadSessionStatsRemoteACFC	OBJECT-TYPE
		SYNTAX		Boolean
		MAX-ACCESS	read-only
		STATUS		current
		DESCRIPTION
			"Address and Control Field Compression negotiated by
			remote LCP"

	::= { pppDeadSessionStatsEntry 209 }

	pppDeadSessionStatsLocalACCM	OBJECT-TYPE
		SYNTAX		INTEGER
		MAX-ACCESS	read-only
		STATUS		current
		DESCRIPTION
			"ACCM negotiated by local LCP"

	::= { pppDeadSessionStatsEntry 210 }

	pppDeadSessionStatsRemoteACCM	OBJECT-TYPE
		SYNTAX		INTEGER
		MAX-ACCESS	read-only
		STATUS		current
		DESCRIPTION
			"ACCM negotiated by remote LCP"

	::= { pppDeadSessionStatsEntry 211 }

	pppDeadSessionStatsLocalMRRU	OBJECT-TYPE
		SYNTAX		INTEGER
		MAX-ACCESS	read-only
		STATUS		current
		DESCRIPTION
			"MRRU negotiated by local LCP"

	::= { pppDeadSessionStatsEntry 212 }

	pppDeadSessionStatsRemoteMRRU	OBJECT-TYPE
		SYNTAX		INTEGER
		MAX-ACCESS	read-only
		STATUS		current
		DESCRIPTION
			"MRRU negotiated by remote LCP"

	::= { pppDeadSessionStatsEntry 213 }

	pppDeadSessionStatsLocalShortSeq	OBJECT-TYPE
		SYNTAX		Boolean
		MAX-ACCESS	read-only
		STATUS		current
		DESCRIPTION
			"MLP short sequence numbers negotiated by local LCP"

	::= { pppDeadSessionStatsEntry 214 }

	pppDeadSessionStatsRemoteShortSeq	OBJECT-TYPE
		SYNTAX		Boolean
		MAX-ACCESS	read-only
		STATUS		current
		DESCRIPTION
			"MLP short sequence numbers negotiated by remote LCP"

	::= { pppDeadSessionStatsEntry 215 }

	pppDeadSessionStatsRemoteAuthenticated	OBJECT-TYPE
		SYNTAX		Boolean
		MAX-ACCESS	read-only
		STATUS		current
		DESCRIPTION
			"Remote user has been authenticated"

	::= { pppDeadSessionStatsEntry 301 }

	pppDeadSessionStatsIPCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of IP Control Protocol negotiation"

	::= { pppDeadSessionStatsEntry 401 }

	pppDeadSessionStatsLocalIPAddress	OBJECT-TYPE
		SYNTAX		INTEGER
		MAX-ACCESS	read-only
		STATUS		current
		DESCRIPTION
			"Local IP address"

	::= { pppDeadSessionStatsEntry 402 }

	pppDeadSessionStatsRemoteIPAddress	OBJECT-TYPE
		SYNTAX		INTEGER
		MAX-ACCESS	read-only
		STATUS		current
		DESCRIPTION
			"IP address assigned to remote user"

	::= { pppDeadSessionStatsEntry 403 }

	pppDeadSessionStatsDNSAddress1	OBJECT-TYPE
		SYNTAX		INTEGER
		MAX-ACCESS	read-only
		STATUS		current
		DESCRIPTION
			"First DNS address passed to remote user"

	::= { pppDeadSessionStatsEntry 404 }

	pppDeadSessionStatsDNSAddress2	OBJECT-TYPE
		SYNTAX		INTEGER
		MAX-ACCESS	read-only
		STATUS		current
		DESCRIPTION
			"Second DNS address passed to remote user"

	::= { pppDeadSessionStatsEntry 405 }

	pppDeadSessionStatsNBNSAddress1	OBJECT-TYPE
		SYNTAX		INTEGER
		MAX-ACCESS	read-only
		STATUS		current
		DESCRIPTION
			"First NBNS address passed to remote user"

	::= { pppDeadSessionStatsEntry 406 }

	pppDeadSessionStatsNBNSAddress2	OBJECT-TYPE
		SYNTAX		INTEGER
		MAX-ACCESS	read-only
		STATUS		current
		DESCRIPTION
			"Second NBNS address passed to remote user"

	::= { pppDeadSessionStatsEntry 407 }

	pppDeadSessionStatsLocalVJ	OBJECT-TYPE
		SYNTAX		Boolean
		MAX-ACCESS	read-only
		STATUS		current
		DESCRIPTION
			"VJ header compression negotiated by local IPCP"

	::= { pppDeadSessionStatsEntry 408 }

	pppDeadSessionStatsLocalVJSlots	OBJECT-TYPE
		SYNTAX		INTEGER
		MAX-ACCESS	read-only
		STATUS		current
		DESCRIPTION
			"Number of VJ slots negotiated by local IPCP"

	::= { pppDeadSessionStatsEntry 409 }

	pppDeadSessionStatsRemoteVJ	OBJECT-TYPE
		SYNTAX		Boolean
		MAX-ACCESS	read-only
		STATUS		current
		DESCRIPTION
			"VJ header compression negotiated by remote IPCP"

	::= { pppDeadSessionStatsEntry 410 }

	pppDeadSessionStatsRemoteVJSlots	OBJECT-TYPE
		SYNTAX		INTEGER
		MAX-ACCESS	read-only
		STATUS		current
		DESCRIPTION
			"Number of VJ slots negotiated by remote IPCP"

	::= { pppDeadSessionStatsEntry 411 }

	pppDeadSessionStatsIPXCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of IPX Control Protocol negotiation"

	::= { pppDeadSessionStatsEntry 451 }

	pppDeadSessionStatsRemoteIPXNetwork	OBJECT-TYPE
		SYNTAX		INTEGER
		MAX-ACCESS	read-only
		STATUS		current
		DESCRIPTION
			"Remote IPX Network number"

	::= { pppDeadSessionStatsEntry 452 }

	pppDeadSessionStatsRemoteIPXNode	OBJECT-TYPE
		SYNTAX		DisplayString (SIZE (0..13))
		MAX-ACCESS	read-only
		STATUS		current
		DESCRIPTION
			"Remote IPX Node number"

	::= { pppDeadSessionStatsEntry 453 }

	pppDeadSessionStatsCCPState	OBJECT-TYPE
		SYNTAX		INTEGER {
				    initial(0),
				    starting(1),
				    closed(2),
				    stopped(3),
				    closing(4),
				    stopping(5),
				    reqSent(6),
				    ackRcvd(7),
				    ackSent(8),
				    opened(9)
				}
		MAX-ACCESS	read-only
		STATUS		current
		DESCRIPTION
			"State of Compression Control Protocol negotiation"

	::= { pppDeadSessionStatsEntry 501 }

	pppDeadSessionStatsLocalCompressAlgorithm	OBJECT-TYPE
		SYNTAX		INTEGER {
				    none(0),
				    stac4(1),
				    mppc(2),
				    stac3(3)
				}
		MAX-ACCESS	read-only
		STATUS		current
		DESCRIPTION
			"Compression algorithm negotiated by local CCP, and
			thus the algorithm used when the CVX decompresses
			data."

	::= { pppDeadSessionStatsEntry 502 }

	pppDeadSessionStatsLocalCompressHistories	OBJECT-TYPE
		SYNTAX		INTEGER
		MAX-ACCESS	read-only
		STATUS		current
		DESCRIPTION
			"Number of compression histories negotiated by local
			CCP"

	::= { pppDeadSessionStatsEntry 503 }

	pppDeadSessionStatsRemoteCompressAlgorithm	OBJECT-TYPE
		SYNTAX		INTEGER {
				    none(0),
				    stac4(1),
				    mppc(2),
				    stac3(3)
				}
		MAX-ACCESS	read-only
		STATUS		current
		DESCRIPTION
			"Compression algorithm negotiated by remote CCP, and
			thus the algorithm used when the CVX compresses data."

	::= { pppDeadSessionStatsEntry 504 }

	pppDeadSessionStatsRemoteCompressHistories	OBJECT-TYPE
		SYNTAX		INTEGER
		MAX-ACCESS	read-only
		STATUS		current
		DESCRIPTION
			"Number of compression histories negotiated by remote
			CCP"

	::= { pppDeadSessionStatsEntry 505 }

	pppDeadSessionStatsMultilinkActive	OBJECT-TYPE
		SYNTAX		Boolean
		MAX-ACCESS	read-only
		STATUS		current
		DESCRIPTION
			"Multilink active"

	::= { pppDeadSessionStatsEntry 601 }

	pppDeadSessionStatsMultilinkLinks	OBJECT-TYPE
		SYNTAX		INTEGER
		MAX-ACCESS	read-only
		STATUS		current
		DESCRIPTION
			"Number of links in multilink bundle. 0 if multilink
			is not active."

	::= { pppDeadSessionStatsEntry 602 }

	pppDeadSessionStatsTotalTxSpeed	OBJECT-TYPE
		SYNTAX		INTEGER
		MAX-ACCESS	read-only
		STATUS		current
		DESCRIPTION
			"Sum of transmit speeds on all links in multilink
			bundle. 0 if multilink is not active"

	::= { pppDeadSessionStatsEntry 603 }

	pppDeadSessionStatsTotalRxSpeed	OBJECT-TYPE
		SYNTAX		INTEGER
		MAX-ACCESS	read-only
		STATUS		current
		DESCRIPTION
			"Sum of receive speeds on all links in multilink
			bundle. 0 if multilink is not active"

	::= { pppDeadSessionStatsEntry 604 }

	pppDeadSessionStatsMLPFragmentsReceived	OBJECT-TYPE
		SYNTAX		INTEGER
		MAX-ACCESS	read-only
		STATUS		current
		DESCRIPTION
			"Total number of multilink fragments received"

	::= { pppDeadSessionStatsEntry 605 }

	pppDeadSessionStatsMLPFragmentsMissing	OBJECT-TYPE
		SYNTAX		INTEGER
		MAX-ACCESS	read-only
		STATUS		current
		DESCRIPTION
			"Number of times a missing multilink fragment was
			detected."

	::= { pppDeadSessionStatsEntry 606 }

	pppDeadSessionStatsMLPFragmentsDropped	OBJECT-TYPE
		SYNTAX		INTEGER
		MAX-ACCESS	read-only
		STATUS		current
		DESCRIPTION
			"Total number of multilink fragments received, but
			dropped"

	::= { pppDeadSessionStatsEntry 607 }

	pppDeadSessionStatsMLPPacketsReassembled	OBJECT-TYPE
		SYNTAX		INTEGER
		MAX-ACCESS	read-only
		STATUS		current
		DESCRIPTION
			"Total number of packets reassembled from multilink
			fragments"

	::= { pppDeadSessionStatsEntry 608 }

	pppDeadSessionStatsMLPPacketsNull	OBJECT-TYPE
		SYNTAX		INTEGER
		MAX-ACCESS	read-only
		STATUS		current
		DESCRIPTION
			"Total number of 0-length packets reassembled"

	::= { pppDeadSessionStatsEntry 609 }

	pppDeadSessionStatsMultilinkLinksAdded	OBJECT-TYPE
		SYNTAX		INTEGER
		MAX-ACCESS	read-only
		STATUS		current
		DESCRIPTION
			"Number of links added to multilink bundle over the
			bundle's life"

	::= { pppDeadSessionStatsEntry 610 }

	pppDeadSessionStatsMultilinkLinksRemoved	OBJECT-TYPE
		SYNTAX		INTEGER
		MAX-ACCESS	read-only
		STATUS		current
		DESCRIPTION
			"Number of links removed from multilink bundle over
			the bundle's life"

	::= { pppDeadSessionStatsEntry 611 }

	pppDeadSessionStatsMultilinkLinksMax	OBJECT-TYPE
		SYNTAX		INTEGER
		MAX-ACCESS	read-only
		STATUS		current
		DESCRIPTION
			"Maximum number of links ever in multilink bundle"

	::= { pppDeadSessionStatsEntry 612 }

	pppDeadSessionStatsMultilinkLinksMaxConfig	OBJECT-TYPE
		SYNTAX		INTEGER
		MAX-ACCESS	read-only
		STATUS		current
		DESCRIPTION
			"Maximum number of links allowed in multilink bundle"

	::= { pppDeadSessionStatsEntry 613 }

	pppDeadSessionStatsTxPackets	OBJECT-TYPE
		SYNTAX		INTEGER
		MAX-ACCESS	read-only
		STATUS		current
		DESCRIPTION
			"Number of protocol packets transmitted"

	::= { pppDeadSessionStatsEntry 1001 }

	pppDeadSessionStatsTxPacketsDropped	OBJECT-TYPE
		SYNTAX		INTEGER
		MAX-ACCESS	read-only
		STATUS		current
		DESCRIPTION
			"Number of protocol packets not transmitted (out of
			resources, queue limit reached, etc.)"

	::= { pppDeadSessionStatsEntry 1002 }

	pppDeadSessionStatsTxBytes	OBJECT-TYPE
		SYNTAX		INTEGER
		MAX-ACCESS	read-only
		STATUS		current
		DESCRIPTION
			"Total number of protocol bytes transmitted"

	::= { pppDeadSessionStatsEntry 1003 }

	pppDeadSessionStatsRxPackets	OBJECT-TYPE
		SYNTAX		INTEGER
		MAX-ACCESS	read-only
		STATUS		current
		DESCRIPTION
			"Number of protocol packets received"

	::= { pppDeadSessionStatsEntry 1004 }

	pppDeadSessionStatsRxPacketsDropped	OBJECT-TYPE
		SYNTAX		INTEGER
		MAX-ACCESS	read-only
		STATUS		current
		DESCRIPTION
			"Number of protocol packets not received (out of
			resources, queue limit reached, etc.)"

	::= { pppDeadSessionStatsEntry 1005 }

	pppDeadSessionStatsRxBytes	OBJECT-TYPE
		SYNTAX		INTEGER
		MAX-ACCESS	read-only
		STATUS		current
		DESCRIPTION
			"Total number of protocol bytes received"

	::= { pppDeadSessionStatsEntry 1006 }

	pppDeadSessionStatsTxCompressing	OBJECT-TYPE
		SYNTAX		Boolean
		MAX-ACCESS	read-only
		STATUS		current
		DESCRIPTION
			"Compression of transmitted frames is enabled in
			configuration"

	::= { pppDeadSessionStatsEntry 1101 }

	pppDeadSessionStatsTxBytesBeforeCompress	OBJECT-TYPE
		SYNTAX		INTEGER
		MAX-ACCESS	read-only
		STATUS		current
		DESCRIPTION
			"Total number of protocol bytes transmitted before
			compression. 0 if compression was not negotiated"

	::= { pppDeadSessionStatsEntry 1102 }

	pppDeadSessionStatsTxBytesAfterCompress	OBJECT-TYPE
		SYNTAX		INTEGER
		MAX-ACCESS	read-only
		STATUS		current
		DESCRIPTION
			"Total number of protocol bytes transmitted after
			compression. 0 if compression was not negotiated"

	::= { pppDeadSessionStatsEntry 1103 }

	pppDeadSessionStatsTxBytesUncompressed	OBJECT-TYPE
		SYNTAX		INTEGER
		MAX-ACCESS	read-only
		STATUS		current
		DESCRIPTION
			"Total number of protocol bytes transmitted without
			compression. This occurs when compression causes the
			data to grow instead of shrink. 0 if compression was
			not negotiated"

	::= { pppDeadSessionStatsEntry 1104 }

	pppDeadSessionStatsRxBytesBeforeCompress	OBJECT-TYPE
		SYNTAX		INTEGER
		MAX-ACCESS	read-only
		STATUS		current
		DESCRIPTION
			"Total number of protocol bytes received before
			compression. 0 if compression was not negotiated"

	::= { pppDeadSessionStatsEntry 1105 }

	pppDeadSessionStatsRxBytesAfterCompress	OBJECT-TYPE
		SYNTAX		INTEGER
		MAX-ACCESS	read-only
		STATUS		current
		DESCRIPTION
			"Total number of protocol bytes received after
			compression. 0 if compression was not negotiated"

	::= { pppDeadSessionStatsEntry 1106 }

	pppDeadSessionStatsRxBytesUncompressed	OBJECT-TYPE
		SYNTAX		INTEGER
		MAX-ACCESS	read-only
		STATUS		current
		DESCRIPTION
			"Total number of protocol bytes received without
			compression. This occurs when compression causes the
			data to grow instead of shrink. 0 if compression was
			not negotiated"

	::= { pppDeadSessionStatsEntry 1107 }

	pppDeadSessionStatsRxCompPacketsDropped	OBJECT-TYPE
		SYNTAX		INTEGER
		MAX-ACCESS	read-only
		STATUS		current
		DESCRIPTION
			"Number of compressed packets received but dropped
			(due to invalid sequence number, data corruption,
			etc.)"

	::= { pppDeadSessionStatsEntry 1108 }

	pppDeadSessionStatsCCPResetsSent	OBJECT-TYPE
		SYNTAX		INTEGER
		MAX-ACCESS	read-only
		STATUS		current
		DESCRIPTION
			"Total number of CCP Reset-Request frames transmitted.
			Each Reset-Request sent indicates that the CVX
			encountered an error while decompressing data
			transmitted by the remote system."

	::= { pppDeadSessionStatsEntry 1109 }

	pppDeadSessionStatsCCPResetsReceived	OBJECT-TYPE
		SYNTAX		INTEGER
		MAX-ACCESS	read-only
		STATUS		current
		DESCRIPTION
			"Total number of CCP Reset-Request frames received.
			Each Reset-Request received indicates that the remote
			system encountered an error while decompressing data
			transmitted by the CVX."

	::= { pppDeadSessionStatsEntry 1110 }

	pppDeadSessionStatsRxResourceErrors	OBJECT-TYPE
		SYNTAX		INTEGER
		MAX-ACCESS	read-only
		STATUS		current
		DESCRIPTION
			"Total number of receives dropped due to lack of a
			buffer"

	::= { pppDeadSessionStatsEntry 1201 }

	pppDeadSessionStatsRxQueueErrors	OBJECT-TYPE
		SYNTAX		INTEGER
		MAX-ACCESS	read-only
		STATUS		current
		DESCRIPTION
			"Total number of receives dropped due to queue depth"

	::= { pppDeadSessionStatsEntry 1202 }

	pppDeadSessionStatsRxCRCErrors	OBJECT-TYPE
		SYNTAX		INTEGER
		MAX-ACCESS	read-only
		STATUS		current
		DESCRIPTION
			"Total number of receives dropped due to invalid CRC"

	::= { pppDeadSessionStatsEntry 1203 }

	pppDeadSessionStatsRxAbortErrors	OBJECT-TYPE
		SYNTAX		INTEGER
		MAX-ACCESS	read-only
		STATUS		current
		DESCRIPTION
			"Total number of receives aborted"

	::= { pppDeadSessionStatsEntry 1204 }

	pppDeadSessionStatsRxOverrunErrors	OBJECT-TYPE
		SYNTAX		INTEGER
		MAX-ACCESS	read-only
		STATUS		current
		DESCRIPTION
			"Total number of receives dropped due to overruns"

	::= { pppDeadSessionStatsEntry 1205 }

	pppDeadSessionStatsRxBigErrors	OBJECT-TYPE
		SYNTAX		INTEGER
		MAX-ACCESS	read-only
		STATUS		current
		DESCRIPTION
			"Total number of receives that were too large"

	::= { pppDeadSessionStatsEntry 1206 }

	pppDeadSessionStatsRxSmallErrors	OBJECT-TYPE
		SYNTAX		INTEGER
		MAX-ACCESS	read-only
		STATUS		current
		DESCRIPTION
			"Total number of receives that were too small"

	::= { pppDeadSessionStatsEntry 1207 }

	pppDeadSessionStatsRxAlignErrors	OBJECT-TYPE
		SYNTAX		INTEGER
		MAX-ACCESS	read-only
		STATUS		current
		DESCRIPTION
			"Total number of receives dropped due to
			mis-alignment"

	::= { pppDeadSessionStatsEntry 1208 }

	pppDeadSessionStatsTxResourceErrors	OBJECT-TYPE
		SYNTAX		INTEGER
		MAX-ACCESS	read-only
		STATUS		current
		DESCRIPTION
			"Total number of transmits dropped due to lack of a
			buffer"

	::= { pppDeadSessionStatsEntry 1209 }

	pppDeadSessionStatsTxQueueErrors	OBJECT-TYPE
		SYNTAX		INTEGER
		MAX-ACCESS	read-only
		STATUS		current
		DESCRIPTION
			"Total number of transmits dropped due to queue depth"

	::= { pppDeadSessionStatsEntry 1210 }

	pppDeadSessionStatsTxBigErrors	OBJECT-TYPE
		SYNTAX		INTEGER
		MAX-ACCESS	read-only
		STATUS		current
		DESCRIPTION
			"Total number of transmits that were too large"

	::= { pppDeadSessionStatsEntry 1211 }

	pppDeadSessionStatsTxUnderrunErrors	OBJECT-TYPE
		SYNTAX		INTEGER
		MAX-ACCESS	read-only
		STATUS		current
		DESCRIPTION
			"Total number of transmits dropped due to underruns"

	::= { pppDeadSessionStatsEntry 1212 }


	pppSummaryStatsTable	OBJECT-TYPE
		SYNTAX		SEQUENCE OF PppSummaryStatsEntry
		MAX-ACCESS	not-accessible
		STATUS		current
		DESCRIPTION
			"PPP summary stats table."

	::= { aptis-monitoring 1319 }

	pppSummaryStatsEntry	OBJECT-TYPE
		SYNTAX		PppSummaryStatsEntry
		MAX-ACCESS	not-accessible
		STATUS		current
		DESCRIPTION
			"This is the structure of entries in the
			 pppSummaryStatsTable."
		INDEX		{ pppSummaryStatsSlotNumber }
	::= { pppSummaryStatsTable 1 }

	PppSummaryStatsEntry ::= SEQUENCE {
		pppSummaryStatsSlotNumber	INTEGER,
		pppSummaryStatsMaxLinks		INTEGER,
		pppSummaryStatsActiveLinks	INTEGER,
		pppSummaryStatsMaxActiveLinks	INTEGER,
		pppSummaryStatsFreeLinks	INTEGER,
		pppSummaryStatsLinksStarted	INTEGER,
		pppSummaryStatsLinksStopped	INTEGER,
		pppSummaryStatsLinksModem	INTEGER,
		pppSummaryStatsLinksHDLC	INTEGER,
		pppSummaryStatsLinksLeased	INTEGER,
		pppSummaryStatsLinksNegotiatedLCP INTEGER,
		pppSummaryStatsLinksAuthenticated INTEGER,
		pppSummaryStatsLinksNegotiatedIPCP INTEGER,
		pppSummaryStatsLinksNegotiatedMLP INTEGER,
		pppSummaryStatsLinksNegotiatedCCP INTEGER,
		pppSummaryStatsLinksNegotiatedIPXCP INTEGER
	}

	pppSummaryStatsSlotNumber	OBJECT-TYPE
		SYNTAX		INTEGER
		MAX-ACCESS	read-only
		STATUS		current
		DESCRIPTION
			"Number of slot reporting these stats"

	::= { pppSummaryStatsEntry 1 }

	pppSummaryStatsMaxLinks	OBJECT-TYPE
		SYNTAX		INTEGER
		MAX-ACCESS	read-only
		STATUS		current
		DESCRIPTION
			"Number of simultaneous PPP links supported"

	::= { pppSummaryStatsEntry 2 }

	pppSummaryStatsActiveLinks	OBJECT-TYPE
		SYNTAX		INTEGER
		MAX-ACCESS	read-only
		STATUS		current
		DESCRIPTION
			"Number of PPP links currently active"

	::= { pppSummaryStatsEntry 3 }

	pppSummaryStatsMaxActiveLinks	OBJECT-TYPE
		SYNTAX		INTEGER
		MAX-ACCESS	read-only
		STATUS		current
		DESCRIPTION
			"Maximum number of PPP links active simultaneously"

	::= { pppSummaryStatsEntry 4 }

	pppSummaryStatsFreeLinks	OBJECT-TYPE
		SYNTAX		INTEGER
		MAX-ACCESS	read-only
		STATUS		current
		DESCRIPTION
			"Number of PPP links currently available"

	::= { pppSummaryStatsEntry 5 }

	pppSummaryStatsLinksStarted	OBJECT-TYPE
		SYNTAX		INTEGER
		MAX-ACCESS	read-only
		STATUS		current
		DESCRIPTION
			"Number of PPP links that have been started"

	::= { pppSummaryStatsEntry 6 }

	pppSummaryStatsLinksStopped	OBJECT-TYPE
		SYNTAX		INTEGER
		MAX-ACCESS	read-only
		STATUS		current
		DESCRIPTION
			"Number of PPP links that have been stopped"

	::= { pppSummaryStatsEntry 7 }

	pppSummaryStatsLinksModem	OBJECT-TYPE
		SYNTAX		INTEGER
		MAX-ACCESS	read-only
		STATUS		current
		DESCRIPTION
			"Number of PPP links that have been on a modem"

	::= { pppSummaryStatsEntry 101 }

	pppSummaryStatsLinksHDLC	OBJECT-TYPE
		SYNTAX		INTEGER
		MAX-ACCESS	read-only
		STATUS		current
		DESCRIPTION
			"Number of PPP links that have been on an ISDN
			B-channel (HDLC)"

	::= { pppSummaryStatsEntry 102 }

	pppSummaryStatsLinksLeased	OBJECT-TYPE
		SYNTAX		INTEGER
		MAX-ACCESS	read-only
		STATUS		current
		DESCRIPTION
			"Number of PPP links that have been on a leased line"

	::= { pppSummaryStatsEntry 103 }

	pppSummaryStatsLinksNegotiatedLCP	OBJECT-TYPE
		SYNTAX		INTEGER
		MAX-ACCESS	read-only
		STATUS		current
		DESCRIPTION
			"Number of PPP links that have successfully negotiated
			LCP"

	::= { pppSummaryStatsEntry 201 }

	pppSummaryStatsLinksAuthenticated	OBJECT-TYPE
		SYNTAX		INTEGER
		MAX-ACCESS	read-only
		STATUS		current
		DESCRIPTION
			"Number of PPP links that have successfully
			authenticated"

	::= { pppSummaryStatsEntry 202 }

	pppSummaryStatsLinksNegotiatedIPCP	OBJECT-TYPE
		SYNTAX		INTEGER
		MAX-ACCESS	read-only
		STATUS		current
		DESCRIPTION
			"Number of PPP links that have successfully negotiated
			IPCP"

	::= { pppSummaryStatsEntry 203 }

	pppSummaryStatsLinksNegotiatedMLP	OBJECT-TYPE
		SYNTAX		INTEGER
		MAX-ACCESS	read-only
		STATUS		current
		DESCRIPTION
			"Number of PPP links that have successfully negotiated
			multilink"

	::= { pppSummaryStatsEntry 204 }

	pppSummaryStatsLinksNegotiatedCCP	OBJECT-TYPE
		SYNTAX		INTEGER
		MAX-ACCESS	read-only
		STATUS		current
		DESCRIPTION
			"Number of PPP links that have successfully negotiated
			compression"

	::= { pppSummaryStatsEntry 205 }

	pppSummaryStatsLinksNegotiatedIPXCP	OBJECT-TYPE
		SYNTAX		INTEGER
		MAX-ACCESS	read-only
		STATUS		current
		DESCRIPTION
			"Number of PPP links that have successfully negotiated
			IPXCP"

	::= { pppSummaryStatsEntry 206 }

-- This file generated from  root.cml by smog.
-- date: Thu Jun 29 01:11:35  2000

	systemSummaryTable	OBJECT-TYPE
		SYNTAX		SEQUENCE OF SystemSummaryEntry
		MAX-ACCESS	not-accessible
		STATUS		current
		DESCRIPTION
			"This is a tagged data structure with a summary of
			various status variables from throughout the CVX
			system. It is not human-readable and is intended for
			consumption by the NMS."

	::= { aptis-monitoring 10 }

	systemSummaryEntry	OBJECT-TYPE
		SYNTAX		SystemSummaryEntry
		MAX-ACCESS	not-accessible
		STATUS		current
		DESCRIPTION
			"This is the structure of entries in the
			 systemSummaryTable."
		INDEX		{ systemSummaryData }
	::= { systemSummaryTable 1 }

	SystemSummaryEntry ::= SEQUENCE {
		systemSummaryData		OCTET STRING
	}

	systemSummaryData	OBJECT-TYPE
		SYNTAX		OCTET STRING (SIZE (0..1024))
		MAX-ACCESS	read-only
		STATUS		current
		DESCRIPTION
			"This is 8-bit binary data. Don't even try to display
			it."

	::= { systemSummaryEntry 1 }


	powerStatusTable	OBJECT-TYPE
		SYNTAX		SEQUENCE OF PowerStatusEntry
		MAX-ACCESS	not-accessible
		STATUS		current
		DESCRIPTION
			"The current state of the power supplies in the
			system, as reported mechanically by the hardware."

	::= { aptis-monitoring 11 }

	powerStatusEntry	OBJECT-TYPE
		SYNTAX		PowerStatusEntry
		MAX-ACCESS	not-accessible
		STATUS		current
		DESCRIPTION
			"This is the structure of entries in the
			 powerStatusTable."
		INDEX		{ powerStatusShelf }
	::= { powerStatusTable 1 }

	PowerStatusEntry ::= SEQUENCE {
		powerStatusShelf		INTEGER,
		powerStatusFanStatus		Boolean,
		powerStatusExternalDC1		Boolean,
		powerStatusExternalDC2		Boolean,
		powerStatusInternalAC1		Boolean,
		powerStatusInternalAC2		Boolean,
		powerStatusInternalACDC1	Boolean,
		powerStatusInternalACDC2	Boolean,
		powerStatusInternalACDC3	Boolean,
		powerStatusCsr1Register		INTEGER
	}

	powerStatusShelf	OBJECT-TYPE
		SYNTAX		INTEGER
		MAX-ACCESS	read-only
		STATUS		current
		DESCRIPTION
			"The shelf number for which the power status is
			reported."

	::= { powerStatusEntry 1 }

	powerStatusFanStatus	OBJECT-TYPE
		SYNTAX		Boolean
		MAX-ACCESS	read-only
		STATUS		current
		DESCRIPTION
			"True if the fan tray is operational."

	::= { powerStatusEntry 2 }

	powerStatusExternalDC1	OBJECT-TYPE
		SYNTAX		Boolean
		MAX-ACCESS	read-only
		STATUS		current
		DESCRIPTION
			"True if the external DC power supply #1 is
			operational."

	::= { powerStatusEntry 3 }

	powerStatusExternalDC2	OBJECT-TYPE
		SYNTAX		Boolean
		MAX-ACCESS	read-only
		STATUS		current
		DESCRIPTION
			"True if the external DC power supply #2 is
			operational."

	::= { powerStatusEntry 4 }

	powerStatusInternalAC1	OBJECT-TYPE
		SYNTAX		Boolean
		MAX-ACCESS	read-only
		STATUS		current
		DESCRIPTION
			"True if the internal AC power supply #1 is
			operational."

	::= { powerStatusEntry 5 }

	powerStatusInternalAC2	OBJECT-TYPE
		SYNTAX		Boolean
		MAX-ACCESS	read-only
		STATUS		current
		DESCRIPTION
			"True if the internal AC power supply #2 is
			operational."

	::= { powerStatusEntry 6 }

	powerStatusInternalACDC1	OBJECT-TYPE
		SYNTAX		Boolean
		MAX-ACCESS	read-only
		STATUS		current
		DESCRIPTION
			"True if the internal AC/DC power supply #1 is
			operational."

	::= { powerStatusEntry 7 }

	powerStatusInternalACDC2	OBJECT-TYPE
		SYNTAX		Boolean
		MAX-ACCESS	read-only
		STATUS		current
		DESCRIPTION
			"True if the internal AC/DC power supply #2 is
			operational."

	::= { powerStatusEntry 8 }

	powerStatusInternalACDC3	OBJECT-TYPE
		SYNTAX		Boolean
		MAX-ACCESS	read-only
		STATUS		current
		DESCRIPTION
			"True if the internal AC/DC power supply #3 is
			operational."

	::= { powerStatusEntry 9 }

	powerStatusCsr1Register	OBJECT-TYPE
		SYNTAX		INTEGER
		MAX-ACCESS	read-only
		STATUS		current
		DESCRIPTION
			"Inverted contents of CSR1"

	::= { powerStatusEntry 10 }


	softwareVersionTable	OBJECT-TYPE
		SYNTAX		SEQUENCE OF SoftwareVersionEntry
		MAX-ACCESS	not-accessible
		STATUS		current
		DESCRIPTION
			"The software version numbers for the system."

	::= { aptis-monitoring 12 }

	softwareVersionEntry	OBJECT-TYPE
		SYNTAX		SoftwareVersionEntry
		MAX-ACCESS	not-accessible
		STATUS		current
		DESCRIPTION
			"This is the structure of entries in the
			 softwareVersionTable."
		INDEX		{ softwareVersionMibVersion }
	::= { softwareVersionTable 1 }

	SoftwareVersionEntry ::= SEQUENCE {
		softwareVersionMibVersion	INTEGER,
		softwareVersionSoftwareRevision	DisplayString,
		softwareVersionProductId	INTEGER,
		softwareVersionMibRevision	INTEGER
	}

	softwareVersionMibVersion	OBJECT-TYPE
		SYNTAX		INTEGER
		MAX-ACCESS	read-only
		STATUS		current
		DESCRIPTION
			"The version of the Aptis Enterprise MIB supported by
			this member. This number changes with every release of
			the software."

	::= { softwareVersionEntry 1 }

	softwareVersionSoftwareRevision	OBJECT-TYPE
		SYNTAX		DisplayString (SIZE (0..20))
		MAX-ACCESS	read-only
		STATUS		current
		DESCRIPTION
			"The version of the CVX software running on this
			system."

	::= { softwareVersionEntry 2 }

	softwareVersionProductId	OBJECT-TYPE
		SYNTAX		INTEGER {
				    cvx1800(1),
				    cvx600(2)
				}
		MAX-ACCESS	read-only
		STATUS		current
		DESCRIPTION
			"The version of the CVX software running on this
			system."

	::= { softwareVersionEntry 3 }

	softwareVersionMibRevision	OBJECT-TYPE
		SYNTAX		INTEGER
		MAX-ACCESS	read-only
		STATUS		current
		DESCRIPTION
			"The revision number of the Aptis Enterprise MIB
			supported by this sytem. This number is incremented
			every time the MIB changes during development."

	::= { softwareVersionEntry 4 }

-- This file generated from  sessions.cml by smog.
-- date: Thu Jun 29 01:11:36  2000

	sessionCountersTable	OBJECT-TYPE
		SYNTAX		SEQUENCE OF SessionCountersEntry
		MAX-ACCESS	not-accessible
		STATUS		current
		DESCRIPTION
			"The current count of sessions in the active and
			inactive tables."

	::= { aptis-monitoring 100 }

	sessionCountersEntry	OBJECT-TYPE
		SYNTAX		SessionCountersEntry
		MAX-ACCESS	not-accessible
		STATUS		current
		DESCRIPTION
			"This is the structure of entries in the
			 sessionCountersTable."
		INDEX		{ sessionCountersActiveLowest }
	::= { sessionCountersTable 1 }

	SessionCountersEntry ::= SEQUENCE {
		sessionCountersActiveLowest	INTEGER,
		sessionCountersActiveHighest	INTEGER,
		sessionCountersActiveCount	INTEGER,
		sessionCountersInactiveLowest	INTEGER,
		sessionCountersInactiveHighest	INTEGER,
		sessionCountersInactiveCount	INTEGER,
		sessionCountersSessionTableSize	INTEGER,
		sessionCountersHistoryLowest	INTEGER,
		sessionCountersHistoryHighest	INTEGER,
		sessionCountersHistoryTableSize	INTEGER,
		sessionCountersBootEra		INTEGER
	}

	sessionCountersActiveLowest	OBJECT-TYPE
		SYNTAX		INTEGER
		MAX-ACCESS	read-only
		STATUS		current
		DESCRIPTION
			"The current lowest ID in the active session table."

	::= { sessionCountersEntry 1 }

	sessionCountersActiveHighest	OBJECT-TYPE
		SYNTAX		INTEGER
		MAX-ACCESS	read-only
		STATUS		current
		DESCRIPTION
			"The current highest ID in the active session table."

	::= { sessionCountersEntry 2 }

	sessionCountersActiveCount	OBJECT-TYPE
		SYNTAX		INTEGER
		MAX-ACCESS	read-only
		STATUS		current
		DESCRIPTION
			"The current count of entries in the active session
			table."

	::= { sessionCountersEntry 3 }

	sessionCountersInactiveLowest	OBJECT-TYPE
		SYNTAX		INTEGER
		MAX-ACCESS	read-only
		STATUS		current
		DESCRIPTION
			"The current lowest ID in the Inactive session table."

	::= { sessionCountersEntry 4 }

	sessionCountersInactiveHighest	OBJECT-TYPE
		SYNTAX		INTEGER
		MAX-ACCESS	read-only
		STATUS		current
		DESCRIPTION
			"The current highest ID in the Inactive session
			table."

	::= { sessionCountersEntry 5 }

	sessionCountersInactiveCount	OBJECT-TYPE
		SYNTAX		INTEGER
		MAX-ACCESS	read-only
		STATUS		current
		DESCRIPTION
			"The current count of entries in the Inactive session
			table."

	::= { sessionCountersEntry 6 }

	sessionCountersSessionTableSize	OBJECT-TYPE
		SYNTAX		INTEGER
		MAX-ACCESS	read-only
		STATUS		current
		DESCRIPTION
			"The maximum number of entries in the session table."

	::= { sessionCountersEntry 7 }

	sessionCountersHistoryLowest	OBJECT-TYPE
		SYNTAX		INTEGER
		MAX-ACCESS	read-only
		STATUS		current
		DESCRIPTION
			"The current lowest index in the SessionHistory
			table."

	::= { sessionCountersEntry 8 }

	sessionCountersHistoryHighest	OBJECT-TYPE
		SYNTAX		INTEGER
		MAX-ACCESS	read-only
		STATUS		current
		DESCRIPTION
			"The current highest index in the SessionHistory
			table."

	::= { sessionCountersEntry 9 }

	sessionCountersHistoryTableSize	OBJECT-TYPE
		SYNTAX		INTEGER
		MAX-ACCESS	read-only
		STATUS		current
		DESCRIPTION
			"The maximum number of entries that the history table
			may hold."

	::= { sessionCountersEntry 11 }

	sessionCountersBootEra	OBJECT-TYPE
		SYNTAX		INTEGER
		MAX-ACCESS	read-only
		STATUS		current
		DESCRIPTION
			"A number identifying the boot era for this system.
			This number will be set to a unique value each time
			the system is rebooted. This variable will not change
			until the System Controller Card (SCC) is rebooted.
			When prepended to a session serial number, yields a
			session identifier which will be unique for this
			system for all time."

	::= { sessionCountersEntry 10 }


	sessionStatusTable	OBJECT-TYPE
		SYNTAX		SEQUENCE OF SessionStatusEntry
		MAX-ACCESS	not-accessible
		STATUS		current
		DESCRIPTION
			"This table describes both active and inactive
			sessions. The table contains all active sessions and
			the most recent inactive sessions, up to a combined
			total of SessionTableSize entries. This table is
			ordered by session serial number. As new entries are
			appended to the bottom of the table, the inactive
			entries with the oldest termination time get aged out
			from near the top of the table."

	::= { aptis-monitoring 101 }

	sessionStatusEntry	OBJECT-TYPE
		SYNTAX		SessionStatusEntry
		MAX-ACCESS	not-accessible
		STATUS		current
		DESCRIPTION
			"This is the structure of entries in the
			 sessionStatusTable."
		INDEX		{ sessionStatusSessionID }
	::= { sessionStatusTable 1 }

	SessionStatusEntry ::= SEQUENCE {
		sessionStatusSessionID		INTEGER,
		sessionStatusState		INTEGER,
		sessionStatusPermanentFlag	INTEGER,
		sessionStatusVpopId		INTEGER,
		sessionStatusName		DisplayString,
		sessionStatusRemoteIP		IpAddress,
		sessionStatusRemoteIPMask	IpAddress,
		sessionStatusLocalIP		IpAddress,
		sessionStatusLocalIPMask	IpAddress,
		sessionStatusLinkService	INTEGER,
		sessionStatusServiceMode	INTEGER,
		sessionStatusStartTime		INTEGER,
		sessionStatusStopTime		INTEGER,
		sessionStatusTimeOfModemSync	INTEGER,
		sessionStatusTimeOfService	INTEGER,
		sessionStatusTerminatingComponent INTEGER,
		sessionStatusTerminationCause	INTEGER,
		sessionStatusLastComponent	INTEGER,
		sessionStatusLayer1Slot		INTEGER,
		sessionStatusLayer2Slot		INTEGER,
		sessionStatusCalledNumber	DisplayString,
		sessionStatusCallingNumber	DisplayString,
		sessionStatusOriginateMode	INTEGER,
		sessionStatusOctetsIn		INTEGER,
		sessionStatusOctetsOut		INTEGER,
		sessionStatusPacketsIn		INTEGER,
		sessionStatusPacketsOut		INTEGER,
		sessionStatusMultiLinkId	INTEGER,
		sessionStatusPort		INTEGER,
		sessionStatusTimeslot		INTEGER,
		sessionStatusLinkCount		INTEGER,
		sessionStatusTxStartDataRate	INTEGER,
		sessionStatusRxStartDataRate	INTEGER,
		sessionStatusTxEndDataRate	INTEGER,
		sessionStatusRxEndDataRate	INTEGER,
		sessionStatusTxMinDataRate	INTEGER,
		sessionStatusRxMinDataRate	INTEGER,
		sessionStatusTxMaxDataRate	INTEGER,
		sessionStatusRxMaxDataRate	INTEGER,
		sessionStatusIop		INTEGER,
		sessionStatusDmm		INTEGER,
		sessionStatusPack		INTEGER,
		sessionStatusDevice		INTEGER,
		sessionStatusTdmStream		INTEGER,
		sessionStatusTdmTimeSlot	INTEGER,
		sessionStatusTerminationReason	DisplayString,
		sessionStatusDuration		INTEGER,
		sessionStatusDurationHMS	DisplayString,
		sessionStatusSs7SessionId	DisplayString,
		sessionStatusModemNumber	INTEGER,
		sessionStatusTunnelType		INTEGER,
		sessionStatusTunnelMediumType	INTEGER,
		sessionStatusTunnelServerAddress IpAddress,
		sessionStatusCallClass		INTEGER,
		sessionStatusTandemPort		INTEGER,
		sessionStatusTandemTimeslot	INTEGER,
		sessionStatusCallClassArray	OCTET STRING,
		sessionStatusCallClassLen	INTEGER,
		sessionStatusActualAuthMethod	INTEGER,
		sessionStatusModemModulation	INTEGER,
		sessionStatusModemErrorCorrection INTEGER,
		sessionStatusModemDataCompression INTEGER,
		sessionStatusModemTxBlocks	INTEGER,
		sessionStatusModemRetransmits	INTEGER,
		sessionStatusModemSNR		INTEGER,
		sessionStatusModemLocalRetrains	INTEGER,
		sessionStatusModemRemoteRetrains INTEGER,
		sessionStatusModemLocalRenegotiations INTEGER,
		sessionStatusModemRemoteRenegotiations INTEGER,
		sessionStatusModemReceiveLineLevel INTEGER,
		sessionStatusRemoteIPXNetwork	INTEGER,
		sessionStatusRemoteIPXNode	DisplayString,
		sessionStatusCleartcpRemoteIP	IpAddress,
		sessionStatusCleartcpRemotePort	INTEGER,
		sessionStatusTunnelId		INTEGER,
		sessionStatusLinkId		INTEGER
	}

	sessionStatusSessionID	OBJECT-TYPE
		SYNTAX		INTEGER
		MAX-ACCESS	read-only
		STATUS		current
		DESCRIPTION
			"The serial number of this session, a unique number
			for this boot era. When combined with the value of
			BootEra, provides a session number that is unique for
			the life of the system."

	::= { sessionStatusEntry 2 }

	sessionStatusState	OBJECT-TYPE
		SYNTAX		INTEGER {
				    inactive(0),
				    active(1)
				}
		MAX-ACCESS	read-only
		STATUS		current
		DESCRIPTION
			"This variable indicates the state of this session."

	::= { sessionStatusEntry 3 }

	sessionStatusPermanentFlag	OBJECT-TYPE
		SYNTAX		INTEGER {
				    unknown(0),
				    switched(1),
				    permanent(2)
				}
		MAX-ACCESS	read-only
		STATUS		current
		DESCRIPTION
			"This variable indicates whether this session is
			permanent(2), meaning a long-lasting locally
			administered session such as a Frame Relay PVC, or
			switched(1), meaning a short-lived session resulting
			from a switched call."

	::= { sessionStatusEntry 10 }

	sessionStatusVpopId	OBJECT-TYPE
		SYNTAX		INTEGER
		MAX-ACCESS	read-only
		STATUS		current
		DESCRIPTION
			"The identifier of the VPOP (administrative Group) to
			which the session belongs. A value of 0 indicates the
			default VPOP."

	::= { sessionStatusEntry 11 }

	sessionStatusName	OBJECT-TYPE
		SYNTAX		DisplayString (SIZE (0..68))
		MAX-ACCESS	read-only
		STATUS		current
		DESCRIPTION
			"The name of the connection peer for this session.
			During authentication of the session, this field may
			contain the name submitted by the peer. During this
			time, the value of timeOfService will be zero. When
			the value of timeOfService is nonzero, this field will
			contain a fully authenticated name."

	::= { sessionStatusEntry 12 }

	sessionStatusRemoteIP	OBJECT-TYPE
		SYNTAX		IpAddress
		MAX-ACCESS	read-only
		STATUS		current
		DESCRIPTION
			"The connection peer's IP address. If the link is
			numbered, then this is the address assigned to the
			other end of the link. If the link is not numbered,
			this may be the single IP address of the peer. For PPP
			connections, this is the result of IPNCP negotiation."

	::= { sessionStatusEntry 13 }

	sessionStatusRemoteIPMask	OBJECT-TYPE
		SYNTAX		IpAddress
		MAX-ACCESS	read-only
		STATUS		current
		DESCRIPTION
			"The connection peer's IP address mask, used in
			conjunction with remoteIP."

	::= { sessionStatusEntry 14 }

	sessionStatusLocalIP	OBJECT-TYPE
		SYNTAX		IpAddress
		MAX-ACCESS	read-only
		STATUS		current
		DESCRIPTION
			"The local IP address for this session. If the link is
			numbered, then this is the address assigned to the
			local end of the link. If the link is not numbered,
			this may be the primary IP address of the system. For
			PPP connections, this is the result of IPNCP
			negotiation."

	::= { sessionStatusEntry 15 }

	sessionStatusLocalIPMask	OBJECT-TYPE
		SYNTAX		IpAddress
		MAX-ACCESS	read-only
		STATUS		current
		DESCRIPTION
			"The local IP address mask for this session, used in
			conjunction with localIP."

	::= { sessionStatusEntry 16 }

	sessionStatusLinkService	OBJECT-TYPE
		SYNTAX		INTEGER {
				    unknown(0),
				    none(1),
				    other(2),
				    isdn56K(3),
				    isdn64K(4),
				    isdnV120(5),
				    isdnV110(6),
				    modemV32(7),
				    modemV34(8),
				    modemK56(9),
				    modemV90(10),
				    ethernet(11),
				    t1Trunk(12),
				    loopback(13),
				    hssi(14),
				    hub(15),
				    voice(16)
				}
		MAX-ACCESS	read-only
		STATUS		current
		DESCRIPTION
			"A description of which link technology is being used
			by the session."

	::= { sessionStatusEntry 17 }

	sessionStatusServiceMode	OBJECT-TYPE
		SYNTAX		INTEGER {
				    unknown(0),
				    none(1),
				    other(2),
				    ppp(3),
				    slip(4),
				    frameRelay(5),
				    ciscoHDLC(6),
				    terminalServer(7),
				    telnet(8),
				    rawTCP(9),
				    rlogin(10),
				    l2tp(11),
				    l2f(12),
				    trunk(13),
				    voice(14),
				    tandem(15),
				    hub(16),
				    ftp(17),
				    dvs(18),
				    fax(19),
				    atmp(20),
				    iptest(21)
				}
		MAX-ACCESS	read-only
		STATUS		current
		DESCRIPTION
			"A description of which session service is being used
			by the session."

	::= { sessionStatusEntry 18 }

	sessionStatusStartTime	OBJECT-TYPE
		SYNTAX		INTEGER
		MAX-ACCESS	read-only
		STATUS		current
		DESCRIPTION
			"The time that this session began, in seconds since
			the system booted."

	::= { sessionStatusEntry 19 }

	sessionStatusStopTime	OBJECT-TYPE
		SYNTAX		INTEGER
		MAX-ACCESS	read-only
		STATUS		current
		DESCRIPTION
			"The time that this session stopped, in seconds since
			the system booted. This variable is only meaningful
			for sessions having the state inactive(0)."

	::= { sessionStatusEntry 20 }

	sessionStatusTimeOfModemSync	OBJECT-TYPE
		SYNTAX		INTEGER
		MAX-ACCESS	read-only
		STATUS		current
		DESCRIPTION
			"The time at which the modem synchronization
			completed, in seconds since the system booted."

	::= { sessionStatusEntry 21 }

	sessionStatusTimeOfService	OBJECT-TYPE
		SYNTAX		INTEGER
		MAX-ACCESS	read-only
		STATUS		current
		DESCRIPTION
			"The time that this session entered its first
			negotiated or configured service, in seconds since the
			system booted. For example, for a session with
			serviceMode PPP, the time at which LCP and IPCP
			negotiations completed and the session was ready to
			forward user data."

	::= { sessionStatusEntry 22 }

	sessionStatusTerminatingComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The component which initiated termination of this
			session. In cases where there are multiple causes of
			session termination, only the first cause detected is
			reported. This variable is only meaningful for
			sessions having the state inactive(0)."

	::= { sessionStatusEntry 23 }

	sessionStatusTerminationCause	OBJECT-TYPE
		SYNTAX		INTEGER
		MAX-ACCESS	read-only
		STATUS		current
		DESCRIPTION
			"The cause which initiated termination of this
			session. In cases where there are multiple causes of
			session termination, only the first cause detected is
			reported. This variable is only meaningful for
			sessions having the state inactive(0)."

	::= { sessionStatusEntry 24 }

	sessionStatusLastComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The last component which was connected in this
			session."

	::= { sessionStatusEntry 25 }

	sessionStatusLayer1Slot	OBJECT-TYPE
		SYNTAX		INTEGER (1..18)
		MAX-ACCESS	read-only
		STATUS		current
		DESCRIPTION
			"The slot where the physical layer of this session is
			terminated."

	::= { sessionStatusEntry 26 }

	sessionStatusLayer2Slot	OBJECT-TYPE
		SYNTAX		INTEGER (1..18)
		MAX-ACCESS	read-only
		STATUS		current
		DESCRIPTION
			"The slot where the data link portion of this session
			is terminated"

	::= { sessionStatusEntry 27 }

	sessionStatusCalledNumber	OBJECT-TYPE
		SYNTAX		DisplayString (SIZE (0..17))
		MAX-ACCESS	read-only
		STATUS		current
		DESCRIPTION
			"16 digit number of called station (if available)"

	::= { sessionStatusEntry 28 }

	sessionStatusCallingNumber	OBJECT-TYPE
		SYNTAX		DisplayString (SIZE (0..17))
		MAX-ACCESS	read-only
		STATUS		current
		DESCRIPTION
			"16 digit number of calling station (if available)"

	::= { sessionStatusEntry 29 }

	sessionStatusOriginateMode	OBJECT-TYPE
		SYNTAX		INTEGER {
				    answer(0),
				    originate(1)
				}
		MAX-ACCESS	read-only
		STATUS		current
		DESCRIPTION
			"The direction of the physical layer call associated
			with this session"

	::= { sessionStatusEntry 30 }

	sessionStatusOctetsIn	OBJECT-TYPE
		SYNTAX		INTEGER
		MAX-ACCESS	read-only
		STATUS		current
		DESCRIPTION
			"The number of octets received from the remote user.
			This value will be zero until a session is
			terminated."

	::= { sessionStatusEntry 31 }

	sessionStatusOctetsOut	OBJECT-TYPE
		SYNTAX		INTEGER
		MAX-ACCESS	read-only
		STATUS		current
		DESCRIPTION
			"The number of octets sent to the remote user. This
			value will be zero until a session is terminated."

	::= { sessionStatusEntry 32 }

	sessionStatusPacketsIn	OBJECT-TYPE
		SYNTAX		INTEGER
		MAX-ACCESS	read-only
		STATUS		current
		DESCRIPTION
			"The number of packets received from the remote user.
			This value will be zero until a session is
			terminated."

	::= { sessionStatusEntry 33 }

	sessionStatusPacketsOut	OBJECT-TYPE
		SYNTAX		INTEGER
		MAX-ACCESS	read-only
		STATUS		current
		DESCRIPTION
			"The number of packets sent to the remote user. This
			value will be zero until a session is terminated."

	::= { sessionStatusEntry 34 }

	sessionStatusMultiLinkId	OBJECT-TYPE
		SYNTAX		INTEGER
		MAX-ACCESS	read-only
		STATUS		current
		DESCRIPTION
			"The multi-link identifier value for PPP calls where
			the multi-link protocol was negotiated."

	::= { sessionStatusEntry 35 }

	sessionStatusPort	OBJECT-TYPE
		SYNTAX		INTEGER
		MAX-ACCESS	read-only
		STATUS		current
		DESCRIPTION
			"The number of the DS1 for this session, relative to
			layer1Slot."

	::= { sessionStatusEntry 36 }

	sessionStatusTimeslot	OBJECT-TYPE
		SYNTAX		INTEGER
		MAX-ACCESS	read-only
		STATUS		current
		DESCRIPTION
			"The number of the DS0 for this session, relative to
			port."

	::= { sessionStatusEntry 37 }

	sessionStatusLinkCount	OBJECT-TYPE
		SYNTAX		INTEGER
		MAX-ACCESS	read-only
		STATUS		current
		DESCRIPTION
			"The number of sessions sharing the same remote IP
			address as this session. After a session is
			terminated, this value will represent the number of
			sessions at the time of termination."

	::= { sessionStatusEntry 38 }

	sessionStatusTxStartDataRate	OBJECT-TYPE
		SYNTAX		INTEGER
		MAX-ACCESS	read-only
		STATUS		current
		DESCRIPTION
			"The transmit DCE data rate for this session. In the
			case of modem sessions, this will be the DCE rate
			reported as a result of initial modem negotiation, and
			may not track rate chanes during the call. For ISDN
			sessions, this will be the actual data service rate of
			the call. For Frame Relay sessions, this will be the
			nominal speed of the Frame Relay Physical Interface,
			even though multiple sessions may be sharing that
			Physical Interface. For other sessions, this will be
			the nominal speed of the physical interface. In no
			case should this be interepreted as a
			Quality-of-Service guarantee, or as the current line
			utilization or effective bandwidth on the interface.
			Note also that in the case of PPP multilink, this
			specifies the rate of only this link in the bundle,
			and not the aggregate rate of all links in the
			bundle."

	::= { sessionStatusEntry 39 }

	sessionStatusRxStartDataRate	OBJECT-TYPE
		SYNTAX		INTEGER
		MAX-ACCESS	read-only
		STATUS		current
		DESCRIPTION
			"The receive data rate for this session. In the case
			of modem sessions, this will be the DCE rate reported
			as a result of initial modem negotiation, and may not
			track rate chanes during the call. For ISDN sessions,
			this will be the actual data service rate of the call.
			For Frame Relay sessions, this will be the nominal
			speed of the Frame Relay Physical Interface, even
			though multiple sessions may be sharing that Physical
			Interface. For other sessions, this will be the
			nominal speed of the physical interface. In no case
			should this be interepreted as a Quality-of-Service
			guarantee, or as the current line utilization or
			effective bandwidth on the interface. Note also that
			in the case of PPP multilink, this specifies the rate
			of only this link in the bundle, and not the aggregate
			rate of all links in the bundle."

	::= { sessionStatusEntry 40 }

	sessionStatusTxEndDataRate	OBJECT-TYPE
		SYNTAX		INTEGER
		MAX-ACCESS	read-only
		STATUS		current
		DESCRIPTION
			"The transmit data rate at the end of a modem
			session."

	::= { sessionStatusEntry 41 }

	sessionStatusRxEndDataRate	OBJECT-TYPE
		SYNTAX		INTEGER
		MAX-ACCESS	read-only
		STATUS		current
		DESCRIPTION
			"The receive data rate at the end of a modem session."

	::= { sessionStatusEntry 42 }

	sessionStatusTxMinDataRate	OBJECT-TYPE
		SYNTAX		INTEGER
		MAX-ACCESS	read-only
		STATUS		current
		DESCRIPTION
			"The minimum transmit data rate during a modem
			session."

	::= { sessionStatusEntry 43 }

	sessionStatusRxMinDataRate	OBJECT-TYPE
		SYNTAX		INTEGER
		MAX-ACCESS	read-only
		STATUS		current
		DESCRIPTION
			"The minimum receive data rate during a modem
			session."

	::= { sessionStatusEntry 44 }

	sessionStatusTxMaxDataRate	OBJECT-TYPE
		SYNTAX		INTEGER
		MAX-ACCESS	read-only
		STATUS		current
		DESCRIPTION
			"The maximum transmit data rate during a modem
			session."

	::= { sessionStatusEntry 45 }

	sessionStatusRxMaxDataRate	OBJECT-TYPE
		SYNTAX		INTEGER
		MAX-ACCESS	read-only
		STATUS		current
		DESCRIPTION
			"The maximum receive data rate during a modem
			session."

	::= { sessionStatusEntry 46 }

	sessionStatusIop	OBJECT-TYPE
		SYNTAX		INTEGER
		MAX-ACCESS	read-only
		STATUS		current
		DESCRIPTION
			"The I/O processor where this session is terminated."

	::= { sessionStatusEntry 47 }

	sessionStatusDmm	OBJECT-TYPE
		SYNTAX		INTEGER
		MAX-ACCESS	read-only
		STATUS		current
		DESCRIPTION
			"The Digital Modem Module where this session is
			terminated."

	::= { sessionStatusEntry 48 }

	sessionStatusPack	OBJECT-TYPE
		SYNTAX		INTEGER
		MAX-ACCESS	read-only
		STATUS		current
		DESCRIPTION
			"The integrated circuit pack where this session is
			terminated."

	::= { sessionStatusEntry 49 }

	sessionStatusDevice	OBJECT-TYPE
		SYNTAX		INTEGER
		MAX-ACCESS	read-only
		STATUS		current
		DESCRIPTION
			"The modem/hdlc where this session is terminated."

	::= { sessionStatusEntry 50 }

	sessionStatusTdmStream	OBJECT-TYPE
		SYNTAX		INTEGER
		MAX-ACCESS	read-only
		STATUS		current
		DESCRIPTION
			"The TDM highway stream associated with this session."

	::= { sessionStatusEntry 51 }

	sessionStatusTdmTimeSlot	OBJECT-TYPE
		SYNTAX		INTEGER
		MAX-ACCESS	read-only
		STATUS		current
		DESCRIPTION
			"The TDM highway time-slot associated with this
			session."

	::= { sessionStatusEntry 52 }

	sessionStatusTerminationReason	OBJECT-TYPE
		SYNTAX		DisplayString (SIZE (0..50))
		MAX-ACCESS	read-only
		STATUS		current
		DESCRIPTION
			"A textual description of the cause which initiated
			termination of this session. In cases where there are
			multiple causes of session termination, only the first
			cause detected is reported."

	::= { sessionStatusEntry 53 }

	sessionStatusDuration	OBJECT-TYPE
		SYNTAX		INTEGER
		MAX-ACCESS	read-only
		STATUS		current
		DESCRIPTION
			"The number of seconds this session has been active."

	::= { sessionStatusEntry 54 }

	sessionStatusDurationHMS	OBJECT-TYPE
		SYNTAX		DisplayString (SIZE (0..20))
		MAX-ACCESS	read-only
		STATUS		current
		DESCRIPTION
			"The length of time this session has been active,
			expressed in DDD HH:MM:SSS.000."

	::= { sessionStatusEntry 55 }

	sessionStatusSs7SessionId	OBJECT-TYPE
		SYNTAX		DisplayString (SIZE (0..70))
		MAX-ACCESS	read-only
		STATUS		current
		DESCRIPTION
			"A uniquie identifier for this session within the ss7
			Network. If this call was not originated using ss7
			signalling, this string will be null."

	::= { sessionStatusEntry 56 }

	sessionStatusModemNumber	OBJECT-TYPE
		SYNTAX		INTEGER
		MAX-ACCESS	read-only
		STATUS		current
		DESCRIPTION
			"The individual modem where this session is
			terminated, numbered from one to the maximum number of
			modems on the slot card."

	::= { sessionStatusEntry 57 }

	sessionStatusTunnelType	OBJECT-TYPE
		SYNTAX		INTEGER {
				    unknown(0),
				    none(1),
				    other(2),
				    l2f(3),
				    l2tp(4),
				    dvs(5),
				    atmp(6)
				}
		MAX-ACCESS	read-only
		STATUS		current
		DESCRIPTION
			"The tunneling protocol being used for this session."

	::= { sessionStatusEntry 58 }

	sessionStatusTunnelMediumType	OBJECT-TYPE
		SYNTAX		INTEGER {
				    unknown(0),
				    none(1),
				    other(2),
				    ip(3)
				}
		MAX-ACCESS	read-only
		STATUS		current
		DESCRIPTION
			"The tunneling medium protocol being used for this
			session."

	::= { sessionStatusEntry 59 }

	sessionStatusTunnelServerAddress	OBJECT-TYPE
		SYNTAX		IpAddress
		MAX-ACCESS	read-only
		STATUS		current
		DESCRIPTION
			"The IP address of the remote machine terminating the
			tunnel for this session."

	::= { sessionStatusEntry 60 }

	sessionStatusCallClass	OBJECT-TYPE
		SYNTAX		INTEGER
		MAX-ACCESS	read-only
		STATUS		current
		DESCRIPTION
			"The class of this call."

	::= { sessionStatusEntry 61 }

	sessionStatusTandemPort	OBJECT-TYPE
		SYNTAX		INTEGER
		MAX-ACCESS	read-only
		STATUS		current
		DESCRIPTION
			"The port used for the outbound portion of a tandem
			call, if applicable."

	::= { sessionStatusEntry 62 }

	sessionStatusTandemTimeslot	OBJECT-TYPE
		SYNTAX		INTEGER
		MAX-ACCESS	read-only
		STATUS		current
		DESCRIPTION
			"The timeslot used for the outbound portion of a
			tandem call, if applicable."

	::= { sessionStatusEntry 63 }

	sessionStatusCallClassArray	OBJECT-TYPE
		SYNTAX		OCTET STRING (SIZE (0..256))
		MAX-ACCESS	read-only
		STATUS		current
		DESCRIPTION
			"An array of octets representing the class of this
			call."

	::= { sessionStatusEntry 64 }

	sessionStatusCallClassLen	OBJECT-TYPE
		SYNTAX		INTEGER
		MAX-ACCESS	read-only
		STATUS		current
		DESCRIPTION
			"The number of octets in callClassArray."

	::= { sessionStatusEntry 65 }

	sessionStatusActualAuthMethod	OBJECT-TYPE
		SYNTAX		INTEGER {
				    radius(1),
				    local(2),
				    remote(3)
				}
		MAX-ACCESS	read-only
		STATUS		current
		DESCRIPTION
			"The actual authentication method which was used to
			gain access to services. Radius, Local, Remote."

	::= { sessionStatusEntry 66 }

	sessionStatusModemModulation	OBJECT-TYPE
		SYNTAX		INTEGER {
				    none(0),
				    unknown(1),
				    bell103(2),
				    bell208(3),
				    bell212(4),
				    v17(5),
				    v21(6),
				    v22(7),
				    v22bis(8),
				    v23(9),
				    v27(10),
				    v29(11),
				    v32(12),
				    v32bis(13),
				    v33(14),
				    v34(15),
				    vFC(16),
				    k56(17),
				    v90(18)
				}
		MAX-ACCESS	read-only
		STATUS		current
		DESCRIPTION
			"For modem sessions, the modulation protocol used, if
			any."

	::= { sessionStatusEntry 67 }

	sessionStatusModemErrorCorrection	OBJECT-TYPE
		SYNTAX		INTEGER {
				    none(0),
				    unknown(1),
				    mNP(2),
				    v42(3)
				}
		MAX-ACCESS	read-only
		STATUS		current
		DESCRIPTION
			"For modem sessions, the error correction protocol
			used, if any."

	::= { sessionStatusEntry 68 }

	sessionStatusModemDataCompression	OBJECT-TYPE
		SYNTAX		INTEGER {
				    none(0),
				    unknown(1),
				    mNP5(2),
				    v42bis(3)
				}
		MAX-ACCESS	read-only
		STATUS		current
		DESCRIPTION
			"For modem sessions, the data compression protocol
			used, if any."

	::= { sessionStatusEntry 69 }

	sessionStatusModemTxBlocks	OBJECT-TYPE
		SYNTAX		INTEGER
		MAX-ACCESS	read-only
		STATUS		current
		DESCRIPTION
			"For modem sessions, the number of blocks transmitted
			by the modem."

	::= { sessionStatusEntry 70 }

	sessionStatusModemRetransmits	OBJECT-TYPE
		SYNTAX		INTEGER
		MAX-ACCESS	read-only
		STATUS		current
		DESCRIPTION
			"For modem sessions, the number of packets
			retransmitted by the modem."

	::= { sessionStatusEntry 71 }

	sessionStatusModemSNR	OBJECT-TYPE
		SYNTAX		INTEGER
		MAX-ACCESS	read-only
		STATUS		current
		DESCRIPTION
			"For modem sessions, the Signal-to-Noise Ratio
			measured at the start of the connection. This value is
			given in dB."

	::= { sessionStatusEntry 72 }

	sessionStatusModemLocalRetrains	OBJECT-TYPE
		SYNTAX		INTEGER
		MAX-ACCESS	read-only
		STATUS		current
		DESCRIPTION
			"For modem sessions, the number of retrain requests
			sent by the local modem."

	::= { sessionStatusEntry 73 }

	sessionStatusModemRemoteRetrains	OBJECT-TYPE
		SYNTAX		INTEGER
		MAX-ACCESS	read-only
		STATUS		current
		DESCRIPTION
			"For modem sessions, the number of retrain requests
			sent by the remote modem."

	::= { sessionStatusEntry 74 }

	sessionStatusModemLocalRenegotiations	OBJECT-TYPE
		SYNTAX		INTEGER
		MAX-ACCESS	read-only
		STATUS		current
		DESCRIPTION
			"For modem sessions, the number of rate renegotiation
			requests sent by the local modem."

	::= { sessionStatusEntry 75 }

	sessionStatusModemRemoteRenegotiations	OBJECT-TYPE
		SYNTAX		INTEGER
		MAX-ACCESS	read-only
		STATUS		current
		DESCRIPTION
			"For modem sessions, the number of rate renegotiation
			requests sent by the remote modem."

	::= { sessionStatusEntry 76 }

	sessionStatusModemReceiveLineLevel	OBJECT-TYPE
		SYNTAX		INTEGER
		MAX-ACCESS	read-only
		STATUS		current
		DESCRIPTION
			"For modem sessions, the receive line signal level.
			This value is given in dB."

	::= { sessionStatusEntry 77 }

	sessionStatusRemoteIPXNetwork	OBJECT-TYPE
		SYNTAX		INTEGER
		MAX-ACCESS	read-only
		STATUS		current
		DESCRIPTION
			"The IPX network assigned to the dial-up user."

	::= { sessionStatusEntry 78 }

	sessionStatusRemoteIPXNode	OBJECT-TYPE
		SYNTAX		DisplayString (SIZE (0..16))
		MAX-ACCESS	read-only
		STATUS		current
		DESCRIPTION
			"The IPX Node number assisgned to the dial-up user"

	::= { sessionStatusEntry 79 }

	sessionStatusCleartcpRemoteIP	OBJECT-TYPE
		SYNTAX		IpAddress
		MAX-ACCESS	read-only
		STATUS		current
		DESCRIPTION
			"Cleartcp Remote IP Address"

	::= { sessionStatusEntry 80 }

	sessionStatusCleartcpRemotePort	OBJECT-TYPE
		SYNTAX		INTEGER
		MAX-ACCESS	read-only
		STATUS		current
		DESCRIPTION
			"Cleartcp Remote Port Address"

	::= { sessionStatusEntry 81 }

	sessionStatusTunnelId	OBJECT-TYPE
		SYNTAX		INTEGER
		MAX-ACCESS	read-only
		STATUS		current
		DESCRIPTION
			"Tunnel Id"

	::= { sessionStatusEntry 82 }

	sessionStatusLinkId	OBJECT-TYPE
		SYNTAX		INTEGER
		MAX-ACCESS	read-only
		STATUS		current
		DESCRIPTION
			"Link Id"

	::= { sessionStatusEntry 83 }


	sessionStatusActiveTable	OBJECT-TYPE
		SYNTAX		SEQUENCE OF SessionStatusActiveEntry
		MAX-ACCESS	not-accessible
		STATUS		current
		DESCRIPTION
			"This table describes all active sessions. This table
			is ordered by session serial number. The current
			bounds of this table at any given time are described
			by the variables ActiveLowest and ActiveHighest."

	::= { aptis-monitoring 102 }

	sessionStatusActiveEntry	OBJECT-TYPE
		SYNTAX		SessionStatusActiveEntry
		MAX-ACCESS	not-accessible
		STATUS		current
		DESCRIPTION
			"This is the structure of entries in the
			 sessionStatusActiveTable."
		INDEX		{ sessionStatusActiveSessionID }
	::= { sessionStatusActiveTable 1 }

	SessionStatusActiveEntry ::= SEQUENCE {
		sessionStatusActiveSessionID	INTEGER,
		sessionStatusActiveState	INTEGER,
		sessionStatusActivePermanentFlag INTEGER,
		sessionStatusActiveVpopId	INTEGER,
		sessionStatusActiveName		DisplayString,
		sessionStatusActiveRemoteIP	IpAddress,
		sessionStatusActiveRemoteIPMask	IpAddress,
		sessionStatusActiveLocalIP	IpAddress,
		sessionStatusActiveLocalIPMask	IpAddress,
		sessionStatusActiveLinkService	INTEGER,
		sessionStatusActiveServiceMode	INTEGER,
		sessionStatusActiveStartTime	INTEGER,
		sessionStatusActiveStopTime	INTEGER,
		sessionStatusActiveTimeOfModemSync INTEGER,
		sessionStatusActiveTimeOfService INTEGER,
		sessionStatusActiveTerminatingComponent INTEGER,
		sessionStatusActiveTerminationCause INTEGER,
		sessionStatusActiveLastComponent INTEGER,
		sessionStatusActiveLayer1Slot	INTEGER,
		sessionStatusActiveLayer2Slot	INTEGER,
		sessionStatusActiveCalledNumber	DisplayString,
		sessionStatusActiveCallingNumber DisplayString,
		sessionStatusActiveOriginateMode INTEGER,
		sessionStatusActiveOctetsIn	INTEGER,
		sessionStatusActiveOctetsOut	INTEGER,
		sessionStatusActivePacketsIn	INTEGER,
		sessionStatusActivePacketsOut	INTEGER,
		sessionStatusActiveMultiLinkId	INTEGER,
		sessionStatusActivePort		INTEGER,
		sessionStatusActiveTimeslot	INTEGER,
		sessionStatusActiveLinkCount	INTEGER,
		sessionStatusActiveTxStartDataRate INTEGER,
		sessionStatusActiveRxStartDataRate INTEGER,
		sessionStatusActiveTxEndDataRate INTEGER,
		sessionStatusActiveRxEndDataRate INTEGER,
		sessionStatusActiveTxMinDataRate INTEGER,
		sessionStatusActiveRxMinDataRate INTEGER,
		sessionStatusActiveTxMaxDataRate INTEGER,
		sessionStatusActiveRxMaxDataRate INTEGER,
		sessionStatusActiveIop		INTEGER,
		sessionStatusActiveDmm		INTEGER,
		sessionStatusActivePack		INTEGER,
		sessionStatusActiveDevice	INTEGER,
		sessionStatusActiveTdmStream	INTEGER,
		sessionStatusActiveTdmTimeSlot	INTEGER,
		sessionStatusActiveTerminationReason DisplayString,
		sessionStatusActiveDuration	INTEGER,
		sessionStatusActiveDurationHMS	DisplayString,
		sessionStatusActiveSs7SessionId	DisplayString,
		sessionStatusActiveModemNumber	INTEGER,
		sessionStatusActiveTunnelType	INTEGER,
		sessionStatusActiveTunnelMediumType INTEGER,
		sessionStatusActiveTunnelServerAddress IpAddress,
		sessionStatusActiveCallClass	INTEGER,
		sessionStatusActiveTandemPort	INTEGER,
		sessionStatusActiveTandemTimeslot INTEGER,
		sessionStatusActiveCallClassArray OCTET STRING,
		sessionStatusActiveCallClassLen	INTEGER,
		sessionStatusActiveActualAuthMethod INTEGER,
		sessionStatusActiveModemModulation INTEGER,
		sessionStatusActiveModemErrorCorrection INTEGER,
		sessionStatusActiveModemDataCompression INTEGER,
		sessionStatusActiveModemTxBlocks INTEGER,
		sessionStatusActiveModemRetransmits INTEGER,
		sessionStatusActiveModemSNR	INTEGER,
		sessionStatusActiveModemLocalRetrains INTEGER,
		sessionStatusActiveModemRemoteRetrains INTEGER,
		sessionStatusActiveModemLocalRenegotiations INTEGER,
		sessionStatusActiveModemRemoteRenegotiations INTEGER,
		sessionStatusActiveModemReceiveLineLevel INTEGER,
		sessionStatusActiveRemoteIPXNetwork INTEGER,
		sessionStatusActiveRemoteIPXNode DisplayString,
		sessionStatusActiveCleartcpRemoteIP IpAddress,
		sessionStatusActiveCleartcpRemotePort INTEGER,
		sessionStatusActiveTunnelId	INTEGER,
		sessionStatusActiveLinkId	INTEGER
	}

	sessionStatusActiveSessionID	OBJECT-TYPE
		SYNTAX		INTEGER
		MAX-ACCESS	read-only
		STATUS		current
		DESCRIPTION
			"The serial number of this session, a unique number
			for this boot era. When combined with the value of
			BootEra, provides a session number that is unique for
			the life of the system. Note that these are very
			sparsely numbered."

	::= { sessionStatusActiveEntry 2 }

	sessionStatusActiveState	OBJECT-TYPE
		SYNTAX		INTEGER {
				    inactive(0),
				    active(1)
				}
		MAX-ACCESS	read-only
		STATUS		current
		DESCRIPTION
			"This variable indicates the state of this session."

	::= { sessionStatusActiveEntry 3 }

	sessionStatusActivePermanentFlag	OBJECT-TYPE
		SYNTAX		INTEGER {
				    unknown(0),
				    switched(1),
				    permanent(2)
				}
		MAX-ACCESS	read-only
		STATUS		current
		DESCRIPTION
			"This variable indicates whether this session is
			permanent(2), meaning a long-lasting locally
			administered session such as a Frame Relay PVC, or
			switched(1), meaning a short-lived session resulting
			from a switched call."

	::= { sessionStatusActiveEntry 10 }

	sessionStatusActiveVpopId	OBJECT-TYPE
		SYNTAX		INTEGER
		MAX-ACCESS	read-only
		STATUS		current
		DESCRIPTION
			"The identifier of the VPOP (administrative Group) to
			which the session belongs. A value of 0 indicates the
			default VPOP."

	::= { sessionStatusActiveEntry 11 }

	sessionStatusActiveName	OBJECT-TYPE
		SYNTAX		DisplayString (SIZE (0..68))
		MAX-ACCESS	read-only
		STATUS		current
		DESCRIPTION
			"The name of the connection peer for this session.
			During authentication of the session, this field may
			contain the name submitted by the peer. During this
			time, the value of timeOfService will be zero. When
			the value of timeOfService is nonzero, this field will
			contain a fully authenticated name."

	::= { sessionStatusActiveEntry 12 }

	sessionStatusActiveRemoteIP	OBJECT-TYPE
		SYNTAX		IpAddress
		MAX-ACCESS	read-only
		STATUS		current
		DESCRIPTION
			"The connection peer's IP address. If the link is
			numbered, then this is the address assigned to the
			other end of the link. If the link is not numbered,
			this may be the single IP address of the peer. For PPP
			connections, this is the result of IPNCP negotiation."

	::= { sessionStatusActiveEntry 13 }

	sessionStatusActiveRemoteIPMask	OBJECT-TYPE
		SYNTAX		IpAddress
		MAX-ACCESS	read-only
		STATUS		current
		DESCRIPTION
			"The connection peer's IP address mask, used in
			conjunction with remoteIP."

	::= { sessionStatusActiveEntry 14 }

	sessionStatusActiveLocalIP	OBJECT-TYPE
		SYNTAX		IpAddress
		MAX-ACCESS	read-only
		STATUS		current
		DESCRIPTION
			"The local IP address for this session. If the link is
			numbered, then this is the address assigned to the
			local end of the link. If the link is not numbered,
			this may be the primary IP address of the system. For
			PPP connections, this is the result of IPNCP
			negotiation."

	::= { sessionStatusActiveEntry 15 }

	sessionStatusActiveLocalIPMask	OBJECT-TYPE
		SYNTAX		IpAddress
		MAX-ACCESS	read-only
		STATUS		current
		DESCRIPTION
			"The local IP address mask for this session, used in
			conjunction with localIP."

	::= { sessionStatusActiveEntry 16 }

	sessionStatusActiveLinkService	OBJECT-TYPE
		SYNTAX		INTEGER {
				    unknown(0),
				    none(1),
				    other(2),
				    isdn56K(3),
				    isdn64K(4),
				    isdnV120(5),
				    isdnV110(6),
				    modemV32(7),
				    modemV34(8),
				    modemK56(9),
				    modemV90(10),
				    ethernet(11),
				    t1Trunk(12),
				    loopback(13),
				    hssi(14),
				    hub(15),
				    voice(16)
				}
		MAX-ACCESS	read-only
		STATUS		current
		DESCRIPTION
			"A description of which link technology is being used
			by the session."

	::= { sessionStatusActiveEntry 17 }

	sessionStatusActiveServiceMode	OBJECT-TYPE
		SYNTAX		INTEGER {
				    unknown(0),
				    none(1),
				    other(2),
				    ppp(3),
				    slip(4),
				    frameRelay(5),
				    ciscoHDLC(6),
				    terminalServer(7),
				    telnet(8),
				    rawTCP(9),
				    rlogin(10),
				    l2tp(11),
				    l2f(12),
				    trunk(13),
				    voice(14),
				    tandem(15),
				    hub(16),
				    ftp(17),
				    dvs(18),
				    fax(19),
				    atmp(20),
				    iptest(21)
				}
		MAX-ACCESS	read-only
		STATUS		current
		DESCRIPTION
			"A description of which session service is being used
			by the session."

	::= { sessionStatusActiveEntry 18 }

	sessionStatusActiveStartTime	OBJECT-TYPE
		SYNTAX		INTEGER
		MAX-ACCESS	read-only
		STATUS		current
		DESCRIPTION
			"The time that this session began, in seconds since
			the system booted."

	::= { sessionStatusActiveEntry 19 }

	sessionStatusActiveStopTime	OBJECT-TYPE
		SYNTAX		INTEGER
		MAX-ACCESS	read-only
		STATUS		current
		DESCRIPTION
			"The time that this session stopped, in seconds since
			the system booted. This variable is only meaningful
			for sessions having the state inactive(0)."

	::= { sessionStatusActiveEntry 20 }

	sessionStatusActiveTimeOfModemSync	OBJECT-TYPE
		SYNTAX		INTEGER
		MAX-ACCESS	read-only
		STATUS		current
		DESCRIPTION
			"The time at which the modem synchronization
			completed, in seconds since the system booted."

	::= { sessionStatusActiveEntry 21 }

	sessionStatusActiveTimeOfService	OBJECT-TYPE
		SYNTAX		INTEGER
		MAX-ACCESS	read-only
		STATUS		current
		DESCRIPTION
			"The time that this session entered its first
			negotiated or configured service, in seconds since the
			system booted. For example, for a session with
			serviceMode PPP, the time at which LCP and IPCP
			negotiations completed and the session was ready to
			forward user data."

	::= { sessionStatusActiveEntry 22 }

	sessionStatusActiveTerminatingComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The component which initiated termination of this
			session. In cases where there are multiple causes of
			session termination, only the first cause detected is
			reported. This variable is only meaningful for
			sessions having the state inactive(0)."

	::= { sessionStatusActiveEntry 23 }

	sessionStatusActiveTerminationCause	OBJECT-TYPE
		SYNTAX		INTEGER
		MAX-ACCESS	read-only
		STATUS		current
		DESCRIPTION
			"The cause which initiated termination of this
			session. In cases where there are multiple causes of
			session termination, only the first cause detected is
			reported. This variable is only meaningful for
			sessions having the state inactive(0)."

	::= { sessionStatusActiveEntry 24 }

	sessionStatusActiveLastComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The last component which was connected in this
			session."

	::= { sessionStatusActiveEntry 25 }

	sessionStatusActiveLayer1Slot	OBJECT-TYPE
		SYNTAX		INTEGER (1..18)
		MAX-ACCESS	read-only
		STATUS		current
		DESCRIPTION
			"The slot where the physical layer of this session is
			terminated."

	::= { sessionStatusActiveEntry 26 }

	sessionStatusActiveLayer2Slot	OBJECT-TYPE
		SYNTAX		INTEGER (1..18)
		MAX-ACCESS	read-only
		STATUS		current
		DESCRIPTION
			"The slot where the data link portion of this session
			is terminated"

	::= { sessionStatusActiveEntry 27 }

	sessionStatusActiveCalledNumber	OBJECT-TYPE
		SYNTAX		DisplayString (SIZE (0..17))
		MAX-ACCESS	read-only
		STATUS		current
		DESCRIPTION
			"16 digit number of called station (if available)"

	::= { sessionStatusActiveEntry 28 }

	sessionStatusActiveCallingNumber	OBJECT-TYPE
		SYNTAX		DisplayString (SIZE (0..17))
		MAX-ACCESS	read-only
		STATUS		current
		DESCRIPTION
			"16 digit number of calling station (if available)"

	::= { sessionStatusActiveEntry 29 }

	sessionStatusActiveOriginateMode	OBJECT-TYPE
		SYNTAX		INTEGER {
				    answer(0),
				    originate(1)
				}
		MAX-ACCESS	read-only
		STATUS		current
		DESCRIPTION
			"The direction of the physical layer call associated
			with this session"

	::= { sessionStatusActiveEntry 30 }

	sessionStatusActiveOctetsIn	OBJECT-TYPE
		SYNTAX		INTEGER
		MAX-ACCESS	read-only
		STATUS		current
		DESCRIPTION
			"The number of octets received from the remote user.
			This value will be zero until a session is
			terminated."

	::= { sessionStatusActiveEntry 31 }

	sessionStatusActiveOctetsOut	OBJECT-TYPE
		SYNTAX		INTEGER
		MAX-ACCESS	read-only
		STATUS		current
		DESCRIPTION
			"The number of octets sent to the remote user. This
			value will be zero until a session is terminated."

	::= { sessionStatusActiveEntry 32 }

	sessionStatusActivePacketsIn	OBJECT-TYPE
		SYNTAX		INTEGER
		MAX-ACCESS	read-only
		STATUS		current
		DESCRIPTION
			"The number of packets received from the remote user.
			This value will be zero until a session is
			terminated."

	::= { sessionStatusActiveEntry 33 }

	sessionStatusActivePacketsOut	OBJECT-TYPE
		SYNTAX		INTEGER
		MAX-ACCESS	read-only
		STATUS		current
		DESCRIPTION
			"The number of packets sent to the remote user. This
			value will be zero until a session is terminated."

	::= { sessionStatusActiveEntry 34 }

	sessionStatusActiveMultiLinkId	OBJECT-TYPE
		SYNTAX		INTEGER
		MAX-ACCESS	read-only
		STATUS		current
		DESCRIPTION
			"The multi-link identifier value for PPP calls where
			the multi-link protocol was negotiated."

	::= { sessionStatusActiveEntry 35 }

	sessionStatusActivePort	OBJECT-TYPE
		SYNTAX		INTEGER
		MAX-ACCESS	read-only
		STATUS		current
		DESCRIPTION
			"The number of the DS1 for this session, relative to
			layer1Slot."

	::= { sessionStatusActiveEntry 36 }

	sessionStatusActiveTimeslot	OBJECT-TYPE
		SYNTAX		INTEGER
		MAX-ACCESS	read-only
		STATUS		current
		DESCRIPTION
			"The number of the DS0 for this session, relative to
			port."

	::= { sessionStatusActiveEntry 37 }

	sessionStatusActiveLinkCount	OBJECT-TYPE
		SYNTAX		INTEGER
		MAX-ACCESS	read-only
		STATUS		current
		DESCRIPTION
			"The number of sessions sharing the same remote IP
			address as this session. After a session is
			terminated, this value will represent the number of
			sessions at the time of termination."

	::= { sessionStatusActiveEntry 38 }

	sessionStatusActiveTxStartDataRate	OBJECT-TYPE
		SYNTAX		INTEGER
		MAX-ACCESS	read-only
		STATUS		current
		DESCRIPTION
			"The transmit DCE data rate for this session. In the
			case of modem sessions, this will be the DCE rate
			reported as a result of initial modem negotiation, and
			may not track rate chanes during the call. For ISDN
			sessions, this will be the actual data service rate of
			the call. For Frame Relay sessions, this will be the
			nominal speed of the Frame Relay Physical Interface,
			even though multiple sessions may be sharing that
			Physical Interface. For other sessions, this will be
			the nominal speed of the physical interface. In no
			case should this be interepreted as a
			Quality-of-Service guarantee, or as the current line
			utilization or effective bandwidth on the interface.
			Note also that in the case of PPP multilink, this
			specifies the rate of only this link in the bundle,
			and not the aggregate rate of all links in the
			bundle."

	::= { sessionStatusActiveEntry 39 }

	sessionStatusActiveRxStartDataRate	OBJECT-TYPE
		SYNTAX		INTEGER
		MAX-ACCESS	read-only
		STATUS		current
		DESCRIPTION
			"The receive data rate for this session. In the case
			of modem sessions, this will be the DCE rate reported
			as a result of initial modem negotiation, and may not
			track rate chanes during the call. For ISDN sessions,
			this will be the actual data service rate of the call.
			For Frame Relay sessions, this will be the nominal
			speed of the Frame Relay Physical Interface, even
			though multiple sessions may be sharing that Physical
			Interface. For other sessions, this will be the
			nominal speed of the physical interface. In no case
			should this be interepreted as a Quality-of-Service
			guarantee, or as the current line utilization or
			effective bandwidth on the interface. Note also that
			in the case of PPP multilink, this specifies the rate
			of only this link in the bundle, and not the aggregate
			rate of all links in the bundle."

	::= { sessionStatusActiveEntry 40 }

	sessionStatusActiveTxEndDataRate	OBJECT-TYPE
		SYNTAX		INTEGER
		MAX-ACCESS	read-only
		STATUS		current
		DESCRIPTION
			"The transmit data rate at the end of a modem
			session."

	::= { sessionStatusActiveEntry 41 }

	sessionStatusActiveRxEndDataRate	OBJECT-TYPE
		SYNTAX		INTEGER
		MAX-ACCESS	read-only
		STATUS		current
		DESCRIPTION
			"The receive data rate at the end of a modem session."

	::= { sessionStatusActiveEntry 42 }

	sessionStatusActiveTxMinDataRate	OBJECT-TYPE
		SYNTAX		INTEGER
		MAX-ACCESS	read-only
		STATUS		current
		DESCRIPTION
			"The minimum transmit data rate during a modem
			session."

	::= { sessionStatusActiveEntry 43 }

	sessionStatusActiveRxMinDataRate	OBJECT-TYPE
		SYNTAX		INTEGER
		MAX-ACCESS	read-only
		STATUS		current
		DESCRIPTION
			"The minimum receive data rate during a modem
			session."

	::= { sessionStatusActiveEntry 44 }

	sessionStatusActiveTxMaxDataRate	OBJECT-TYPE
		SYNTAX		INTEGER
		MAX-ACCESS	read-only
		STATUS		current
		DESCRIPTION
			"The maximum transmit data rate during a modem
			session."

	::= { sessionStatusActiveEntry 45 }

	sessionStatusActiveRxMaxDataRate	OBJECT-TYPE
		SYNTAX		INTEGER
		MAX-ACCESS	read-only
		STATUS		current
		DESCRIPTION
			"The maximum receive data rate during a modem
			session."

	::= { sessionStatusActiveEntry 46 }

	sessionStatusActiveIop	OBJECT-TYPE
		SYNTAX		INTEGER
		MAX-ACCESS	read-only
		STATUS		current
		DESCRIPTION
			"The I/O processor where this session is terminated."

	::= { sessionStatusActiveEntry 47 }

	sessionStatusActiveDmm	OBJECT-TYPE
		SYNTAX		INTEGER
		MAX-ACCESS	read-only
		STATUS		current
		DESCRIPTION
			"The Digital Modem Module where this session is
			terminated."

	::= { sessionStatusActiveEntry 48 }

	sessionStatusActivePack	OBJECT-TYPE
		SYNTAX		INTEGER
		MAX-ACCESS	read-only
		STATUS		current
		DESCRIPTION
			"The integrated circuit pack where this session is
			terminated."

	::= { sessionStatusActiveEntry 49 }

	sessionStatusActiveDevice	OBJECT-TYPE
		SYNTAX		INTEGER
		MAX-ACCESS	read-only
		STATUS		current
		DESCRIPTION
			"The modem/hdlc where this session is terminated."

	::= { sessionStatusActiveEntry 50 }

	sessionStatusActiveTdmStream	OBJECT-TYPE
		SYNTAX		INTEGER
		MAX-ACCESS	read-only
		STATUS		current
		DESCRIPTION
			"The TDM highway stream associated with this session."

	::= { sessionStatusActiveEntry 51 }

	sessionStatusActiveTdmTimeSlot	OBJECT-TYPE
		SYNTAX		INTEGER
		MAX-ACCESS	read-only
		STATUS		current
		DESCRIPTION
			"The TDM highway time-slot associated with this
			session."

	::= { sessionStatusActiveEntry 52 }

	sessionStatusActiveTerminationReason	OBJECT-TYPE
		SYNTAX		DisplayString (SIZE (0..50))
		MAX-ACCESS	read-only
		STATUS		current
		DESCRIPTION
			"A textual description of the cause which initiated
			termination of this session. In cases where there are
			multiple causes of session termination, only the first
			cause detected is reported."

	::= { sessionStatusActiveEntry 53 }

	sessionStatusActiveDuration	OBJECT-TYPE
		SYNTAX		INTEGER
		MAX-ACCESS	read-only
		STATUS		current
		DESCRIPTION
			"The number of seconds this session has been active."

	::= { sessionStatusActiveEntry 54 }

	sessionStatusActiveDurationHMS	OBJECT-TYPE
		SYNTAX		DisplayString (SIZE (0..20))
		MAX-ACCESS	read-only
		STATUS		current
		DESCRIPTION
			"The length of time this session has been active,
			expressed in DDD HH:MM:SSS.000."

	::= { sessionStatusActiveEntry 55 }

	sessionStatusActiveSs7SessionId	OBJECT-TYPE
		SYNTAX		DisplayString (SIZE (0..41))
		MAX-ACCESS	read-only
		STATUS		current
		DESCRIPTION
			"A uniquie identifier for this session within the ss7
			Network. If this call was not originated using ss7
			signalling, this string will be null."

	::= { sessionStatusActiveEntry 56 }

	sessionStatusActiveModemNumber	OBJECT-TYPE
		SYNTAX		INTEGER
		MAX-ACCESS	read-only
		STATUS		current
		DESCRIPTION
			"The individual modem where this session is
			terminated, numbered from one to the maximum number of
			modems on the slot card."

	::= { sessionStatusActiveEntry 57 }

	sessionStatusActiveTunnelType	OBJECT-TYPE
		SYNTAX		INTEGER {
				    unknown(0),
				    none(1),
				    other(2),
				    l2f(3),
				    l2tp(4),
				    dvs(5),
				    atmp(6)
				}
		MAX-ACCESS	read-only
		STATUS		current
		DESCRIPTION
			"The tunneling protocol being used for this session."

	::= { sessionStatusActiveEntry 58 }

	sessionStatusActiveTunnelMediumType	OBJECT-TYPE
		SYNTAX		INTEGER {
				    unknown(0),
				    none(1),
				    other(2),
				    ip(3)
				}
		MAX-ACCESS	read-only
		STATUS		current
		DESCRIPTION
			"The tunneling medium protocol being used for this
			session."

	::= { sessionStatusActiveEntry 59 }

	sessionStatusActiveTunnelServerAddress	OBJECT-TYPE
		SYNTAX		IpAddress
		MAX-ACCESS	read-only
		STATUS		current
		DESCRIPTION
			"The IP address of the remote machine terminating the
			tunnel for this session."

	::= { sessionStatusActiveEntry 60 }

	sessionStatusActiveCallClass	OBJECT-TYPE
		SYNTAX		INTEGER
		MAX-ACCESS	read-only
		STATUS		current
		DESCRIPTION
			"The class of this call."

	::= { sessionStatusActiveEntry 61 }

	sessionStatusActiveTandemPort	OBJECT-TYPE
		SYNTAX		INTEGER
		MAX-ACCESS	read-only
		STATUS		current
		DESCRIPTION
			"The port used for the outbound portion of a tandem
			call, if applicable."

	::= { sessionStatusActiveEntry 62 }

	sessionStatusActiveTandemTimeslot	OBJECT-TYPE
		SYNTAX		INTEGER
		MAX-ACCESS	read-only
		STATUS		current
		DESCRIPTION
			"The timeslot used for the outbound portion of a
			tandem call, if applicable."

	::= { sessionStatusActiveEntry 63 }

	sessionStatusActiveCallClassArray	OBJECT-TYPE
		SYNTAX		OCTET STRING (SIZE (0..256))
		MAX-ACCESS	read-only
		STATUS		current
		DESCRIPTION
			"An array of octets representing the class of this
			call."

	::= { sessionStatusActiveEntry 64 }

	sessionStatusActiveCallClassLen	OBJECT-TYPE
		SYNTAX		INTEGER
		MAX-ACCESS	read-only
		STATUS		current
		DESCRIPTION
			"The number of octets in callClassArray."

	::= { sessionStatusActiveEntry 65 }

	sessionStatusActiveActualAuthMethod	OBJECT-TYPE
		SYNTAX		INTEGER {
				    radius(1),
				    local(2),
				    remote(3)
				}
		MAX-ACCESS	read-only
		STATUS		current
		DESCRIPTION
			"The actual authentication method which was used to
			gain access to services. Radius, Local, Remote."

	::= { sessionStatusActiveEntry 66 }

	sessionStatusActiveModemModulation	OBJECT-TYPE
		SYNTAX		INTEGER {
				    none(0),
				    unknown(1),
				    bell103(2),
				    bell208(3),
				    bell212(4),
				    v17(5),
				    v21(6),
				    v22(7),
				    v22bis(8),
				    v23(9),
				    v27(10),
				    v29(11),
				    v32(12),
				    v32bis(13),
				    v33(14),
				    v34(15),
				    vFC(16),
				    k56(17),
				    v90(18)
				}
		MAX-ACCESS	read-only
		STATUS		current
		DESCRIPTION
			"For modem sessions, the modulation protocol used, if
			any."

	::= { sessionStatusActiveEntry 67 }

	sessionStatusActiveModemErrorCorrection	OBJECT-TYPE
		SYNTAX		INTEGER {
				    none(0),
				    unknown(1),
				    mNP(2),
				    v42(3)
				}
		MAX-ACCESS	read-only
		STATUS		current
		DESCRIPTION
			"For modem sessions, the error correction protocol
			used, if any."

	::= { sessionStatusActiveEntry 68 }

	sessionStatusActiveModemDataCompression	OBJECT-TYPE
		SYNTAX		INTEGER {
				    none(0),
				    unknown(1),
				    mNP5(2),
				    v42bis(3)
				}
		MAX-ACCESS	read-only
		STATUS		current
		DESCRIPTION
			"For modem sessions, the data compression protocol
			used, if any."

	::= { sessionStatusActiveEntry 69 }

	sessionStatusActiveModemTxBlocks	OBJECT-TYPE
		SYNTAX		INTEGER
		MAX-ACCESS	read-only
		STATUS		current
		DESCRIPTION
			"For modem sessions, the number of blocks transmitted
			by the modem."

	::= { sessionStatusActiveEntry 70 }

	sessionStatusActiveModemRetransmits	OBJECT-TYPE
		SYNTAX		INTEGER
		MAX-ACCESS	read-only
		STATUS		current
		DESCRIPTION
			"For modem sessions, the number of packets
			retransmitted by the modem."

	::= { sessionStatusActiveEntry 71 }

	sessionStatusActiveModemSNR	OBJECT-TYPE
		SYNTAX		INTEGER
		MAX-ACCESS	read-only
		STATUS		current
		DESCRIPTION
			"For modem sessions, the Signal-to-Noise Ratio
			measured at the start of the connection. This value is
			given in dB."

	::= { sessionStatusActiveEntry 72 }

	sessionStatusActiveModemLocalRetrains	OBJECT-TYPE
		SYNTAX		INTEGER
		MAX-ACCESS	read-only
		STATUS		current
		DESCRIPTION
			"For modem sessions, the number of retrain requests
			sent by the local modem."

	::= { sessionStatusActiveEntry 73 }

	sessionStatusActiveModemRemoteRetrains	OBJECT-TYPE
		SYNTAX		INTEGER
		MAX-ACCESS	read-only
		STATUS		current
		DESCRIPTION
			"For modem sessions, the number of retrain requests
			sent by the remote modem."

	::= { sessionStatusActiveEntry 74 }

	sessionStatusActiveModemLocalRenegotiations	OBJECT-TYPE
		SYNTAX		INTEGER
		MAX-ACCESS	read-only
		STATUS		current
		DESCRIPTION
			"For modem sessions, the number of rate renegotiation
			requests sent by the local modem."

	::= { sessionStatusActiveEntry 75 }

	sessionStatusActiveModemRemoteRenegotiations	OBJECT-TYPE
		SYNTAX		INTEGER
		MAX-ACCESS	read-only
		STATUS		current
		DESCRIPTION
			"For modem sessions, the number of rate renegotiation
			requests sent by the remote modem."

	::= { sessionStatusActiveEntry 76 }

	sessionStatusActiveModemReceiveLineLevel	OBJECT-TYPE
		SYNTAX		INTEGER
		MAX-ACCESS	read-only
		STATUS		current
		DESCRIPTION
			"For modem sessions, the receive line signal level.
			This value is given in dB."

	::= { sessionStatusActiveEntry 77 }

	sessionStatusActiveRemoteIPXNetwork	OBJECT-TYPE
		SYNTAX		INTEGER
		MAX-ACCESS	read-only
		STATUS		current
		DESCRIPTION
			"The IPX network assigned to the dial-up user."

	::= { sessionStatusActiveEntry 78 }

	sessionStatusActiveRemoteIPXNode	OBJECT-TYPE
		SYNTAX		DisplayString (SIZE (0..16))
		MAX-ACCESS	read-only
		STATUS		current
		DESCRIPTION
			"The IPX Node number assisgned to the dial-up user"

	::= { sessionStatusActiveEntry 79 }

	sessionStatusActiveCleartcpRemoteIP	OBJECT-TYPE
		SYNTAX		IpAddress
		MAX-ACCESS	read-only
		STATUS		current
		DESCRIPTION
			"Cleartcp Remote IP Address"

	::= { sessionStatusActiveEntry 80 }

	sessionStatusActiveCleartcpRemotePort	OBJECT-TYPE
		SYNTAX		INTEGER
		MAX-ACCESS	read-only
		STATUS		current
		DESCRIPTION
			"Cleartcp Remote Port Address"

	::= { sessionStatusActiveEntry 81 }

	sessionStatusActiveTunnelId	OBJECT-TYPE
		SYNTAX		INTEGER
		MAX-ACCESS	read-only
		STATUS		current
		DESCRIPTION
			"Tunnel Id"

	::= { sessionStatusActiveEntry 82 }

	sessionStatusActiveLinkId	OBJECT-TYPE
		SYNTAX		INTEGER
		MAX-ACCESS	read-only
		STATUS		current
		DESCRIPTION
			"Link Id"

	::= { sessionStatusActiveEntry 83 }


	sessionStatusInactiveTable	OBJECT-TYPE
		SYNTAX		SEQUENCE OF SessionStatusInactiveEntry
		MAX-ACCESS	not-accessible
		STATUS		current
		DESCRIPTION
			"The table contains the most recent inactive sessions,
			up to a maximum of SessionTableSize entries. The
			bounds of this table at any given time are described
			by the variables InactiveLowest and InactiveHighest.
			This table is ordered by session serial number. As new
			entries are appended to the bottom of the table, the
			inactive entries with the oldest termination time get
			aged out from near the top of the table."

	::= { aptis-monitoring 103 }

	sessionStatusInactiveEntry	OBJECT-TYPE
		SYNTAX		SessionStatusInactiveEntry
		MAX-ACCESS	not-accessible
		STATUS		current
		DESCRIPTION
			"This is the structure of entries in the
			 sessionStatusInactiveTable."
		INDEX		{ sessionStatusInactiveSessionID }
	::= { sessionStatusInactiveTable 1 }

	SessionStatusInactiveEntry ::= SEQUENCE {
		sessionStatusInactiveSessionID	INTEGER,
		sessionStatusInactiveState	INTEGER,
		sessionStatusInactivePermanentFlag INTEGER,
		sessionStatusInactiveVpopId	INTEGER,
		sessionStatusInactiveName	DisplayString,
		sessionStatusInactiveRemoteIP	IpAddress,
		sessionStatusInactiveRemoteIPMask IpAddress,
		sessionStatusInactiveLocalIP	IpAddress,
		sessionStatusInactiveLocalIPMask IpAddress,
		sessionStatusInactiveLinkService INTEGER,
		sessionStatusInactiveServiceMode INTEGER,
		sessionStatusInactiveStartTime	INTEGER,
		sessionStatusInactiveStopTime	INTEGER,
		sessionStatusInactiveTimeOfModemSync INTEGER,
		sessionStatusInactiveTimeOfService INTEGER,
		sessionStatusInactiveTerminatingComponent INTEGER,
		sessionStatusInactiveTerminationCause INTEGER,
		sessionStatusInactiveLastComponent INTEGER,
		sessionStatusInactiveLayer1Slot	INTEGER,
		sessionStatusInactiveLayer2Slot	INTEGER,
		sessionStatusInactiveCalledNumber DisplayString,
		sessionStatusInactiveCallingNumber DisplayString,
		sessionStatusInactiveOriginateMode INTEGER,
		sessionStatusInactiveOctetsIn	INTEGER,
		sessionStatusInactiveOctetsOut	INTEGER,
		sessionStatusInactivePacketsIn	INTEGER,
		sessionStatusInactivePacketsOut	INTEGER,
		sessionStatusInactiveMultiLinkId INTEGER,
		sessionStatusInactivePort	INTEGER,
		sessionStatusInactiveTimeslot	INTEGER,
		sessionStatusInactiveLinkCount	INTEGER,
		sessionStatusInactiveTxStartDataRate INTEGER,
		sessionStatusInactiveRxStartDataRate INTEGER,
		sessionStatusInactiveTxEndDataRate INTEGER,
		sessionStatusInactiveRxEndDataRate INTEGER,
		sessionStatusInactiveTxMinDataRate INTEGER,
		sessionStatusInactiveRxMinDataRate INTEGER,
		sessionStatusInactiveTxMaxDataRate INTEGER,
		sessionStatusInactiveRxMaxDataRate INTEGER,
		sessionStatusInactiveIop	INTEGER,
		sessionStatusInactiveDmm	INTEGER,
		sessionStatusInactivePack	INTEGER,
		sessionStatusInactiveDevice	INTEGER,
		sessionStatusInactiveTdmStream	INTEGER,
		sessionStatusInactiveTdmTimeSlot INTEGER,
		sessionStatusInactiveTerminationReason DisplayString,
		sessionStatusInactiveDuration	INTEGER,
		sessionStatusInactiveDurationHMS DisplayString,
		sessionStatusInactiveSs7SessionId DisplayString,
		sessionStatusInactiveModemNumber INTEGER,
		sessionStatusInactiveTunnelType	INTEGER,
		sessionStatusInactiveTunnelMediumType INTEGER,
		sessionStatusInactiveTunnelServerAddress IpAddress,
		sessionStatusInactiveCallClass	INTEGER,
		sessionStatusInactiveTandemPort	INTEGER,
		sessionStatusInactiveTandemTimeslot INTEGER,
		sessionStatusInactiveCallClassArray OCTET STRING,
		sessionStatusInactiveCallClassLen INTEGER,
		sessionStatusInactiveActualAuthMethod INTEGER,
		sessionStatusInactiveModemModulation INTEGER,
		sessionStatusInactiveModemErrorCorrection INTEGER,
		sessionStatusInactiveModemDataCompression INTEGER,
		sessionStatusInactiveModemTxBlocks INTEGER,
		sessionStatusInactiveModemRetransmits INTEGER,
		sessionStatusInactiveModemSNR	INTEGER,
		sessionStatusInactiveModemLocalRetrains INTEGER,
		sessionStatusInactiveModemRemoteRetrains INTEGER,
		sessionStatusInactiveModemLocalRenegotiations INTEGER,
		sessionStatusInactiveModemRemoteRenegotiations INTEGER,
		sessionStatusInactiveModemReceiveLineLevel INTEGER,
		sessionStatusInactiveRemoteIPXNetwork INTEGER,
		sessionStatusInactiveRemoteIPXNode DisplayString,
		sessionStatusInactiveCleartcpRemoteIP IpAddress,
		sessionStatusInactiveCleartcpRemotePort INTEGER,
		sessionStatusInactiveTunnelId	INTEGER,
		sessionStatusInactiveLinkId	INTEGER
	}

	sessionStatusInactiveSessionID	OBJECT-TYPE
		SYNTAX		INTEGER
		MAX-ACCESS	read-only
		STATUS		current
		DESCRIPTION
			"The serial number of this session, a unique number
			for this boot era. When combined with the value of
			BootEra, provides a session number that is unique for
			the life of the system. Note that these are very
			sparsely numbered."

	::= { sessionStatusInactiveEntry 2 }

	sessionStatusInactiveState	OBJECT-TYPE
		SYNTAX		INTEGER {
				    inactive(0),
				    active(1)
				}
		MAX-ACCESS	read-only
		STATUS		current
		DESCRIPTION
			"This variable indicates the state of this session."

	::= { sessionStatusInactiveEntry 3 }

	sessionStatusInactivePermanentFlag	OBJECT-TYPE
		SYNTAX		INTEGER {
				    unknown(0),
				    switched(1),
				    permanent(2)
				}
		MAX-ACCESS	read-only
		STATUS		current
		DESCRIPTION
			"This variable indicates whether this session is
			permanent(2), meaning a long-lasting locally
			administered session such as a Frame Relay PVC, or
			switched(1), meaning a short-lived session resulting
			from a switched call."

	::= { sessionStatusInactiveEntry 10 }

	sessionStatusInactiveVpopId	OBJECT-TYPE
		SYNTAX		INTEGER
		MAX-ACCESS	read-only
		STATUS		current
		DESCRIPTION
			"The identifier of the VPOP (administrative Group) to
			which the session belongs. A value of 0 indicates the
			default VPOP."

	::= { sessionStatusInactiveEntry 11 }

	sessionStatusInactiveName	OBJECT-TYPE
		SYNTAX		DisplayString (SIZE (0..68))
		MAX-ACCESS	read-only
		STATUS		current
		DESCRIPTION
			"The name of the connection peer for this session.
			During authentication of the session, this field may
			contain the name submitted by the peer. During this
			time, the value of timeOfService will be zero. When
			the value of timeOfService is nonzero, this field will
			contain a fully authenticated name."

	::= { sessionStatusInactiveEntry 12 }

	sessionStatusInactiveRemoteIP	OBJECT-TYPE
		SYNTAX		IpAddress
		MAX-ACCESS	read-only
		STATUS		current
		DESCRIPTION
			"The connection peer's IP address. If the link is
			numbered, then this is the address assigned to the
			other end of the link. If the link is not numbered,
			this may be the single IP address of the peer. For PPP
			connections, this is the result of IPNCP negotiation."

	::= { sessionStatusInactiveEntry 13 }

	sessionStatusInactiveRemoteIPMask	OBJECT-TYPE
		SYNTAX		IpAddress
		MAX-ACCESS	read-only
		STATUS		current
		DESCRIPTION
			"The connection peer's IP address mask, used in
			conjunction with remoteIP."

	::= { sessionStatusInactiveEntry 14 }

	sessionStatusInactiveLocalIP	OBJECT-TYPE
		SYNTAX		IpAddress
		MAX-ACCESS	read-only
		STATUS		current
		DESCRIPTION
			"The local IP address for this session. If the link is
			numbered, then this is the address assigned to the
			local end of the link. If the link is not numbered,
			this may be the primary IP address of the system. For
			PPP connections, this is the result of IPNCP
			negotiation."

	::= { sessionStatusInactiveEntry 15 }

	sessionStatusInactiveLocalIPMask	OBJECT-TYPE
		SYNTAX		IpAddress
		MAX-ACCESS	read-only
		STATUS		current
		DESCRIPTION
			"The local IP address mask for this session, used in
			conjunction with localIP."

	::= { sessionStatusInactiveEntry 16 }

	sessionStatusInactiveLinkService	OBJECT-TYPE
		SYNTAX		INTEGER {
				    unknown(0),
				    none(1),
				    other(2),
				    isdn56K(3),
				    isdn64K(4),
				    isdnV120(5),
				    isdnV110(6),
				    modemV32(7),
				    modemV34(8),
				    modemK56(9),
				    modemV90(10),
				    ethernet(11),
				    t1Trunk(12),
				    loopback(13),
				    hssi(14),
				    hub(15),
				    voice(16)
				}
		MAX-ACCESS	read-only
		STATUS		current
		DESCRIPTION
			"A description of which link technology is being used
			by the session."

	::= { sessionStatusInactiveEntry 17 }

	sessionStatusInactiveServiceMode	OBJECT-TYPE
		SYNTAX		INTEGER {
				    unknown(0),
				    none(1),
				    other(2),
				    ppp(3),
				    slip(4),
				    frameRelay(5),
				    ciscoHDLC(6),
				    terminalServer(7),
				    telnet(8),
				    rawTCP(9),
				    rlogin(10),
				    l2tp(11),
				    l2f(12),
				    trunk(13),
				    voice(14),
				    tandem(15),
				    hub(16),
				    ftp(17),
				    dvs(18),
				    fax(19),
				    atmp(20),
				    iptest(21)
				}
		MAX-ACCESS	read-only
		STATUS		current
		DESCRIPTION
			"A description of which session service is being used
			by the session."

	::= { sessionStatusInactiveEntry 18 }

	sessionStatusInactiveStartTime	OBJECT-TYPE
		SYNTAX		INTEGER
		MAX-ACCESS	read-only
		STATUS		current
		DESCRIPTION
			"The time that this session began, in seconds since
			the system booted."

	::= { sessionStatusInactiveEntry 19 }

	sessionStatusInactiveStopTime	OBJECT-TYPE
		SYNTAX		INTEGER
		MAX-ACCESS	read-only
		STATUS		current
		DESCRIPTION
			"The time that this session stopped, in seconds since
			the system booted. This variable is only meaningful
			for sessions having the state inactive(0)."

	::= { sessionStatusInactiveEntry 20 }

	sessionStatusInactiveTimeOfModemSync	OBJECT-TYPE
		SYNTAX		INTEGER
		MAX-ACCESS	read-only
		STATUS		current
		DESCRIPTION
			"The time at which the modem synchronization
			completed, in seconds since the system booted."

	::= { sessionStatusInactiveEntry 21 }

	sessionStatusInactiveTimeOfService	OBJECT-TYPE
		SYNTAX		INTEGER
		MAX-ACCESS	read-only
		STATUS		current
		DESCRIPTION
			"The time that this session entered its first
			negotiated or configured service, in seconds since the
			system booted. For example, for a session with
			serviceMode PPP, the time at which LCP and IPCP
			negotiations completed and the session was ready to
			forward user data."

	::= { sessionStatusInactiveEntry 22 }

	sessionStatusInactiveTerminatingComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The component which initiated termination of this
			session. In cases where there are multiple causes of
			session termination, only the first cause detected is
			reported. This variable is only meaningful for
			sessions having the state inactive(0)."

	::= { sessionStatusInactiveEntry 23 }

	sessionStatusInactiveTerminationCause	OBJECT-TYPE
		SYNTAX		INTEGER
		MAX-ACCESS	read-only
		STATUS		current
		DESCRIPTION
			"The cause which initiated termination of this
			session. In cases where there are multiple causes of
			session termination, only the first cause detected is
			reported. This variable is only meaningful for
			sessions having the state inactive(0)."

	::= { sessionStatusInactiveEntry 24 }

	sessionStatusInactiveLastComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The last component which was connected in this
			session."

	::= { sessionStatusInactiveEntry 25 }

	sessionStatusInactiveLayer1Slot	OBJECT-TYPE
		SYNTAX		INTEGER (1..18)
		MAX-ACCESS	read-only
		STATUS		current
		DESCRIPTION
			"The slot where the physical layer of this session is
			terminated."

	::= { sessionStatusInactiveEntry 26 }

	sessionStatusInactiveLayer2Slot	OBJECT-TYPE
		SYNTAX		INTEGER (1..18)
		MAX-ACCESS	read-only
		STATUS		current
		DESCRIPTION
			"The slot where the data link portion of this session
			is terminated"

	::= { sessionStatusInactiveEntry 27 }

	sessionStatusInactiveCalledNumber	OBJECT-TYPE
		SYNTAX		DisplayString (SIZE (0..17))
		MAX-ACCESS	read-only
		STATUS		current
		DESCRIPTION
			"16 digit number of called station (if available)"

	::= { sessionStatusInactiveEntry 28 }

	sessionStatusInactiveCallingNumber	OBJECT-TYPE
		SYNTAX		DisplayString (SIZE (0..17))
		MAX-ACCESS	read-only
		STATUS		current
		DESCRIPTION
			"16 digit number of calling station (if available)"

	::= { sessionStatusInactiveEntry 29 }

	sessionStatusInactiveOriginateMode	OBJECT-TYPE
		SYNTAX		INTEGER {
				    answer(0),
				    originate(1)
				}
		MAX-ACCESS	read-only
		STATUS		current
		DESCRIPTION
			"The direction of the physical layer call associated
			with this session"

	::= { sessionStatusInactiveEntry 30 }

	sessionStatusInactiveOctetsIn	OBJECT-TYPE
		SYNTAX		INTEGER
		MAX-ACCESS	read-only
		STATUS		current
		DESCRIPTION
			"The number of octets received from the remote user.
			This value will be zero until a session is
			terminated."

	::= { sessionStatusInactiveEntry 31 }

	sessionStatusInactiveOctetsOut	OBJECT-TYPE
		SYNTAX		INTEGER
		MAX-ACCESS	read-only
		STATUS		current
		DESCRIPTION
			"The number of octets sent to the remote user. This
			value will be zero until a session is terminated."

	::= { sessionStatusInactiveEntry 32 }

	sessionStatusInactivePacketsIn	OBJECT-TYPE
		SYNTAX		INTEGER
		MAX-ACCESS	read-only
		STATUS		current
		DESCRIPTION
			"The number of packets received from the remote user.
			This value will be zero until a session is
			terminated."

	::= { sessionStatusInactiveEntry 33 }

	sessionStatusInactivePacketsOut	OBJECT-TYPE
		SYNTAX		INTEGER
		MAX-ACCESS	read-only
		STATUS		current
		DESCRIPTION
			"The number of packets sent to the remote user. This
			value will be zero until a session is terminated."

	::= { sessionStatusInactiveEntry 34 }

	sessionStatusInactiveMultiLinkId	OBJECT-TYPE
		SYNTAX		INTEGER
		MAX-ACCESS	read-only
		STATUS		current
		DESCRIPTION
			"The multi-link identifier value for PPP calls where
			the multi-link protocol was negotiated."

	::= { sessionStatusInactiveEntry 35 }

	sessionStatusInactivePort	OBJECT-TYPE
		SYNTAX		INTEGER
		MAX-ACCESS	read-only
		STATUS		current
		DESCRIPTION
			"The number of the DS1 for this session, relative to
			layer1Slot."

	::= { sessionStatusInactiveEntry 36 }

	sessionStatusInactiveTimeslot	OBJECT-TYPE
		SYNTAX		INTEGER
		MAX-ACCESS	read-only
		STATUS		current
		DESCRIPTION
			"The number of the DS0 for this session, relative to
			port."

	::= { sessionStatusInactiveEntry 37 }

	sessionStatusInactiveLinkCount	OBJECT-TYPE
		SYNTAX		INTEGER
		MAX-ACCESS	read-only
		STATUS		current
		DESCRIPTION
			"The number of sessions sharing the same remote IP
			address as this session. After a session is
			terminated, this value will represent the number of
			sessions at the time of termination."

	::= { sessionStatusInactiveEntry 38 }

	sessionStatusInactiveTxStartDataRate	OBJECT-TYPE
		SYNTAX		INTEGER
		MAX-ACCESS	read-only
		STATUS		current
		DESCRIPTION
			"The transmit DCE data rate for this session. In the
			case of modem sessions, this will be the DCE rate
			reported as a result of initial modem negotiation, and
			may not track rate chanes during the call. For ISDN
			sessions, this will be the actual data service rate of
			the call. For Frame Relay sessions, this will be the
			nominal speed of the Frame Relay Physical Interface,
			even though multiple sessions may be sharing that
			Physical Interface. For other sessions, this will be
			the nominal speed of the physical interface. In no
			case should this be interepreted as a
			Quality-of-Service guarantee, or as the current line
			utilization or effective bandwidth on the interface.
			Note also that in the case of PPP multilink, this
			specifies the rate of only this link in the bundle,
			and not the aggregate rate of all links in the
			bundle."

	::= { sessionStatusInactiveEntry 39 }

	sessionStatusInactiveRxStartDataRate	OBJECT-TYPE
		SYNTAX		INTEGER
		MAX-ACCESS	read-only
		STATUS		current
		DESCRIPTION
			"The receive data rate for this session. In the case
			of modem sessions, this will be the DCE rate reported
			as a result of initial modem negotiation, and may not
			track rate chanes during the call. For ISDN sessions,
			this will be the actual data service rate of the call.
			For Frame Relay sessions, this will be the nominal
			speed of the Frame Relay Physical Interface, even
			though multiple sessions may be sharing that Physical
			Interface. For other sessions, this will be the
			nominal speed of the physical interface. In no case
			should this be interepreted as a Quality-of-Service
			guarantee, or as the current line utilization or
			effective bandwidth on the interface. Note also that
			in the case of PPP multilink, this specifies the rate
			of only this link in the bundle, and not the aggregate
			rate of all links in the bundle."

	::= { sessionStatusInactiveEntry 40 }

	sessionStatusInactiveTxEndDataRate	OBJECT-TYPE
		SYNTAX		INTEGER
		MAX-ACCESS	read-only
		STATUS		current
		DESCRIPTION
			"The transmit data rate at the end of a modem
			session."

	::= { sessionStatusInactiveEntry 41 }

	sessionStatusInactiveRxEndDataRate	OBJECT-TYPE
		SYNTAX		INTEGER
		MAX-ACCESS	read-only
		STATUS		current
		DESCRIPTION
			"The receive data rate at the end of a modem session."

	::= { sessionStatusInactiveEntry 42 }

	sessionStatusInactiveTxMinDataRate	OBJECT-TYPE
		SYNTAX		INTEGER
		MAX-ACCESS	read-only
		STATUS		current
		DESCRIPTION
			"The minimum transmit data rate during a modem
			session."

	::= { sessionStatusInactiveEntry 43 }

	sessionStatusInactiveRxMinDataRate	OBJECT-TYPE
		SYNTAX		INTEGER
		MAX-ACCESS	read-only
		STATUS		current
		DESCRIPTION
			"The minimum receive data rate during a modem
			session."

	::= { sessionStatusInactiveEntry 44 }

	sessionStatusInactiveTxMaxDataRate	OBJECT-TYPE
		SYNTAX		INTEGER
		MAX-ACCESS	read-only
		STATUS		current
		DESCRIPTION
			"The maximum transmit data rate during a modem
			session."

	::= { sessionStatusInactiveEntry 45 }

	sessionStatusInactiveRxMaxDataRate	OBJECT-TYPE
		SYNTAX		INTEGER
		MAX-ACCESS	read-only
		STATUS		current
		DESCRIPTION
			"The maximum receive data rate during a modem
			session."

	::= { sessionStatusInactiveEntry 46 }

	sessionStatusInactiveIop	OBJECT-TYPE
		SYNTAX		INTEGER
		MAX-ACCESS	read-only
		STATUS		current
		DESCRIPTION
			"The I/O processor where this session is terminated."

	::= { sessionStatusInactiveEntry 47 }

	sessionStatusInactiveDmm	OBJECT-TYPE
		SYNTAX		INTEGER
		MAX-ACCESS	read-only
		STATUS		current
		DESCRIPTION
			"The Digital Modem Module where this session is
			terminated."

	::= { sessionStatusInactiveEntry 48 }

	sessionStatusInactivePack	OBJECT-TYPE
		SYNTAX		INTEGER
		MAX-ACCESS	read-only
		STATUS		current
		DESCRIPTION
			"The integrated circuit pack where this session is
			terminated."

	::= { sessionStatusInactiveEntry 49 }

	sessionStatusInactiveDevice	OBJECT-TYPE
		SYNTAX		INTEGER
		MAX-ACCESS	read-only
		STATUS		current
		DESCRIPTION
			"The modem/hdlc where this session is terminated."

	::= { sessionStatusInactiveEntry 50 }

	sessionStatusInactiveTdmStream	OBJECT-TYPE
		SYNTAX		INTEGER
		MAX-ACCESS	read-only
		STATUS		current
		DESCRIPTION
			"The TDM highway stream associated with this session."

	::= { sessionStatusInactiveEntry 51 }

	sessionStatusInactiveTdmTimeSlot	OBJECT-TYPE
		SYNTAX		INTEGER
		MAX-ACCESS	read-only
		STATUS		current
		DESCRIPTION
			"The TDM highway time-slot associated with this
			session."

	::= { sessionStatusInactiveEntry 52 }

	sessionStatusInactiveTerminationReason	OBJECT-TYPE
		SYNTAX		DisplayString (SIZE (0..50))
		MAX-ACCESS	read-only
		STATUS		current
		DESCRIPTION
			"A textual description of the cause which initiated
			termination of this session. In cases where there are
			multiple causes of session termination, only the first
			cause detected is reported."

	::= { sessionStatusInactiveEntry 53 }

	sessionStatusInactiveDuration	OBJECT-TYPE
		SYNTAX		INTEGER
		MAX-ACCESS	read-only
		STATUS		current
		DESCRIPTION
			"The number of seconds this session has been active."

	::= { sessionStatusInactiveEntry 54 }

	sessionStatusInactiveDurationHMS	OBJECT-TYPE
		SYNTAX		DisplayString (SIZE (0..20))
		MAX-ACCESS	read-only
		STATUS		current
		DESCRIPTION
			"The length of time this session has been active,
			expressed in DDD HH:MM:SSS.000."

	::= { sessionStatusInactiveEntry 55 }

	sessionStatusInactiveSs7SessionId	OBJECT-TYPE
		SYNTAX		DisplayString (SIZE (0..41))
		MAX-ACCESS	read-only
		STATUS		current
		DESCRIPTION
			"A uniquie identifier for this session within the ss7
			Network. If this call was not originated using ss7
			signalling, this string will be null."

	::= { sessionStatusInactiveEntry 56 }

	sessionStatusInactiveModemNumber	OBJECT-TYPE
		SYNTAX		INTEGER
		MAX-ACCESS	read-only
		STATUS		current
		DESCRIPTION
			"The individual modem where this session is
			terminated, numbered from one to the maximum number of
			modems on the slot card."

	::= { sessionStatusInactiveEntry 57 }

	sessionStatusInactiveTunnelType	OBJECT-TYPE
		SYNTAX		INTEGER {
				    unknown(0),
				    none(1),
				    other(2),
				    l2f(3),
				    l2tp(4),
				    dvs(5),
				    atmp(6)
				}
		MAX-ACCESS	read-only
		STATUS		current
		DESCRIPTION
			"The tunneling protocol being used for this session."

	::= { sessionStatusInactiveEntry 58 }

	sessionStatusInactiveTunnelMediumType	OBJECT-TYPE
		SYNTAX		INTEGER {
				    unknown(0),
				    none(1),
				    other(2),
				    ip(3)
				}
		MAX-ACCESS	read-only
		STATUS		current
		DESCRIPTION
			"The tunneling medium protocol being used for this
			session."

	::= { sessionStatusInactiveEntry 59 }

	sessionStatusInactiveTunnelServerAddress	OBJECT-TYPE
		SYNTAX		IpAddress
		MAX-ACCESS	read-only
		STATUS		current
		DESCRIPTION
			"The IP address of the remote machine terminating the
			tunnel for this session."

	::= { sessionStatusInactiveEntry 60 }

	sessionStatusInactiveCallClass	OBJECT-TYPE
		SYNTAX		INTEGER
		MAX-ACCESS	read-only
		STATUS		current
		DESCRIPTION
			"The class of this call."

	::= { sessionStatusInactiveEntry 61 }

	sessionStatusInactiveTandemPort	OBJECT-TYPE
		SYNTAX		INTEGER
		MAX-ACCESS	read-only
		STATUS		current
		DESCRIPTION
			"The port used for the outbound portion of a tandem
			call, if applicable."

	::= { sessionStatusInactiveEntry 62 }

	sessionStatusInactiveTandemTimeslot	OBJECT-TYPE
		SYNTAX		INTEGER
		MAX-ACCESS	read-only
		STATUS		current
		DESCRIPTION
			"The timeslot used for the outbound portion of a
			tandem call, if applicable."

	::= { sessionStatusInactiveEntry 63 }

	sessionStatusInactiveCallClassArray	OBJECT-TYPE
		SYNTAX		OCTET STRING (SIZE (0..256))
		MAX-ACCESS	read-only
		STATUS		current
		DESCRIPTION
			"An array of octets representing the class of this
			call."

	::= { sessionStatusInactiveEntry 64 }

	sessionStatusInactiveCallClassLen	OBJECT-TYPE
		SYNTAX		INTEGER
		MAX-ACCESS	read-only
		STATUS		current
		DESCRIPTION
			"The number of octets in callClassArray."

	::= { sessionStatusInactiveEntry 65 }

	sessionStatusInactiveActualAuthMethod	OBJECT-TYPE
		SYNTAX		INTEGER {
				    radius(1),
				    local(2),
				    remote(3)
				}
		MAX-ACCESS	read-only
		STATUS		current
		DESCRIPTION
			"The actual authentication method which was used to
			gain access to services. Radius, Local, Remote."

	::= { sessionStatusInactiveEntry 66 }

	sessionStatusInactiveModemModulation	OBJECT-TYPE
		SYNTAX		INTEGER {
				    none(0),
				    unknown(1),
				    bell103(2),
				    bell208(3),
				    bell212(4),
				    v17(5),
				    v21(6),
				    v22(7),
				    v22bis(8),
				    v23(9),
				    v27(10),
				    v29(11),
				    v32(12),
				    v32bis(13),
				    v33(14),
				    v34(15),
				    vFC(16),
				    k56(17),
				    v90(18)
				}
		MAX-ACCESS	read-only
		STATUS		current
		DESCRIPTION
			"For modem sessions, the modulation protocol used, if
			any."

	::= { sessionStatusInactiveEntry 67 }

	sessionStatusInactiveModemErrorCorrection	OBJECT-TYPE
		SYNTAX		INTEGER {
				    none(0),
				    unknown(1),
				    mNP(2),
				    v42(3)
				}
		MAX-ACCESS	read-only
		STATUS		current
		DESCRIPTION
			"For modem sessions, the error correction protocol
			used, if any."

	::= { sessionStatusInactiveEntry 68 }

	sessionStatusInactiveModemDataCompression	OBJECT-TYPE
		SYNTAX		INTEGER {
				    none(0),
				    unknown(1),
				    mNP5(2),
				    v42bis(3)
				}
		MAX-ACCESS	read-only
		STATUS		current
		DESCRIPTION
			"For modem sessions, the data compression protocol
			used, if any."

	::= { sessionStatusInactiveEntry 69 }

	sessionStatusInactiveModemTxBlocks	OBJECT-TYPE
		SYNTAX		INTEGER
		MAX-ACCESS	read-only
		STATUS		current
		DESCRIPTION
			"For modem sessions, the number of blocks transmitted
			by the modem."

	::= { sessionStatusInactiveEntry 70 }

	sessionStatusInactiveModemRetransmits	OBJECT-TYPE
		SYNTAX		INTEGER
		MAX-ACCESS	read-only
		STATUS		current
		DESCRIPTION
			"For modem sessions, the number of packets
			retransmitted by the modem."

	::= { sessionStatusInactiveEntry 71 }

	sessionStatusInactiveModemSNR	OBJECT-TYPE
		SYNTAX		INTEGER
		MAX-ACCESS	read-only
		STATUS		current
		DESCRIPTION
			"For modem sessions, the Signal-to-Noise Ratio
			measured at the start of the connection. This value is
			given in dB."

	::= { sessionStatusInactiveEntry 72 }

	sessionStatusInactiveModemLocalRetrains	OBJECT-TYPE
		SYNTAX		INTEGER
		MAX-ACCESS	read-only
		STATUS		current
		DESCRIPTION
			"For modem sessions, the number of retrain requests
			sent by the local modem."

	::= { sessionStatusInactiveEntry 73 }

	sessionStatusInactiveModemRemoteRetrains	OBJECT-TYPE
		SYNTAX		INTEGER
		MAX-ACCESS	read-only
		STATUS		current
		DESCRIPTION
			"For modem sessions, the number of retrain requests
			sent by the remote modem."

	::= { sessionStatusInactiveEntry 74 }

	sessionStatusInactiveModemLocalRenegotiations	OBJECT-TYPE
		SYNTAX		INTEGER
		MAX-ACCESS	read-only
		STATUS		current
		DESCRIPTION
			"For modem sessions, the number of rate renegotiation
			requests sent by the local modem."

	::= { sessionStatusInactiveEntry 75 }

	sessionStatusInactiveModemRemoteRenegotiations	OBJECT-TYPE
		SYNTAX		INTEGER
		MAX-ACCESS	read-only
		STATUS		current
		DESCRIPTION
			"For modem sessions, the number of rate renegotiation
			requests sent by the remote modem."

	::= { sessionStatusInactiveEntry 76 }

	sessionStatusInactiveModemReceiveLineLevel	OBJECT-TYPE
		SYNTAX		INTEGER
		MAX-ACCESS	read-only
		STATUS		current
		DESCRIPTION
			"For modem sessions, the receive line signal level.
			This value is given in dB."

	::= { sessionStatusInactiveEntry 77 }

	sessionStatusInactiveRemoteIPXNetwork	OBJECT-TYPE
		SYNTAX		INTEGER
		MAX-ACCESS	read-only
		STATUS		current
		DESCRIPTION
			"The IPX network assigned to the dial-up user."

	::= { sessionStatusInactiveEntry 78 }

	sessionStatusInactiveRemoteIPXNode	OBJECT-TYPE
		SYNTAX		DisplayString (SIZE (0..16))
		MAX-ACCESS	read-only
		STATUS		current
		DESCRIPTION
			"The IPX Node number assisgned to the dial-up user"

	::= { sessionStatusInactiveEntry 79 }

	sessionStatusInactiveCleartcpRemoteIP	OBJECT-TYPE
		SYNTAX		IpAddress
		MAX-ACCESS	read-only
		STATUS		current
		DESCRIPTION
			"Cleartcp Remote IP Address"

	::= { sessionStatusInactiveEntry 80 }

	sessionStatusInactiveCleartcpRemotePort	OBJECT-TYPE
		SYNTAX		INTEGER
		MAX-ACCESS	read-only
		STATUS		current
		DESCRIPTION
			"Cleartcp Remote Port Address"

	::= { sessionStatusInactiveEntry 81 }

	sessionStatusInactiveTunnelId	OBJECT-TYPE
		SYNTAX		INTEGER
		MAX-ACCESS	read-only
		STATUS		current
		DESCRIPTION
			"Tunnel Id"

	::= { sessionStatusInactiveEntry 82 }

	sessionStatusInactiveLinkId	OBJECT-TYPE
		SYNTAX		INTEGER
		MAX-ACCESS	read-only
		STATUS		current
		DESCRIPTION
			"Link Id"

	::= { sessionStatusInactiveEntry 83 }


	sessionStatusReverseTable	OBJECT-TYPE
		SYNTAX		SEQUENCE OF SessionStatusReverseEntry
		MAX-ACCESS	not-accessible
		STATUS		current
		DESCRIPTION
			"Session Status Reverse Configuration Information."

	::= { aptis-monitoring 106 }

	sessionStatusReverseEntry	OBJECT-TYPE
		SYNTAX		SessionStatusReverseEntry
		MAX-ACCESS	not-accessible
		STATUS		current
		DESCRIPTION
			"This is the structure of entries in the
			 sessionStatusReverseTable."
		INDEX		{ sessionStatusReverseSessionID }
	::= { sessionStatusReverseTable 1 }

	SessionStatusReverseEntry ::= SEQUENCE {
		sessionStatusReverseSessionID	INTEGER,
		sessionStatusReverseState	INTEGER,
		sessionStatusReversePermanentFlag INTEGER,
		sessionStatusReverseVpopId	INTEGER,
		sessionStatusReverseName	DisplayString,
		sessionStatusReverseRemoteIP	IpAddress,
		sessionStatusReverseRemoteIPMask IpAddress,
		sessionStatusReverseLocalIP	IpAddress,
		sessionStatusReverseLocalIPMask	IpAddress,
		sessionStatusReverseLinkService	INTEGER,
		sessionStatusReverseServiceMode	INTEGER,
		sessionStatusReverseStartTime	INTEGER,
		sessionStatusReverseStopTime	INTEGER,
		sessionStatusReverseTimeOfModemSync INTEGER,
		sessionStatusReverseTimeOfService INTEGER,
		sessionStatusReverseTerminatingComponent INTEGER,
		sessionStatusReverseTerminationCause INTEGER,
		sessionStatusReverseLastComponent INTEGER,
		sessionStatusReverseLayer1Slot	INTEGER,
		sessionStatusReverseLayer2Slot	INTEGER,
		sessionStatusReverseCalledNumber DisplayString,
		sessionStatusReverseCallingNumber DisplayString,
		sessionStatusReverseOriginateMode INTEGER,
		sessionStatusReverseOctetsIn	INTEGER,
		sessionStatusReverseOctetsOut	INTEGER,
		sessionStatusReversePacketsIn	INTEGER,
		sessionStatusReversePacketsOut	INTEGER,
		sessionStatusReverseMultiLinkId	INTEGER,
		sessionStatusReversePort	INTEGER,
		sessionStatusReverseTimeslot	INTEGER,
		sessionStatusReverseLinkCount	INTEGER,
		sessionStatusReverseTxStartDataRate INTEGER,
		sessionStatusReverseRxStartDataRate INTEGER,
		sessionStatusReverseTxEndDataRate INTEGER,
		sessionStatusReverseRxEndDataRate INTEGER,
		sessionStatusReverseTxMinDataRate INTEGER,
		sessionStatusReverseRxMinDataRate INTEGER,
		sessionStatusReverseTxMaxDataRate INTEGER,
		sessionStatusReverseRxMaxDataRate INTEGER,
		sessionStatusReverseIop		INTEGER,
		sessionStatusReverseDmm		INTEGER,
		sessionStatusReversePack	INTEGER,
		sessionStatusReverseDevice	INTEGER,
		sessionStatusReverseTdmStream	INTEGER,
		sessionStatusReverseTdmTimeSlot	INTEGER,
		sessionStatusReverseTerminationReason DisplayString,
		sessionStatusReverseDuration	INTEGER,
		sessionStatusReverseDurationHMS	DisplayString,
		sessionStatusReverseSs7SessionId DisplayString,
		sessionStatusReverseModemNumber	INTEGER,
		sessionStatusReverseTunnelType	INTEGER,
		sessionStatusReverseTunnelMediumType INTEGER,
		sessionStatusReverseTunnelServerAddress IpAddress,
		sessionStatusReverseCallClass	INTEGER,
		sessionStatusReverseTandemPort	INTEGER,
		sessionStatusReverseTandemTimeslot INTEGER,
		sessionStatusReverseCallClassArray OCTET STRING,
		sessionStatusReverseCallClassLen INTEGER,
		sessionStatusReverseActualAuthMethod INTEGER,
		sessionStatusReverseModemModulation INTEGER,
		sessionStatusReverseModemErrorCorrection INTEGER,
		sessionStatusReverseModemDataCompression INTEGER,
		sessionStatusReverseModemTxBlocks INTEGER,
		sessionStatusReverseModemRetransmits INTEGER,
		sessionStatusReverseModemSNR	INTEGER,
		sessionStatusReverseModemLocalRetrains INTEGER,
		sessionStatusReverseModemRemoteRetrains INTEGER,
		sessionStatusReverseModemLocalRenegotiations INTEGER,
		sessionStatusReverseModemRemoteRenegotiations INTEGER,
		sessionStatusReverseModemReceiveLineLevel INTEGER,
		sessionStatusReverseRemoteIPXNetwork INTEGER,
		sessionStatusReverseRemoteIPXNode DisplayString,
		sessionStatusReverseCleartcpRemoteIP IpAddress,
		sessionStatusReverseCleartcpRemotePort INTEGER,
		sessionStatusReverseTunnelId	INTEGER,
		sessionStatusReverseLinkId	INTEGER
	}

	sessionStatusReverseSessionID	OBJECT-TYPE
		SYNTAX		INTEGER
		MAX-ACCESS	read-only
		STATUS		current
		DESCRIPTION
			"The serial number of this session, a unique number
			for this boot era. When combined with the value of
			BootEra, provides a session number that is unique for
			the life of the system. Note that these are very
			sparsely numbered."

	::= { sessionStatusReverseEntry 2 }

	sessionStatusReverseState	OBJECT-TYPE
		SYNTAX		INTEGER {
				    inactive(0),
				    active(1)
				}
		MAX-ACCESS	read-only
		STATUS		current
		DESCRIPTION
			"This variable indicates the state of this session."

	::= { sessionStatusReverseEntry 3 }

	sessionStatusReversePermanentFlag	OBJECT-TYPE
		SYNTAX		INTEGER {
				    unknown(0),
				    switched(1),
				    permanent(2)
				}
		MAX-ACCESS	read-only
		STATUS		current
		DESCRIPTION
			"This variable indicates whether this session is
			permanent(2), meaning a long-lasting locally
			administered session such as a Frame Relay PVC, or
			switched(1), meaning a short-lived session resulting
			from a switched call."

	::= { sessionStatusReverseEntry 10 }

	sessionStatusReverseVpopId	OBJECT-TYPE
		SYNTAX		INTEGER
		MAX-ACCESS	read-only
		STATUS		current
		DESCRIPTION
			"The identifier of the VPOP (administrative Group) to
			which the session belongs. A value of 0 indicates the
			default VPOP."

	::= { sessionStatusReverseEntry 11 }

	sessionStatusReverseName	OBJECT-TYPE
		SYNTAX		DisplayString (SIZE (0..68))
		MAX-ACCESS	read-only
		STATUS		current
		DESCRIPTION
			"The name of the connection peer for this session.
			During authentication of the session, this field may
			contain the name submitted by the peer. During this
			time, the value of timeOfService will be zero. When
			the value of timeOfService is nonzero, this field will
			contain a fully authenticated name."

	::= { sessionStatusReverseEntry 12 }

	sessionStatusReverseRemoteIP	OBJECT-TYPE
		SYNTAX		IpAddress
		MAX-ACCESS	read-only
		STATUS		current
		DESCRIPTION
			"The connection peer's IP address. If the link is
			numbered, then this is the address assigned to the
			other end of the link. If the link is not numbered,
			this may be the single IP address of the peer. For PPP
			connections, this is the result of IPNCP negotiation."

	::= { sessionStatusReverseEntry 13 }

	sessionStatusReverseRemoteIPMask	OBJECT-TYPE
		SYNTAX		IpAddress
		MAX-ACCESS	read-only
		STATUS		current
		DESCRIPTION
			"The connection peer's IP address mask, used in
			conjunction with remoteIP."

	::= { sessionStatusReverseEntry 14 }

	sessionStatusReverseLocalIP	OBJECT-TYPE
		SYNTAX		IpAddress
		MAX-ACCESS	read-only
		STATUS		current
		DESCRIPTION
			"The local IP address for this session. If the link is
			numbered, then this is the address assigned to the
			local end of the link. If the link is not numbered,
			this may be the primary IP address of the system. For
			PPP connections, this is the result of IPNCP
			negotiation."

	::= { sessionStatusReverseEntry 15 }

	sessionStatusReverseLocalIPMask	OBJECT-TYPE
		SYNTAX		IpAddress
		MAX-ACCESS	read-only
		STATUS		current
		DESCRIPTION
			"The local IP address mask for this session, used in
			conjunction with localIP."

	::= { sessionStatusReverseEntry 16 }

	sessionStatusReverseLinkService	OBJECT-TYPE
		SYNTAX		INTEGER {
				    unknown(0),
				    none(1),
				    other(2),
				    isdn56K(3),
				    isdn64K(4),
				    isdnV120(5),
				    isdnV110(6),
				    modemV32(7),
				    modemV34(8),
				    modemK56(9),
				    modemV90(10),
				    ethernet(11),
				    t1Trunk(12),
				    loopback(13),
				    hssi(14),
				    hub(15),
				    voice(16)
				}
		MAX-ACCESS	read-only
		STATUS		current
		DESCRIPTION
			"A description of which link technology is being used
			by the session."

	::= { sessionStatusReverseEntry 17 }

	sessionStatusReverseServiceMode	OBJECT-TYPE
		SYNTAX		INTEGER {
				    unknown(0),
				    none(1),
				    other(2),
				    ppp(3),
				    slip(4),
				    frameRelay(5),
				    ciscoHDLC(6),
				    terminalServer(7),
				    telnet(8),
				    rawTCP(9),
				    rlogin(10),
				    l2tp(11),
				    l2f(12),
				    trunk(13),
				    voice(14),
				    tandem(15),
				    hub(16),
				    ftp(17),
				    dvs(18),
				    fax(19),
				    atmp(20),
				    iptest(21)
				}
		MAX-ACCESS	read-only
		STATUS		current
		DESCRIPTION
			"A description of which session service is being used
			by the session."

	::= { sessionStatusReverseEntry 18 }

	sessionStatusReverseStartTime	OBJECT-TYPE
		SYNTAX		INTEGER
		MAX-ACCESS	read-only
		STATUS		current
		DESCRIPTION
			"The time that this session began, in seconds since
			the system booted."

	::= { sessionStatusReverseEntry 19 }

	sessionStatusReverseStopTime	OBJECT-TYPE
		SYNTAX		INTEGER
		MAX-ACCESS	read-only
		STATUS		current
		DESCRIPTION
			"The time that this session stopped, in seconds since
			the system booted. This variable is only meaningful
			for sessions having the state inactive(0)."

	::= { sessionStatusReverseEntry 20 }

	sessionStatusReverseTimeOfModemSync	OBJECT-TYPE
		SYNTAX		INTEGER
		MAX-ACCESS	read-only
		STATUS		current
		DESCRIPTION
			"The time at which the modem synchronization
			completed, in seconds since the system booted."

	::= { sessionStatusReverseEntry 21 }

	sessionStatusReverseTimeOfService	OBJECT-TYPE
		SYNTAX		INTEGER
		MAX-ACCESS	read-only
		STATUS		current
		DESCRIPTION
			"The time that this session entered its first
			negotiated or configured service, in seconds since the
			system booted. For example, for a session with
			serviceMode PPP, the time at which LCP and IPCP
			negotiations completed and the session was ready to
			forward user data."

	::= { sessionStatusReverseEntry 22 }

	sessionStatusReverseTerminatingComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The component which initiated termination of this
			session. In cases where there are multiple causes of
			session termination, only the first cause detected is
			reported. This variable is only meaningful for
			sessions having the state inactive(0)."

	::= { sessionStatusReverseEntry 23 }

	sessionStatusReverseTerminationCause	OBJECT-TYPE
		SYNTAX		INTEGER
		MAX-ACCESS	read-only
		STATUS		current
		DESCRIPTION
			"The cause which initiated termination of this
			session. In cases where there are multiple causes of
			session termination, only the first cause detected is
			reported. This variable is only meaningful for
			sessions having the state inactive(0)."

	::= { sessionStatusReverseEntry 24 }

	sessionStatusReverseLastComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The last component which was connected in this
			session."

	::= { sessionStatusReverseEntry 25 }

	sessionStatusReverseLayer1Slot	OBJECT-TYPE
		SYNTAX		INTEGER (1..18)
		MAX-ACCESS	read-only
		STATUS		current
		DESCRIPTION
			"The slot where the physical layer of this session is
			terminated."

	::= { sessionStatusReverseEntry 26 }

	sessionStatusReverseLayer2Slot	OBJECT-TYPE
		SYNTAX		INTEGER (1..18)
		MAX-ACCESS	read-only
		STATUS		current
		DESCRIPTION
			"The slot where the data link portion of this session
			is terminated"

	::= { sessionStatusReverseEntry 27 }

	sessionStatusReverseCalledNumber	OBJECT-TYPE
		SYNTAX		DisplayString (SIZE (0..17))
		MAX-ACCESS	read-only
		STATUS		current
		DESCRIPTION
			"16 digit number of called station (if available)"

	::= { sessionStatusReverseEntry 28 }

	sessionStatusReverseCallingNumber	OBJECT-TYPE
		SYNTAX		DisplayString (SIZE (0..17))
		MAX-ACCESS	read-only
		STATUS		current
		DESCRIPTION
			"16 digit number of calling station (if available)"

	::= { sessionStatusReverseEntry 29 }

	sessionStatusReverseOriginateMode	OBJECT-TYPE
		SYNTAX		INTEGER {
				    answer(0),
				    originate(1)
				}
		MAX-ACCESS	read-only
		STATUS		current
		DESCRIPTION
			"The direction of the physical layer call associated
			with this session"

	::= { sessionStatusReverseEntry 30 }

	sessionStatusReverseOctetsIn	OBJECT-TYPE
		SYNTAX		INTEGER
		MAX-ACCESS	read-only
		STATUS		current
		DESCRIPTION
			"The number of octets received from the remote user.
			This value will be zero until a session is
			terminated."

	::= { sessionStatusReverseEntry 31 }

	sessionStatusReverseOctetsOut	OBJECT-TYPE
		SYNTAX		INTEGER
		MAX-ACCESS	read-only
		STATUS		current
		DESCRIPTION
			"The number of octets sent to the remote user. This
			value will be zero until a session is terminated."

	::= { sessionStatusReverseEntry 32 }

	sessionStatusReversePacketsIn	OBJECT-TYPE
		SYNTAX		INTEGER
		MAX-ACCESS	read-only
		STATUS		current
		DESCRIPTION
			"The number of packets received from the remote user.
			This value will be zero until a session is
			terminated."

	::= { sessionStatusReverseEntry 33 }

	sessionStatusReversePacketsOut	OBJECT-TYPE
		SYNTAX		INTEGER
		MAX-ACCESS	read-only
		STATUS		current
		DESCRIPTION
			"The number of packets sent to the remote user. This
			value will be zero until a session is terminated."

	::= { sessionStatusReverseEntry 34 }

	sessionStatusReverseMultiLinkId	OBJECT-TYPE
		SYNTAX		INTEGER
		MAX-ACCESS	read-only
		STATUS		current
		DESCRIPTION
			"The multi-link identifier value for PPP calls where
			the multi-link protocol was negotiated."

	::= { sessionStatusReverseEntry 35 }

	sessionStatusReversePort	OBJECT-TYPE
		SYNTAX		INTEGER
		MAX-ACCESS	read-only
		STATUS		current
		DESCRIPTION
			"The number of the DS1 for this session, relative to
			layer1Slot."

	::= { sessionStatusReverseEntry 36 }

	sessionStatusReverseTimeslot	OBJECT-TYPE
		SYNTAX		INTEGER
		MAX-ACCESS	read-only
		STATUS		current
		DESCRIPTION
			"The number of the DS0 for this session, relative to
			port."

	::= { sessionStatusReverseEntry 37 }

	sessionStatusReverseLinkCount	OBJECT-TYPE
		SYNTAX		INTEGER
		MAX-ACCESS	read-only
		STATUS		current
		DESCRIPTION
			"The number of sessions sharing the same remote IP
			address as this session. After a session is
			terminated, this value will represent the number of
			sessions at the time of termination."

	::= { sessionStatusReverseEntry 38 }

	sessionStatusReverseTxStartDataRate	OBJECT-TYPE
		SYNTAX		INTEGER
		MAX-ACCESS	read-only
		STATUS		current
		DESCRIPTION
			"The transmit DCE data rate for this session. In the
			case of modem sessions, this will be the DCE rate
			reported as a result of initial modem negotiation, and
			may not track rate chanes during the call. For ISDN
			sessions, this will be the actual data service rate of
			the call. For Frame Relay sessions, this will be the
			nominal speed of the Frame Relay Physical Interface,
			even though multiple sessions may be sharing that
			Physical Interface. For other sessions, this will be
			the nominal speed of the physical interface. In no
			case should this be interepreted as a
			Quality-of-Service guarantee, or as the current line
			utilization or effective bandwidth on the interface.
			Note also that in the case of PPP multilink, this
			specifies the rate of only this link in the bundle,
			and not the aggregate rate of all links in the
			bundle."

	::= { sessionStatusReverseEntry 39 }

	sessionStatusReverseRxStartDataRate	OBJECT-TYPE
		SYNTAX		INTEGER
		MAX-ACCESS	read-only
		STATUS		current
		DESCRIPTION
			"The receive data rate for this session. In the case
			of modem sessions, this will be the DCE rate reported
			as a result of initial modem negotiation, and may not
			track rate chanes during the call. For ISDN sessions,
			this will be the actual data service rate of the call.
			For Frame Relay sessions, this will be the nominal
			speed of the Frame Relay Physical Interface, even
			though multiple sessions may be sharing that Physical
			Interface. For other sessions, this will be the
			nominal speed of the physical interface. In no case
			should this be interepreted as a Quality-of-Service
			guarantee, or as the current line utilization or
			effective bandwidth on the interface. Note also that
			in the case of PPP multilink, this specifies the rate
			of only this link in the bundle, and not the aggregate
			rate of all links in the bundle."

	::= { sessionStatusReverseEntry 40 }

	sessionStatusReverseTxEndDataRate	OBJECT-TYPE
		SYNTAX		INTEGER
		MAX-ACCESS	read-only
		STATUS		current
		DESCRIPTION
			"The transmit data rate at the end of a modem
			session."

	::= { sessionStatusReverseEntry 41 }

	sessionStatusReverseRxEndDataRate	OBJECT-TYPE
		SYNTAX		INTEGER
		MAX-ACCESS	read-only
		STATUS		current
		DESCRIPTION
			"The receive data rate at the end of a modem session."

	::= { sessionStatusReverseEntry 42 }

	sessionStatusReverseTxMinDataRate	OBJECT-TYPE
		SYNTAX		INTEGER
		MAX-ACCESS	read-only
		STATUS		current
		DESCRIPTION
			"The minimum transmit data rate during a modem
			session."

	::= { sessionStatusReverseEntry 43 }

	sessionStatusReverseRxMinDataRate	OBJECT-TYPE
		SYNTAX		INTEGER
		MAX-ACCESS	read-only
		STATUS		current
		DESCRIPTION
			"The minimum receive data rate during a modem
			session."

	::= { sessionStatusReverseEntry 44 }

	sessionStatusReverseTxMaxDataRate	OBJECT-TYPE
		SYNTAX		INTEGER
		MAX-ACCESS	read-only
		STATUS		current
		DESCRIPTION
			"The maximum transmit data rate during a modem
			session."

	::= { sessionStatusReverseEntry 45 }

	sessionStatusReverseRxMaxDataRate	OBJECT-TYPE
		SYNTAX		INTEGER
		MAX-ACCESS	read-only
		STATUS		current
		DESCRIPTION
			"The maximum receive data rate during a modem
			session."

	::= { sessionStatusReverseEntry 46 }

	sessionStatusReverseIop	OBJECT-TYPE
		SYNTAX		INTEGER
		MAX-ACCESS	read-only
		STATUS		current
		DESCRIPTION
			"The I/O processor where this session is terminated."

	::= { sessionStatusReverseEntry 47 }

	sessionStatusReverseDmm	OBJECT-TYPE
		SYNTAX		INTEGER
		MAX-ACCESS	read-only
		STATUS		current
		DESCRIPTION
			"The Digital Modem Module where this session is
			terminated."

	::= { sessionStatusReverseEntry 48 }

	sessionStatusReversePack	OBJECT-TYPE
		SYNTAX		INTEGER
		MAX-ACCESS	read-only
		STATUS		current
		DESCRIPTION
			"The integrated circuit pack where this session is
			terminated."

	::= { sessionStatusReverseEntry 49 }

	sessionStatusReverseDevice	OBJECT-TYPE
		SYNTAX		INTEGER
		MAX-ACCESS	read-only
		STATUS		current
		DESCRIPTION
			"The modem/hdlc where this session is terminated."

	::= { sessionStatusReverseEntry 50 }

	sessionStatusReverseTdmStream	OBJECT-TYPE
		SYNTAX		INTEGER
		MAX-ACCESS	read-only
		STATUS		current
		DESCRIPTION
			"The TDM highway stream associated with this session."

	::= { sessionStatusReverseEntry 51 }

	sessionStatusReverseTdmTimeSlot	OBJECT-TYPE
		SYNTAX		INTEGER
		MAX-ACCESS	read-only
		STATUS		current
		DESCRIPTION
			"The TDM highway time-slot associated with this
			session."

	::= { sessionStatusReverseEntry 52 }

	sessionStatusReverseTerminationReason	OBJECT-TYPE
		SYNTAX		DisplayString (SIZE (0..50))
		MAX-ACCESS	read-only
		STATUS		current
		DESCRIPTION
			"A textual description of the cause which initiated
			termination of this session. In cases where there are
			multiple causes of session termination, only the first
			cause detected is reported."

	::= { sessionStatusReverseEntry 53 }

	sessionStatusReverseDuration	OBJECT-TYPE
		SYNTAX		INTEGER
		MAX-ACCESS	read-only
		STATUS		current
		DESCRIPTION
			"The number of seconds this session has been active."

	::= { sessionStatusReverseEntry 54 }

	sessionStatusReverseDurationHMS	OBJECT-TYPE
		SYNTAX		DisplayString (SIZE (0..20))
		MAX-ACCESS	read-only
		STATUS		current
		DESCRIPTION
			"The length of time this session has been active,
			expressed in DDD HH:MM:SSS.000."

	::= { sessionStatusReverseEntry 55 }

	sessionStatusReverseSs7SessionId	OBJECT-TYPE
		SYNTAX		DisplayString (SIZE (0..41))
		MAX-ACCESS	read-only
		STATUS		current
		DESCRIPTION
			"A uniquie identifier for this session within the ss7
			Network. If this call was not originated using ss7
			signalling, this string will be null."

	::= { sessionStatusReverseEntry 56 }

	sessionStatusReverseModemNumber	OBJECT-TYPE
		SYNTAX		INTEGER
		MAX-ACCESS	read-only
		STATUS		current
		DESCRIPTION
			"The individual modem where this session is
			terminated, numbered from one to the maximum number of
			modems on the slot card."

	::= { sessionStatusReverseEntry 57 }

	sessionStatusReverseTunnelType	OBJECT-TYPE
		SYNTAX		INTEGER {
				    unknown(0),
				    none(1),
				    other(2),
				    l2f(3),
				    l2tp(4),
				    dvs(5),
				    atmp(6)
				}
		MAX-ACCESS	read-only
		STATUS		current
		DESCRIPTION
			"The tunneling protocol being used for this session."

	::= { sessionStatusReverseEntry 58 }

	sessionStatusReverseTunnelMediumType	OBJECT-TYPE
		SYNTAX		INTEGER {
				    unknown(0),
				    none(1),
				    other(2),
				    ip(3)
				}
		MAX-ACCESS	read-only
		STATUS		current
		DESCRIPTION
			"The tunneling medium protocol being used for this
			session."

	::= { sessionStatusReverseEntry 59 }

	sessionStatusReverseTunnelServerAddress	OBJECT-TYPE
		SYNTAX		IpAddress
		MAX-ACCESS	read-only
		STATUS		current
		DESCRIPTION
			"The IP address of the remote machine terminating the
			tunnel for this session."

	::= { sessionStatusReverseEntry 60 }

	sessionStatusReverseCallClass	OBJECT-TYPE
		SYNTAX		INTEGER
		MAX-ACCESS	read-only
		STATUS		current
		DESCRIPTION
			"The class of this call."

	::= { sessionStatusReverseEntry 61 }

	sessionStatusReverseTandemPort	OBJECT-TYPE
		SYNTAX		INTEGER
		MAX-ACCESS	read-only
		STATUS		current
		DESCRIPTION
			"The port used for the outbound portion of a tandem
			call, if applicable."

	::= { sessionStatusReverseEntry 62 }

	sessionStatusReverseTandemTimeslot	OBJECT-TYPE
		SYNTAX		INTEGER
		MAX-ACCESS	read-only
		STATUS		current
		DESCRIPTION
			"The timeslot used for the outbound portion of a
			tandem call, if applicable."

	::= { sessionStatusReverseEntry 63 }

	sessionStatusReverseCallClassArray	OBJECT-TYPE
		SYNTAX		OCTET STRING (SIZE (0..256))
		MAX-ACCESS	read-only
		STATUS		current
		DESCRIPTION
			"An array of octets representing the class of this
			call."

	::= { sessionStatusReverseEntry 64 }

	sessionStatusReverseCallClassLen	OBJECT-TYPE
		SYNTAX		INTEGER
		MAX-ACCESS	read-only
		STATUS		current
		DESCRIPTION
			"The number of octets in callClassArray."

	::= { sessionStatusReverseEntry 65 }

	sessionStatusReverseActualAuthMethod	OBJECT-TYPE
		SYNTAX		INTEGER {
				    radius(1),
				    local(2),
				    remote(3)
				}
		MAX-ACCESS	read-only
		STATUS		current
		DESCRIPTION
			"The actual authentication method which was used to
			gain access to services. Radius, Local, Remote."

	::= { sessionStatusReverseEntry 66 }

	sessionStatusReverseModemModulation	OBJECT-TYPE
		SYNTAX		INTEGER {
				    none(0),
				    unknown(1),
				    bell103(2),
				    bell208(3),
				    bell212(4),
				    v17(5),
				    v21(6),
				    v22(7),
				    v22bis(8),
				    v23(9),
				    v27(10),
				    v29(11),
				    v32(12),
				    v32bis(13),
				    v33(14),
				    v34(15),
				    vFC(16),
				    k56(17),
				    v90(18)
				}
		MAX-ACCESS	read-only
		STATUS		current
		DESCRIPTION
			"For modem sessions, the modulation protocol used, if
			any."

	::= { sessionStatusReverseEntry 67 }

	sessionStatusReverseModemErrorCorrection	OBJECT-TYPE
		SYNTAX		INTEGER {
				    none(0),
				    unknown(1),
				    mNP(2),
				    v42(3)
				}
		MAX-ACCESS	read-only
		STATUS		current
		DESCRIPTION
			"For modem sessions, the error correction protocol
			used, if any."

	::= { sessionStatusReverseEntry 68 }

	sessionStatusReverseModemDataCompression	OBJECT-TYPE
		SYNTAX		INTEGER {
				    none(0),
				    unknown(1),
				    mNP5(2),
				    v42bis(3)
				}
		MAX-ACCESS	read-only
		STATUS		current
		DESCRIPTION
			"For modem sessions, the data compression protocol
			used, if any."

	::= { sessionStatusReverseEntry 69 }

	sessionStatusReverseModemTxBlocks	OBJECT-TYPE
		SYNTAX		INTEGER
		MAX-ACCESS	read-only
		STATUS		current
		DESCRIPTION
			"For modem sessions, the number of blocks transmitted
			by the modem."

	::= { sessionStatusReverseEntry 70 }

	sessionStatusReverseModemRetransmits	OBJECT-TYPE
		SYNTAX		INTEGER
		MAX-ACCESS	read-only
		STATUS		current
		DESCRIPTION
			"For modem sessions, the number of packets
			retransmitted by the modem."

	::= { sessionStatusReverseEntry 71 }

	sessionStatusReverseModemSNR	OBJECT-TYPE
		SYNTAX		INTEGER
		MAX-ACCESS	read-only
		STATUS		current
		DESCRIPTION
			"For modem sessions, the Signal-to-Noise Ratio
			measured at the start of the connection. This value is
			given in dB."

	::= { sessionStatusReverseEntry 72 }

	sessionStatusReverseModemLocalRetrains	OBJECT-TYPE
		SYNTAX		INTEGER
		MAX-ACCESS	read-only
		STATUS		current
		DESCRIPTION
			"For modem sessions, the number of retrain requests
			sent by the local modem."

	::= { sessionStatusReverseEntry 73 }

	sessionStatusReverseModemRemoteRetrains	OBJECT-TYPE
		SYNTAX		INTEGER
		MAX-ACCESS	read-only
		STATUS		current
		DESCRIPTION
			"For modem sessions, the number of retrain requests
			sent by the remote modem."

	::= { sessionStatusReverseEntry 74 }

	sessionStatusReverseModemLocalRenegotiations	OBJECT-TYPE
		SYNTAX		INTEGER
		MAX-ACCESS	read-only
		STATUS		current
		DESCRIPTION
			"For modem sessions, the number of rate renegotiation
			requests sent by the local modem."

	::= { sessionStatusReverseEntry 75 }

	sessionStatusReverseModemRemoteRenegotiations	OBJECT-TYPE
		SYNTAX		INTEGER
		MAX-ACCESS	read-only
		STATUS		current
		DESCRIPTION
			"For modem sessions, the number of rate renegotiation
			requests sent by the remote modem."

	::= { sessionStatusReverseEntry 76 }

	sessionStatusReverseModemReceiveLineLevel	OBJECT-TYPE
		SYNTAX		INTEGER
		MAX-ACCESS	read-only
		STATUS		current
		DESCRIPTION
			"For modem sessions, the receive line signal level.
			This value is given in dB."

	::= { sessionStatusReverseEntry 77 }

	sessionStatusReverseRemoteIPXNetwork	OBJECT-TYPE
		SYNTAX		INTEGER
		MAX-ACCESS	read-only
		STATUS		current
		DESCRIPTION
			"The IPX network assigned to the dial-up user."

	::= { sessionStatusReverseEntry 78 }

	sessionStatusReverseRemoteIPXNode	OBJECT-TYPE
		SYNTAX		DisplayString (SIZE (0..16))
		MAX-ACCESS	read-only
		STATUS		current
		DESCRIPTION
			"The IPX Node number assisgned to the dial-up user"

	::= { sessionStatusReverseEntry 79 }

	sessionStatusReverseCleartcpRemoteIP	OBJECT-TYPE
		SYNTAX		IpAddress
		MAX-ACCESS	read-only
		STATUS		current
		DESCRIPTION
			"Cleartcp Remote IP Address"

	::= { sessionStatusReverseEntry 80 }

	sessionStatusReverseCleartcpRemotePort	OBJECT-TYPE
		SYNTAX		INTEGER
		MAX-ACCESS	read-only
		STATUS		current
		DESCRIPTION
			"Cleartcp Remote Port Address"

	::= { sessionStatusReverseEntry 81 }

	sessionStatusReverseTunnelId	OBJECT-TYPE
		SYNTAX		INTEGER
		MAX-ACCESS	read-only
		STATUS		current
		DESCRIPTION
			"Tunnel Id"

	::= { sessionStatusReverseEntry 82 }

	sessionStatusReverseLinkId	OBJECT-TYPE
		SYNTAX		INTEGER
		MAX-ACCESS	read-only
		STATUS		current
		DESCRIPTION
			"Link Id"

	::= { sessionStatusReverseEntry 83 }


	sessionComponentsTable	OBJECT-TYPE
		SYNTAX		SEQUENCE OF SessionComponentsEntry
		MAX-ACCESS	not-accessible
		STATUS		current
		DESCRIPTION
			"Session Components Information."

	::= { aptis-monitoring 213 }

	sessionComponentsEntry	OBJECT-TYPE
		SYNTAX		SessionComponentsEntry
		MAX-ACCESS	not-accessible
		STATUS		current
		DESCRIPTION
			"This is the structure of entries in the
			 sessionComponentsTable."
		INDEX		{ sessionComponentsSessionIndex, sessionComponentsIndex }
	::= { sessionComponentsTable 1 }

	SessionComponentsEntry ::= SEQUENCE {
		sessionComponentsSessionIndex	INTEGER,
		sessionComponentsIndex		INTEGER,
		sessionComponentsComponentType	INTEGER,
		sessionComponentsComponentState	INTEGER,
		sessionComponentsStatHandle	INTEGER
	}

	sessionComponentsSessionIndex	OBJECT-TYPE
		SYNTAX		INTEGER
		MAX-ACCESS	read-only
		STATUS		current
		DESCRIPTION
			"The serial number of the session to which this
			component belongs."

	::= { sessionComponentsEntry 1 }

	sessionComponentsIndex	OBJECT-TYPE
		SYNTAX		INTEGER
		MAX-ACCESS	read-only
		STATUS		current
		DESCRIPTION
			"The ordinal number representing the relative location
			of this component in relation to other components
			within a session."

	::= { sessionComponentsEntry 2 }

	sessionComponentsComponentType	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"A component participating in the session."

	::= { sessionComponentsEntry 3 }

	sessionComponentsComponentState	OBJECT-TYPE
		SYNTAX		INTEGER
		MAX-ACCESS	read-only
		STATUS		current
		DESCRIPTION
			"A number indicating the current state of the
			component participating in the session. Note that this
			is really an enum with different values, depending
			upon which component is being reported."

	::= { sessionComponentsEntry 4 }

	sessionComponentsStatHandle	OBJECT-TYPE
		SYNTAX		INTEGER
		MAX-ACCESS	read-only
		STATUS		current
		DESCRIPTION
			"A number which may be used to retrieve the statistics
			for this component."

	::= { sessionComponentsEntry 5 }


	sessionTraceTable	OBJECT-TYPE
		SYNTAX		SEQUENCE OF SessionTraceEntry
		MAX-ACCESS	not-accessible
		STATUS		current
		DESCRIPTION
			"Session Trace Configuration Information."

	::= { aptis-monitoring 214 }

	sessionTraceEntry	OBJECT-TYPE
		SYNTAX		SessionTraceEntry
		MAX-ACCESS	not-accessible
		STATUS		current
		DESCRIPTION
			"This is the structure of entries in the
			 sessionTraceTable."
		INDEX		{ sessionTraceSessionIndex, sessionTraceIndex }
	::= { sessionTraceTable 1 }

	SessionTraceEntry ::= SEQUENCE {
		sessionTraceSessionIndex	INTEGER,
		sessionTraceIndex		INTEGER,
		sessionTraceAbsoluteTimeStamp	INTEGER,
		sessionTraceRelativeTimeStamp	INTEGER,
		sessionTraceLogEntry		DisplayString
	}

	sessionTraceSessionIndex	OBJECT-TYPE
		SYNTAX		INTEGER
		MAX-ACCESS	read-only
		STATUS		current
		DESCRIPTION
			"The serial number of the session to which this
			component belongs."

	::= { sessionTraceEntry 1 }

	sessionTraceIndex	OBJECT-TYPE
		SYNTAX		INTEGER
		MAX-ACCESS	read-only
		STATUS		current
		DESCRIPTION
			"The internal reference number for this log entry."

	::= { sessionTraceEntry 2 }

	sessionTraceAbsoluteTimeStamp	OBJECT-TYPE
		SYNTAX		INTEGER
		MAX-ACCESS	read-only
		STATUS		current
		DESCRIPTION
			"The time that this event occurred, in milliseconds
			relative to SysUpTime."

	::= { sessionTraceEntry 3 }

	sessionTraceRelativeTimeStamp	OBJECT-TYPE
		SYNTAX		INTEGER
		MAX-ACCESS	read-only
		STATUS		current
		DESCRIPTION
			"The time that this event occurred, in milliseconds
			relative to session beginning."

	::= { sessionTraceEntry 4 }

	sessionTraceLogEntry	OBJECT-TYPE
		SYNTAX		DisplayString (SIZE (0..128))
		MAX-ACCESS	read-only
		STATUS		current
		DESCRIPTION
			"An event occuring during the life of a session."

	::= { sessionTraceEntry 5 }


	sessionSlotsTable	OBJECT-TYPE
		SYNTAX		SEQUENCE OF SessionSlotsEntry
		MAX-ACCESS	not-accessible
		STATUS		current
		DESCRIPTION
			"The current usage of cvx slots in all active
			sessions."

	::= { aptis-monitoring 215 }

	sessionSlotsEntry	OBJECT-TYPE
		SYNTAX		SessionSlotsEntry
		MAX-ACCESS	not-accessible
		STATUS		current
		DESCRIPTION
			"This is the structure of entries in the
			 sessionSlotsTable."
		INDEX		{ sessionSlotsTrunkCount }
	::= { sessionSlotsTable 1 }

	SessionSlotsEntry ::= SEQUENCE {
		sessionSlotsTrunkCount		INTEGER,
		sessionSlotsSlot1Count		INTEGER,
		sessionSlotsSlot2Count		INTEGER,
		sessionSlotsSlot3Count		INTEGER,
		sessionSlotsSlot4Count		INTEGER,
		sessionSlotsSlot5Count		INTEGER,
		sessionSlotsSlot6Count		INTEGER,
		sessionSlotsSlot7Count		INTEGER,
		sessionSlotsSlot8Count		INTEGER,
		sessionSlotsSlot9Count		INTEGER,
		sessionSlotsSlot10Count		INTEGER,
		sessionSlotsSlot11Count		INTEGER,
		sessionSlotsSlot12Count		INTEGER,
		sessionSlotsSlot13Count		INTEGER,
		sessionSlotsSlot14Count		INTEGER,
		sessionSlotsSlot15Count		INTEGER,
		sessionSlotsSlot16Count		INTEGER,
		sessionSlotsSlot17Count		INTEGER,
		sessionSlotsSlot18Count		INTEGER
	}

	sessionSlotsTrunkCount	OBJECT-TYPE
		SYNTAX		INTEGER
		MAX-ACCESS	read-only
		STATUS		current
		DESCRIPTION
			"The number of sessions active on slot 1."

	::= { sessionSlotsEntry 1 }

	sessionSlotsSlot1Count	OBJECT-TYPE
		SYNTAX		INTEGER
		MAX-ACCESS	read-only
		STATUS		current
		DESCRIPTION
			"The number of sessions active on slot 1."

	::= { sessionSlotsEntry 2 }

	sessionSlotsSlot2Count	OBJECT-TYPE
		SYNTAX		INTEGER
		MAX-ACCESS	read-only
		STATUS		current
		DESCRIPTION
			"The number of sessions active on slot 2."

	::= { sessionSlotsEntry 3 }

	sessionSlotsSlot3Count	OBJECT-TYPE
		SYNTAX		INTEGER
		MAX-ACCESS	read-only
		STATUS		current
		DESCRIPTION
			"The number of sessions active on slot 3."

	::= { sessionSlotsEntry 4 }

	sessionSlotsSlot4Count	OBJECT-TYPE
		SYNTAX		INTEGER
		MAX-ACCESS	read-only
		STATUS		current
		DESCRIPTION
			"The number of sessions active on slot 4."

	::= { sessionSlotsEntry 5 }

	sessionSlotsSlot5Count	OBJECT-TYPE
		SYNTAX		INTEGER
		MAX-ACCESS	read-only
		STATUS		current
		DESCRIPTION
			"The number of sessions active on slot 5."

	::= { sessionSlotsEntry 6 }

	sessionSlotsSlot6Count	OBJECT-TYPE
		SYNTAX		INTEGER
		MAX-ACCESS	read-only
		STATUS		current
		DESCRIPTION
			"The number of sessions active on slot 6."

	::= { sessionSlotsEntry 7 }

	sessionSlotsSlot7Count	OBJECT-TYPE
		SYNTAX		INTEGER
		MAX-ACCESS	read-only
		STATUS		current
		DESCRIPTION
			"The number of sessions active on slot 7."

	::= { sessionSlotsEntry 8 }

	sessionSlotsSlot8Count	OBJECT-TYPE
		SYNTAX		INTEGER
		MAX-ACCESS	read-only
		STATUS		current
		DESCRIPTION
			"The number of sessions active on slot 8."

	::= { sessionSlotsEntry 9 }

	sessionSlotsSlot9Count	OBJECT-TYPE
		SYNTAX		INTEGER
		MAX-ACCESS	read-only
		STATUS		current
		DESCRIPTION
			"The number of sessions active on slot 9."

	::= { sessionSlotsEntry 10 }

	sessionSlotsSlot10Count	OBJECT-TYPE
		SYNTAX		INTEGER
		MAX-ACCESS	read-only
		STATUS		current
		DESCRIPTION
			"The number of sessions active on slot 10."

	::= { sessionSlotsEntry 11 }

	sessionSlotsSlot11Count	OBJECT-TYPE
		SYNTAX		INTEGER
		MAX-ACCESS	read-only
		STATUS		current
		DESCRIPTION
			"The number of sessions active on slot 11."

	::= { sessionSlotsEntry 12 }

	sessionSlotsSlot12Count	OBJECT-TYPE
		SYNTAX		INTEGER
		MAX-ACCESS	read-only
		STATUS		current
		DESCRIPTION
			"The number of sessions active on slot 12."

	::= { sessionSlotsEntry 13 }

	sessionSlotsSlot13Count	OBJECT-TYPE
		SYNTAX		INTEGER
		MAX-ACCESS	read-only
		STATUS		current
		DESCRIPTION
			"The number of sessions active on slot 13."

	::= { sessionSlotsEntry 14 }

	sessionSlotsSlot14Count	OBJECT-TYPE
		SYNTAX		INTEGER
		MAX-ACCESS	read-only
		STATUS		current
		DESCRIPTION
			"The number of sessions active on slot 14."

	::= { sessionSlotsEntry 15 }

	sessionSlotsSlot15Count	OBJECT-TYPE
		SYNTAX		INTEGER
		MAX-ACCESS	read-only
		STATUS		current
		DESCRIPTION
			"The number of sessions active on slot 15."

	::= { sessionSlotsEntry 16 }

	sessionSlotsSlot16Count	OBJECT-TYPE
		SYNTAX		INTEGER
		MAX-ACCESS	read-only
		STATUS		current
		DESCRIPTION
			"The number of sessions active on slot 16."

	::= { sessionSlotsEntry 17 }

	sessionSlotsSlot17Count	OBJECT-TYPE
		SYNTAX		INTEGER
		MAX-ACCESS	read-only
		STATUS		current
		DESCRIPTION
			"The number of sessions active on slot 17."

	::= { sessionSlotsEntry 18 }

	sessionSlotsSlot18Count	OBJECT-TYPE
		SYNTAX		INTEGER
		MAX-ACCESS	read-only
		STATUS		current
		DESCRIPTION
			"The number of sessions active on slot 18."

	::= { sessionSlotsEntry 19 }


	sessionSummaryTable	OBJECT-TYPE
		SYNTAX		SEQUENCE OF SessionSummaryEntry
		MAX-ACCESS	not-accessible
		STATUS		current
		DESCRIPTION
			"A summary of all session activity."

	::= { aptis-monitoring 216 }

	sessionSummaryEntry	OBJECT-TYPE
		SYNTAX		SessionSummaryEntry
		MAX-ACCESS	not-accessible
		STATUS		current
		DESCRIPTION
			"This is the structure of entries in the
			 sessionSummaryTable."
		INDEX		{ sessionSummaryActiveUnknown }
	::= { sessionSummaryTable 1 }

	SessionSummaryEntry ::= SEQUENCE {
		sessionSummaryActiveUnknown	INTEGER,
		sessionSummaryMaximumUnknown	INTEGER,
		sessionSummaryInactiveUnknown	INTEGER,
		sessionSummaryActiveNone	INTEGER,
		sessionSummaryMaximumNone	INTEGER,
		sessionSummaryInactiveNone	INTEGER,
		sessionSummaryActiveOther	INTEGER,
		sessionSummaryMaximumOther	INTEGER,
		sessionSummaryInactiveOther	INTEGER,
		sessionSummaryActivePpp		INTEGER,
		sessionSummaryMaximumPpp	INTEGER,
		sessionSummaryInactivePpp	INTEGER,
		sessionSummaryActiveSlip	INTEGER,
		sessionSummaryMaximumSlip	INTEGER,
		sessionSummaryInactiveSlip	INTEGER,
		sessionSummaryActiveFrameRelay	INTEGER,
		sessionSummaryMaximumFrameRelay	INTEGER,
		sessionSummaryInactiveFrameRelay INTEGER,
		sessionSummaryActiveCiscoHDLC	INTEGER,
		sessionSummaryMaximumCiscoHDLC	INTEGER,
		sessionSummaryInactiveCiscoHDLC	INTEGER,
		sessionSummaryActiveTerminalServer INTEGER,
		sessionSummaryMaximumTerminalServer INTEGER,
		sessionSummaryInactiveTerminalServer INTEGER,
		sessionSummaryActiveTelnet	INTEGER,
		sessionSummaryMaximumTelnet	INTEGER,
		sessionSummaryInactiveTelnet	INTEGER,
		sessionSummaryActiveRawTCP	INTEGER,
		sessionSummaryMaximumRawTCP	INTEGER,
		sessionSummaryInactiveRawTCP	INTEGER,
		sessionSummaryActiveRlogin	INTEGER,
		sessionSummaryMaximumRlogin	INTEGER,
		sessionSummaryInactiveRlogin	INTEGER,
		sessionSummaryActiveL2tp	INTEGER,
		sessionSummaryMaximumL2tp	INTEGER,
		sessionSummaryInactiveL2tp	INTEGER,
		sessionSummaryActiveL2f		INTEGER,
		sessionSummaryMaximumL2f	INTEGER,
		sessionSummaryInactiveL2f	INTEGER,
		sessionSummaryActiveTrunk	INTEGER,
		sessionSummaryMaximumTrunk	INTEGER,
		sessionSummaryInactiveTrunk	INTEGER,
		sessionSummaryActiveVoice	INTEGER,
		sessionSummaryMaximumVoice	INTEGER,
		sessionSummaryInactiveVoice	INTEGER,
		sessionSummaryActiveTandem	INTEGER,
		sessionSummaryMaximumTandem	INTEGER,
		sessionSummaryInactiveTandem	INTEGER,
		sessionSummaryActiveFtp		INTEGER,
		sessionSummaryMaximumFtp	INTEGER,
		sessionSummaryInactiveFtp	INTEGER,
		sessionSummaryActiveDvs		INTEGER,
		sessionSummaryMaximumDvs	INTEGER,
		sessionSummaryInactiveDvs	INTEGER,
		sessionSummaryActiveAtmp	INTEGER,
		sessionSummaryMaximumAtmp	INTEGER,
		sessionSummaryInactiveAtmp	INTEGER,
		sessionSummaryActiveFax		INTEGER,
		sessionSummaryMaximumFax	INTEGER,
		sessionSummaryInactiveFax	INTEGER,
		sessionSummaryActiveHub		INTEGER,
		sessionSummaryMaximumHub	INTEGER,
		sessionSummaryInactiveHub	INTEGER,
		sessionSummaryActiveTest	INTEGER,
		sessionSummaryMaximumTest	INTEGER,
		sessionSummaryInactiveTest	INTEGER,
		sessionSummaryMaximumTotal	INTEGER
	}

	sessionSummaryActiveUnknown	OBJECT-TYPE
		SYNTAX		INTEGER
		MAX-ACCESS	read-only
		STATUS		current
		DESCRIPTION
			"The number of sessions active but not yet providing
			service."

	::= { sessionSummaryEntry 1 }

	sessionSummaryMaximumUnknown	OBJECT-TYPE
		SYNTAX		INTEGER
		MAX-ACCESS	read-only
		STATUS		current
		DESCRIPTION
			"The maximum number of sessions active but not yet
			providing service."

	::= { sessionSummaryEntry 2 }

	sessionSummaryInactiveUnknown	OBJECT-TYPE
		SYNTAX		INTEGER
		MAX-ACCESS	read-only
		STATUS		current
		DESCRIPTION
			"The number of sessions which terminated prior to
			providing service."

	::= { sessionSummaryEntry 3 }

	sessionSummaryActiveNone	OBJECT-TYPE
		SYNTAX		INTEGER
		MAX-ACCESS	read-only
		STATUS		current
		DESCRIPTION
			"The number of active sessions where the service mode
			is not known."

	::= { sessionSummaryEntry 4 }

	sessionSummaryMaximumNone	OBJECT-TYPE
		SYNTAX		INTEGER
		MAX-ACCESS	read-only
		STATUS		current
		DESCRIPTION
			"The maximum number of active sessions where the
			service mode is not known."

	::= { sessionSummaryEntry 5 }

	sessionSummaryInactiveNone	OBJECT-TYPE
		SYNTAX		INTEGER
		MAX-ACCESS	read-only
		STATUS		current
		DESCRIPTION
			"The number of sessions which have been terminated
			where the service mode was not known."

	::= { sessionSummaryEntry 6 }

	sessionSummaryActiveOther	OBJECT-TYPE
		SYNTAX		INTEGER
		MAX-ACCESS	read-only
		STATUS		current
		DESCRIPTION
			"The number of active sessions where the service mode
			is not known."

	::= { sessionSummaryEntry 7 }

	sessionSummaryMaximumOther	OBJECT-TYPE
		SYNTAX		INTEGER
		MAX-ACCESS	read-only
		STATUS		current
		DESCRIPTION
			"The maximum number of active sessions where the
			service mode is not known."

	::= { sessionSummaryEntry 8 }

	sessionSummaryInactiveOther	OBJECT-TYPE
		SYNTAX		INTEGER
		MAX-ACCESS	read-only
		STATUS		current
		DESCRIPTION
			"The number of sessions which have been terminated
			where the service mode was not known."

	::= { sessionSummaryEntry 9 }

	sessionSummaryActivePpp	OBJECT-TYPE
		SYNTAX		INTEGER
		MAX-ACCESS	read-only
		STATUS		current
		DESCRIPTION
			"The number of active ppp sessions."

	::= { sessionSummaryEntry 10 }

	sessionSummaryMaximumPpp	OBJECT-TYPE
		SYNTAX		INTEGER
		MAX-ACCESS	read-only
		STATUS		current
		DESCRIPTION
			"The maximum number of active ppp sessions."

	::= { sessionSummaryEntry 11 }

	sessionSummaryInactivePpp	OBJECT-TYPE
		SYNTAX		INTEGER
		MAX-ACCESS	read-only
		STATUS		current
		DESCRIPTION
			"The number of ppp sessions which have been
			terminated."

	::= { sessionSummaryEntry 12 }

	sessionSummaryActiveSlip	OBJECT-TYPE
		SYNTAX		INTEGER
		MAX-ACCESS	read-only
		STATUS		current
		DESCRIPTION
			"The number of active slip sessions."

	::= { sessionSummaryEntry 13 }

	sessionSummaryMaximumSlip	OBJECT-TYPE
		SYNTAX		INTEGER
		MAX-ACCESS	read-only
		STATUS		current
		DESCRIPTION
			"The maximum number of active slip sessions."

	::= { sessionSummaryEntry 14 }

	sessionSummaryInactiveSlip	OBJECT-TYPE
		SYNTAX		INTEGER
		MAX-ACCESS	read-only
		STATUS		current
		DESCRIPTION
			"The number of slip sessions which have been
			terminated."

	::= { sessionSummaryEntry 15 }

	sessionSummaryActiveFrameRelay	OBJECT-TYPE
		SYNTAX		INTEGER
		MAX-ACCESS	read-only
		STATUS		current
		DESCRIPTION
			"The number of active frameRelay sessions."

	::= { sessionSummaryEntry 16 }

	sessionSummaryMaximumFrameRelay	OBJECT-TYPE
		SYNTAX		INTEGER
		MAX-ACCESS	read-only
		STATUS		current
		DESCRIPTION
			"The maximum number of active frameRelay sessions."

	::= { sessionSummaryEntry 17 }

	sessionSummaryInactiveFrameRelay	OBJECT-TYPE
		SYNTAX		INTEGER
		MAX-ACCESS	read-only
		STATUS		current
		DESCRIPTION
			"The number of frameRelay sessions which have been
			terminated."

	::= { sessionSummaryEntry 18 }

	sessionSummaryActiveCiscoHDLC	OBJECT-TYPE
		SYNTAX		INTEGER
		MAX-ACCESS	read-only
		STATUS		current
		DESCRIPTION
			"The number of active ciscoHDLC sessions."

	::= { sessionSummaryEntry 19 }

	sessionSummaryMaximumCiscoHDLC	OBJECT-TYPE
		SYNTAX		INTEGER
		MAX-ACCESS	read-only
		STATUS		current
		DESCRIPTION
			"The maximum number of active ciscoHDLC sessions."

	::= { sessionSummaryEntry 20 }

	sessionSummaryInactiveCiscoHDLC	OBJECT-TYPE
		SYNTAX		INTEGER
		MAX-ACCESS	read-only
		STATUS		current
		DESCRIPTION
			"The number of ciscoHDLC sessions which have been
			terminated."

	::= { sessionSummaryEntry 21 }

	sessionSummaryActiveTerminalServer	OBJECT-TYPE
		SYNTAX		INTEGER
		MAX-ACCESS	read-only
		STATUS		current
		DESCRIPTION
			"The number of active terminalServer sessions."

	::= { sessionSummaryEntry 22 }

	sessionSummaryMaximumTerminalServer	OBJECT-TYPE
		SYNTAX		INTEGER
		MAX-ACCESS	read-only
		STATUS		current
		DESCRIPTION
			"The maximum number of active terminalServer
			sessions."

	::= { sessionSummaryEntry 23 }

	sessionSummaryInactiveTerminalServer	OBJECT-TYPE
		SYNTAX		INTEGER
		MAX-ACCESS	read-only
		STATUS		current
		DESCRIPTION
			"The number of terminalServer sessions which have been
			terminated."

	::= { sessionSummaryEntry 24 }

	sessionSummaryActiveTelnet	OBJECT-TYPE
		SYNTAX		INTEGER
		MAX-ACCESS	read-only
		STATUS		current
		DESCRIPTION
			"The number of active telnet sessions."

	::= { sessionSummaryEntry 25 }

	sessionSummaryMaximumTelnet	OBJECT-TYPE
		SYNTAX		INTEGER
		MAX-ACCESS	read-only
		STATUS		current
		DESCRIPTION
			"The maximum number of active telnet sessions."

	::= { sessionSummaryEntry 26 }

	sessionSummaryInactiveTelnet	OBJECT-TYPE
		SYNTAX		INTEGER
		MAX-ACCESS	read-only
		STATUS		current
		DESCRIPTION
			"The number of telnet sessions which have been
			terminated."

	::= { sessionSummaryEntry 27 }

	sessionSummaryActiveRawTCP	OBJECT-TYPE
		SYNTAX		INTEGER
		MAX-ACCESS	read-only
		STATUS		current
		DESCRIPTION
			"The number of active rawTCP sessions."

	::= { sessionSummaryEntry 28 }

	sessionSummaryMaximumRawTCP	OBJECT-TYPE
		SYNTAX		INTEGER
		MAX-ACCESS	read-only
		STATUS		current
		DESCRIPTION
			"The maximum number of active rawTCP sessions."

	::= { sessionSummaryEntry 29 }

	sessionSummaryInactiveRawTCP	OBJECT-TYPE
		SYNTAX		INTEGER
		MAX-ACCESS	read-only
		STATUS		current
		DESCRIPTION
			"The number of rawTCP sessions which have been
			terminated."

	::= { sessionSummaryEntry 30 }

	sessionSummaryActiveRlogin	OBJECT-TYPE
		SYNTAX		INTEGER
		MAX-ACCESS	read-only
		STATUS		current
		DESCRIPTION
			"The number of active rlogin sessions."

	::= { sessionSummaryEntry 31 }

	sessionSummaryMaximumRlogin	OBJECT-TYPE
		SYNTAX		INTEGER
		MAX-ACCESS	read-only
		STATUS		current
		DESCRIPTION
			"The maximum number of active rlogin sessions."

	::= { sessionSummaryEntry 32 }

	sessionSummaryInactiveRlogin	OBJECT-TYPE
		SYNTAX		INTEGER
		MAX-ACCESS	read-only
		STATUS		current
		DESCRIPTION
			"The number of rlogin sessions which have been
			terminated."

	::= { sessionSummaryEntry 33 }

	sessionSummaryActiveL2tp	OBJECT-TYPE
		SYNTAX		INTEGER
		MAX-ACCESS	read-only
		STATUS		current
		DESCRIPTION
			"The number of active l2tp sessions."

	::= { sessionSummaryEntry 34 }

	sessionSummaryMaximumL2tp	OBJECT-TYPE
		SYNTAX		INTEGER
		MAX-ACCESS	read-only
		STATUS		current
		DESCRIPTION
			"The maximum number of active l2tp sessions."

	::= { sessionSummaryEntry 35 }

	sessionSummaryInactiveL2tp	OBJECT-TYPE
		SYNTAX		INTEGER
		MAX-ACCESS	read-only
		STATUS		current
		DESCRIPTION
			"The number of l2tp sessions which have been
			terminated."

	::= { sessionSummaryEntry 36 }

	sessionSummaryActiveL2f	OBJECT-TYPE
		SYNTAX		INTEGER
		MAX-ACCESS	read-only
		STATUS		current
		DESCRIPTION
			"The number of active l2f sessions."

	::= { sessionSummaryEntry 37 }

	sessionSummaryMaximumL2f	OBJECT-TYPE
		SYNTAX		INTEGER
		MAX-ACCESS	read-only
		STATUS		current
		DESCRIPTION
			"The maximum number of active l2f sessions."

	::= { sessionSummaryEntry 38 }

	sessionSummaryInactiveL2f	OBJECT-TYPE
		SYNTAX		INTEGER
		MAX-ACCESS	read-only
		STATUS		current
		DESCRIPTION
			"The number of l2f sessions which have been
			terminated."

	::= { sessionSummaryEntry 39 }

	sessionSummaryActiveTrunk	OBJECT-TYPE
		SYNTAX		INTEGER
		MAX-ACCESS	read-only
		STATUS		current
		DESCRIPTION
			"The number of active trunk sessions."

	::= { sessionSummaryEntry 40 }

	sessionSummaryMaximumTrunk	OBJECT-TYPE
		SYNTAX		INTEGER
		MAX-ACCESS	read-only
		STATUS		current
		DESCRIPTION
			"The maximum number of active trunk sessions."

	::= { sessionSummaryEntry 41 }

	sessionSummaryInactiveTrunk	OBJECT-TYPE
		SYNTAX		INTEGER
		MAX-ACCESS	read-only
		STATUS		current
		DESCRIPTION
			"The number of trunk sessions which have been
			terminated."

	::= { sessionSummaryEntry 42 }

	sessionSummaryActiveVoice	OBJECT-TYPE
		SYNTAX		INTEGER
		MAX-ACCESS	read-only
		STATUS		current
		DESCRIPTION
			"The number of active voice sessions."

	::= { sessionSummaryEntry 43 }

	sessionSummaryMaximumVoice	OBJECT-TYPE
		SYNTAX		INTEGER
		MAX-ACCESS	read-only
		STATUS		current
		DESCRIPTION
			"The maximum number of active voice sessions."

	::= { sessionSummaryEntry 44 }

	sessionSummaryInactiveVoice	OBJECT-TYPE
		SYNTAX		INTEGER
		MAX-ACCESS	read-only
		STATUS		current
		DESCRIPTION
			"The number of voice sessions which have been
			terminated."

	::= { sessionSummaryEntry 45 }

	sessionSummaryActiveTandem	OBJECT-TYPE
		SYNTAX		INTEGER
		MAX-ACCESS	read-only
		STATUS		current
		DESCRIPTION
			"The number of active tandem sessions."

	::= { sessionSummaryEntry 46 }

	sessionSummaryMaximumTandem	OBJECT-TYPE
		SYNTAX		INTEGER
		MAX-ACCESS	read-only
		STATUS		current
		DESCRIPTION
			"The maximum number of active tandem sessions."

	::= { sessionSummaryEntry 47 }

	sessionSummaryInactiveTandem	OBJECT-TYPE
		SYNTAX		INTEGER
		MAX-ACCESS	read-only
		STATUS		current
		DESCRIPTION
			"The number of tandem sessions which have been
			terminated."

	::= { sessionSummaryEntry 48 }

	sessionSummaryActiveFtp	OBJECT-TYPE
		SYNTAX		INTEGER
		MAX-ACCESS	read-only
		STATUS		current
		DESCRIPTION
			"The number of active ftp sessions."

	::= { sessionSummaryEntry 49 }

	sessionSummaryMaximumFtp	OBJECT-TYPE
		SYNTAX		INTEGER
		MAX-ACCESS	read-only
		STATUS		current
		DESCRIPTION
			"The maximum number of active ftp sessions."

	::= { sessionSummaryEntry 50 }

	sessionSummaryInactiveFtp	OBJECT-TYPE
		SYNTAX		INTEGER
		MAX-ACCESS	read-only
		STATUS		current
		DESCRIPTION
			"The number of ftp sessions which have been
			terminated."

	::= { sessionSummaryEntry 51 }

	sessionSummaryActiveDvs	OBJECT-TYPE
		SYNTAX		INTEGER
		MAX-ACCESS	read-only
		STATUS		current
		DESCRIPTION
			"The number of active dvs sessions."

	::= { sessionSummaryEntry 52 }

	sessionSummaryMaximumDvs	OBJECT-TYPE
		SYNTAX		INTEGER
		MAX-ACCESS	read-only
		STATUS		current
		DESCRIPTION
			"The maximum number of active dvs sessions."

	::= { sessionSummaryEntry 53 }

	sessionSummaryInactiveDvs	OBJECT-TYPE
		SYNTAX		INTEGER
		MAX-ACCESS	read-only
		STATUS		current
		DESCRIPTION
			"The number of dvs sessions which have been
			terminated."

	::= { sessionSummaryEntry 54 }

	sessionSummaryActiveAtmp	OBJECT-TYPE
		SYNTAX		INTEGER
		MAX-ACCESS	read-only
		STATUS		current
		DESCRIPTION
			"The number of active atmp sessions."

	::= { sessionSummaryEntry 55 }

	sessionSummaryMaximumAtmp	OBJECT-TYPE
		SYNTAX		INTEGER
		MAX-ACCESS	read-only
		STATUS		current
		DESCRIPTION
			"The maximum number of active atmp sessions."

	::= { sessionSummaryEntry 56 }

	sessionSummaryInactiveAtmp	OBJECT-TYPE
		SYNTAX		INTEGER
		MAX-ACCESS	read-only
		STATUS		current
		DESCRIPTION
			"The number of atmp sessions which have been
			terminated."

	::= { sessionSummaryEntry 57 }

	sessionSummaryActiveFax	OBJECT-TYPE
		SYNTAX		INTEGER
		MAX-ACCESS	read-only
		STATUS		current
		DESCRIPTION
			"The number of active fax sessions."

	::= { sessionSummaryEntry 58 }

	sessionSummaryMaximumFax	OBJECT-TYPE
		SYNTAX		INTEGER
		MAX-ACCESS	read-only
		STATUS		current
		DESCRIPTION
			"The maximum number of active fax sessions."

	::= { sessionSummaryEntry 59 }

	sessionSummaryInactiveFax	OBJECT-TYPE
		SYNTAX		INTEGER
		MAX-ACCESS	read-only
		STATUS		current
		DESCRIPTION
			"The number of fax sessions which have been
			terminated."

	::= { sessionSummaryEntry 60 }

	sessionSummaryActiveHub	OBJECT-TYPE
		SYNTAX		INTEGER
		MAX-ACCESS	read-only
		STATUS		current
		DESCRIPTION
			"The number of active hub sessions."

	::= { sessionSummaryEntry 61 }

	sessionSummaryMaximumHub	OBJECT-TYPE
		SYNTAX		INTEGER
		MAX-ACCESS	read-only
		STATUS		current
		DESCRIPTION
			"The maximum number of active hub sessions."

	::= { sessionSummaryEntry 62 }

	sessionSummaryInactiveHub	OBJECT-TYPE
		SYNTAX		INTEGER
		MAX-ACCESS	read-only
		STATUS		current
		DESCRIPTION
			"The number of hub sessions which have been
			terminated."

	::= { sessionSummaryEntry 63 }

	sessionSummaryActiveTest	OBJECT-TYPE
		SYNTAX		INTEGER
		MAX-ACCESS	read-only
		STATUS		current
		DESCRIPTION
			"The number of active test sessions."

	::= { sessionSummaryEntry 64 }

	sessionSummaryMaximumTest	OBJECT-TYPE
		SYNTAX		INTEGER
		MAX-ACCESS	read-only
		STATUS		current
		DESCRIPTION
			"The maximum number of active test sessions."

	::= { sessionSummaryEntry 65 }

	sessionSummaryInactiveTest	OBJECT-TYPE
		SYNTAX		INTEGER
		MAX-ACCESS	read-only
		STATUS		current
		DESCRIPTION
			"The number of test sessions which have been
			terminated."

	::= { sessionSummaryEntry 66 }

	sessionSummaryMaximumTotal	OBJECT-TYPE
		SYNTAX		INTEGER
		MAX-ACCESS	read-only
		STATUS		current
		DESCRIPTION
			"The maximum number of active calls achieved on the
			system."

	::= { sessionSummaryEntry 67 }


	sessionDiscCauseTable	OBJECT-TYPE
		SYNTAX		SEQUENCE OF SessionDiscCauseEntry
		MAX-ACCESS	not-accessible
		STATUS		current
		DESCRIPTION
			"Session Disconnect Cause Information."

	::= { aptis-monitoring 104 }

	sessionDiscCauseEntry	OBJECT-TYPE
		SYNTAX		SessionDiscCauseEntry
		MAX-ACCESS	not-accessible
		STATUS		current
		DESCRIPTION
			"This is the structure of entries in the
			 sessionDiscCauseTable."
		INDEX		{ sessionDiscCauseIndex }
	::= { sessionDiscCauseTable 1 }

	SessionDiscCauseEntry ::= SEQUENCE {
		sessionDiscCauseIndex		INTEGER,
		sessionDiscCauseComponent	INTEGER,
		sessionDiscCauseCause		INTEGER,
		sessionDiscCauseReason		DisplayString,
		sessionDiscCauseCount		INTEGER
	}

	sessionDiscCauseIndex	OBJECT-TYPE
		SYNTAX		INTEGER
		MAX-ACCESS	read-only
		STATUS		current
		DESCRIPTION
			"An index into the table of disconnect causes."

	::= { sessionDiscCauseEntry 1 }

	sessionDiscCauseComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The component which initiated termination of this
			session. In cases where there are multiple causes of
			session termination, only the first cause detected is
			reported."

	::= { sessionDiscCauseEntry 2 }

	sessionDiscCauseCause	OBJECT-TYPE
		SYNTAX		INTEGER
		MAX-ACCESS	read-only
		STATUS		current
		DESCRIPTION
			"The cause which initiated termination of this
			session. In cases where there are multiple causes of
			session termination, only the first cause detected is
			reported."

	::= { sessionDiscCauseEntry 3 }

	sessionDiscCauseReason	OBJECT-TYPE
		SYNTAX		DisplayString (SIZE (0..50))
		MAX-ACCESS	read-only
		STATUS		current
		DESCRIPTION
			"A textual description of the cause which initiated
			termination of this session. In cases where there are
			multiple causes of session termination, only the first
			cause detected is reported."

	::= { sessionDiscCauseEntry 4 }

	sessionDiscCauseCount	OBJECT-TYPE
		SYNTAX		INTEGER
		MAX-ACCESS	read-only
		STATUS		current
		DESCRIPTION
			"The number of times this component/cause has resulted
			in session termination."

	::= { sessionDiscCauseEntry 5 }


	sessionStatusHistoryTable	OBJECT-TYPE
		SYNTAX		SEQUENCE OF SessionStatusHistoryEntry
		MAX-ACCESS	not-accessible
		STATUS		current
		DESCRIPTION
			"The table provides a historical view of the inactive
			sessions in the session table. It contains inactive
			sessions up to a maximum of SessionTableSize entries.
			This table is ordered by termination time of the
			sessions. The bounds of this table at any given time
			are described by the variables HistoryLowest and
			HistoryHighest. As new entries are inserted into the
			table, the inactive entries with the oldest
			termination time get aged out from the table."

	::= { aptis-monitoring 107 }

	sessionStatusHistoryEntry	OBJECT-TYPE
		SYNTAX		SessionStatusHistoryEntry
		MAX-ACCESS	not-accessible
		STATUS		current
		DESCRIPTION
			"This is the structure of entries in the
			 sessionStatusHistoryTable."
		INDEX		{ sessionStatusHistoryIndex }
	::= { sessionStatusHistoryTable 1 }

	SessionStatusHistoryEntry ::= SEQUENCE {
		sessionStatusHistoryIndex	INTEGER,
		sessionStatusHistorySessionID	INTEGER,
		sessionStatusHistoryState	INTEGER,
		sessionStatusHistoryPermanentFlag INTEGER,
		sessionStatusHistoryVpopId	INTEGER,
		sessionStatusHistoryName	DisplayString,
		sessionStatusHistoryRemoteIP	IpAddress,
		sessionStatusHistoryRemoteIPMask IpAddress,
		sessionStatusHistoryLocalIP	IpAddress,
		sessionStatusHistoryLocalIPMask	IpAddress,
		sessionStatusHistoryLinkService	INTEGER,
		sessionStatusHistoryServiceMode	INTEGER,
		sessionStatusHistoryStartTime	INTEGER,
		sessionStatusHistoryStopTime	INTEGER,
		sessionStatusHistoryTimeOfModemSync INTEGER,
		sessionStatusHistoryTimeOfService INTEGER,
		sessionStatusHistoryTerminatingComponent INTEGER,
		sessionStatusHistoryTerminationCause INTEGER,
		sessionStatusHistoryLastComponent INTEGER,
		sessionStatusHistoryLayer1Slot	INTEGER,
		sessionStatusHistoryLayer2Slot	INTEGER,
		sessionStatusHistoryCalledNumber DisplayString,
		sessionStatusHistoryCallingNumber DisplayString,
		sessionStatusHistoryOriginateMode INTEGER,
		sessionStatusHistoryOctetsIn	INTEGER,
		sessionStatusHistoryOctetsOut	INTEGER,
		sessionStatusHistoryPacketsIn	INTEGER,
		sessionStatusHistoryPacketsOut	INTEGER,
		sessionStatusHistoryMultiLinkId	INTEGER,
		sessionStatusHistoryPort	INTEGER,
		sessionStatusHistoryTimeslot	INTEGER,
		sessionStatusHistoryLinkCount	INTEGER,
		sessionStatusHistoryTxStartDataRate INTEGER,
		sessionStatusHistoryRxStartDataRate INTEGER,
		sessionStatusHistoryTxEndDataRate INTEGER,
		sessionStatusHistoryRxEndDataRate INTEGER,
		sessionStatusHistoryTxMinDataRate INTEGER,
		sessionStatusHistoryRxMinDataRate INTEGER,
		sessionStatusHistoryTxMaxDataRate INTEGER,
		sessionStatusHistoryRxMaxDataRate INTEGER,
		sessionStatusHistoryIop		INTEGER,
		sessionStatusHistoryDmm		INTEGER,
		sessionStatusHistoryPack	INTEGER,
		sessionStatusHistoryDevice	INTEGER,
		sessionStatusHistoryTdmStream	INTEGER,
		sessionStatusHistoryTdmTimeSlot	INTEGER,
		sessionStatusHistoryTerminationReason DisplayString,
		sessionStatusHistoryDuration	INTEGER,
		sessionStatusHistoryDurationHMS	DisplayString,
		sessionStatusHistorySs7SessionId DisplayString,
		sessionStatusHistoryModemNumber	INTEGER,
		sessionStatusHistoryTunnelType	INTEGER,
		sessionStatusHistoryTunnelMediumType INTEGER,
		sessionStatusHistoryTunnelServerAddress IpAddress,
		sessionStatusHistoryCallClass	INTEGER,
		sessionStatusHistoryTandemPort	INTEGER,
		sessionStatusHistoryTandemTimeslot INTEGER,
		sessionStatusHistoryCallClassArray OCTET STRING,
		sessionStatusHistoryCallClassLen INTEGER,
		sessionStatusHistoryActualAuthMethod INTEGER,
		sessionStatusHistoryModemModulation INTEGER,
		sessionStatusHistoryModemErrorCorrection INTEGER,
		sessionStatusHistoryModemDataCompression INTEGER,
		sessionStatusHistoryModemTxBlocks INTEGER,
		sessionStatusHistoryModemRetransmits INTEGER,
		sessionStatusHistoryModemSNR	INTEGER,
		sessionStatusHistoryModemLocalRetrains INTEGER,
		sessionStatusHistoryModemRemoteRetrains INTEGER,
		sessionStatusHistoryModemLocalRenegotiations INTEGER,
		sessionStatusHistoryModemRemoteRenegotiations INTEGER,
		sessionStatusHistoryModemReceiveLineLevel INTEGER,
		sessionStatusHistoryRemoteIPXNetwork INTEGER,
		sessionStatusHistoryRemoteIPXNode DisplayString,
		sessionStatusHistoryCleartcpRemoteIP IpAddress,
		sessionStatusHistoryCleartcpRemotePort INTEGER,
		sessionStatusHistoryTunnelId	INTEGER,
		sessionStatusHistoryLinkId	INTEGER
	}

	sessionStatusHistoryIndex	OBJECT-TYPE
		SYNTAX		INTEGER (1..2000)
		MAX-ACCESS	read-only
		STATUS		current
		DESCRIPTION
			"An index into a ring buffer of the last 2000
			sessions."

	::= { sessionStatusHistoryEntry 1 }

	sessionStatusHistorySessionID	OBJECT-TYPE
		SYNTAX		INTEGER
		MAX-ACCESS	read-only
		STATUS		current
		DESCRIPTION
			"The serial number of this session, a unique number
			for this boot era. When combined with the value of
			BootEra, provides a session number that is unique for
			the life of the system."

	::= { sessionStatusHistoryEntry 2 }

	sessionStatusHistoryState	OBJECT-TYPE
		SYNTAX		INTEGER {
				    inactive(0),
				    active(1)
				}
		MAX-ACCESS	read-only
		STATUS		current
		DESCRIPTION
			"This variable indicates the state of this session."

	::= { sessionStatusHistoryEntry 3 }

	sessionStatusHistoryPermanentFlag	OBJECT-TYPE
		SYNTAX		INTEGER {
				    unknown(0),
				    switched(1),
				    permanent(2)
				}
		MAX-ACCESS	read-only
		STATUS		current
		DESCRIPTION
			"This variable indicates whether this session is
			permanent(2), meaning a long-lasting locally
			administered session such as a Frame Relay PVC, or
			switched(1), meaning a short-lived session resulting
			from a switched call."

	::= { sessionStatusHistoryEntry 10 }

	sessionStatusHistoryVpopId	OBJECT-TYPE
		SYNTAX		INTEGER
		MAX-ACCESS	read-only
		STATUS		current
		DESCRIPTION
			"The identifier of the VPOP (administrative Group) to
			which the session belongs. A value of 0 indicates the
			default VPOP."

	::= { sessionStatusHistoryEntry 11 }

	sessionStatusHistoryName	OBJECT-TYPE
		SYNTAX		DisplayString (SIZE (0..68))
		MAX-ACCESS	read-only
		STATUS		current
		DESCRIPTION
			"The name of the connection peer for this session.
			During authentication of the session, this field may
			contain the name submitted by the peer. During this
			time, the value of timeOfService will be zero. When
			the value of timeOfService is nonzero, this field will
			contain a fully authenticated name."

	::= { sessionStatusHistoryEntry 12 }

	sessionStatusHistoryRemoteIP	OBJECT-TYPE
		SYNTAX		IpAddress
		MAX-ACCESS	read-only
		STATUS		current
		DESCRIPTION
			"The connection peer's IP address. If the link is
			numbered, then this is the address assigned to the
			other end of the link. If the link is not numbered,
			this may be the single IP address of the peer. For PPP
			connections, this is the result of IPNCP negotiation."

	::= { sessionStatusHistoryEntry 13 }

	sessionStatusHistoryRemoteIPMask	OBJECT-TYPE
		SYNTAX		IpAddress
		MAX-ACCESS	read-only
		STATUS		current
		DESCRIPTION
			"The connection peer's IP address mask, used in
			conjunction with remoteIP."

	::= { sessionStatusHistoryEntry 14 }

	sessionStatusHistoryLocalIP	OBJECT-TYPE
		SYNTAX		IpAddress
		MAX-ACCESS	read-only
		STATUS		current
		DESCRIPTION
			"The local IP address for this session. If the link is
			numbered, then this is the address assigned to the
			local end of the link. If the link is not numbered,
			this may be the primary IP address of the system. For
			PPP connections, this is the result of IPNCP
			negotiation."

	::= { sessionStatusHistoryEntry 15 }

	sessionStatusHistoryLocalIPMask	OBJECT-TYPE
		SYNTAX		IpAddress
		MAX-ACCESS	read-only
		STATUS		current
		DESCRIPTION
			"The local IP address mask for this session, used in
			conjunction with localIP."

	::= { sessionStatusHistoryEntry 16 }

	sessionStatusHistoryLinkService	OBJECT-TYPE
		SYNTAX		INTEGER {
				    unknown(0),
				    none(1),
				    other(2),
				    isdn56K(3),
				    isdn64K(4),
				    isdnV120(5),
				    isdnV110(6),
				    modemV32(7),
				    modemV34(8),
				    modemK56(9),
				    modemV90(10),
				    ethernet(11),
				    t1Trunk(12),
				    loopback(13),
				    hssi(14),
				    hub(15),
				    voice(16)
				}
		MAX-ACCESS	read-only
		STATUS		current
		DESCRIPTION
			"A description of which link technology is being used
			by the session."

	::= { sessionStatusHistoryEntry 17 }

	sessionStatusHistoryServiceMode	OBJECT-TYPE
		SYNTAX		INTEGER {
				    unknown(0),
				    none(1),
				    other(2),
				    ppp(3),
				    slip(4),
				    frameRelay(5),
				    ciscoHDLC(6),
				    terminalServer(7),
				    telnet(8),
				    rawTCP(9),
				    rlogin(10),
				    l2tp(11),
				    l2f(12),
				    trunk(13),
				    voice(14),
				    tandem(15),
				    hub(16),
				    ftp(17),
				    dvs(18),
				    fax(19),
				    atmp(20),
				    iptest(21)
				}
		MAX-ACCESS	read-only
		STATUS		current
		DESCRIPTION
			"A description of which session service is being used
			by the session."

	::= { sessionStatusHistoryEntry 18 }

	sessionStatusHistoryStartTime	OBJECT-TYPE
		SYNTAX		INTEGER
		MAX-ACCESS	read-only
		STATUS		current
		DESCRIPTION
			"The time that this session began, in seconds since
			the system booted."

	::= { sessionStatusHistoryEntry 19 }

	sessionStatusHistoryStopTime	OBJECT-TYPE
		SYNTAX		INTEGER
		MAX-ACCESS	read-only
		STATUS		current
		DESCRIPTION
			"The time that this session stopped, in seconds since
			the system booted. This variable is only meaningful
			for sessions having the state inactive(0)."

	::= { sessionStatusHistoryEntry 20 }

	sessionStatusHistoryTimeOfModemSync	OBJECT-TYPE
		SYNTAX		INTEGER
		MAX-ACCESS	read-only
		STATUS		current
		DESCRIPTION
			"The time at which the modem synchronization
			completed, in seconds since the system booted."

	::= { sessionStatusHistoryEntry 21 }

	sessionStatusHistoryTimeOfService	OBJECT-TYPE
		SYNTAX		INTEGER
		MAX-ACCESS	read-only
		STATUS		current
		DESCRIPTION
			"The time that this session entered its first
			negotiated or configured service, in seconds since the
			system booted. For example, for a session with
			serviceMode PPP, the time at which LCP and IPCP
			negotiations completed and the session was ready to
			forward user data."

	::= { sessionStatusHistoryEntry 22 }

	sessionStatusHistoryTerminatingComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The component which initiated termination of this
			session. In cases where there are multiple causes of
			session termination, only the first cause detected is
			reported. This variable is only meaningful for
			sessions having the state inactive(0)."

	::= { sessionStatusHistoryEntry 23 }

	sessionStatusHistoryTerminationCause	OBJECT-TYPE
		SYNTAX		INTEGER
		MAX-ACCESS	read-only
		STATUS		current
		DESCRIPTION
			"The cause which initiated termination of this
			session. In cases where there are multiple causes of
			session termination, only the first cause detected is
			reported. This variable is only meaningful for
			sessions having the state inactive(0)."

	::= { sessionStatusHistoryEntry 24 }

	sessionStatusHistoryLastComponent	OBJECT-TYPE
		SYNTAX		INTEGER {
				    unknown(0),
				    none(1),
				    other(2),
				    df(3),
				    ds0(4),
				    modem(5),
				    hdlc(6),
				    ppp(7),
				    slip(8),
				    chdlc(9),
				    fr(10),
				    ip(11),
				    telnet(12),
				    cleartcp(13),
				    l2tp(14),
				    ether(15),
				    trunkip(16),
				    fepdf(17),
				    lineip(18),
				    loopback(19),
				    shell(20),
				    rlogin(21),
				    hssi(22),
				    sm(23),
				    vl(24),
				    voip(25),
				    l2f(26),
				    l2ftunnel(27),
				    dvs(28),
				    dvstunnel(29),
				    fax(30),
				    l2tproute(31),
				    atmp(32),
				    atmptunnel(33),
				    iptest(34)
				}
		MAX-ACCESS	read-only
		STATUS		current
		DESCRIPTION
			"The last component which was connected in this
			session."

	::= { sessionStatusHistoryEntry 25 }

	sessionStatusHistoryLayer1Slot	OBJECT-TYPE
		SYNTAX		INTEGER (1..18)
		MAX-ACCESS	read-only
		STATUS		current
		DESCRIPTION
			"The slot where the physical layer of this session is
			terminated."

	::= { sessionStatusHistoryEntry 26 }

	sessionStatusHistoryLayer2Slot	OBJECT-TYPE
		SYNTAX		INTEGER (1..18)
		MAX-ACCESS	read-only
		STATUS		current
		DESCRIPTION
			"The slot where the data link portion of this session
			is terminated"

	::= { sessionStatusHistoryEntry 27 }

	sessionStatusHistoryCalledNumber	OBJECT-TYPE
		SYNTAX		DisplayString (SIZE (0..17))
		MAX-ACCESS	read-only
		STATUS		current
		DESCRIPTION
			"16 digit number of called station (if available)"

	::= { sessionStatusHistoryEntry 28 }

	sessionStatusHistoryCallingNumber	OBJECT-TYPE
		SYNTAX		DisplayString (SIZE (0..17))
		MAX-ACCESS	read-only
		STATUS		current
		DESCRIPTION
			"16 digit number of calling station (if available)"

	::= { sessionStatusHistoryEntry 29 }

	sessionStatusHistoryOriginateMode	OBJECT-TYPE
		SYNTAX		INTEGER {
				    answer(0),
				    originate(1)
				}
		MAX-ACCESS	read-only
		STATUS		current
		DESCRIPTION
			"The direction of the physical layer call associated
			with this session"

	::= { sessionStatusHistoryEntry 30 }

	sessionStatusHistoryOctetsIn	OBJECT-TYPE
		SYNTAX		INTEGER
		MAX-ACCESS	read-only
		STATUS		current
		DESCRIPTION
			"The number of octets received from the remote user.
			This value will be zero until a session is
			terminated."

	::= { sessionStatusHistoryEntry 31 }

	sessionStatusHistoryOctetsOut	OBJECT-TYPE
		SYNTAX		INTEGER
		MAX-ACCESS	read-only
		STATUS		current
		DESCRIPTION
			"The number of octets sent to the remote user. This
			value will be zero until a session is terminated."

	::= { sessionStatusHistoryEntry 32 }

	sessionStatusHistoryPacketsIn	OBJECT-TYPE
		SYNTAX		INTEGER
		MAX-ACCESS	read-only
		STATUS		current
		DESCRIPTION
			"The number of packets received from the remote user.
			This value will be zero until a session is
			terminated."

	::= { sessionStatusHistoryEntry 33 }

	sessionStatusHistoryPacketsOut	OBJECT-TYPE
		SYNTAX		INTEGER
		MAX-ACCESS	read-only
		STATUS		current
		DESCRIPTION
			"The number of packets sent to the remote user. This
			value will be zero until a session is terminated."

	::= { sessionStatusHistoryEntry 34 }

	sessionStatusHistoryMultiLinkId	OBJECT-TYPE
		SYNTAX		INTEGER
		MAX-ACCESS	read-only
		STATUS		current
		DESCRIPTION
			"The multi-link identifier value for PPP calls where
			the multi-link protocol was negotiated."

	::= { sessionStatusHistoryEntry 35 }

	sessionStatusHistoryPort	OBJECT-TYPE
		SYNTAX		INTEGER
		MAX-ACCESS	read-only
		STATUS		current
		DESCRIPTION
			"The number of the DS1 for this session, relative to
			layer1Slot."

	::= { sessionStatusHistoryEntry 36 }

	sessionStatusHistoryTimeslot	OBJECT-TYPE
		SYNTAX		INTEGER
		MAX-ACCESS	read-only
		STATUS		current
		DESCRIPTION
			"The number of the DS0 for this session, relative to
			port."

	::= { sessionStatusHistoryEntry 37 }

	sessionStatusHistoryLinkCount	OBJECT-TYPE
		SYNTAX		INTEGER
		MAX-ACCESS	read-only
		STATUS		current
		DESCRIPTION
			"The number of sessions sharing the same remote IP
			address as this session. After a session is
			terminated, this value will represent the number of
			sessions at the time of termination."

	::= { sessionStatusHistoryEntry 38 }

	sessionStatusHistoryTxStartDataRate	OBJECT-TYPE
		SYNTAX		INTEGER
		MAX-ACCESS	read-only
		STATUS		current
		DESCRIPTION
			"The transmit DCE data rate for this session. In the
			case of modem sessions, this will be the DCE rate
			reported as a result of initial modem negotiation, and
			may not track rate chanes during the call. For ISDN
			sessions, this will be the actual data service rate of
			the call. For Frame Relay sessions, this will be the
			nominal speed of the Frame Relay Physical Interface,
			even though multiple sessions may be sharing that
			Physical Interface. For other sessions, this will be
			the nominal speed of the physical interface. In no
			case should this be interepreted as a
			Quality-of-Service guarantee, or as the current line
			utilization or effective bandwidth on the interface.
			Note also that in the case of PPP multilink, this
			specifies the rate of only this link in the bundle,
			and not the aggregate rate of all links in the
			bundle."

	::= { sessionStatusHistoryEntry 39 }

	sessionStatusHistoryRxStartDataRate	OBJECT-TYPE
		SYNTAX		INTEGER
		MAX-ACCESS	read-only
		STATUS		current
		DESCRIPTION
			"The receive data rate for this session. In the case
			of modem sessions, this will be the DCE rate reported
			as a result of initial modem negotiation, and may not
			track rate chanes during the call. For ISDN sessions,
			this will be the actual data service rate of the call.
			For Frame Relay sessions, this will be the nominal
			speed of the Frame Relay Physical Interface, even
			though multiple sessions may be sharing that Physical
			Interface. For other sessions, this will be the
			nominal speed of the physical interface. In no case
			should this be interepreted as a Quality-of-Service
			guarantee, or as the current line utilization or
			effective bandwidth on the interface. Note also that
			in the case of PPP multilink, this specifies the rate
			of only this link in the bundle, and not the aggregate
			rate of all links in the bundle."

	::= { sessionStatusHistoryEntry 40 }

	sessionStatusHistoryTxEndDataRate	OBJECT-TYPE
		SYNTAX		INTEGER
		MAX-ACCESS	read-only
		STATUS		current
		DESCRIPTION
			"The transmit data rate at the end of a modem
			session."

	::= { sessionStatusHistoryEntry 41 }

	sessionStatusHistoryRxEndDataRate	OBJECT-TYPE
		SYNTAX		INTEGER
		MAX-ACCESS	read-only
		STATUS		current
		DESCRIPTION
			"The receive data rate at the end of a modem session."

	::= { sessionStatusHistoryEntry 42 }

	sessionStatusHistoryTxMinDataRate	OBJECT-TYPE
		SYNTAX		INTEGER
		MAX-ACCESS	read-only
		STATUS		current
		DESCRIPTION
			"The minimum transmit data rate during a modem
			session."

	::= { sessionStatusHistoryEntry 43 }

	sessionStatusHistoryRxMinDataRate	OBJECT-TYPE
		SYNTAX		INTEGER
		MAX-ACCESS	read-only
		STATUS		current
		DESCRIPTION
			"The minimum receive data rate during a modem
			session."

	::= { sessionStatusHistoryEntry 44 }

	sessionStatusHistoryTxMaxDataRate	OBJECT-TYPE
		SYNTAX		INTEGER
		MAX-ACCESS	read-only
		STATUS		current
		DESCRIPTION
			"The maximum transmit data rate during a modem
			session."

	::= { sessionStatusHistoryEntry 45 }

	sessionStatusHistoryRxMaxDataRate	OBJECT-TYPE
		SYNTAX		INTEGER
		MAX-ACCESS	read-only
		STATUS		current
		DESCRIPTION
			"The maximum receive data rate during a modem
			session."

	::= { sessionStatusHistoryEntry 46 }

	sessionStatusHistoryIop	OBJECT-TYPE
		SYNTAX		INTEGER
		MAX-ACCESS	read-only
		STATUS		current
		DESCRIPTION
			"The I/O processor where this session is terminated."

	::= { sessionStatusHistoryEntry 47 }

	sessionStatusHistoryDmm	OBJECT-TYPE
		SYNTAX		INTEGER
		MAX-ACCESS	read-only
		STATUS		current
		DESCRIPTION
			"The Digital Modem Module where this session is
			terminated."

	::= { sessionStatusHistoryEntry 48 }

	sessionStatusHistoryPack	OBJECT-TYPE
		SYNTAX		INTEGER
		MAX-ACCESS	read-only
		STATUS		current
		DESCRIPTION
			"The integrated circuit pack where this session is
			terminated."

	::= { sessionStatusHistoryEntry 49 }

	sessionStatusHistoryDevice	OBJECT-TYPE
		SYNTAX		INTEGER
		MAX-ACCESS	read-only
		STATUS		current
		DESCRIPTION
			"The modem/hdlc where this session is terminated."

	::= { sessionStatusHistoryEntry 50 }

	sessionStatusHistoryTdmStream	OBJECT-TYPE
		SYNTAX		INTEGER
		MAX-ACCESS	read-only
		STATUS		current
		DESCRIPTION
			"The TDM highway stream associated with this session."

	::= { sessionStatusHistoryEntry 51 }

	sessionStatusHistoryTdmTimeSlot	OBJECT-TYPE
		SYNTAX		INTEGER
		MAX-ACCESS	read-only
		STATUS		current
		DESCRIPTION
			"The TDM highway time-slot associated with this
			session."

	::= { sessionStatusHistoryEntry 52 }

	sessionStatusHistoryTerminationReason	OBJECT-TYPE
		SYNTAX		DisplayString (SIZE (0..50))
		MAX-ACCESS	read-only
		STATUS		current
		DESCRIPTION
			"A textual description of the cause which initiated
			termination of this session. In cases where there are
			multiple causes of session termination, only the first
			cause detected is reported."

	::= { sessionStatusHistoryEntry 53 }

	sessionStatusHistoryDuration	OBJECT-TYPE
		SYNTAX		INTEGER
		MAX-ACCESS	read-only
		STATUS		current
		DESCRIPTION
			"The number of seconds this session has been active."

	::= { sessionStatusHistoryEntry 54 }

	sessionStatusHistoryDurationHMS	OBJECT-TYPE
		SYNTAX		DisplayString (SIZE (0..20))
		MAX-ACCESS	read-only
		STATUS		current
		DESCRIPTION
			"The length of time this session has been active,
			expressed in DDD HH:MM:SSS.000."

	::= { sessionStatusHistoryEntry 55 }

	sessionStatusHistorySs7SessionId	OBJECT-TYPE
		SYNTAX		DisplayString (SIZE (0..41))
		MAX-ACCESS	read-only
		STATUS		current
		DESCRIPTION
			"A uniquie identifier for this session within the ss7
			Network. If this call was not originated using ss7
			signalling, this string will be null."

	::= { sessionStatusHistoryEntry 56 }

	sessionStatusHistoryModemNumber	OBJECT-TYPE
		SYNTAX		INTEGER
		MAX-ACCESS	read-only
		STATUS		current
		DESCRIPTION
			"The individual modem where this session is
			terminated, numbered from one to the maximum number of
			modems on the slot card."

	::= { sessionStatusHistoryEntry 57 }

	sessionStatusHistoryTunnelType	OBJECT-TYPE
		SYNTAX		INTEGER {
				    unknown(0),
				    none(1),
				    other(2),
				    l2f(3),
				    l2tp(4),
				    dvs(5),
				    atmp(6)
				}
		MAX-ACCESS	read-only
		STATUS		current
		DESCRIPTION
			"The tunneling protocol being used for this session."

	::= { sessionStatusHistoryEntry 58 }

	sessionStatusHistoryTunnelMediumType	OBJECT-TYPE
		SYNTAX		INTEGER {
				    unknown(0),
				    none(1),
				    other(2),
				    ip(3)
				}
		MAX-ACCESS	read-only
		STATUS		current
		DESCRIPTION
			"The tunneling medium protocol being used for this
			session."

	::= { sessionStatusHistoryEntry 59 }

	sessionStatusHistoryTunnelServerAddress	OBJECT-TYPE
		SYNTAX		IpAddress
		MAX-ACCESS	read-only
		STATUS		current
		DESCRIPTION
			"The IP address of the remote machine terminating the
			tunnel for this session."

	::= { sessionStatusHistoryEntry 60 }

	sessionStatusHistoryCallClass	OBJECT-TYPE
		SYNTAX		INTEGER
		MAX-ACCESS	read-only
		STATUS		current
		DESCRIPTION
			"The class of this call."

	::= { sessionStatusHistoryEntry 61 }

	sessionStatusHistoryTandemPort	OBJECT-TYPE
		SYNTAX		INTEGER
		MAX-ACCESS	read-only
		STATUS		current
		DESCRIPTION
			"The port used for the outbound portion of a tandem
			call, if applicable."

	::= { sessionStatusHistoryEntry 62 }

	sessionStatusHistoryTandemTimeslot	OBJECT-TYPE
		SYNTAX		INTEGER
		MAX-ACCESS	read-only
		STATUS		current
		DESCRIPTION
			"The timeslot used for the outbound portion of a
			tandem call, if applicable."

	::= { sessionStatusHistoryEntry 63 }

	sessionStatusHistoryCallClassArray	OBJECT-TYPE
		SYNTAX		OCTET STRING (SIZE (0..256))
		MAX-ACCESS	read-only
		STATUS		current
		DESCRIPTION
			"An array of octets representing the class of this
			call."

	::= { sessionStatusHistoryEntry 64 }

	sessionStatusHistoryCallClassLen	OBJECT-TYPE
		SYNTAX		INTEGER
		MAX-ACCESS	read-only
		STATUS		current
		DESCRIPTION
			"The number of octets in callClassArray."

	::= { sessionStatusHistoryEntry 65 }

	sessionStatusHistoryActualAuthMethod	OBJECT-TYPE
		SYNTAX		INTEGER {
				    radius(1),
				    local(2),
				    remote(3)
				}
		MAX-ACCESS	read-only
		STATUS		current
		DESCRIPTION
			"The actual authentication method which was used to
			gain access to services. Radius, Local, Remote."

	::= { sessionStatusHistoryEntry 66 }

	sessionStatusHistoryModemModulation	OBJECT-TYPE
		SYNTAX		INTEGER {
				    none(0),
				    unknown(1),
				    bell103(2),
				    bell208(3),
				    bell212(4),
				    v17(5),
				    v21(6),
				    v22(7),
				    v22bis(8),
				    v23(9),
				    v27(10),
				    v29(11),
				    v32(12),
				    v32bis(13),
				    v33(14),
				    v34(15),
				    vFC(16),
				    k56(17),
				    v90(18)
				}
		MAX-ACCESS	read-only
		STATUS		current
		DESCRIPTION
			"For modem sessions, the modulation protocol used, if
			any."

	::= { sessionStatusHistoryEntry 67 }

	sessionStatusHistoryModemErrorCorrection	OBJECT-TYPE
		SYNTAX		INTEGER {
				    none(0),
				    unknown(1),
				    mNP(2),
				    v42(3)
				}
		MAX-ACCESS	read-only
		STATUS		current
		DESCRIPTION
			"For modem sessions, the error correction protocol
			used, if any."

	::= { sessionStatusHistoryEntry 68 }

	sessionStatusHistoryModemDataCompression	OBJECT-TYPE
		SYNTAX		INTEGER {
				    none(0),
				    unknown(1),
				    mNP5(2),
				    v42bis(3)
				}
		MAX-ACCESS	read-only
		STATUS		current
		DESCRIPTION
			"For modem sessions, the data compression protocol
			used, if any."

	::= { sessionStatusHistoryEntry 69 }

	sessionStatusHistoryModemTxBlocks	OBJECT-TYPE
		SYNTAX		INTEGER
		MAX-ACCESS	read-only
		STATUS		current
		DESCRIPTION
			"For modem sessions, the number of blocks transmitted
			by the modem."

	::= { sessionStatusHistoryEntry 70 }

	sessionStatusHistoryModemRetransmits	OBJECT-TYPE
		SYNTAX		INTEGER
		MAX-ACCESS	read-only
		STATUS		current
		DESCRIPTION
			"For modem sessions, the number of packets
			retransmitted by the modem."

	::= { sessionStatusHistoryEntry 71 }

	sessionStatusHistoryModemSNR	OBJECT-TYPE
		SYNTAX		INTEGER
		MAX-ACCESS	read-only
		STATUS		current
		DESCRIPTION
			"For modem sessions, the Signal-to-Noise Ratio
			measured at the start of the connection. This value is
			given in dB."

	::= { sessionStatusHistoryEntry 72 }

	sessionStatusHistoryModemLocalRetrains	OBJECT-TYPE
		SYNTAX		INTEGER
		MAX-ACCESS	read-only
		STATUS		current
		DESCRIPTION
			"For modem sessions, the number of retrain requests
			sent by the local modem."

	::= { sessionStatusHistoryEntry 73 }

	sessionStatusHistoryModemRemoteRetrains	OBJECT-TYPE
		SYNTAX		INTEGER
		MAX-ACCESS	read-only
		STATUS		current
		DESCRIPTION
			"For modem sessions, the number of retrain requests
			sent by the remote modem."

	::= { sessionStatusHistoryEntry 74 }

	sessionStatusHistoryModemLocalRenegotiations	OBJECT-TYPE
		SYNTAX		INTEGER
		MAX-ACCESS	read-only
		STATUS		current
		DESCRIPTION
			"For modem sessions, the number of rate renegotiation
			requests sent by the local modem."

	::= { sessionStatusHistoryEntry 75 }

	sessionStatusHistoryModemRemoteRenegotiations	OBJECT-TYPE
		SYNTAX		INTEGER
		MAX-ACCESS	read-only
		STATUS		current
		DESCRIPTION
			"For modem sessions, the number of rate renegotiation
			requests sent by the remote modem."

	::= { sessionStatusHistoryEntry 76 }

	sessionStatusHistoryModemReceiveLineLevel	OBJECT-TYPE
		SYNTAX		INTEGER
		MAX-ACCESS	read-only
		STATUS		current
		DESCRIPTION
			"For modem sessions, the receive line signal level.
			This value is given in dB."

	::= { sessionStatusHistoryEntry 77 }

	sessionStatusHistoryRemoteIPXNetwork	OBJECT-TYPE
		SYNTAX		INTEGER
		MAX-ACCESS	read-only
		STATUS		current
		DESCRIPTION
			"The IPX network assigned to the dial-up user."

	::= { sessionStatusHistoryEntry 78 }

	sessionStatusHistoryRemoteIPXNode	OBJECT-TYPE
		SYNTAX		DisplayString (SIZE (0..16))
		MAX-ACCESS	read-only
		STATUS		current
		DESCRIPTION
			"The IPX Node number assisgned to the dial-up user"

	::= { sessionStatusHistoryEntry 79 }

	sessionStatusHistoryCleartcpRemoteIP	OBJECT-TYPE
		SYNTAX		IpAddress
		MAX-ACCESS	read-only
		STATUS		current
		DESCRIPTION
			"Cleartcp Remote IP Address"

	::= { sessionStatusHistoryEntry 80 }

	sessionStatusHistoryCleartcpRemotePort	OBJECT-TYPE
		SYNTAX		INTEGER
		MAX-ACCESS	read-only
		STATUS		current
		DESCRIPTION
			"Cleartcp Remote Port Address"

	::= { sessionStatusHistoryEntry 81 }

	sessionStatusHistoryTunnelId	OBJECT-TYPE
		SYNTAX		INTEGER
		MAX-ACCESS	read-only
		STATUS		current
		DESCRIPTION
			"Tunnel Id"

	::= { sessionStatusHistoryEntry 82 }

	sessionStatusHistoryLinkId	OBJECT-TYPE
		SYNTAX		INTEGER
		MAX-ACCESS	read-only
		STATUS		current
		DESCRIPTION
			"Link Id"

	::= { sessionStatusHistoryEntry 83 }


	sessionMultilinkTable	OBJECT-TYPE
		SYNTAX		SEQUENCE OF SessionMultilinkEntry
		MAX-ACCESS	not-accessible
		STATUS		current
		DESCRIPTION
			"Session Multilink Configuration Information."

	::= { aptis-monitoring 217 }

	sessionMultilinkEntry	OBJECT-TYPE
		SYNTAX		SessionMultilinkEntry
		MAX-ACCESS	not-accessible
		STATUS		current
		DESCRIPTION
			"This is the structure of entries in the
			 sessionMultilinkTable."
		INDEX		{ sessionMultilinkSessionId }
	::= { sessionMultilinkTable 1 }

	SessionMultilinkEntry ::= SEQUENCE {
		sessionMultilinkNegotiated	INTEGER,
		sessionMultilinkSessionId	INTEGER,
		sessionMultilinkNameLength	INTEGER,
		sessionMultilinkUserName	DisplayString,
		sessionMultilinkMyMRRU		INTEGER,
		sessionMultilinkPeerMRRU	INTEGER,
		sessionMultilinkMyShortSequence	INTEGER,
		sessionMultilinkPeerShortSequence INTEGER,
		sessionMultilinkMyEIDType	INTEGER,
		sessionMultilinkPeerEIDType	INTEGER,
		sessionMultilinkMyEIDLength	INTEGER,
		sessionMultilinkPeerEIDLength	INTEGER,
		sessionMultilinkMyEIDData	DisplayString,
		sessionMultilinkPeerEIDData	DisplayString
	}

	sessionMultilinkNegotiated	OBJECT-TYPE
		SYNTAX		INTEGER
		MAX-ACCESS	read-only
		STATUS		current
		DESCRIPTION
			"The serial number of this session, a unique number
			for this boot era. When combined with the value of
			BootEra, provides a session number that is unique for
			the life of the system."

	::= { sessionMultilinkEntry 1 }

	sessionMultilinkSessionId	OBJECT-TYPE
		SYNTAX		INTEGER
		MAX-ACCESS	read-only
		STATUS		current
		DESCRIPTION
			"The serial number of this session, a unique number
			for this boot era. When combined with the value of
			BootEra, provides a session number that is unique for
			the life of the system."

	::= { sessionMultilinkEntry 2 }

	sessionMultilinkNameLength	OBJECT-TYPE
		SYNTAX		INTEGER
		MAX-ACCESS	read-only
		STATUS		current
		DESCRIPTION
			"Length of authenticated user's name (0 means no
			authentication)."

	::= { sessionMultilinkEntry 3 }

	sessionMultilinkUserName	OBJECT-TYPE
		SYNTAX		DisplayString (SIZE (0..64))
		MAX-ACCESS	read-only
		STATUS		current
		DESCRIPTION
			"User's name (null-terminated, null not included in
			length)."

	::= { sessionMultilinkEntry 4 }

	sessionMultilinkMyMRRU	OBJECT-TYPE
		SYNTAX		INTEGER
		MAX-ACCESS	read-only
		STATUS		current
		DESCRIPTION
			"MRRU value I negotiated (0 means not negotiated)."

	::= { sessionMultilinkEntry 5 }

	sessionMultilinkPeerMRRU	OBJECT-TYPE
		SYNTAX		INTEGER
		MAX-ACCESS	read-only
		STATUS		current
		DESCRIPTION
			"MRRU value the peer negotiated (0 means not
			negotiated)."

	::= { sessionMultilinkEntry 6 }

	sessionMultilinkMyShortSequence	OBJECT-TYPE
		SYNTAX		INTEGER
		MAX-ACCESS	read-only
		STATUS		current
		DESCRIPTION
			"1 if I negotiated short sequence #, 0 if not."

	::= { sessionMultilinkEntry 7 }

	sessionMultilinkPeerShortSequence	OBJECT-TYPE
		SYNTAX		INTEGER
		MAX-ACCESS	read-only
		STATUS		current
		DESCRIPTION
			"1 if peer negotiated short sequence #, 0 if not."

	::= { sessionMultilinkEntry 8 }

	sessionMultilinkMyEIDType	OBJECT-TYPE
		SYNTAX		INTEGER
		MAX-ACCESS	read-only
		STATUS		current
		DESCRIPTION
			"EID type I negotiated (0 means not negotiated)."

	::= { sessionMultilinkEntry 9 }

	sessionMultilinkPeerEIDType	OBJECT-TYPE
		SYNTAX		INTEGER
		MAX-ACCESS	read-only
		STATUS		current
		DESCRIPTION
			"EID type peer negotiated (0 means not negotiated)."

	::= { sessionMultilinkEntry 10 }

	sessionMultilinkMyEIDLength	OBJECT-TYPE
		SYNTAX		INTEGER
		MAX-ACCESS	read-only
		STATUS		current
		DESCRIPTION
			"Length of my EID data (0 means not negotiated)."

	::= { sessionMultilinkEntry 11 }

	sessionMultilinkPeerEIDLength	OBJECT-TYPE
		SYNTAX		INTEGER
		MAX-ACCESS	read-only
		STATUS		current
		DESCRIPTION
			"Length of peer's EID data (0 means not negotiated)."

	::= { sessionMultilinkEntry 12 }

	sessionMultilinkMyEIDData	OBJECT-TYPE
		SYNTAX		DisplayString (SIZE (0..32))
		MAX-ACCESS	read-only
		STATUS		current
		DESCRIPTION
			"EID data I negotiated (if any)."

	::= { sessionMultilinkEntry 13 }

	sessionMultilinkPeerEIDData	OBJECT-TYPE
		SYNTAX		DisplayString (SIZE (0..32))
		MAX-ACCESS	read-only
		STATUS		current
		DESCRIPTION
			"EID data peer negotiated (if any)."

	::= { sessionMultilinkEntry 14 }


	sessionVpopTable	OBJECT-TYPE
		SYNTAX		SEQUENCE OF SessionVpopEntry
		MAX-ACCESS	not-accessible
		STATUS		current
		DESCRIPTION
			"Session VPOP Information."

	::= { aptis-monitoring 218 }

	sessionVpopEntry	OBJECT-TYPE
		SYNTAX		SessionVpopEntry
		MAX-ACCESS	not-accessible
		STATUS		current
		DESCRIPTION
			"This is the structure of entries in the
			 sessionVpopTable."
		INDEX		{ sessionVpopVpopIndex, sessionVpopCallType, sessionVpopProtocol }
	::= { sessionVpopTable 1 }

	SessionVpopEntry ::= SEQUENCE {
		sessionVpopVpopIndex		INTEGER,
		sessionVpopVpopId		INTEGER,
		sessionVpopCallType		INTEGER,
		sessionVpopProtocol		INTEGER,
		sessionVpopCurrentCount		INTEGER,
		sessionVpopCurrentDuration	INTEGER,
		sessionVpopCumulativeCount	INTEGER,
		sessionVpopCumulativeDuration	INTEGER
	}

	sessionVpopVpopIndex	OBJECT-TYPE
		SYNTAX		INTEGER
		MAX-ACCESS	read-only
		STATUS		current
		DESCRIPTION
			"vpop Index (one based)."

	::= { sessionVpopEntry 1 }

	sessionVpopVpopId	OBJECT-TYPE
		SYNTAX		INTEGER
		MAX-ACCESS	read-only
		STATUS		current
		DESCRIPTION
			"VPOP Id (zero based)."

	::= { sessionVpopEntry 2 }

	sessionVpopCallType	OBJECT-TYPE
		SYNTAX		INTEGER {
				    other(1),
				    trunk(2),
				    modem(3),
				    isdn(4),
				    v110(5),
				    v120(6)
				}
		MAX-ACCESS	read-only
		STATUS		current
		DESCRIPTION
			"Data link call type"

	::= { sessionVpopEntry 3 }

	sessionVpopProtocol	OBJECT-TYPE
		SYNTAX		INTEGER {
				    setup(1),
				    other(2),
				    trunk(3),
				    ppp(4),
				    cleartcp(5),
				    tunnelled(6)
				}
		MAX-ACCESS	read-only
		STATUS		current
		DESCRIPTION
			"Transport protocol"

	::= { sessionVpopEntry 4 }

	sessionVpopCurrentCount	OBJECT-TYPE
		SYNTAX		INTEGER
		MAX-ACCESS	read-only
		STATUS		current
		DESCRIPTION
			"The number of sessions currently active"

	::= { sessionVpopEntry 5 }

	sessionVpopCurrentDuration	OBJECT-TYPE
		SYNTAX		INTEGER
		MAX-ACCESS	read-only
		STATUS		current
		DESCRIPTION
			"The combined duration of all currently active
			sessions of this type, for this vpop."

	::= { sessionVpopEntry 6 }

	sessionVpopCumulativeCount	OBJECT-TYPE
		SYNTAX		INTEGER
		MAX-ACCESS	read-only
		STATUS		current
		DESCRIPTION
			"The cumulative number of sessions of this type, for
			this vpop, both active and inactive, since system
			boot"

	::= { sessionVpopEntry 7 }

	sessionVpopCumulativeDuration	OBJECT-TYPE
		SYNTAX		INTEGER
		MAX-ACCESS	read-only
		STATUS		current
		DESCRIPTION
			"The combined duration of of all sessions of this
			type, for this vpop, both active and inactive, since
			system boot"

	::= { sessionVpopEntry 8 }

-- This file generated from  slots.cml by smog.
-- date: Thu Jun 29 01:11:45  2000

	slotStatusTable	OBJECT-TYPE
		SYNTAX		SEQUENCE OF SlotStatusEntry
		MAX-ACCESS	not-accessible
		STATUS		obsolete
		DESCRIPTION
			"This table describes the status of the physical slots
			in a CVX switch. NOTE: cards in the CVX chassis report
			two card types per slot. The Service Module is the
			main logic board, residing in the 'front' of the slot.
			The Line Termination Module, residing in the 'back' of
			the slot, houses the data and power connectors for the
			system."

	::= { aptis-monitoring 201 }

	slotStatusEntry	OBJECT-TYPE
		SYNTAX		SlotStatusEntry
		MAX-ACCESS	not-accessible
		STATUS		current
		DESCRIPTION
			"This is the structure of entries in the
			 slotStatusTable."
		INDEX		{ slotStatusShelfNumber, slotStatusSlotIndex }
	::= { slotStatusTable 1 }

	SlotStatusEntry ::= SEQUENCE {
		slotStatusShelfNumber		INTEGER,
		slotStatusSlotIndex		INTEGER,
		slotStatusSlotStatus		INTEGER,
		slotStatusPartNumber		INTEGER,
		slotStatusSerialNumber		INTEGER,
		slotStatusHardwareRev		DisplayString,
		slotStatusStiffwareRev		DisplayString,
		slotStatusFirmwareRev		DisplayString,
		slotStatusSystemMem		INTEGER,
		slotStatusOtherMem		INTEGER,
		slotStatusTemperature		INTEGER,
		slotStatusSlotType		INTEGER,
		slotStatusSlotOos		INTEGER,
		slotStatusServiceModule		INTEGER,
		slotStatusLineTerminationModule	INTEGER
	}

	slotStatusShelfNumber	OBJECT-TYPE
		SYNTAX		INTEGER
		MAX-ACCESS	read-only
		STATUS		current
		DESCRIPTION
			"The number of the shelf in which this slot resides."

	::= { slotStatusEntry 1 }

	slotStatusSlotIndex	OBJECT-TYPE
		SYNTAX		INTEGER (1..32)
		MAX-ACCESS	read-only
		STATUS		current
		DESCRIPTION
			"The physical slot number."

	::= { slotStatusEntry 2 }

	slotStatusSlotStatus	OBJECT-TYPE
		SYNTAX		INTEGER {
				    slotStatusEmpty(0),
				    slotStatusNoPower(1),
				    slotStatusPresent(2),
				    slotStatusReady(3),
				    slotStatusLoading(4),
				    slotStatusStarted(5),
				    slotStatusIniting(6),
				    slotStatusUp(7),
				    slotStatusDown(8),
				    slotStatusUnknown(9),
				    slotStatusPulled(10),
				    slotStatusFailed(11),
				    slotStatusBadCard(12),
				    slotStatusStandby(13)
				}
		MAX-ACCESS	read-only
		STATUS		current
		DESCRIPTION
			"The current state of the slot card."

	::= { slotStatusEntry 3 }

	slotStatusPartNumber	OBJECT-TYPE
		SYNTAX		INTEGER
		MAX-ACCESS	read-only
		STATUS		current
		DESCRIPTION
			"Identifies the card in this slot by part number, The
			OID will be defined in the aptis-reg.aptis-components
			subtree."

	::= { slotStatusEntry 4 }

	slotStatusSerialNumber	OBJECT-TYPE
		SYNTAX		INTEGER
		MAX-ACCESS	read-only
		STATUS		current
		DESCRIPTION
			"The serial number of the card, as reported by the
			slot card hardware. If the slot card does not report a
			value, or if it is not currently readable, then this
			variable will have the value of zero."

	::= { slotStatusEntry 5 }

	slotStatusHardwareRev	OBJECT-TYPE
		SYNTAX		DisplayString (SIZE (0..64))
		MAX-ACCESS	read-only
		STATUS		current
		DESCRIPTION
			"The hardware revision of the card, as reported by the
			slot card hardware. If the slot card does not report a
			value, or if it is not currently readable, then this
			variable will have the value of zero."

	::= { slotStatusEntry 6 }

	slotStatusStiffwareRev	OBJECT-TYPE
		SYNTAX		DisplayString (SIZE (0..64))
		MAX-ACCESS	read-only
		STATUS		current
		DESCRIPTION
			"The stiffware revision of the card, as reported by
			the slot card hardware. If the slot card does not
			report a value, or if it is not currently readable,
			then this variable will have the value of zero."

	::= { slotStatusEntry 7 }

	slotStatusFirmwareRev	OBJECT-TYPE
		SYNTAX		DisplayString (SIZE (0..128))
		MAX-ACCESS	read-only
		STATUS		current
		DESCRIPTION
			"The revision string of the firmware running on the
			card, as reported by the firmware."

	::= { slotStatusEntry 8 }

	slotStatusSystemMem	OBJECT-TYPE
		SYNTAX		INTEGER
		MAX-ACCESS	read-only
		STATUS		current
		DESCRIPTION
			"The amount of memory, in Kilobytes, in the card's
			main memory region. If that amount is unknown, then
			this variable will have the value of zero."

	::= { slotStatusEntry 9 }

	slotStatusOtherMem	OBJECT-TYPE
		SYNTAX		INTEGER
		MAX-ACCESS	read-only
		STATUS		current
		DESCRIPTION
			"The amount of memory, in Kilobytes, in the card's
			auxilliary memory region. If that amount is unknown,
			then this variable will have the value of zero. NOTE
			that the exact nature and use of this memory may vary
			by slot card."

	::= { slotStatusEntry 10 }

	slotStatusTemperature	OBJECT-TYPE
		SYNTAX		INTEGER
		MAX-ACCESS	read-only
		STATUS		current
		DESCRIPTION
			"The temperature of the slot card as reported by
			hardware, in degrees Celsius."

	::= { slotStatusEntry 11 }

	slotStatusSlotType	OBJECT-TYPE
		SYNTAX		INTEGER {
				    slotEmpty(0),
				    slotScc(1),
				    slotMac(2),
				    slotDac(3),
				    slotUnknown(4)
				}
		MAX-ACCESS	read-only
		STATUS		current
		DESCRIPTION
			"The general type of the slot card. More specific
			detail on the type of card may be found in
			serviceModule and lineTerminationModule variables."

	::= { slotStatusEntry 12 }

	slotStatusSlotOos	OBJECT-TYPE
		SYNTAX		INTEGER
		MAX-ACCESS	read-only
		STATUS		current
		DESCRIPTION
			"Current oos value for this slot."

	::= { slotStatusEntry 13 }

	slotStatusServiceModule	OBJECT-TYPE
		SYNTAX		INTEGER
		MAX-ACCESS	read-only
		STATUS		current
		DESCRIPTION
			"The part number of the Service Module in this slot."

	::= { slotStatusEntry 14 }

	slotStatusLineTerminationModule	OBJECT-TYPE
		SYNTAX		INTEGER {
				    ltmEmpty(0),
				    dS3(820121),
				    dS3R(820131),
				    dS3P(820141),
				    dS3PR(820151),
				    t1(820322),
				    e1(820323)
				}
		MAX-ACCESS	read-only
		STATUS		current
		DESCRIPTION
			"The part number of the line termination module in
			this slot."

	::= { slotStatusEntry 15 }


	slotStatusNewTable	OBJECT-TYPE
		SYNTAX		SEQUENCE OF SlotStatusNewEntry
		MAX-ACCESS	not-accessible
		STATUS		current
		DESCRIPTION
			"This table describes the status of the physical slots
			in a CVX switch. NOTE: cards in the CVX chassis report
			two card types per slot. The Service Module is the
			main logic board, residing in the 'front' of the slot.
			The Line Termination Module, residing in the 'back' of
			the slot, houses the data and power connectors for the
			system. This table replaces the slot_status table
			which should be considered obsolete."

	::= { aptis-monitoring 205 }

	slotStatusNewEntry	OBJECT-TYPE
		SYNTAX		SlotStatusNewEntry
		MAX-ACCESS	not-accessible
		STATUS		current
		DESCRIPTION
			"This is the structure of entries in the
			 slotStatusNewTable."
		INDEX		{ slotStatusNewShelfNumber, slotStatusNewSlotIndex }
	::= { slotStatusNewTable 1 }

	SlotStatusNewEntry ::= SEQUENCE {
		slotStatusNewShelfNumber	INTEGER,
		slotStatusNewSlotIndex		INTEGER,
		slotStatusNewSlotStatus		INTEGER,
		slotStatusNewSlotType		INTEGER,
		slotStatusNewProductCode	DisplayString,
		slotStatusNewSlotSerialNumber	DisplayString,
		slotStatusNewFabricationRev	DisplayString,
		slotStatusNewPalRev		DisplayString,
		slotStatusNewReworkRev		INTEGER,
		slotStatusNewFirmwareRev	DisplayString,
		slotStatusNewTemperature	INTEGER,
		slotStatusNewSlotOos		INTEGER,
		slotStatusNewLineTerminationModuleType INTEGER
	}

	slotStatusNewShelfNumber	OBJECT-TYPE
		SYNTAX		INTEGER
		MAX-ACCESS	read-only
		STATUS		current
		DESCRIPTION
			"The number of the shelf in which this slot resides."

	::= { slotStatusNewEntry 1 }

	slotStatusNewSlotIndex	OBJECT-TYPE
		SYNTAX		INTEGER (1..32)
		MAX-ACCESS	read-only
		STATUS		current
		DESCRIPTION
			"The physical slot number."

	::= { slotStatusNewEntry 2 }

	slotStatusNewSlotStatus	OBJECT-TYPE
		SYNTAX		INTEGER {
				    slotStatusEmpty(0),
				    slotStatusNoPower(1),
				    slotStatusPresent(2),
				    slotStatusReady(3),
				    slotStatusLoading(4),
				    slotStatusStarted(5),
				    slotStatusIniting(6),
				    slotStatusUp(7),
				    slotStatusDown(8),
				    slotStatusUnknown(9),
				    slotStatusPulled(10),
				    slotStatusFailed(11),
				    slotStatusBadCard(12),
				    slotStatusStandby(13)
				}
		MAX-ACCESS	read-only
		STATUS		current
		DESCRIPTION
			"The current state of the slot card."

	::= { slotStatusNewEntry 3 }

	slotStatusNewSlotType	OBJECT-TYPE
		SYNTAX		INTEGER {
				    slotEmpty(0),
				    slotScc(1),
				    slotMac(2),
				    slotDac(3),
				    slotUnknown(4)
				}
		MAX-ACCESS	read-only
		STATUS		current
		DESCRIPTION
			"The general type of the slot card. More specific
			detail on the type of card may be found in
			serviceModule and lineTerminationModule variables."

	::= { slotStatusNewEntry 4 }

	slotStatusNewProductCode	OBJECT-TYPE
		SYNTAX		DisplayString (SIZE (0..11))
		MAX-ACCESS	read-only
		STATUS		current
		DESCRIPTION
			"Identifies the card in this slot by part number."

	::= { slotStatusNewEntry 5 }

	slotStatusNewSlotSerialNumber	OBJECT-TYPE
		SYNTAX		DisplayString (SIZE (0..15))
		MAX-ACCESS	read-only
		STATUS		current
		DESCRIPTION
			"The serial number of the card, as reported by the
			slot card hardware. If the slot card does not report a
			value, or if it is not currently readable, then this
			variable will have the value of zero."

	::= { slotStatusNewEntry 6 }

	slotStatusNewFabricationRev	OBJECT-TYPE
		SYNTAX		DisplayString (SIZE (0..1))
		MAX-ACCESS	read-only
		STATUS		current
		DESCRIPTION
			"The hardware revision of the card, as reported by the
			slot card hardware. If the slot card does not report a
			value, or if it is not currently readable, then this
			variable will have the value of zero."

	::= { slotStatusNewEntry 7 }

	slotStatusNewPalRev	OBJECT-TYPE
		SYNTAX		DisplayString (SIZE (0..1))
		MAX-ACCESS	read-only
		STATUS		current
		DESCRIPTION
			"The PAL revision of the card, as reported by the slot
			card hardware. If the slot card does not report a
			value, or if it is not currently readable, then this
			variable will have the value of zero."

	::= { slotStatusNewEntry 8 }

	slotStatusNewReworkRev	OBJECT-TYPE
		SYNTAX		INTEGER
		MAX-ACCESS	read-only
		STATUS		current
		DESCRIPTION
			"The rework revision of the card, as reported by the
			slot card hardware. If the slot card does not report a
			value, or if it is not currently readable, then this
			variable will have the value of zero."

	::= { slotStatusNewEntry 9 }

	slotStatusNewFirmwareRev	OBJECT-TYPE
		SYNTAX		DisplayString (SIZE (0..128))
		MAX-ACCESS	read-only
		STATUS		current
		DESCRIPTION
			"The revision string of the firmware running on the
			card, as reported by the firmware."

	::= { slotStatusNewEntry 10 }

	slotStatusNewTemperature	OBJECT-TYPE
		SYNTAX		INTEGER
		MAX-ACCESS	read-only
		STATUS		current
		DESCRIPTION
			"The temperature of the slot card as reported by
			hardware, in degrees Celsius."

	::= { slotStatusNewEntry 11 }

	slotStatusNewSlotOos	OBJECT-TYPE
		SYNTAX		INTEGER
		MAX-ACCESS	read-only
		STATUS		current
		DESCRIPTION
			"Current oos value for this slot."

	::= { slotStatusNewEntry 12 }

	slotStatusNewLineTerminationModuleType	OBJECT-TYPE
		SYNTAX		INTEGER {
				    ltmEmpty(0),
				    dS3(820121),
				    dS3R(820131),
				    dS3P(820141),
				    dS3PR(820151),
				    t1(820322),
				    e1(820323),
				    t1x24(820324),
				    e1x24(820325),
				    dS3x2(820326),
				    dS3x2R(820327),
				    dS3x2P(820328),
				    dS3x2PR(820329)
				}
		MAX-ACCESS	read-only
		STATUS		current
		DESCRIPTION
			"The type of line termination module connected to the
			card in this slot. If no line termination module is
			connected, this value is 0."

	::= { slotStatusNewEntry 13 }


	timerStatsTable	OBJECT-TYPE
		SYNTAX		SEQUENCE OF TimerStatsEntry
		MAX-ACCESS	not-accessible
		STATUS		current
		DESCRIPTION
			"timer stats"

	::= { aptis-monitoring 3601 }

	timerStatsEntry	OBJECT-TYPE
		SYNTAX		TimerStatsEntry
		MAX-ACCESS	not-accessible
		STATUS		current
		DESCRIPTION
			"This is the structure of entries in the
			 timerStatsTable."
		INDEX		{ timerStatsSlotNumber }
	::= { timerStatsTable 1 }

	TimerStatsEntry ::= SEQUENCE {
		timerStatsSlotNumber		INTEGER,
		timerStatsCardType		INTEGER,
		timerStatsCPUNumber		INTEGER,
		timerStatsTimerEntrySize	INTEGER,
		timerStatsTimerMemorySize	INTEGER,
		timerStatsTotalCount		INTEGER,
		timerStatsFreeCount		INTEGER,
		timerStatsFreeMin		INTEGER,
		timerStatsActiveCount		INTEGER,
		timerStatsActiveMax		INTEGER,
		timerStatsAllocSuccesses	INTEGER,
		timerStatsAllocFails		INTEGER,
		timerStatsFreeSuccesses		INTEGER,
		timerStatsFreeFails		INTEGER
	}

	timerStatsSlotNumber	OBJECT-TYPE
		SYNTAX		INTEGER
		MAX-ACCESS	read-only
		STATUS		current
		DESCRIPTION
			"Slot number"

	::= { timerStatsEntry 1 }

	timerStatsCardType	OBJECT-TYPE
		SYNTAX		INTEGER {
				    unknown(0),
				    sCC(1),
				    dAC(2),
				    mAC(3)
				}
		MAX-ACCESS	read-only
		STATUS		current
		DESCRIPTION
			"Type of card reporting timer information"

	::= { timerStatsEntry 2 }

	timerStatsCPUNumber	OBJECT-TYPE
		SYNTAX		INTEGER
		MAX-ACCESS	read-only
		STATUS		current
		DESCRIPTION
			"CPU number (0 = main CPU, 1..n = IOP)"

	::= { timerStatsEntry 3 }

	timerStatsTimerEntrySize	OBJECT-TYPE
		SYNTAX		INTEGER
		MAX-ACCESS	read-only
		STATUS		current
		DESCRIPTION
			"Size of each timer data structure"

	::= { timerStatsEntry 101 }

	timerStatsTimerMemorySize	OBJECT-TYPE
		SYNTAX		INTEGER
		MAX-ACCESS	read-only
		STATUS		current
		DESCRIPTION
			"Total amount of memory used for timer entries"

	::= { timerStatsEntry 102 }

	timerStatsTotalCount	OBJECT-TYPE
		SYNTAX		INTEGER
		MAX-ACCESS	read-only
		STATUS		current
		DESCRIPTION
			"Total number of timer entries created"

	::= { timerStatsEntry 201 }

	timerStatsFreeCount	OBJECT-TYPE
		SYNTAX		INTEGER
		MAX-ACCESS	read-only
		STATUS		current
		DESCRIPTION
			"Total number of timer entries currently unused"

	::= { timerStatsEntry 202 }

	timerStatsFreeMin	OBJECT-TYPE
		SYNTAX		INTEGER
		MAX-ACCESS	read-only
		STATUS		current
		DESCRIPTION
			"Minimum number of timer entries unused"

	::= { timerStatsEntry 203 }

	timerStatsActiveCount	OBJECT-TYPE
		SYNTAX		INTEGER
		MAX-ACCESS	read-only
		STATUS		current
		DESCRIPTION
			"Total number of timer entries currently active"

	::= { timerStatsEntry 204 }

	timerStatsActiveMax	OBJECT-TYPE
		SYNTAX		INTEGER
		MAX-ACCESS	read-only
		STATUS		current
		DESCRIPTION
			"Maximum number of timer entries active"

	::= { timerStatsEntry 205 }

	timerStatsAllocSuccesses	OBJECT-TYPE
		SYNTAX		INTEGER
		MAX-ACCESS	read-only
		STATUS		current
		DESCRIPTION
			"Number of timers successfully allocated"

	::= { timerStatsEntry 301 }

	timerStatsAllocFails	OBJECT-TYPE
		SYNTAX		INTEGER
		MAX-ACCESS	read-only
		STATUS		current
		DESCRIPTION
			"Number of timer allocations that failed"

	::= { timerStatsEntry 302 }

	timerStatsFreeSuccesses	OBJECT-TYPE
		SYNTAX		INTEGER
		MAX-ACCESS	read-only
		STATUS		current
		DESCRIPTION
			"Number of timers successfully freed"

	::= { timerStatsEntry 303 }

	timerStatsFreeFails	OBJECT-TYPE
		SYNTAX		INTEGER
		MAX-ACCESS	read-only
		STATUS		current
		DESCRIPTION
			"Number of timer frees that failed"

	::= { timerStatsEntry 304 }


	memoryStatsTableTable	OBJECT-TYPE
		SYNTAX		SEQUENCE OF MemoryStatsTableEntry
		MAX-ACCESS	not-accessible
		STATUS		current
		DESCRIPTION
			"memory stats table"

	::= { aptis-monitoring 3605 }

	memoryStatsTableEntry	OBJECT-TYPE
		SYNTAX		MemoryStatsTableEntry
		MAX-ACCESS	not-accessible
		STATUS		current
		DESCRIPTION
			"This is the structure of entries in the
			 memoryStatsTableTable."
		INDEX		{ memoryStatsTableSlotNumber }
	::= { memoryStatsTableTable 1 }

	MemoryStatsTableEntry ::= SEQUENCE {
		memoryStatsTableSlotNumber	INTEGER,
		memoryStatsTableCardType	INTEGER,
		memoryStatsTableCPUNumber	INTEGER,
		memoryStatsTableTotalSize	INTEGER,
		memoryStatsTableManagedSize	INTEGER,
		memoryStatsTableFreeSize	INTEGER,
		memoryStatsTableFreeBlockCount	INTEGER,
		memoryStatsTableFreeLargestBlock INTEGER,
		memoryStatsTableFreeSmallestBlock INTEGER,
		memoryStatsTableUsedSize	INTEGER,
		memoryStatsTableUsedBlockCount	INTEGER,
		memoryStatsTableUsedLargestBlock INTEGER,
		memoryStatsTableUsedSmallestBlock INTEGER,
		memoryStatsTableAllocSuccesses	INTEGER,
		memoryStatsTableAllocFails	INTEGER,
		memoryStatsTableFreeSuccesses	INTEGER,
		memoryStatsTableFreeFails	INTEGER
	}

	memoryStatsTableSlotNumber	OBJECT-TYPE
		SYNTAX		INTEGER {
				    bep(1),
				    fep(2),
				    slot1(3),
				    slot2(4),
				    slot3(5),
				    slot4(6),
				    slot5(7),
				    slot6(8),
				    slot7(9),
				    slot8(10),
				    slot11(11),
				    slot12(12),
				    slot13(13),
				    slot14(14),
				    slot15(15),
				    slot16(16),
				    slot17(17),
				    slot18(18)
				}
		MAX-ACCESS	read-only
		STATUS		current
		DESCRIPTION
			"Slot number"

	::= { memoryStatsTableEntry 1 }

	memoryStatsTableCardType	OBJECT-TYPE
		SYNTAX		INTEGER {
				    unk(0),
				    sCC(1),
				    dAC(2),
				    mAC(3)
				}
		MAX-ACCESS	read-only
		STATUS		current
		DESCRIPTION
			"Type of card reporting timer information"

	::= { memoryStatsTableEntry 2 }

	memoryStatsTableCPUNumber	OBJECT-TYPE
		SYNTAX		INTEGER
		MAX-ACCESS	read-only
		STATUS		current
		DESCRIPTION
			"CPU number (0 = main CPU, 1..n = IOP)"

	::= { memoryStatsTableEntry 3 }

	memoryStatsTableTotalSize	OBJECT-TYPE
		SYNTAX		INTEGER
		MAX-ACCESS	read-only
		STATUS		current
		DESCRIPTION
			"Total amount of memory available to CPU"

	::= { memoryStatsTableEntry 101 }

	memoryStatsTableManagedSize	OBJECT-TYPE
		SYNTAX		INTEGER
		MAX-ACCESS	read-only
		STATUS		current
		DESCRIPTION
			"Amount of memory given to memory allocation system"

	::= { memoryStatsTableEntry 102 }

	memoryStatsTableFreeSize	OBJECT-TYPE
		SYNTAX		INTEGER
		MAX-ACCESS	read-only
		STATUS		current
		DESCRIPTION
			"Amount of free memory"

	::= { memoryStatsTableEntry 201 }

	memoryStatsTableFreeBlockCount	OBJECT-TYPE
		SYNTAX		INTEGER
		MAX-ACCESS	read-only
		STATUS		current
		DESCRIPTION
			"Size of largest free block"

	::= { memoryStatsTableEntry 202 }

	memoryStatsTableFreeLargestBlock	OBJECT-TYPE
		SYNTAX		INTEGER
		MAX-ACCESS	read-only
		STATUS		current
		DESCRIPTION
			"Size of largest free block"

	::= { memoryStatsTableEntry 203 }

	memoryStatsTableFreeSmallestBlock	OBJECT-TYPE
		SYNTAX		INTEGER
		MAX-ACCESS	read-only
		STATUS		current
		DESCRIPTION
			"Size of smallest free block"

	::= { memoryStatsTableEntry 204 }

	memoryStatsTableUsedSize	OBJECT-TYPE
		SYNTAX		INTEGER
		MAX-ACCESS	read-only
		STATUS		current
		DESCRIPTION
			"Amount of used memory"

	::= { memoryStatsTableEntry 301 }

	memoryStatsTableUsedBlockCount	OBJECT-TYPE
		SYNTAX		INTEGER
		MAX-ACCESS	read-only
		STATUS		current
		DESCRIPTION
			"Size of largest used block"

	::= { memoryStatsTableEntry 302 }

	memoryStatsTableUsedLargestBlock	OBJECT-TYPE
		SYNTAX		INTEGER
		MAX-ACCESS	read-only
		STATUS		current
		DESCRIPTION
			"Size of largest used block"

	::= { memoryStatsTableEntry 303 }

	memoryStatsTableUsedSmallestBlock	OBJECT-TYPE
		SYNTAX		INTEGER
		MAX-ACCESS	read-only
		STATUS		current
		DESCRIPTION
			"Size of smallest used block"

	::= { memoryStatsTableEntry 304 }

	memoryStatsTableAllocSuccesses	OBJECT-TYPE
		SYNTAX		INTEGER
		MAX-ACCESS	read-only
		STATUS		current
		DESCRIPTION
			"Number of successful allocations"

	::= { memoryStatsTableEntry 401 }

	memoryStatsTableAllocFails	OBJECT-TYPE
		SYNTAX		INTEGER
		MAX-ACCESS	read-only
		STATUS		current
		DESCRIPTION
			"Number of failed allocations"

	::= { memoryStatsTableEntry 402 }

	memoryStatsTableFreeSuccesses	OBJECT-TYPE
		SYNTAX		INTEGER
		MAX-ACCESS	read-only
		STATUS		current
		DESCRIPTION
			"Number of successful frees"

	::= { memoryStatsTableEntry 403 }

	memoryStatsTableFreeFails	OBJECT-TYPE
		SYNTAX		INTEGER
		MAX-ACCESS	read-only
		STATUS		current
		DESCRIPTION
			"Number of failed frees"

	::= { memoryStatsTableEntry 404 }


	pbufStatsTable	OBJECT-TYPE
		SYNTAX		SEQUENCE OF PbufStatsEntry
		MAX-ACCESS	not-accessible
		STATUS		current
		DESCRIPTION
			"pbuf stats"

	::= { aptis-monitoring 3603 }

	pbufStatsEntry	OBJECT-TYPE
		SYNTAX		PbufStatsEntry
		MAX-ACCESS	not-accessible
		STATUS		current
		DESCRIPTION
			"This is the structure of entries in the
			 pbufStatsTable."
		INDEX		{ pbufStatsSlotNumber }
	::= { pbufStatsTable 1 }

	PbufStatsEntry ::= SEQUENCE {
		pbufStatsSlotNumber		INTEGER,
		pbufStatsCardType		INTEGER,
		pbufStatsCPUNumber		INTEGER,
		pbufStatsDataSize0		INTEGER,
		pbufStatsTotalCount0		INTEGER,
		pbufStatsAllocatedCount0	INTEGER,
		pbufStatsPermAllocatedCount0	INTEGER,
		pbufStatsAllocatedMax0		INTEGER,
		pbufStatsFreeCount0		INTEGER,
		pbufStatsFreeMin0		INTEGER,
		pbufStatsAllocSuccesses0	INTEGER,
		pbufStatsAllocFails0		INTEGER,
		pbufStatsFreeSuccesses0		INTEGER,
		pbufStatsFreeFails0		INTEGER,
		pbufStatsDataSize1		INTEGER,
		pbufStatsTotalCount1		INTEGER,
		pbufStatsAllocatedCount1	INTEGER,
		pbufStatsPermAllocatedCount1	INTEGER,
		pbufStatsAllocatedMax1		INTEGER,
		pbufStatsFreeCount1		INTEGER,
		pbufStatsFreeMin1		INTEGER,
		pbufStatsAllocSuccesses1	INTEGER,
		pbufStatsAllocFails1		INTEGER,
		pbufStatsFreeSuccesses1		INTEGER,
		pbufStatsFreeFails1		INTEGER,
		pbufStatsDataSize2		INTEGER,
		pbufStatsTotalCount2		INTEGER,
		pbufStatsAllocatedCount2	INTEGER,
		pbufStatsPermAllocatedCount2	INTEGER,
		pbufStatsAllocatedMax2		INTEGER,
		pbufStatsFreeCount2		INTEGER,
		pbufStatsFreeMin2		INTEGER,
		pbufStatsAllocSuccesses2	INTEGER,
		pbufStatsAllocFails2		INTEGER,
		pbufStatsFreeSuccesses2		INTEGER,
		pbufStatsFreeFails2		INTEGER,
		pbufStatsDataSize3		INTEGER,
		pbufStatsTotalCount3		INTEGER,
		pbufStatsAllocatedCount3	INTEGER,
		pbufStatsPermAllocatedCount3	INTEGER,
		pbufStatsAllocatedMax3		INTEGER,
		pbufStatsFreeCount3		INTEGER,
		pbufStatsFreeMin3		INTEGER,
		pbufStatsAllocSuccesses3	INTEGER,
		pbufStatsAllocFails3		INTEGER,
		pbufStatsFreeSuccesses3		INTEGER,
		pbufStatsFreeFails3		INTEGER,
		pbufStatsDataSize4		INTEGER,
		pbufStatsTotalCount4		INTEGER,
		pbufStatsAllocatedCount4	INTEGER,
		pbufStatsPermAllocatedCount4	INTEGER,
		pbufStatsAllocatedMax4		INTEGER,
		pbufStatsFreeCount4		INTEGER,
		pbufStatsFreeMin4		INTEGER,
		pbufStatsAllocSuccesses4	INTEGER,
		pbufStatsAllocFails4		INTEGER,
		pbufStatsFreeSuccesses4		INTEGER,
		pbufStatsFreeFails4		INTEGER,
		pbufStatsDataSize5		INTEGER,
		pbufStatsTotalCount5		INTEGER,
		pbufStatsAllocatedCount5	INTEGER,
		pbufStatsPermAllocatedCount5	INTEGER,
		pbufStatsAllocatedMax5		INTEGER,
		pbufStatsFreeCount5		INTEGER,
		pbufStatsFreeMin5		INTEGER,
		pbufStatsAllocSuccesses5	INTEGER,
		pbufStatsAllocFails5		INTEGER,
		pbufStatsFreeSuccesses5		INTEGER,
		pbufStatsFreeFails5		INTEGER
	}

	pbufStatsSlotNumber	OBJECT-TYPE
		SYNTAX		INTEGER
		MAX-ACCESS	read-only
		STATUS		current
		DESCRIPTION
			"Slot number"

	::= { pbufStatsEntry 1 }

	pbufStatsCardType	OBJECT-TYPE
		SYNTAX		INTEGER {
				    unknown(0),
				    sCC(1),
				    tSC(2),
				    mAC(3)
				}
		MAX-ACCESS	read-only
		STATUS		current
		DESCRIPTION
			"Type of card reporting timer information"

	::= { pbufStatsEntry 2 }

	pbufStatsCPUNumber	OBJECT-TYPE
		SYNTAX		INTEGER
		MAX-ACCESS	read-only
		STATUS		current
		DESCRIPTION
			"CPU number (0 = main CPU, 1..n = IOP)"

	::= { pbufStatsEntry 3 }

	pbufStatsDataSize0	OBJECT-TYPE
		SYNTAX		INTEGER
		MAX-ACCESS	read-only
		STATUS		current
		DESCRIPTION
			"User data size of size-0 buffers"

	::= { pbufStatsEntry 101 }

	pbufStatsTotalCount0	OBJECT-TYPE
		SYNTAX		INTEGER
		MAX-ACCESS	read-only
		STATUS		current
		DESCRIPTION
			"Number of size-0 buffers created"

	::= { pbufStatsEntry 102 }

	pbufStatsAllocatedCount0	OBJECT-TYPE
		SYNTAX		INTEGER
		MAX-ACCESS	read-only
		STATUS		current
		DESCRIPTION
			"Number of size-0 buffers currently allocated"

	::= { pbufStatsEntry 103 }

	pbufStatsPermAllocatedCount0	OBJECT-TYPE
		SYNTAX		INTEGER
		MAX-ACCESS	read-only
		STATUS		current
		DESCRIPTION
			"Number of size-0 buffers permanently allocated"

	::= { pbufStatsEntry 104 }

	pbufStatsAllocatedMax0	OBJECT-TYPE
		SYNTAX		INTEGER
		MAX-ACCESS	read-only
		STATUS		current
		DESCRIPTION
			"Maximum number of size-0 buffers allocated"

	::= { pbufStatsEntry 105 }

	pbufStatsFreeCount0	OBJECT-TYPE
		SYNTAX		INTEGER
		MAX-ACCESS	read-only
		STATUS		current
		DESCRIPTION
			"Number of size-0 buffers currently free"

	::= { pbufStatsEntry 106 }

	pbufStatsFreeMin0	OBJECT-TYPE
		SYNTAX		INTEGER
		MAX-ACCESS	read-only
		STATUS		current
		DESCRIPTION
			"Minimum number of size-0 buffers free"

	::= { pbufStatsEntry 107 }

	pbufStatsAllocSuccesses0	OBJECT-TYPE
		SYNTAX		INTEGER
		MAX-ACCESS	read-only
		STATUS		current
		DESCRIPTION
			"Number of successful size-0 buffer allocations"

	::= { pbufStatsEntry 108 }

	pbufStatsAllocFails0	OBJECT-TYPE
		SYNTAX		INTEGER
		MAX-ACCESS	read-only
		STATUS		current
		DESCRIPTION
			"Number of failed size-0 buffer allocations"

	::= { pbufStatsEntry 109 }

	pbufStatsFreeSuccesses0	OBJECT-TYPE
		SYNTAX		INTEGER
		MAX-ACCESS	read-only
		STATUS		current
		DESCRIPTION
			"Number of successful size-0 buffer frees"

	::= { pbufStatsEntry 110 }

	pbufStatsFreeFails0	OBJECT-TYPE
		SYNTAX		INTEGER
		MAX-ACCESS	read-only
		STATUS		current
		DESCRIPTION
			"Number of failed size-0 buffer frees"

	::= { pbufStatsEntry 111 }

	pbufStatsDataSize1	OBJECT-TYPE
		SYNTAX		INTEGER
		MAX-ACCESS	read-only
		STATUS		current
		DESCRIPTION
			"User data size of size-1 buffers"

	::= { pbufStatsEntry 201 }

	pbufStatsTotalCount1	OBJECT-TYPE
		SYNTAX		INTEGER
		MAX-ACCESS	read-only
		STATUS		current
		DESCRIPTION
			"Number of size-1 buffers created"

	::= { pbufStatsEntry 202 }

	pbufStatsAllocatedCount1	OBJECT-TYPE
		SYNTAX		INTEGER
		MAX-ACCESS	read-only
		STATUS		current
		DESCRIPTION
			"Number of size-1 buffers currently allocated"

	::= { pbufStatsEntry 203 }

	pbufStatsPermAllocatedCount1	OBJECT-TYPE
		SYNTAX		INTEGER
		MAX-ACCESS	read-only
		STATUS		current
		DESCRIPTION
			"Number of size-1 buffers permanently allocated"

	::= { pbufStatsEntry 204 }

	pbufStatsAllocatedMax1	OBJECT-TYPE
		SYNTAX		INTEGER
		MAX-ACCESS	read-only
		STATUS		current
		DESCRIPTION
			"Maximum number of size-1 buffers allocated"

	::= { pbufStatsEntry 205 }

	pbufStatsFreeCount1	OBJECT-TYPE
		SYNTAX		INTEGER
		MAX-ACCESS	read-only
		STATUS		current
		DESCRIPTION
			"Number of size-1 buffers currently free"

	::= { pbufStatsEntry 206 }

	pbufStatsFreeMin1	OBJECT-TYPE
		SYNTAX		INTEGER
		MAX-ACCESS	read-only
		STATUS		current
		DESCRIPTION
			"Minimum number of size-1 buffers free"

	::= { pbufStatsEntry 207 }

	pbufStatsAllocSuccesses1	OBJECT-TYPE
		SYNTAX		INTEGER
		MAX-ACCESS	read-only
		STATUS		current
		DESCRIPTION
			"Number of successful size-1 buffer allocations"

	::= { pbufStatsEntry 208 }

	pbufStatsAllocFails1	OBJECT-TYPE
		SYNTAX		INTEGER
		MAX-ACCESS	read-only
		STATUS		current
		DESCRIPTION
			"Number of failed size-1 buffer allocations"

	::= { pbufStatsEntry 209 }

	pbufStatsFreeSuccesses1	OBJECT-TYPE
		SYNTAX		INTEGER
		MAX-ACCESS	read-only
		STATUS		current
		DESCRIPTION
			"Number of successful size-1 buffer frees"

	::= { pbufStatsEntry 210 }

	pbufStatsFreeFails1	OBJECT-TYPE
		SYNTAX		INTEGER
		MAX-ACCESS	read-only
		STATUS		current
		DESCRIPTION
			"Number of failed size-1 buffer frees"

	::= { pbufStatsEntry 211 }

	pbufStatsDataSize2	OBJECT-TYPE
		SYNTAX		INTEGER
		MAX-ACCESS	read-only
		STATUS		current
		DESCRIPTION
			"User data size of size-2 buffers"

	::= { pbufStatsEntry 301 }

	pbufStatsTotalCount2	OBJECT-TYPE
		SYNTAX		INTEGER
		MAX-ACCESS	read-only
		STATUS		current
		DESCRIPTION
			"Number of size-2 buffers created"

	::= { pbufStatsEntry 302 }

	pbufStatsAllocatedCount2	OBJECT-TYPE
		SYNTAX		INTEGER
		MAX-ACCESS	read-only
		STATUS		current
		DESCRIPTION
			"Number of size-2 buffers currently allocated"

	::= { pbufStatsEntry 303 }

	pbufStatsPermAllocatedCount2	OBJECT-TYPE
		SYNTAX		INTEGER
		MAX-ACCESS	read-only
		STATUS		current
		DESCRIPTION
			"Number of size-2 buffers permanently allocated"

	::= { pbufStatsEntry 304 }

	pbufStatsAllocatedMax2	OBJECT-TYPE
		SYNTAX		INTEGER
		MAX-ACCESS	read-only
		STATUS		current
		DESCRIPTION
			"Maximum number of size-2 buffers allocated"

	::= { pbufStatsEntry 305 }

	pbufStatsFreeCount2	OBJECT-TYPE
		SYNTAX		INTEGER
		MAX-ACCESS	read-only
		STATUS		current
		DESCRIPTION
			"Number of size-2 buffers currently free"

	::= { pbufStatsEntry 306 }

	pbufStatsFreeMin2	OBJECT-TYPE
		SYNTAX		INTEGER
		MAX-ACCESS	read-only
		STATUS		current
		DESCRIPTION
			"Minimum number of size-2 buffers free"

	::= { pbufStatsEntry 307 }

	pbufStatsAllocSuccesses2	OBJECT-TYPE
		SYNTAX		INTEGER
		MAX-ACCESS	read-only
		STATUS		current
		DESCRIPTION
			"Number of successful size-2 buffer allocations"

	::= { pbufStatsEntry 308 }

	pbufStatsAllocFails2	OBJECT-TYPE
		SYNTAX		INTEGER
		MAX-ACCESS	read-only
		STATUS		current
		DESCRIPTION
			"Number of failed size-2 buffer allocations"

	::= { pbufStatsEntry 309 }

	pbufStatsFreeSuccesses2	OBJECT-TYPE
		SYNTAX		INTEGER
		MAX-ACCESS	read-only
		STATUS		current
		DESCRIPTION
			"Number of successful size-2 buffer frees"

	::= { pbufStatsEntry 310 }

	pbufStatsFreeFails2	OBJECT-TYPE
		SYNTAX		INTEGER
		MAX-ACCESS	read-only
		STATUS		current
		DESCRIPTION
			"Number of failed size-2 buffer frees"

	::= { pbufStatsEntry 311 }

	pbufStatsDataSize3	OBJECT-TYPE
		SYNTAX		INTEGER
		MAX-ACCESS	read-only
		STATUS		current
		DESCRIPTION
			"User data size of size-3 buffers"

	::= { pbufStatsEntry 401 }

	pbufStatsTotalCount3	OBJECT-TYPE
		SYNTAX		INTEGER
		MAX-ACCESS	read-only
		STATUS		current
		DESCRIPTION
			"Number of size-3 buffers created"

	::= { pbufStatsEntry 402 }

	pbufStatsAllocatedCount3	OBJECT-TYPE
		SYNTAX		INTEGER
		MAX-ACCESS	read-only
		STATUS		current
		DESCRIPTION
			"Number of size-3 buffers currently allocated"

	::= { pbufStatsEntry 403 }

	pbufStatsPermAllocatedCount3	OBJECT-TYPE
		SYNTAX		INTEGER
		MAX-ACCESS	read-only
		STATUS		current
		DESCRIPTION
			"Number of size-3 buffers permanently allocated"

	::= { pbufStatsEntry 404 }

	pbufStatsAllocatedMax3	OBJECT-TYPE
		SYNTAX		INTEGER
		MAX-ACCESS	read-only
		STATUS		current
		DESCRIPTION
			"Maximum number of size-3 buffers allocated"

	::= { pbufStatsEntry 405 }

	pbufStatsFreeCount3	OBJECT-TYPE
		SYNTAX		INTEGER
		MAX-ACCESS	read-only
		STATUS		current
		DESCRIPTION
			"Number of size-3 buffers currently free"

	::= { pbufStatsEntry 406 }

	pbufStatsFreeMin3	OBJECT-TYPE
		SYNTAX		INTEGER
		MAX-ACCESS	read-only
		STATUS		current
		DESCRIPTION
			"Minimum number of size-3 buffers free"

	::= { pbufStatsEntry 407 }

	pbufStatsAllocSuccesses3	OBJECT-TYPE
		SYNTAX		INTEGER
		MAX-ACCESS	read-only
		STATUS		current
		DESCRIPTION
			"Number of successful size-3 buffer allocations"

	::= { pbufStatsEntry 408 }

	pbufStatsAllocFails3	OBJECT-TYPE
		SYNTAX		INTEGER
		MAX-ACCESS	read-only
		STATUS		current
		DESCRIPTION
			"Number of failed size-3 buffer allocations"

	::= { pbufStatsEntry 409 }

	pbufStatsFreeSuccesses3	OBJECT-TYPE
		SYNTAX		INTEGER
		MAX-ACCESS	read-only
		STATUS		current
		DESCRIPTION
			"Number of successful size-3 buffer frees"

	::= { pbufStatsEntry 410 }

	pbufStatsFreeFails3	OBJECT-TYPE
		SYNTAX		INTEGER
		MAX-ACCESS	read-only
		STATUS		current
		DESCRIPTION
			"Number of failed size-3 buffer frees"

	::= { pbufStatsEntry 411 }

	pbufStatsDataSize4	OBJECT-TYPE
		SYNTAX		INTEGER
		MAX-ACCESS	read-only
		STATUS		current
		DESCRIPTION
			"User data size of size-4 buffers"

	::= { pbufStatsEntry 501 }

	pbufStatsTotalCount4	OBJECT-TYPE
		SYNTAX		INTEGER
		MAX-ACCESS	read-only
		STATUS		current
		DESCRIPTION
			"Number of size-4 buffers created"

	::= { pbufStatsEntry 502 }

	pbufStatsAllocatedCount4	OBJECT-TYPE
		SYNTAX		INTEGER
		MAX-ACCESS	read-only
		STATUS		current
		DESCRIPTION
			"Number of size-4 buffers currently allocated"

	::= { pbufStatsEntry 503 }

	pbufStatsPermAllocatedCount4	OBJECT-TYPE
		SYNTAX		INTEGER
		MAX-ACCESS	read-only
		STATUS		current
		DESCRIPTION
			"Number of size-4 buffers permanently allocated"

	::= { pbufStatsEntry 504 }

	pbufStatsAllocatedMax4	OBJECT-TYPE
		SYNTAX		INTEGER
		MAX-ACCESS	read-only
		STATUS		current
		DESCRIPTION
			"Maximum number of size-4 buffers allocated"

	::= { pbufStatsEntry 505 }

	pbufStatsFreeCount4	OBJECT-TYPE
		SYNTAX		INTEGER
		MAX-ACCESS	read-only
		STATUS		current
		DESCRIPTION
			"Number of size-4 buffers currently free"

	::= { pbufStatsEntry 506 }

	pbufStatsFreeMin4	OBJECT-TYPE
		SYNTAX		INTEGER
		MAX-ACCESS	read-only
		STATUS		current
		DESCRIPTION
			"Minimum number of size-4 buffers free"

	::= { pbufStatsEntry 507 }

	pbufStatsAllocSuccesses4	OBJECT-TYPE
		SYNTAX		INTEGER
		MAX-ACCESS	read-only
		STATUS		current
		DESCRIPTION
			"Number of successful size-4 buffer allocations"

	::= { pbufStatsEntry 508 }

	pbufStatsAllocFails4	OBJECT-TYPE
		SYNTAX		INTEGER
		MAX-ACCESS	read-only
		STATUS		current
		DESCRIPTION
			"Number of failed size-4 buffer allocations"

	::= { pbufStatsEntry 509 }

	pbufStatsFreeSuccesses4	OBJECT-TYPE
		SYNTAX		INTEGER
		MAX-ACCESS	read-only
		STATUS		current
		DESCRIPTION
			"Number of successful size-4 buffer frees"

	::= { pbufStatsEntry 510 }

	pbufStatsFreeFails4	OBJECT-TYPE
		SYNTAX		INTEGER
		MAX-ACCESS	read-only
		STATUS		current
		DESCRIPTION
			"Number of failed size-4 buffer frees"

	::= { pbufStatsEntry 511 }

	pbufStatsDataSize5	OBJECT-TYPE
		SYNTAX		INTEGER
		MAX-ACCESS	read-only
		STATUS		current
		DESCRIPTION
			"User data size of size-5 buffers"

	::= { pbufStatsEntry 601 }

	pbufStatsTotalCount5	OBJECT-TYPE
		SYNTAX		INTEGER
		MAX-ACCESS	read-only
		STATUS		current
		DESCRIPTION
			"Number of size-5 buffers created"

	::= { pbufStatsEntry 602 }

	pbufStatsAllocatedCount5	OBJECT-TYPE
		SYNTAX		INTEGER
		MAX-ACCESS	read-only
		STATUS		current
		DESCRIPTION
			"Number of size-5 buffers currently allocated"

	::= { pbufStatsEntry 603 }

	pbufStatsPermAllocatedCount5	OBJECT-TYPE
		SYNTAX		INTEGER
		MAX-ACCESS	read-only
		STATUS		current
		DESCRIPTION
			"Number of size-5 buffers permanently allocated"

	::= { pbufStatsEntry 604 }

	pbufStatsAllocatedMax5	OBJECT-TYPE
		SYNTAX		INTEGER
		MAX-ACCESS	read-only
		STATUS		current
		DESCRIPTION
			"Maximum number of size-5 buffers allocated"

	::= { pbufStatsEntry 605 }

	pbufStatsFreeCount5	OBJECT-TYPE
		SYNTAX		INTEGER
		MAX-ACCESS	read-only
		STATUS		current
		DESCRIPTION
			"Number of size-5 buffers currently free"

	::= { pbufStatsEntry 606 }

	pbufStatsFreeMin5	OBJECT-TYPE
		SYNTAX		INTEGER
		MAX-ACCESS	read-only
		STATUS		current
		DESCRIPTION
			"Minimum number of size-5 buffers free"

	::= { pbufStatsEntry 607 }

	pbufStatsAllocSuccesses5	OBJECT-TYPE
		SYNTAX		INTEGER
		MAX-ACCESS	read-only
		STATUS		current
		DESCRIPTION
			"Number of successful size-5 buffer allocations"

	::= { pbufStatsEntry 608 }

	pbufStatsAllocFails5	OBJECT-TYPE
		SYNTAX		INTEGER
		MAX-ACCESS	read-only
		STATUS		current
		DESCRIPTION
			"Number of failed size-5 buffer allocations"

	::= { pbufStatsEntry 609 }

	pbufStatsFreeSuccesses5	OBJECT-TYPE
		SYNTAX		INTEGER
		MAX-ACCESS	read-only
		STATUS		current
		DESCRIPTION
			"Number of successful size-5 buffer frees"

	::= { pbufStatsEntry 610 }

	pbufStatsFreeFails5	OBJECT-TYPE
		SYNTAX		INTEGER
		MAX-ACCESS	read-only
		STATUS		current
		DESCRIPTION
			"Number of failed size-5 buffer frees"

	::= { pbufStatsEntry 611 }


	taskStatsTableTable	OBJECT-TYPE
		SYNTAX		SEQUENCE OF TaskStatsTableEntry
		MAX-ACCESS	not-accessible
		STATUS		current
		DESCRIPTION
			"task stats table"

	::= { aptis-monitoring 3606 }

	taskStatsTableEntry	OBJECT-TYPE
		SYNTAX		TaskStatsTableEntry
		MAX-ACCESS	not-accessible
		STATUS		current
		DESCRIPTION
			"This is the structure of entries in the
			 taskStatsTableTable."
		INDEX		{ taskStatsTableSlotNumber, taskStatsTableTaskIndex }
	::= { taskStatsTableTable 1 }

	TaskStatsTableEntry ::= SEQUENCE {
		taskStatsTableSlotNumber	INTEGER,
		taskStatsTableTaskIndex		INTEGER,
		taskStatsTableTaskID		INTEGER,
		taskStatsTableTaskName		DisplayString,
		taskStatsTableTCBSize		INTEGER,
		taskStatsTableTCB		OCTET STRING,
		taskStatsTableWaitObjectName	DisplayString,
		taskStatsTableTicksPerSecond	INTEGER,
		taskStatsTableTicksElapsed	INTEGER,
		taskStatsTableStackAddress1	INTEGER,
		taskStatsTableStackAddress2	INTEGER,
		taskStatsTableStackAddress3	INTEGER,
		taskStatsTableStackAddress4	INTEGER,
		taskStatsTableStackAddress5	INTEGER,
		taskStatsTableStackAddress6	INTEGER,
		taskStatsTableStackAddress7	INTEGER,
		taskStatsTableStackAddress8	INTEGER,
		taskStatsTableStackAddress9	INTEGER,
		taskStatsTableStackAddress10	INTEGER,
		taskStatsTableRunTime		INTEGER,
		taskStatsTableContextSwitches	INTEGER,
		taskStatsTableGlobalPool	INTEGER,
		taskStatsTableIntervalTime	INTEGER,
		taskStatsTableTotalTime		INTEGER,
		taskStatsTableIntervalSize	INTEGER,
		taskStatsTableKernelPool	INTEGER,
		taskStatsTableTaskPool		INTEGER,
		taskStatsTableIsrTimes		DisplayString,
		taskStatsTableIdle5Seconds	INTEGER,
		taskStatsTableIdleMinute	INTEGER,
		taskStatsTableIdle5Minute	INTEGER,
		taskStatsTableIdleHour		INTEGER,
		taskStatsTableIdleDay		INTEGER
	}

	taskStatsTableSlotNumber	OBJECT-TYPE
		SYNTAX		INTEGER {
				    bep(1),
				    fep(2),
				    slot1(3),
				    slot2(4),
				    slot3(5),
				    slot4(6),
				    slot5(7),
				    slot6(8),
				    slot7(9),
				    slot8(10),
				    slot11(11),
				    slot12(12),
				    slot13(13),
				    slot14(14),
				    slot15(15),
				    slot16(16),
				    slot17(17),
				    slot18(18)
				}
		MAX-ACCESS	read-only
		STATUS		current
		DESCRIPTION
			"Slot number"

	::= { taskStatsTableEntry 1 }

	taskStatsTableTaskIndex	OBJECT-TYPE
		SYNTAX		INTEGER
		MAX-ACCESS	read-only
		STATUS		current
		DESCRIPTION
			"Task index. This is a sequential number."

	::= { taskStatsTableEntry 2 }

	taskStatsTableTaskID	OBJECT-TYPE
		SYNTAX		INTEGER
		MAX-ACCESS	read-only
		STATUS		current
		DESCRIPTION
			"Task ID"

	::= { taskStatsTableEntry 3 }

	taskStatsTableTaskName	OBJECT-TYPE
		SYNTAX		DisplayString (SIZE (0..8))
		MAX-ACCESS	read-only
		STATUS		current
		DESCRIPTION
			"Task Name"

	::= { taskStatsTableEntry 4 }

	taskStatsTableTCBSize	OBJECT-TYPE
		SYNTAX		INTEGER
		MAX-ACCESS	read-only
		STATUS		current
		DESCRIPTION
			"Size in bytes of TCB"

	::= { taskStatsTableEntry 11 }

	taskStatsTableTCB	OBJECT-TYPE
		SYNTAX		OCTET STRING (SIZE (0..512))
		MAX-ACCESS	read-only
		STATUS		current
		DESCRIPTION
			"PSOS TCB Data"

	::= { taskStatsTableEntry 12 }

	taskStatsTableWaitObjectName	OBJECT-TYPE
		SYNTAX		DisplayString (SIZE (0..8))
		MAX-ACCESS	read-only
		STATUS		current
		DESCRIPTION
			"Name of object task is waiting on"

	::= { taskStatsTableEntry 21 }

	taskStatsTableTicksPerSecond	OBJECT-TYPE
		SYNTAX		INTEGER
		MAX-ACCESS	read-only
		STATUS		current
		DESCRIPTION
			"PSOS Ticks per second"

	::= { taskStatsTableEntry 22 }

	taskStatsTableTicksElapsed	OBJECT-TYPE
		SYNTAX		INTEGER
		MAX-ACCESS	read-only
		STATUS		current
		DESCRIPTION
			"PSOS Ticks elapsed"

	::= { taskStatsTableEntry 23 }

	taskStatsTableStackAddress1	OBJECT-TYPE
		SYNTAX		INTEGER
		MAX-ACCESS	read-only
		STATUS		current
		DESCRIPTION
			"Stack address 1"

	::= { taskStatsTableEntry 31 }

	taskStatsTableStackAddress2	OBJECT-TYPE
		SYNTAX		INTEGER
		MAX-ACCESS	read-only
		STATUS		current
		DESCRIPTION
			"Stack address 2"

	::= { taskStatsTableEntry 32 }

	taskStatsTableStackAddress3	OBJECT-TYPE
		SYNTAX		INTEGER
		MAX-ACCESS	read-only
		STATUS		current
		DESCRIPTION
			"Stack address 3"

	::= { taskStatsTableEntry 33 }

	taskStatsTableStackAddress4	OBJECT-TYPE
		SYNTAX		INTEGER
		MAX-ACCESS	read-only
		STATUS		current
		DESCRIPTION
			"Stack address 4"

	::= { taskStatsTableEntry 34 }

	taskStatsTableStackAddress5	OBJECT-TYPE
		SYNTAX		INTEGER
		MAX-ACCESS	read-only
		STATUS		current
		DESCRIPTION
			"Stack address 5"

	::= { taskStatsTableEntry 35 }

	taskStatsTableStackAddress6	OBJECT-TYPE
		SYNTAX		INTEGER
		MAX-ACCESS	read-only
		STATUS		current
		DESCRIPTION
			"Stack address 6"

	::= { taskStatsTableEntry 36 }

	taskStatsTableStackAddress7	OBJECT-TYPE
		SYNTAX		INTEGER
		MAX-ACCESS	read-only
		STATUS		current
		DESCRIPTION
			"Stack address 7"

	::= { taskStatsTableEntry 37 }

	taskStatsTableStackAddress8	OBJECT-TYPE
		SYNTAX		INTEGER
		MAX-ACCESS	read-only
		STATUS		current
		DESCRIPTION
			"Stack address 8"

	::= { taskStatsTableEntry 38 }

	taskStatsTableStackAddress9	OBJECT-TYPE
		SYNTAX		INTEGER
		MAX-ACCESS	read-only
		STATUS		current
		DESCRIPTION
			"Stack address 9"

	::= { taskStatsTableEntry 39 }

	taskStatsTableStackAddress10	OBJECT-TYPE
		SYNTAX		INTEGER
		MAX-ACCESS	read-only
		STATUS		current
		DESCRIPTION
			"Stack address 10"

	::= { taskStatsTableEntry 40 }

	taskStatsTableRunTime	OBJECT-TYPE
		SYNTAX		INTEGER
		MAX-ACCESS	read-only
		STATUS		current
		DESCRIPTION
			"Total task run time in miliseconds"

	::= { taskStatsTableEntry 41 }

	taskStatsTableContextSwitches	OBJECT-TYPE
		SYNTAX		INTEGER
		MAX-ACCESS	read-only
		STATUS		current
		DESCRIPTION
			"Task context switches since creation"

	::= { taskStatsTableEntry 42 }

	taskStatsTableGlobalPool	OBJECT-TYPE
		SYNTAX		INTEGER
		MAX-ACCESS	read-only
		STATUS		current
		DESCRIPTION
			"Global pool used by task"

	::= { taskStatsTableEntry 43 }

	taskStatsTableIntervalTime	OBJECT-TYPE
		SYNTAX		INTEGER
		MAX-ACCESS	read-only
		STATUS		current
		DESCRIPTION
			"Total task run time in miliseconds since last
			request"

	::= { taskStatsTableEntry 44 }

	taskStatsTableTotalTime	OBJECT-TYPE
		SYNTAX		INTEGER
		MAX-ACCESS	read-only
		STATUS		current
		DESCRIPTION
			"Run time for all in miliseconds"

	::= { taskStatsTableEntry 45 }

	taskStatsTableIntervalSize	OBJECT-TYPE
		SYNTAX		INTEGER
		MAX-ACCESS	read-only
		STATUS		current
		DESCRIPTION
			"Run time for all in miliseconds in last interval"

	::= { taskStatsTableEntry 46 }

	taskStatsTableKernelPool	OBJECT-TYPE
		SYNTAX		INTEGER
		MAX-ACCESS	read-only
		STATUS		current
		DESCRIPTION
			"Memory used by kernel"

	::= { taskStatsTableEntry 47 }

	taskStatsTableTaskPool	OBJECT-TYPE
		SYNTAX		INTEGER
		MAX-ACCESS	read-only
		STATUS		current
		DESCRIPTION
			"Total memory allocated by tasks"

	::= { taskStatsTableEntry 48 }

	taskStatsTableIsrTimes	OBJECT-TYPE
		SYNTAX		DisplayString (SIZE (0..128))
		MAX-ACCESS	read-only
		STATUS		current
		DESCRIPTION
			"Time spent processor isr routines"

	::= { taskStatsTableEntry 49 }

	taskStatsTableIdle5Seconds	OBJECT-TYPE
		SYNTAX		INTEGER
		MAX-ACCESS	read-only
		STATUS		current
		DESCRIPTION
			"Total processor idle time last 5 seconds"

	::= { taskStatsTableEntry 50 }

	taskStatsTableIdleMinute	OBJECT-TYPE
		SYNTAX		INTEGER
		MAX-ACCESS	read-only
		STATUS		current
		DESCRIPTION
			"Total processor idle time last minute"

	::= { taskStatsTableEntry 51 }

	taskStatsTableIdle5Minute	OBJECT-TYPE
		SYNTAX		INTEGER
		MAX-ACCESS	read-only
		STATUS		current
		DESCRIPTION
			"Total processor idle time last 5 minutes"

	::= { taskStatsTableEntry 52 }

	taskStatsTableIdleHour	OBJECT-TYPE
		SYNTAX		INTEGER
		MAX-ACCESS	read-only
		STATUS		current
		DESCRIPTION
			"Total processor idle time last hour"

	::= { taskStatsTableEntry 53 }

	taskStatsTableIdleDay	OBJECT-TYPE
		SYNTAX		INTEGER
		MAX-ACCESS	read-only
		STATUS		current
		DESCRIPTION
			"Total processor idle time last day"

	::= { taskStatsTableEntry 54 }

-- This file generated from  t1.cml by smog.
-- date: Thu Jun 29 01:11:48  2000

	t1StatsTable	OBJECT-TYPE
		SYNTAX		SEQUENCE OF T1StatsEntry
		MAX-ACCESS	not-accessible
		STATUS		current
		DESCRIPTION
			"T1 Stats."

	::= { aptis-monitoring 2102 }

	t1StatsEntry	OBJECT-TYPE
		SYNTAX		T1StatsEntry
		MAX-ACCESS	not-accessible
		STATUS		current
		DESCRIPTION
			"This is the structure of entries in the
			 t1StatsTable."
		INDEX		{ t1StatsSlotIndex, t1StatsLineNumber }
	::= { t1StatsTable 1 }

	T1StatsEntry ::= SEQUENCE {
		t1StatsAlarmStatus		INTEGER,
		t1StatsSlotIndex		INTEGER,
		t1StatsLineNumber		INTEGER
	}

	t1StatsAlarmStatus	OBJECT-TYPE
		SYNTAX		INTEGER {
				    noalarm(0),
				    yellowalarm(1),
				    redalarm(2),
				    bluealarm(3)
				}
		MAX-ACCESS	read-only
		STATUS		current
		DESCRIPTION
			"T1 layer 1 alarms."

	::= { t1StatsEntry 1 }

	t1StatsSlotIndex	OBJECT-TYPE
		SYNTAX		INTEGER (1..32)
		MAX-ACCESS	read-only
		STATUS		current
		DESCRIPTION
			"The physical slot number associated with this line."

	::= { t1StatsEntry 2 }

	t1StatsLineNumber	OBJECT-TYPE
		SYNTAX		INTEGER (1..56)
		MAX-ACCESS	read-only
		STATUS		current
		DESCRIPTION
			"The line number of the line to which the Alarm Status
			applies."

	::= { t1StatsEntry 3 }


	t1CountsTable	OBJECT-TYPE
		SYNTAX		SEQUENCE OF T1CountsEntry
		MAX-ACCESS	not-accessible
		STATUS		current
		DESCRIPTION
			"T1 Interface Counters."

	::= { aptis-monitoring 2103 }

	t1CountsEntry	OBJECT-TYPE
		SYNTAX		T1CountsEntry
		MAX-ACCESS	not-accessible
		STATUS		current
		DESCRIPTION
			"This is the structure of entries in the
			 t1CountsTable."
		INDEX		{ t1CountsSlotIndex, t1CountsLineNumber }
	::= { t1CountsTable 1 }

	T1CountsEntry ::= SEQUENCE {
		t1CountsChannelCount		INTEGER,
		t1CountsChannelsInUse		INTEGER,
		t1CountsIncomingCallAttempts	INTEGER,
		t1CountsIncomingConnects	INTEGER,
		t1CountsIncomingDisconnects	INTEGER,
		t1CountsOutgoingCallAttempts	INTEGER,
		t1CountsOutgoingConnects	INTEGER,
		t1CountsOutgoingDisconnects	INTEGER,
		t1CountsSessionAbortMessages	INTEGER,
		t1CountsSlotIndex		INTEGER,
		t1CountsLineNumber		INTEGER
	}

	t1CountsChannelCount	OBJECT-TYPE
		SYNTAX		INTEGER
		MAX-ACCESS	read-only
		STATUS		current
		DESCRIPTION
			"DS0s (B-channels) on this interface."

	::= { t1CountsEntry 1 }

	t1CountsChannelsInUse	OBJECT-TYPE
		SYNTAX		INTEGER
		MAX-ACCESS	read-only
		STATUS		current
		DESCRIPTION
			"DS0s (B-channels) in use."

	::= { t1CountsEntry 2 }

	t1CountsIncomingCallAttempts	OBJECT-TYPE
		SYNTAX		INTEGER
		MAX-ACCESS	read-only
		STATUS		current
		DESCRIPTION
			"Incoming call attempts on this T1."

	::= { t1CountsEntry 3 }

	t1CountsIncomingConnects	OBJECT-TYPE
		SYNTAX		INTEGER
		MAX-ACCESS	read-only
		STATUS		current
		DESCRIPTION
			"Incoming connect messages."

	::= { t1CountsEntry 4 }

	t1CountsIncomingDisconnects	OBJECT-TYPE
		SYNTAX		INTEGER
		MAX-ACCESS	read-only
		STATUS		current
		DESCRIPTION
			"Incoming disconnect messages."

	::= { t1CountsEntry 5 }

	t1CountsOutgoingCallAttempts	OBJECT-TYPE
		SYNTAX		INTEGER
		MAX-ACCESS	read-only
		STATUS		current
		DESCRIPTION
			"Outgoing call attempts on this T1."

	::= { t1CountsEntry 6 }

	t1CountsOutgoingConnects	OBJECT-TYPE
		SYNTAX		INTEGER
		MAX-ACCESS	read-only
		STATUS		current
		DESCRIPTION
			"Outgoing connect messages."

	::= { t1CountsEntry 7 }

	t1CountsOutgoingDisconnects	OBJECT-TYPE
		SYNTAX		INTEGER
		MAX-ACCESS	read-only
		STATUS		current
		DESCRIPTION
			"Outgoing disconnect messages."

	::= { t1CountsEntry 8 }

	t1CountsSessionAbortMessages	OBJECT-TYPE
		SYNTAX		INTEGER
		MAX-ACCESS	read-only
		STATUS		current
		DESCRIPTION
			"Abort messages from the session manager"

	::= { t1CountsEntry 9 }

	t1CountsSlotIndex	OBJECT-TYPE
		SYNTAX		INTEGER (1..32)
		MAX-ACCESS	read-only
		STATUS		current
		DESCRIPTION
			"The physical slot number associated with this line."

	::= { t1CountsEntry 10 }

	t1CountsLineNumber	OBJECT-TYPE
		SYNTAX		INTEGER (1..56)
		MAX-ACCESS	read-only
		STATUS		current
		DESCRIPTION
			"The line number of the line to which the Alarm Status
			applies."

	::= { t1CountsEntry 11 }


	t1SummaryStatsTable	OBJECT-TYPE
		SYNTAX		SEQUENCE OF T1SummaryStatsEntry
		MAX-ACCESS	not-accessible
		STATUS		current
		DESCRIPTION
			"T1 Line Summary Stats."

	::= { aptis-monitoring 2104 }

	t1SummaryStatsEntry	OBJECT-TYPE
		SYNTAX		T1SummaryStatsEntry
		MAX-ACCESS	not-accessible
		STATUS		current
		DESCRIPTION
			"This is the structure of entries in the
			 t1SummaryStatsTable."
		INDEX		{ t1SummaryStatsSlotIndex, t1SummaryStatsLineNumber }
	::= { t1SummaryStatsTable 1 }

	T1SummaryStatsEntry ::= SEQUENCE {
		t1SummaryStatsRingingChannels	INTEGER,
		t1SummaryStatsConnectedChannels	INTEGER,
		t1SummaryStatsClearingChannels	INTEGER,
		t1SummaryStatsSlotIndex		INTEGER,
		t1SummaryStatsLineNumber	INTEGER,
		t1SummaryStatsFunctionalChannels INTEGER,
		t1SummaryStatsIdleChannels	INTEGER
	}

	t1SummaryStatsRingingChannels	OBJECT-TYPE
		SYNTAX		INTEGER
		MAX-ACCESS	read-only
		STATUS		current
		DESCRIPTION
			"Bit mask of b-channels that have calls coming up,
			with b-channel 1 at 0x02, 2 at 0x04, etc."

	::= { t1SummaryStatsEntry 1 }

	t1SummaryStatsConnectedChannels	OBJECT-TYPE
		SYNTAX		INTEGER
		MAX-ACCESS	read-only
		STATUS		current
		DESCRIPTION
			"Bit mask of b-channels that have calls connected,
			with b-channel 1 at 0x02, 2 at 0x04, etc."

	::= { t1SummaryStatsEntry 2 }

	t1SummaryStatsClearingChannels	OBJECT-TYPE
		SYNTAX		INTEGER
		MAX-ACCESS	read-only
		STATUS		current
		DESCRIPTION
			"Bit mask of b-channels that have calls going down,
			with b-channel 1 at 0x02, 2 at 0x04, etc."

	::= { t1SummaryStatsEntry 3 }

	t1SummaryStatsSlotIndex	OBJECT-TYPE
		SYNTAX		INTEGER (1..32)
		MAX-ACCESS	read-only
		STATUS		current
		DESCRIPTION
			"The physical slot number associated with this line."

	::= { t1SummaryStatsEntry 4 }

	t1SummaryStatsLineNumber	OBJECT-TYPE
		SYNTAX		INTEGER (1..56)
		MAX-ACCESS	read-only
		STATUS		current
		DESCRIPTION
			"The line number of the line to which the Alarm Status
			applies."

	::= { t1SummaryStatsEntry 5 }

	t1SummaryStatsFunctionalChannels	OBJECT-TYPE
		SYNTAX		INTEGER
		MAX-ACCESS	read-only
		STATUS		current
		DESCRIPTION
			"Bit mask of b-channels that are in the functional
			state."

	::= { t1SummaryStatsEntry 6 }

	t1SummaryStatsIdleChannels	OBJECT-TYPE
		SYNTAX		INTEGER
		MAX-ACCESS	read-only
		STATUS		current
		DESCRIPTION
			"Bit mask of b-channels that are in the idle state."

	::= { t1SummaryStatsEntry 7 }

-- This file generated from  t3.cml by smog.
-- date: Thu Jun 29 01:11:48  2000

	t3StatsTable	OBJECT-TYPE
		SYNTAX		SEQUENCE OF T3StatsEntry
		MAX-ACCESS	not-accessible
		STATUS		current
		DESCRIPTION
			"T3 Line Stats."

	::= { aptis-monitoring 2008 }

	t3StatsEntry	OBJECT-TYPE
		SYNTAX		T3StatsEntry
		MAX-ACCESS	not-accessible
		STATUS		current
		DESCRIPTION
			"This is the structure of entries in the
			 t3StatsTable."
		INDEX		{ t3StatsSlotIndex, t3StatsLineNumber }
	::= { t3StatsTable 1 }

	T3StatsEntry ::= SEQUENCE {
		t3StatsLineState		INTEGER,
		t3StatsSlotIndex		INTEGER,
		t3StatsLineNumber		INTEGER,
		t3StatsRedundant		Boolean,
		t3StatsDs1Count			INTEGER,
		t3StatsActiveDs1Count		INTEGER,
		t3StatsExternalClockPort	Boolean
	}

	t3StatsLineState	OBJECT-TYPE
		SYNTAX		INTEGER {
				    noalarm(0),
				    yellowalarm(1),
				    redalarm(2),
				    bluealarm(3)
				}
		MAX-ACCESS	read-only
		STATUS		current
		DESCRIPTION
			"Current state of this line."

	::= { t3StatsEntry 1 }

	t3StatsSlotIndex	OBJECT-TYPE
		SYNTAX		INTEGER (1..18)
		MAX-ACCESS	read-only
		STATUS		current
		DESCRIPTION
			"The physical slot number associated with this line."

	::= { t3StatsEntry 2 }

	t3StatsLineNumber	OBJECT-TYPE
		SYNTAX		INTEGER (1..2)
		MAX-ACCESS	read-only
		STATUS		current
		DESCRIPTION
			"The line number of the line to which the Line State
			applies."

	::= { t3StatsEntry 3 }

	t3StatsRedundant	OBJECT-TYPE
		SYNTAX		Boolean
		MAX-ACCESS	read-only
		STATUS		current
		DESCRIPTION
			"Whether this T3 has a redundant backup."

	::= { t3StatsEntry 4 }

	t3StatsDs1Count	OBJECT-TYPE
		SYNTAX		INTEGER (1..56)
		MAX-ACCESS	read-only
		STATUS		current
		DESCRIPTION
			"The number of DS1 lines on this T3."

	::= { t3StatsEntry 5 }

	t3StatsActiveDs1Count	OBJECT-TYPE
		SYNTAX		INTEGER (0..56)
		MAX-ACCESS	read-only
		STATUS		current
		DESCRIPTION
			"The number of active DS1 lines on this T3."

	::= { t3StatsEntry 6 }

	t3StatsExternalClockPort	OBJECT-TYPE
		SYNTAX		Boolean
		MAX-ACCESS	read-only
		STATUS		current
		DESCRIPTION
			"Whether this T3 LTM has an external clock reference
			port. (only available on some models)"

	::= { t3StatsEntry 7 }

-- This file generated from  thruway.cml by smog.
-- date: Thu Jun 29 01:11:48  2000

	ss7StatusTable	OBJECT-TYPE
		SYNTAX		SEQUENCE OF Ss7StatusEntry
		MAX-ACCESS	not-accessible
		STATUS		current
		DESCRIPTION
			"ss7 status table."

	::= { aptis-monitoring 500 }

	ss7StatusEntry	OBJECT-TYPE
		SYNTAX		Ss7StatusEntry
		MAX-ACCESS	not-accessible
		STATUS		current
		DESCRIPTION
			"This is the structure of entries in the
			 ss7StatusTable."
		INDEX		{ ss7StatusIndex }
	::= { ss7StatusTable 1 }

	Ss7StatusEntry ::= SEQUENCE {
		ss7StatusIndex			INTEGER,
		ss7StatusState			DisplayString,
		ss7StatusNetworkId		DisplayString,
		ss7StatusCalledId		DisplayString,
		ss7StatusCallingId		DisplayString,
		ss7StatusCallType		INTEGER,
		ss7StatusSlot			INTEGER,
		ss7StatusPort			INTEGER,
		ss7StatusTimeSlot		INTEGER,
		ss7StatusSessionId		INTEGER,
		ss7StatusServerId		DisplayString,
		ss7StatusStartTime		INTEGER
	}

	ss7StatusIndex	OBJECT-TYPE
		SYNTAX		INTEGER
		MAX-ACCESS	read-only
		STATUS		current
		DESCRIPTION
			"The serial number of this ss7 session."

	::= { ss7StatusEntry 1 }

	ss7StatusState	OBJECT-TYPE
		SYNTAX		DisplayString (SIZE (0..20))
		MAX-ACCESS	read-only
		STATUS		current
		DESCRIPTION
			"The current state of this session."

	::= { ss7StatusEntry 2 }

	ss7StatusNetworkId	OBJECT-TYPE
		SYNTAX		DisplayString (SIZE (0..21))
		MAX-ACCESS	read-only
		STATUS		current
		DESCRIPTION
			"The INC assigned session Id for this session."

	::= { ss7StatusEntry 3 }

	ss7StatusCalledId	OBJECT-TYPE
		SYNTAX		DisplayString (SIZE (0..20))
		MAX-ACCESS	read-only
		STATUS		current
		DESCRIPTION
			"The called number for this session."

	::= { ss7StatusEntry 4 }

	ss7StatusCallingId	OBJECT-TYPE
		SYNTAX		DisplayString (SIZE (0..20))
		MAX-ACCESS	read-only
		STATUS		current
		DESCRIPTION
			"The calling number for this session."

	::= { ss7StatusEntry 5 }

	ss7StatusCallType	OBJECT-TYPE
		SYNTAX		INTEGER {
				    analog(0),
				    isdn(1),
				    loopback(2),
				    cotegress(3),
				    cotingress(4),
				    tandem(5),
				    t102generate(6),
				    t102detect(7),
				    t108egress(8)
				}
		MAX-ACCESS	read-only
		STATUS		current
		DESCRIPTION
			"The call type for this session."

	::= { ss7StatusEntry 6 }

	ss7StatusSlot	OBJECT-TYPE
		SYNTAX		INTEGER
		MAX-ACCESS	read-only
		STATUS		current
		DESCRIPTION
			"The slot specified by the thruway controller to
			terminate this session."

	::= { ss7StatusEntry 7 }

	ss7StatusPort	OBJECT-TYPE
		SYNTAX		INTEGER
		MAX-ACCESS	read-only
		STATUS		current
		DESCRIPTION
			"The DS1 specified by the thruway controller to
			terminate this session."

	::= { ss7StatusEntry 8 }

	ss7StatusTimeSlot	OBJECT-TYPE
		SYNTAX		INTEGER
		MAX-ACCESS	read-only
		STATUS		current
		DESCRIPTION
			"The DS0 specified by the thruway controller to
			terminate this session."

	::= { ss7StatusEntry 9 }

	ss7StatusSessionId	OBJECT-TYPE
		SYNTAX		INTEGER
		MAX-ACCESS	read-only
		STATUS		current
		DESCRIPTION
			"The session Id assigned to this session by the CVX (0
			if unknown)."

	::= { ss7StatusEntry 10 }

	ss7StatusServerId	OBJECT-TYPE
		SYNTAX		DisplayString (SIZE (0..41))
		MAX-ACCESS	read-only
		STATUS		current
		DESCRIPTION
			"The server identifier for the network controller
			responsible for initiating this session."

	::= { ss7StatusEntry 11 }

	ss7StatusStartTime	OBJECT-TYPE
		SYNTAX		INTEGER
		MAX-ACCESS	read-only
		STATUS		current
		DESCRIPTION
			"The time that this session began."

	::= { ss7StatusEntry 12 }


	ss7TraceTable	OBJECT-TYPE
		SYNTAX		SEQUENCE OF Ss7TraceEntry
		MAX-ACCESS	not-accessible
		STATUS		current
		DESCRIPTION
			"ss7 trace table."

	::= { aptis-monitoring 501 }

	ss7TraceEntry	OBJECT-TYPE
		SYNTAX		Ss7TraceEntry
		MAX-ACCESS	not-accessible
		STATUS		current
		DESCRIPTION
			"This is the structure of entries in the
			 ss7TraceTable."
		INDEX		{ ss7TraceSs7Index, ss7TraceIndex }
	::= { ss7TraceTable 1 }

	Ss7TraceEntry ::= SEQUENCE {
		ss7TraceSs7Index		INTEGER,
		ss7TraceIndex			INTEGER,
		ss7TraceAbsoluteTimeStamp	INTEGER,
		ss7TraceRelativeTimeStamp	INTEGER,
		ss7TraceLogEntry		DisplayString
	}

	ss7TraceSs7Index	OBJECT-TYPE
		SYNTAX		INTEGER
		MAX-ACCESS	read-only
		STATUS		current
		DESCRIPTION
			"The serial number of the ss7 session to which this
			component belongs."

	::= { ss7TraceEntry 1 }

	ss7TraceIndex	OBJECT-TYPE
		SYNTAX		INTEGER
		MAX-ACCESS	read-only
		STATUS		current
		DESCRIPTION
			"The internal reference number for this log entry."

	::= { ss7TraceEntry 2 }

	ss7TraceAbsoluteTimeStamp	OBJECT-TYPE
		SYNTAX		INTEGER
		MAX-ACCESS	read-only
		STATUS		current
		DESCRIPTION
			"The time that this event occurred, in milliseconds
			relative to SysUpTime."

	::= { ss7TraceEntry 3 }

	ss7TraceRelativeTimeStamp	OBJECT-TYPE
		SYNTAX		INTEGER
		MAX-ACCESS	read-only
		STATUS		current
		DESCRIPTION
			"The time that this event occurred, in milliseconds
			relative to session beginning."

	::= { ss7TraceEntry 4 }

	ss7TraceLogEntry	OBJECT-TYPE
		SYNTAX		DisplayString (SIZE (0..128))
		MAX-ACCESS	read-only
		STATUS		current
		DESCRIPTION
			"An event occuring during the life of an ss7 session."

	::= { ss7TraceEntry 5 }


	ss7StatusReverseTable	OBJECT-TYPE
		SYNTAX		SEQUENCE OF Ss7StatusReverseEntry
		MAX-ACCESS	not-accessible
		STATUS		current
		DESCRIPTION
			"ss7 status reverse table."

	::= { aptis-monitoring 502 }

	ss7StatusReverseEntry	OBJECT-TYPE
		SYNTAX		Ss7StatusReverseEntry
		MAX-ACCESS	not-accessible
		STATUS		current
		DESCRIPTION
			"This is the structure of entries in the
			 ss7StatusReverseTable."
		INDEX		{ ss7StatusReverseIndex }
	::= { ss7StatusReverseTable 1 }

	Ss7StatusReverseEntry ::= SEQUENCE {
		ss7StatusReverseIndex		INTEGER,
		ss7StatusReverseState		DisplayString,
		ss7StatusReverseNetworkId	DisplayString,
		ss7StatusReverseCalledId	DisplayString,
		ss7StatusReverseCallingId	DisplayString,
		ss7StatusReverseCallType	INTEGER,
		ss7StatusReverseSlot		INTEGER,
		ss7StatusReversePort		INTEGER,
		ss7StatusReverseTimeSlot	INTEGER,
		ss7StatusReverseSessionId	INTEGER,
		ss7StatusReverseServerId	DisplayString,
		ss7StatusReverseStartTime	INTEGER
	}

	ss7StatusReverseIndex	OBJECT-TYPE
		SYNTAX		INTEGER
		MAX-ACCESS	read-only
		STATUS		current
		DESCRIPTION
			"The serial number of this ss7 session."

	::= { ss7StatusReverseEntry 1 }

	ss7StatusReverseState	OBJECT-TYPE
		SYNTAX		DisplayString (SIZE (0..20))
		MAX-ACCESS	read-only
		STATUS		current
		DESCRIPTION
			"The current state of this session."

	::= { ss7StatusReverseEntry 2 }

	ss7StatusReverseNetworkId	OBJECT-TYPE
		SYNTAX		DisplayString (SIZE (0..21))
		MAX-ACCESS	read-only
		STATUS		current
		DESCRIPTION
			"The INC assigned session Id for this session."

	::= { ss7StatusReverseEntry 3 }

	ss7StatusReverseCalledId	OBJECT-TYPE
		SYNTAX		DisplayString (SIZE (0..20))
		MAX-ACCESS	read-only
		STATUS		current
		DESCRIPTION
			"The called number for this session."

	::= { ss7StatusReverseEntry 4 }

	ss7StatusReverseCallingId	OBJECT-TYPE
		SYNTAX		DisplayString (SIZE (0..20))
		MAX-ACCESS	read-only
		STATUS		current
		DESCRIPTION
			"The calling number for this session."

	::= { ss7StatusReverseEntry 5 }

	ss7StatusReverseCallType	OBJECT-TYPE
		SYNTAX		INTEGER {
				    analog(0),
				    isdn(1),
				    loopback(2),
				    cotegress(3),
				    cotingress(4),
				    tandem(5),
				    t102generate(6),
				    t102detect(7),
				    t108egress(8)
				}
		MAX-ACCESS	read-only
		STATUS		current
		DESCRIPTION
			"The call type for this session."

	::= { ss7StatusReverseEntry 6 }

	ss7StatusReverseSlot	OBJECT-TYPE
		SYNTAX		INTEGER
		MAX-ACCESS	read-only
		STATUS		current
		DESCRIPTION
			"The slot specified by the thruway controller to
			terminate this session."

	::= { ss7StatusReverseEntry 7 }

	ss7StatusReversePort	OBJECT-TYPE
		SYNTAX		INTEGER
		MAX-ACCESS	read-only
		STATUS		current
		DESCRIPTION
			"The DS1 specified by the thruway controller to
			terminate this session."

	::= { ss7StatusReverseEntry 8 }

	ss7StatusReverseTimeSlot	OBJECT-TYPE
		SYNTAX		INTEGER
		MAX-ACCESS	read-only
		STATUS		current
		DESCRIPTION
			"The DS0 specified by the thruway controller to
			terminate this session."

	::= { ss7StatusReverseEntry 9 }

	ss7StatusReverseSessionId	OBJECT-TYPE
		SYNTAX		INTEGER
		MAX-ACCESS	read-only
		STATUS		current
		DESCRIPTION
			"The session Id assigned to this session by the CVX (0
			if unknown)."

	::= { ss7StatusReverseEntry 10 }

	ss7StatusReverseServerId	OBJECT-TYPE
		SYNTAX		DisplayString (SIZE (0..41))
		MAX-ACCESS	read-only
		STATUS		current
		DESCRIPTION
			"The server identifier for the network controller
			responsible for initiating this session."

	::= { ss7StatusReverseEntry 11 }

	ss7StatusReverseStartTime	OBJECT-TYPE
		SYNTAX		INTEGER
		MAX-ACCESS	read-only
		STATUS		current
		DESCRIPTION
			"The time that this session began."

	::= { ss7StatusReverseEntry 12 }


	ss7CountersTable	OBJECT-TYPE
		SYNTAX		SEQUENCE OF Ss7CountersEntry
		MAX-ACCESS	not-accessible
		STATUS		current
		DESCRIPTION
			"ss7 counters table."

	::= { aptis-monitoring 503 }

	ss7CountersEntry	OBJECT-TYPE
		SYNTAX		Ss7CountersEntry
		MAX-ACCESS	not-accessible
		STATUS		current
		DESCRIPTION
			"This is the structure of entries in the
			 ss7CountersTable."
		INDEX		{ ss7CountersNumActive }
	::= { ss7CountersTable 1 }

	Ss7CountersEntry ::= SEQUENCE {
		ss7CountersNumActive		INTEGER,
		ss7CountersNumInactive		INTEGER,
		ss7CountersRetainedFree		INTEGER,
		ss7CountersRetainedFull		INTEGER,
		ss7CountersOneshotFree		INTEGER,
		ss7CountersOneshotFull		INTEGER,
		ss7CountersDsmccFree		INTEGER,
		ss7CountersDsmccFull		INTEGER
	}

	ss7CountersNumActive	OBJECT-TYPE
		SYNTAX		INTEGER
		MAX-ACCESS	read-only
		STATUS		current
		DESCRIPTION
			"The number of active ss7 sessions."

	::= { ss7CountersEntry 1 }

	ss7CountersNumInactive	OBJECT-TYPE
		SYNTAX		INTEGER
		MAX-ACCESS	read-only
		STATUS		current
		DESCRIPTION
			"The number of inactive ss7 sessions."

	::= { ss7CountersEntry 2 }

	ss7CountersRetainedFree	OBJECT-TYPE
		SYNTAX		INTEGER
		MAX-ACCESS	read-only
		STATUS		current
		DESCRIPTION
			"The number of free signaling message blocks."

	::= { ss7CountersEntry 3 }

	ss7CountersRetainedFull	OBJECT-TYPE
		SYNTAX		INTEGER
		MAX-ACCESS	read-only
		STATUS		current
		DESCRIPTION
			"The number of full signaling message blocks."

	::= { ss7CountersEntry 4 }

	ss7CountersOneshotFree	OBJECT-TYPE
		SYNTAX		INTEGER
		MAX-ACCESS	read-only
		STATUS		current
		DESCRIPTION
			"The number of free status message blocks."

	::= { ss7CountersEntry 5 }

	ss7CountersOneshotFull	OBJECT-TYPE
		SYNTAX		INTEGER
		MAX-ACCESS	read-only
		STATUS		current
		DESCRIPTION
			"The number of full status message blocks."

	::= { ss7CountersEntry 6 }

	ss7CountersDsmccFree	OBJECT-TYPE
		SYNTAX		INTEGER
		MAX-ACCESS	read-only
		STATUS		current
		DESCRIPTION
			"The number of free dsmcc message control blocks."

	::= { ss7CountersEntry 7 }

	ss7CountersDsmccFull	OBJECT-TYPE
		SYNTAX		INTEGER
		MAX-ACCESS	read-only
		STATUS		current
		DESCRIPTION
			"The number of full dsmcc message control blocks."

	::= { ss7CountersEntry 8 }


	ipdcTraceTable	OBJECT-TYPE
		SYNTAX		SEQUENCE OF IpdcTraceEntry
		MAX-ACCESS	not-accessible
		STATUS		current
		DESCRIPTION
			"IPDC trace table."

	::= { aptis-monitoring 504 }

	ipdcTraceEntry	OBJECT-TYPE
		SYNTAX		IpdcTraceEntry
		MAX-ACCESS	not-accessible
		STATUS		current
		DESCRIPTION
			"This is the structure of entries in the
			 ipdcTraceTable."
		INDEX		{ ipdcTraceIndex }
	::= { ipdcTraceTable 1 }

	IpdcTraceEntry ::= SEQUENCE {
		ipdcTraceIndex			INTEGER,
		ipdcTraceTimeStamp		INTEGER,
		ipdcTraceDirection		INTEGER,
		ipdcTraceMsgSize		INTEGER,
		ipdcTraceIpdcMsg		OCTET STRING
	}

	ipdcTraceIndex	OBJECT-TYPE
		SYNTAX		INTEGER
		MAX-ACCESS	read-only
		STATUS		current
		DESCRIPTION
			"The internal reference number for this trace entry."

	::= { ipdcTraceEntry 1 }

	ipdcTraceTimeStamp	OBJECT-TYPE
		SYNTAX		INTEGER
		MAX-ACCESS	read-only
		STATUS		current
		DESCRIPTION
			"The time that this event occurred, in milliseconds
			relative to SysUpTime."

	::= { ipdcTraceEntry 2 }

	ipdcTraceDirection	OBJECT-TYPE
		SYNTAX		INTEGER {
				    transmit(0),
				    receive(1)
				}
		MAX-ACCESS	read-only
		STATUS		current
		DESCRIPTION
			"The direction of this message."

	::= { ipdcTraceEntry 3 }

	ipdcTraceMsgSize	OBJECT-TYPE
		SYNTAX		INTEGER
		MAX-ACCESS	read-only
		STATUS		current
		DESCRIPTION
			"The number of octets in this ipsc message."

	::= { ipdcTraceEntry 4 }

	ipdcTraceIpdcMsg	OBJECT-TYPE
		SYNTAX		OCTET STRING (SIZE (0..256))
		MAX-ACCESS	read-only
		STATUS		current
		DESCRIPTION
			"An array of octets representing an ipdc message."

	::= { ipdcTraceEntry 5 }

-- This file generated from  time.cml by smog.
-- date: Thu Jun 29 01:11:49  2000

	systemTimeTable	OBJECT-TYPE
		SYNTAX		SEQUENCE OF SystemTimeEntry
		MAX-ACCESS	not-accessible
		STATUS		current
		DESCRIPTION
			"This class provides some time values that are global
			to the system."

	::= { aptis-monitoring 15 }

	systemTimeEntry	OBJECT-TYPE
		SYNTAX		SystemTimeEntry
		MAX-ACCESS	not-accessible
		STATUS		current
		DESCRIPTION
			"This is the structure of entries in the
			 systemTimeTable."
		INDEX		{ systemTimeFixedBootTime }
	::= { systemTimeTable 1 }

	SystemTimeEntry ::= SEQUENCE {
		systemTimeFixedBootTime		INTEGER,
		systemTimeUTCOffset		INTEGER,
		systemTimeUpTime		INTEGER
	}

	systemTimeFixedBootTime	OBJECT-TYPE
		SYNTAX		INTEGER
		MAX-ACCESS	read-only
		STATUS		current
		DESCRIPTION
			"The UTC time of system boot, in seconds relative to
			00:00:00 on Jan 1, 1900. This value will be unaffected
			by time management protocols such as NTP."

	::= { systemTimeEntry 1 }

	systemTimeUTCOffset	OBJECT-TYPE
		SYNTAX		INTEGER
		MAX-ACCESS	read-only
		STATUS		current
		DESCRIPTION
			"The offset from UTC, in seconds. Useful for
			displaying system time in a local format."

	::= { systemTimeEntry 2 }

	systemTimeUpTime	OBJECT-TYPE
		SYNTAX		INTEGER
		MAX-ACCESS	read-only
		STATUS		current
		DESCRIPTION
			"The number of seconds since the last system reboot.
			Similar to SysUpTime but is in seconds resolution
			instead of TimeTicks."

	::= { systemTimeEntry 3 }

-- This file generated from  tsc.cml by smog.
-- date: Thu Jun 29 01:11:49  2000

	dacStatusTable	OBJECT-TYPE
		SYNTAX		SEQUENCE OF DacStatusEntry
		MAX-ACCESS	not-accessible
		STATUS		current
		DESCRIPTION
			"DAC Status Information."

	::= { aptis-monitoring 2002 }

	dacStatusEntry	OBJECT-TYPE
		SYNTAX		DacStatusEntry
		MAX-ACCESS	not-accessible
		STATUS		current
		DESCRIPTION
			"This is the structure of entries in the
			 dacStatusTable."
		INDEX		{ dacStatusClockSourcePrimary }
	::= { dacStatusTable 1 }

	DacStatusEntry ::= SEQUENCE {
		dacStatusClockSourcePrimary	INTEGER,
		dacStatusClockSourceSecondary	INTEGER,
		dacStatusLTMType		INTEGER
	}

	dacStatusClockSourcePrimary	OBJECT-TYPE
		SYNTAX		INTEGER
		MAX-ACCESS	read-only
		STATUS		current
		DESCRIPTION
			"DAC Primary Clocking Source."

	::= { dacStatusEntry 1 }

	dacStatusClockSourceSecondary	OBJECT-TYPE
		SYNTAX		INTEGER
		MAX-ACCESS	read-only
		STATUS		current
		DESCRIPTION
			"DAC Secondary Clocking Source."

	::= { dacStatusEntry 2 }

	dacStatusLTMType	OBJECT-TYPE
		SYNTAX		INTEGER {
				    t1by12(1),
				    e1by12(2),
				    t3by1(3),
				    t3by2(4),
				    t1by24(5),
				    e1by24(6),
				    t3by4(7),
				    redundant(17)
				}
		MAX-ACCESS	read-only
		STATUS		current
		DESCRIPTION
			"DAC LTM (Line Termination Module) Type."

	::= { dacStatusEntry 3 }


	dacTraceTable	OBJECT-TYPE
		SYNTAX		SEQUENCE OF DacTraceEntry
		MAX-ACCESS	not-accessible
		STATUS		current
		DESCRIPTION
			"DAC Trace Configuration."

	::= { aptis-monitoring 2003 }

	dacTraceEntry	OBJECT-TYPE
		SYNTAX		DacTraceEntry
		MAX-ACCESS	not-accessible
		STATUS		current
		DESCRIPTION
			"This is the structure of entries in the
			 dacTraceTable."
		INDEX		{ dacTraceIndex }
	::= { dacTraceTable 1 }

	DacTraceEntry ::= SEQUENCE {
		dacTraceIndex			INTEGER,
		dacTraceLocation		INTEGER,
		dacTraceDirection		INTEGER,
		dacTraceType			INTEGER,
		dacTraceTimestamp		INTEGER,
		dacTraceLen			INTEGER,
		dacTraceData			OCTET STRING
	}

	dacTraceIndex	OBJECT-TYPE
		SYNTAX		INTEGER
		MAX-ACCESS	read-only
		STATUS		current
		DESCRIPTION
			"DAC index value."

	::= { dacTraceEntry 1 }

	dacTraceLocation	OBJECT-TYPE
		SYNTAX		INTEGER {
				    sM(1),
				    tN(2),
				    hDLC(3),
				    uSFSM(4)
				}
		MAX-ACCESS	read-only
		STATUS		current
		DESCRIPTION
			"DAC Trace Message Source."

	::= { dacTraceEntry 2 }

	dacTraceDirection	OBJECT-TYPE
		SYNTAX		INTEGER {
				    transmit(1),
				    receive(2)
				}
		MAX-ACCESS	read-only
		STATUS		current
		DESCRIPTION
			"DAC Trace Message Source Layer."

	::= { dacTraceEntry 3 }

	dacTraceType	OBJECT-TYPE
		SYNTAX		INTEGER {
				    smCreate(1),
				    smResource(2),
				    smSetup(3),
				    smConnect(4),
				    smMove(5),
				    smDisconnect(6),
				    smAbort(7),
				    smActivated(8),
				    smConnected(9),
				    smReady(10),
				    smMoved(11),
				    smLinkFailed(12),
				    smDisconnected(13),
				    smResourceSet(14),
				    ccSetup(15),
				    ccConnect(16),
				    ccDisconnect(17),
				    ccAlloc(18),
				    ccClear(19),
				    ccRestart(20),
				    tnSetupInd(21),
				    tnSetupReq(22),
				    tnSetupConf(23),
				    tnAlertingReq(24),
				    tnAlertingInd(25),
				    tnCallProcReq(26),
				    tnCallProcInd(27),
				    tnConnectReq(28),
				    tnConnectInd(29),
				    tnConnectConf(30),
				    tnDiscReq(31),
				    tnDiscInd(32),
				    tnClearReq(33),
				    tnClearInd(34),
				    tnClearConf(35),
				    tnClearResp(36),
				    tnSetupResp(37)
				}
		MAX-ACCESS	read-only
		STATUS		current
		DESCRIPTION
			"DAC Trace Message Typecode."

	::= { dacTraceEntry 4 }

	dacTraceTimestamp	OBJECT-TYPE
		SYNTAX		INTEGER
		MAX-ACCESS	read-only
		STATUS		current
		DESCRIPTION
			"DAC Trace Message Timestamp."

	::= { dacTraceEntry 5 }

	dacTraceLen	OBJECT-TYPE
		SYNTAX		INTEGER (0..300)
		MAX-ACCESS	read-only
		STATUS		current
		DESCRIPTION
			"DAC Trace Message Character Length."

	::= { dacTraceEntry 6 }

	dacTraceData	OBJECT-TYPE
		SYNTAX		OCTET STRING (SIZE (0..300))
		MAX-ACCESS	read-only
		STATUS		current
		DESCRIPTION
			"DAC Trace Message Text."

	::= { dacTraceEntry 7 }


	dacClockingTable	OBJECT-TYPE
		SYNTAX		SEQUENCE OF DacClockingEntry
		MAX-ACCESS	not-accessible
		STATUS		current
		DESCRIPTION
			"DAC Clocking Information."

	::= { aptis-monitoring 2050 }

	dacClockingEntry	OBJECT-TYPE
		SYNTAX		DacClockingEntry
		MAX-ACCESS	not-accessible
		STATUS		current
		DESCRIPTION
			"This is the structure of entries in the
			 dacClockingTable."
		INDEX		{ dacClockingIndex }
	::= { dacClockingTable 1 }

	DacClockingEntry ::= SEQUENCE {
		dacClockingIndex		INTEGER,
		dacClockingClockSourcePrimary	INTEGER,
		dacClockingClockSourceSecondary	INTEGER,
		dacClockingForce		Boolean
	}

	dacClockingIndex	OBJECT-TYPE
		SYNTAX		INTEGER
		MAX-ACCESS	read-only
		STATUS		current
		DESCRIPTION
			"DAC Clocking Information Index."

	::= { dacClockingEntry 1 }

	dacClockingClockSourcePrimary	OBJECT-TYPE
		SYNTAX		INTEGER {
				    if0(0),
				    if1(1),
				    if2(2),
				    if3(3),
				    if4(4),
				    if5(5),
				    if6(6),
				    if7(7),
				    if8(8),
				    if9(9),
				    if10(10),
				    if11(11),
				    if12(12),
				    if13(13),
				    if14(14),
				    if15(15),
				    if16(16),
				    if17(17),
				    if18(18),
				    if19(19),
				    if20(20),
				    if21(21),
				    if22(22),
				    if23(23),
				    if24(24),
				    if25(25),
				    if26(26),
				    if27(27),
				    if28(28),
				    if29(29),
				    if30(30),
				    if31(31),
				    if32(32),
				    if33(33),
				    if34(34),
				    if35(35),
				    if36(36),
				    if37(37),
				    if38(38),
				    if39(39),
				    if40(40),
				    if41(41),
				    if42(42),
				    if43(43),
				    if44(44),
				    if45(45),
				    if46(46),
				    if47(47),
				    if48(48),
				    if49(49),
				    if50(50),
				    if51(51),
				    if52(52),
				    if53(53),
				    if54(54),
				    if55(55),
				    external(200),
				    auto1(201),
				    auto2(202),
				    disabled(255)
				}
		MAX-ACCESS	read-only
		STATUS		current
		DESCRIPTION
			"DAC Primary Clocking Source."

	::= { dacClockingEntry 2 }

	dacClockingClockSourceSecondary	OBJECT-TYPE
		SYNTAX		INTEGER {
				    if0(0),
				    if1(1),
				    if2(2),
				    if3(3),
				    if4(4),
				    if5(5),
				    if6(6),
				    if7(7),
				    if8(8),
				    if9(9),
				    if10(10),
				    if11(11),
				    if12(12),
				    if13(13),
				    if14(14),
				    if15(15),
				    if16(16),
				    if17(17),
				    if18(18),
				    if19(19),
				    if20(20),
				    if21(21),
				    if22(22),
				    if23(23),
				    if24(24),
				    if25(25),
				    if26(26),
				    if27(27),
				    if28(28),
				    if29(29),
				    if30(30),
				    if31(31),
				    if32(32),
				    if33(33),
				    if34(34),
				    if35(35),
				    if36(36),
				    if37(37),
				    if38(38),
				    if39(39),
				    if40(40),
				    if41(41),
				    if42(42),
				    if43(43),
				    if44(44),
				    if45(45),
				    if46(46),
				    if47(47),
				    if48(48),
				    if49(49),
				    if50(50),
				    if51(51),
				    if52(52),
				    if53(53),
				    if54(54),
				    if55(55),
				    external(200),
				    auto1(201),
				    auto2(202),
				    disabled(255)
				}
		MAX-ACCESS	read-only
		STATUS		current
		DESCRIPTION
			"DAC Secondary Clocking Source."

	::= { dacClockingEntry 3 }

	dacClockingForce	OBJECT-TYPE
		SYNTAX		Boolean
		MAX-ACCESS	read-only
		STATUS		current
		DESCRIPTION
			"DAC Clocking FORCE Flag."

	::= { dacClockingEntry 4 }

-- This file generated from  ipshow.cml by smog.
-- date: Thu Jun 29 01:11:50  2000

	ipstatRouteEntryTable	OBJECT-TYPE
		SYNTAX		SEQUENCE OF IpstatRouteEntryEntry
		MAX-ACCESS	not-accessible
		STATUS		current
		DESCRIPTION
			"IP Route Entry."

	::= { aptis-monitoring 3701 }

	ipstatRouteEntryEntry	OBJECT-TYPE
		SYNTAX		IpstatRouteEntryEntry
		MAX-ACCESS	not-accessible
		STATUS		current
		DESCRIPTION
			"This is the structure of entries in the
			 ipstatRouteEntryTable."
		INDEX		{ ipstatRouteEntryPrevXxrt }
	::= { ipstatRouteEntryTable 1 }

	IpstatRouteEntryEntry ::= SEQUENCE {
		ipstatRouteEntryPrevXxrt	INTEGER,
		ipstatRouteEntryNextIprt	INTEGER,
		ipstatRouteEntryPrevIndex	INTEGER,
		ipstatRouteEntryGenNumber	INTEGER,
		ipstatRouteEntryNextIprtIndex	INTEGER,
		ipstatRouteEntryIpAddress	IpAddress,
		ipstatRouteEntryIpMask		INTEGER,
		ipstatRouteEntryCircuitId	INTEGER,
		ipstatRouteEntryTYPE		INTEGER,
		ipstatRouteEntryOwner		INTEGER,
		ipstatRouteEntryPathAndCost	OCTET STRING,
		ipstatRouteEntryTrig		INTEGER,
		ipstatRouteEntryTag		INTEGER,
		ipstatRouteEntryPrivate		INTEGER,
		ipstatRouteEntryPathType	INTEGER,
		ipstatRouteEntryCost		INTEGER
	}

	ipstatRouteEntryPrevXxrt	OBJECT-TYPE
		SYNTAX		INTEGER
		MAX-ACCESS	read-only
		STATUS		current
		DESCRIPTION
			"Prev IP Route."

	::= { ipstatRouteEntryEntry 1 }

	ipstatRouteEntryNextIprt	OBJECT-TYPE
		SYNTAX		INTEGER
		MAX-ACCESS	read-only
		STATUS		current
		DESCRIPTION
			"Next IP Route."

	::= { ipstatRouteEntryEntry 2 }

	ipstatRouteEntryPrevIndex	OBJECT-TYPE
		SYNTAX		INTEGER
		MAX-ACCESS	read-only
		STATUS		current
		DESCRIPTION
			"Prev Index."

	::= { ipstatRouteEntryEntry 3 }

	ipstatRouteEntryGenNumber	OBJECT-TYPE
		SYNTAX		INTEGER
		MAX-ACCESS	read-only
		STATUS		current
		DESCRIPTION
			"Gen Number."

	::= { ipstatRouteEntryEntry 4 }

	ipstatRouteEntryNextIprtIndex	OBJECT-TYPE
		SYNTAX		INTEGER
		MAX-ACCESS	read-only
		STATUS		current
		DESCRIPTION
			"Next IP Route Index."

	::= { ipstatRouteEntryEntry 5 }

	ipstatRouteEntryIpAddress	OBJECT-TYPE
		SYNTAX		IpAddress
		MAX-ACCESS	read-only
		STATUS		current
		DESCRIPTION
			"Route IP Address."

	::= { ipstatRouteEntryEntry 6 }

	ipstatRouteEntryIpMask	OBJECT-TYPE
		SYNTAX		INTEGER
		MAX-ACCESS	read-only
		STATUS		current
		DESCRIPTION
			"Route IP Mask."

	::= { ipstatRouteEntryEntry 7 }

	ipstatRouteEntryCircuitId	OBJECT-TYPE
		SYNTAX		INTEGER
		MAX-ACCESS	read-only
		STATUS		current
		DESCRIPTION
			"Route Circuit ID."

	::= { ipstatRouteEntryEntry 8 }

	ipstatRouteEntryTYPE	OBJECT-TYPE
		SYNTAX		INTEGER
		MAX-ACCESS	read-only
		STATUS		current
		DESCRIPTION
			"Route Circuit Type."

	::= { ipstatRouteEntryEntry 9 }

	ipstatRouteEntryOwner	OBJECT-TYPE
		SYNTAX		INTEGER
		MAX-ACCESS	read-only
		STATUS		current
		DESCRIPTION
			"Route Owner."

	::= { ipstatRouteEntryEntry 10 }

	ipstatRouteEntryPathAndCost	OBJECT-TYPE
		SYNTAX		OCTET STRING (SIZE (0..512))
		MAX-ACCESS	read-only
		STATUS		current
		DESCRIPTION
			"Route Path and Cost."

	::= { ipstatRouteEntryEntry 11 }

	ipstatRouteEntryTrig	OBJECT-TYPE
		SYNTAX		INTEGER
		MAX-ACCESS	read-only
		STATUS		current
		DESCRIPTION
			"Trigger."

	::= { ipstatRouteEntryEntry 12 }

	ipstatRouteEntryTag	OBJECT-TYPE
		SYNTAX		INTEGER
		MAX-ACCESS	read-only
		STATUS		current
		DESCRIPTION
			"Tag."

	::= { ipstatRouteEntryEntry 13 }

	ipstatRouteEntryPrivate	OBJECT-TYPE
		SYNTAX		INTEGER
		MAX-ACCESS	read-only
		STATUS		current
		DESCRIPTION
			"Private."

	::= { ipstatRouteEntryEntry 14 }

	ipstatRouteEntryPathType	OBJECT-TYPE
		SYNTAX		INTEGER {
				    mpath(1),
				    simple(2)
				}
		MAX-ACCESS	read-only
		STATUS		current
		DESCRIPTION
			"Path Type."

	::= { ipstatRouteEntryEntry 15 }

	ipstatRouteEntryCost	OBJECT-TYPE
		SYNTAX		INTEGER
		MAX-ACCESS	read-only
		STATUS		current
		DESCRIPTION
			"Cost."

	::= { ipstatRouteEntryEntry 16 }

-- This file generated from  dvs.cml by smog.
-- date: Thu Jun 29 01:11:50  2000

	dvsStatusTable	OBJECT-TYPE
		SYNTAX		SEQUENCE OF DvsStatusEntry
		MAX-ACCESS	not-accessible
		STATUS		current
		DESCRIPTION
			"DVS Tunnel status."

	::= { aptis-monitoring 1505 }

	dvsStatusEntry	OBJECT-TYPE
		SYNTAX		DvsStatusEntry
		MAX-ACCESS	not-accessible
		STATUS		current
		DESCRIPTION
			"This is the structure of entries in the
			 dvsStatusTable."
		INDEX		{ dvsStatusLocalCLID }
	::= { dvsStatusTable 1 }

	DvsStatusEntry ::= SEQUENCE {
		dvsStatusLocalCLID		INTEGER,
		dvsStatusRemoteCLID		INTEGER,
		dvsStatusLocalAddress		IpAddress,
		dvsStatusRemoteAddress		IpAddress,
		dvsStatusTunnelState		INTEGER,
		dvsStatusUpTime			INTEGER,
		dvsStatusMacSlotNumber		INTEGER,
		dvsStatusVPOP			INTEGER,
		dvsStatusGreInPackets		INTEGER,
		dvsStatusGreOutPackets		INTEGER,
		dvsStatusGreChecksumError	INTEGER,
		dvsStatusGreInDropped		INTEGER,
		dvsStatusGreOutDropped		INTEGER,
		dvsStatusDeadSession		Boolean,
		dvsStatusRemoteIPXNetwork	INTEGER,
		dvsStatusRemoteIPXNode		DisplayString,
		dvsStatusIPInPackets		INTEGER,
		dvsStatusIPOutPackets		INTEGER,
		dvsStatusIPXInPackets		INTEGER,
		dvsStatusIPXOutPackets		INTEGER
	}

	dvsStatusLocalCLID	OBJECT-TYPE
		SYNTAX		INTEGER
		MAX-ACCESS	read-only
		STATUS		current
		DESCRIPTION
			"The local identifier for this tunnel"

	::= { dvsStatusEntry 1 }

	dvsStatusRemoteCLID	OBJECT-TYPE
		SYNTAX		INTEGER
		MAX-ACCESS	read-only
		STATUS		current
		DESCRIPTION
			"The identifier of the remote endpoint for this
			tunnel."

	::= { dvsStatusEntry 2 }

	dvsStatusLocalAddress	OBJECT-TYPE
		SYNTAX		IpAddress
		MAX-ACCESS	read-only
		STATUS		current
		DESCRIPTION
			"The local IP address used to send tunnel packets to
			the gateway."

	::= { dvsStatusEntry 3 }

	dvsStatusRemoteAddress	OBJECT-TYPE
		SYNTAX		IpAddress
		MAX-ACCESS	read-only
		STATUS		current
		DESCRIPTION
			"The IP address of the remote gateway for the tunnel."

	::= { dvsStatusEntry 4 }

	dvsStatusTunnelState	OBJECT-TYPE
		SYNTAX		INTEGER {
				    iDLE(0),
				    aWGWCFG(1),
				    aUTHREPLY(2),
				    pRIMGWTO(3),
				    mODPPPCFG(4),
				    dHCP(5),
				    mIP(6),
				    oPEN(7),
				    dISC(8)
				}
		MAX-ACCESS	read-only
		STATUS		current
		DESCRIPTION
			"The current state of the tunnel."

	::= { dvsStatusEntry 5 }

	dvsStatusUpTime	OBJECT-TYPE
		SYNTAX		INTEGER
		MAX-ACCESS	read-only
		STATUS		current
		DESCRIPTION
			"The time this tunnel has been active."

	::= { dvsStatusEntry 6 }

	dvsStatusMacSlotNumber	OBJECT-TYPE
		SYNTAX		INTEGER
		MAX-ACCESS	read-only
		STATUS		current
		DESCRIPTION
			"The slot number of the MAC card that is the local
			endpoint for this tunnel."

	::= { dvsStatusEntry 7 }

	dvsStatusVPOP	OBJECT-TYPE
		SYNTAX		INTEGER
		MAX-ACCESS	read-only
		STATUS		current
		DESCRIPTION
			"The VPOP id to which this tunnel belongs."

	::= { dvsStatusEntry 8 }

	dvsStatusGreInPackets	OBJECT-TYPE
		SYNTAX		INTEGER
		MAX-ACCESS	read-only
		STATUS		current
		DESCRIPTION
			"The total number of GRE packets received on the
			tunnel."

	::= { dvsStatusEntry 9 }

	dvsStatusGreOutPackets	OBJECT-TYPE
		SYNTAX		INTEGER
		MAX-ACCESS	read-only
		STATUS		current
		DESCRIPTION
			"The total number of GRE packets sent on the tunnel."

	::= { dvsStatusEntry 10 }

	dvsStatusGreChecksumError	OBJECT-TYPE
		SYNTAX		INTEGER
		MAX-ACCESS	read-only
		STATUS		current
		DESCRIPTION
			"The total number of GRE packets received with bad
			checksums for this tunnel."

	::= { dvsStatusEntry 11 }

	dvsStatusGreInDropped	OBJECT-TYPE
		SYNTAX		INTEGER
		MAX-ACCESS	read-only
		STATUS		current
		DESCRIPTION
			"The total number of GRE packets dropped on receive
			for this tunnel."

	::= { dvsStatusEntry 12 }

	dvsStatusGreOutDropped	OBJECT-TYPE
		SYNTAX		INTEGER
		MAX-ACCESS	read-only
		STATUS		current
		DESCRIPTION
			"The total number of GRE packets dropped on send for
			this tunnel."

	::= { dvsStatusEntry 13 }

	dvsStatusDeadSession	OBJECT-TYPE
		SYNTAX		Boolean
		MAX-ACCESS	read-only
		STATUS		current
		DESCRIPTION
			"True if session is dead/disconnected"

	::= { dvsStatusEntry 14 }

	dvsStatusRemoteIPXNetwork	OBJECT-TYPE
		SYNTAX		INTEGER
		MAX-ACCESS	read-only
		STATUS		current
		DESCRIPTION
			"Remote IPX Network Number"

	::= { dvsStatusEntry 15 }

	dvsStatusRemoteIPXNode	OBJECT-TYPE
		SYNTAX		DisplayString (SIZE (0..16))
		MAX-ACCESS	read-only
		STATUS		current
		DESCRIPTION
			"IPX node number to assign to remote user."

	::= { dvsStatusEntry 16 }

	dvsStatusIPInPackets	OBJECT-TYPE
		SYNTAX		INTEGER
		MAX-ACCESS	read-only
		STATUS		current
		DESCRIPTION
			"Total number of IP packets received"

	::= { dvsStatusEntry 17 }

	dvsStatusIPOutPackets	OBJECT-TYPE
		SYNTAX		INTEGER
		MAX-ACCESS	read-only
		STATUS		current
		DESCRIPTION
			"Total number of IP packets tunneled"

	::= { dvsStatusEntry 18 }

	dvsStatusIPXInPackets	OBJECT-TYPE
		SYNTAX		INTEGER
		MAX-ACCESS	read-only
		STATUS		current
		DESCRIPTION
			"Total number of IPX packets received"

	::= { dvsStatusEntry 19 }

	dvsStatusIPXOutPackets	OBJECT-TYPE
		SYNTAX		INTEGER
		MAX-ACCESS	read-only
		STATUS		current
		DESCRIPTION
			"Total number of IPX packets tunneled"

	::= { dvsStatusEntry 20 }


	dvsLogEntryTable	OBJECT-TYPE
		SYNTAX		SEQUENCE OF DvsLogEntryEntry
		MAX-ACCESS	not-accessible
		STATUS		current
		DESCRIPTION
			"DVS Tunnel log entry."

	::= { aptis-monitoring 1506 }

	dvsLogEntryEntry	OBJECT-TYPE
		SYNTAX		DvsLogEntryEntry
		MAX-ACCESS	not-accessible
		STATUS		current
		DESCRIPTION
			"This is the structure of entries in the
			 dvsLogEntryTable."
		INDEX		{ dvsLogEntryIndex }
	::= { dvsLogEntryTable 1 }

	DvsLogEntryEntry ::= SEQUENCE {
		dvsLogEntryIndex		INTEGER,
		dvsLogEntryMinIndex		INTEGER,
		dvsLogEntryMaxIndex		INTEGER,
		dvsLogEntryEntryText		OCTET STRING,
		dvsLogEntryTunnelCLID		INTEGER,
		dvsLogEntryUpTime		INTEGER
	}

	dvsLogEntryIndex	OBJECT-TYPE
		SYNTAX		INTEGER
		MAX-ACCESS	read-only
		STATUS		current
		DESCRIPTION
			"Log entry index"

	::= { dvsLogEntryEntry 1 }

	dvsLogEntryMinIndex	OBJECT-TYPE
		SYNTAX		INTEGER
		MAX-ACCESS	read-only
		STATUS		current
		DESCRIPTION
			"Index of oldest event available"

	::= { dvsLogEntryEntry 2 }

	dvsLogEntryMaxIndex	OBJECT-TYPE
		SYNTAX		INTEGER
		MAX-ACCESS	read-only
		STATUS		current
		DESCRIPTION
			"Index of newest event available"

	::= { dvsLogEntryEntry 3 }

	dvsLogEntryEntryText	OBJECT-TYPE
		SYNTAX		OCTET STRING (SIZE (0..1024))
		MAX-ACCESS	read-only
		STATUS		current
		DESCRIPTION
			"Log entry text."

	::= { dvsLogEntryEntry 4 }

	dvsLogEntryTunnelCLID	OBJECT-TYPE
		SYNTAX		INTEGER
		MAX-ACCESS	read-only
		STATUS		current
		DESCRIPTION
			"The Local Identifier for this tunnel"

	::= { dvsLogEntryEntry 5 }

	dvsLogEntryUpTime	OBJECT-TYPE
		SYNTAX		INTEGER
		MAX-ACCESS	read-only
		STATUS		current
		DESCRIPTION
			"Time this tunnel has been active"

	::= { dvsLogEntryEntry 6 }


	dvsDeadLogEntryTable	OBJECT-TYPE
		SYNTAX		SEQUENCE OF DvsDeadLogEntryEntry
		MAX-ACCESS	not-accessible
		STATUS		current
		DESCRIPTION
			"DVS Tunnel dead log entry."

	::= { aptis-monitoring 1520 }

	dvsDeadLogEntryEntry	OBJECT-TYPE
		SYNTAX		DvsDeadLogEntryEntry
		MAX-ACCESS	not-accessible
		STATUS		current
		DESCRIPTION
			"This is the structure of entries in the
			 dvsDeadLogEntryTable."
		INDEX		{ dvsDeadLogEntryIndex }
	::= { dvsDeadLogEntryTable 1 }

	DvsDeadLogEntryEntry ::= SEQUENCE {
		dvsDeadLogEntryIndex		INTEGER,
		dvsDeadLogEntryMinIndex		INTEGER,
		dvsDeadLogEntryMaxIndex		INTEGER,
		dvsDeadLogEntryEntryText	OCTET STRING,
		dvsDeadLogEntryTunnelCLID	INTEGER,
		dvsDeadLogEntryUpTime		INTEGER
	}

	dvsDeadLogEntryIndex	OBJECT-TYPE
		SYNTAX		INTEGER
		MAX-ACCESS	read-only
		STATUS		current
		DESCRIPTION
			"Log entry index"

	::= { dvsDeadLogEntryEntry 1 }

	dvsDeadLogEntryMinIndex	OBJECT-TYPE
		SYNTAX		INTEGER
		MAX-ACCESS	read-only
		STATUS		current
		DESCRIPTION
			"Index of oldest event available"

	::= { dvsDeadLogEntryEntry 2 }

	dvsDeadLogEntryMaxIndex	OBJECT-TYPE
		SYNTAX		INTEGER
		MAX-ACCESS	read-only
		STATUS		current
		DESCRIPTION
			"Index of newest event available"

	::= { dvsDeadLogEntryEntry 3 }

	dvsDeadLogEntryEntryText	OBJECT-TYPE
		SYNTAX		OCTET STRING (SIZE (0..1024))
		MAX-ACCESS	read-only
		STATUS		current
		DESCRIPTION
			"Log entry text."

	::= { dvsDeadLogEntryEntry 4 }

	dvsDeadLogEntryTunnelCLID	OBJECT-TYPE
		SYNTAX		INTEGER
		MAX-ACCESS	read-only
		STATUS		current
		DESCRIPTION
			"The Local Identifier for this tunnel"

	::= { dvsDeadLogEntryEntry 5 }

	dvsDeadLogEntryUpTime	OBJECT-TYPE
		SYNTAX		INTEGER
		MAX-ACCESS	read-only
		STATUS		current
		DESCRIPTION
			"Time this tunnel has been active"

	::= { dvsDeadLogEntryEntry 6 }


	dvsStatusDeadTable	OBJECT-TYPE
		SYNTAX		SEQUENCE OF DvsStatusDeadEntry
		MAX-ACCESS	not-accessible
		STATUS		current
		DESCRIPTION
			"DVS Tunnel dead status."

	::= { aptis-monitoring 1521 }

	dvsStatusDeadEntry	OBJECT-TYPE
		SYNTAX		DvsStatusDeadEntry
		MAX-ACCESS	not-accessible
		STATUS		current
		DESCRIPTION
			"This is the structure of entries in the
			 dvsStatusDeadTable."
		INDEX		{ dvsStatusDeadTunnelCLID }
	::= { dvsStatusDeadTable 1 }

	DvsStatusDeadEntry ::= SEQUENCE {
		dvsStatusDeadTunnelCLID		INTEGER,
		dvsStatusDeadRemoteCLID		INTEGER,
		dvsStatusDeadRemoteAddress	IpAddress,
		dvsStatusDeadTunnelState	INTEGER,
		dvsStatusDeadUpTime		INTEGER,
		dvsStatusDeadMacSlotNumber	INTEGER,
		dvsStatusDeadVPOP		INTEGER,
		dvsStatusDeadGreInPackets	INTEGER,
		dvsStatusDeadGreOutPackets	INTEGER,
		dvsStatusDeadGreChecksumError	INTEGER,
		dvsStatusDeadGreInDropped	INTEGER,
		dvsStatusDeadGreOutDropped	INTEGER,
		dvsStatusDeadDeadSession	Boolean
	}

	dvsStatusDeadTunnelCLID	OBJECT-TYPE
		SYNTAX		INTEGER
		MAX-ACCESS	read-only
		STATUS		current
		DESCRIPTION
			"The local identifier for this tunnel"

	::= { dvsStatusDeadEntry 1 }

	dvsStatusDeadRemoteCLID	OBJECT-TYPE
		SYNTAX		INTEGER
		MAX-ACCESS	read-only
		STATUS		current
		DESCRIPTION
			"The identifier of the remote endpoint for this
			tunnel."

	::= { dvsStatusDeadEntry 2 }

	dvsStatusDeadRemoteAddress	OBJECT-TYPE
		SYNTAX		IpAddress
		MAX-ACCESS	read-only
		STATUS		current
		DESCRIPTION
			"The IP address of the remote gateway for the tunnel."

	::= { dvsStatusDeadEntry 3 }

	dvsStatusDeadTunnelState	OBJECT-TYPE
		SYNTAX		INTEGER {
				    iDLE(0),
				    aWGWCFG(1),
				    aUTHREPLY(2),
				    pRIMGWTO(3),
				    mODPPPCFG(4),
				    dHCP(5),
				    mIP(6),
				    oPEN(7),
				    dISC(8)
				}
		MAX-ACCESS	read-only
		STATUS		current
		DESCRIPTION
			"The current state of the tunnel."

	::= { dvsStatusDeadEntry 4 }

	dvsStatusDeadUpTime	OBJECT-TYPE
		SYNTAX		INTEGER
		MAX-ACCESS	read-only
		STATUS		current
		DESCRIPTION
			"The time this tunnel has been active."

	::= { dvsStatusDeadEntry 5 }

	dvsStatusDeadMacSlotNumber	OBJECT-TYPE
		SYNTAX		INTEGER
		MAX-ACCESS	read-only
		STATUS		current
		DESCRIPTION
			"The slot number of the MAC card that is the local
			endpoint for this tunnel."

	::= { dvsStatusDeadEntry 6 }

	dvsStatusDeadVPOP	OBJECT-TYPE
		SYNTAX		INTEGER
		MAX-ACCESS	read-only
		STATUS		current
		DESCRIPTION
			"The VPOP id to which this tunnel belongs."

	::= { dvsStatusDeadEntry 7 }

	dvsStatusDeadGreInPackets	OBJECT-TYPE
		SYNTAX		INTEGER
		MAX-ACCESS	read-only
		STATUS		current
		DESCRIPTION
			"The total number of GRE packets received on the
			tunnel."

	::= { dvsStatusDeadEntry 8 }

	dvsStatusDeadGreOutPackets	OBJECT-TYPE
		SYNTAX		INTEGER
		MAX-ACCESS	read-only
		STATUS		current
		DESCRIPTION
			"The total number of GRE packets sent on the tunnel."

	::= { dvsStatusDeadEntry 9 }

	dvsStatusDeadGreChecksumError	OBJECT-TYPE
		SYNTAX		INTEGER
		MAX-ACCESS	read-only
		STATUS		current
		DESCRIPTION
			"The total number of GRE packets received with bad
			checksums for this tunnel."

	::= { dvsStatusDeadEntry 10 }

	dvsStatusDeadGreInDropped	OBJECT-TYPE
		SYNTAX		INTEGER
		MAX-ACCESS	read-only
		STATUS		current
		DESCRIPTION
			"The total number of GRE packets dropped on receive
			for this tunnel."

	::= { dvsStatusDeadEntry 11 }

	dvsStatusDeadGreOutDropped	OBJECT-TYPE
		SYNTAX		INTEGER
		MAX-ACCESS	read-only
		STATUS		current
		DESCRIPTION
			"The total number of GRE packets dropped on send for
			this tunnel."

	::= { dvsStatusDeadEntry 12 }

	dvsStatusDeadDeadSession	OBJECT-TYPE
		SYNTAX		Boolean
		MAX-ACCESS	read-only
		STATUS		current
		DESCRIPTION
			"True if session is dead/disconnected"

	::= { dvsStatusDeadEntry 13 }

-- This file generated from  igmp.cml by smog.
-- date: Thu Jun 29 01:11:51  2000

	ipstatIgmpEntryTable	OBJECT-TYPE
		SYNTAX		SEQUENCE OF IpstatIgmpEntryEntry
		MAX-ACCESS	not-accessible
		STATUS		current
		DESCRIPTION
			"IP Group Management Protocol Information."

	::= { aptis-monitoring 3801 }

	ipstatIgmpEntryEntry	OBJECT-TYPE
		SYNTAX		IpstatIgmpEntryEntry
		MAX-ACCESS	not-accessible
		STATUS		current
		DESCRIPTION
			"This is the structure of entries in the
			 ipstatIgmpEntryTable."
		INDEX		{ ipstatIgmpEntryIPAddress }
	::= { ipstatIgmpEntryTable 1 }

	IpstatIgmpEntryEntry ::= SEQUENCE {
		ipstatIgmpEntryIPAddress	IpAddress,
		ipstatIgmpEntryIPAddrfrom	IpAddress,
		ipstatIgmpEntryCliId		INTEGER,
		ipstatIgmpEntryTimeout		INTEGER,
		ipstatIgmpEntryCount		INTEGER,
		ipstatIgmpEntryState		INTEGER
	}

	ipstatIgmpEntryIPAddress	OBJECT-TYPE
		SYNTAX		IpAddress
		MAX-ACCESS	read-only
		STATUS		current
		DESCRIPTION
			"IGMP Multicast Group IP Address."

	::= { ipstatIgmpEntryEntry 1 }

	ipstatIgmpEntryIPAddrfrom	OBJECT-TYPE
		SYNTAX		IpAddress
		MAX-ACCESS	read-only
		STATUS		current
		DESCRIPTION
			"IGMP Host IP Address."

	::= { ipstatIgmpEntryEntry 2 }

	ipstatIgmpEntryCliId	OBJECT-TYPE
		SYNTAX		INTEGER
		MAX-ACCESS	read-only
		STATUS		current
		DESCRIPTION
			"IGMP Client ID."

	::= { ipstatIgmpEntryEntry 3 }

	ipstatIgmpEntryTimeout	OBJECT-TYPE
		SYNTAX		INTEGER
		MAX-ACCESS	read-only
		STATUS		current
		DESCRIPTION
			"IGMP Timeout."

	::= { ipstatIgmpEntryEntry 4 }

	ipstatIgmpEntryCount	OBJECT-TYPE
		SYNTAX		INTEGER
		MAX-ACCESS	read-only
		STATUS		current
		DESCRIPTION
			"IGMP use count."

	::= { ipstatIgmpEntryEntry 5 }

	ipstatIgmpEntryState	OBJECT-TYPE
		SYNTAX		INTEGER {
				    nomem(1),
				    v1mem(2),
				    check(3),
				    mem(4)
				}
		MAX-ACCESS	read-only
		STATUS		current
		DESCRIPTION
			"IGMP State."

	::= { ipstatIgmpEntryEntry 6 }

END
