--			Ascend miboc3int MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBOC3INT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    miboC3InterfaceProfile  OBJECT IDENTIFIER ::= { configuration 153}

	-- The miboC3InterfaceProfile table
	--
	-- This table contains parameters for the miboC3InterfaceProfile profile
	--

    miboC3InterfaceProfileTable	OBJECT-TYPE
	SYNTAX		SEQUENCE OF MiboC3InterfaceProfileEntry
	ACCESS		not-accessible
	STATUS		mandatory
	DESCRIPTION	"A list of miboC3InterfaceProfile profile entries."
	::= { miboC3InterfaceProfile 1 }

    miboC3InterfaceProfileEntry	OBJECT-TYPE
	SYNTAX		MiboC3InterfaceProfileEntry
	ACCESS		not-accessible
	STATUS		mandatory
	DESCRIPTION	"A miboC3InterfaceProfile entry containing objects that
			 maps to the parameters of miboC3InterfaceProfile profile."
	INDEX		{ oC3InterfaceProfile-Shelf-o, oC3InterfaceProfile-Slot-o, oC3InterfaceProfile-Item-o }
	::= { miboC3InterfaceProfileTable 1 }

    MiboC3InterfaceProfileEntry ::=
	SEQUENCE {
	    oC3InterfaceProfile-Shelf-o
		INTEGER,
	    oC3InterfaceProfile-Slot-o
		INTEGER,
	    oC3InterfaceProfile-Item-o
		INTEGER,
	    oC3InterfaceProfile-Name
		DisplayString,
	    oC3InterfaceProfile-PhysicalAddress-Shelf
		INTEGER,
	    oC3InterfaceProfile-PhysicalAddress-Slot
		INTEGER,
	    oC3InterfaceProfile-PhysicalAddress-ItemNumber
		INTEGER,
	    oC3InterfaceProfile-LimControl-PrimaryLpm
		INTEGER,
	    oC3InterfaceProfile-LimControl-ActiveLine
		INTEGER,
	    oC3InterfaceProfile-LineParams-Name
		DisplayString,
	    oC3InterfaceProfile-LineParams-PhysicalAddress-Shelf
		INTEGER,
	    oC3InterfaceProfile-LineParams-PhysicalAddress-Slot
		INTEGER,
	    oC3InterfaceProfile-LineParams-PhysicalAddress-ItemNumber
		INTEGER,
	    oC3InterfaceProfile-LineParams-Enabled
		INTEGER,
	    oC3InterfaceProfile-LineParams-AuPointer
		INTEGER,
	    oC3InterfaceProfile-LineParams-Signaling
		INTEGER,
	    oC3InterfaceProfile-LineParams-LoopTiming
		INTEGER,
	    oC3InterfaceProfile-LineParams-Loopback
		INTEGER,
	    oC3InterfaceProfile-LineParams-ApsConfigName
		DisplayString,
	    oC3InterfaceProfile-Action-o
		INTEGER
	}

    oC3InterfaceProfile-Shelf-o	OBJECT-TYPE
	SYNTAX	INTEGER
	ACCESS	read-only
	STATUS	mandatory
	DESCRIPTION	""
	::= { miboC3InterfaceProfileEntry 1 }

    oC3InterfaceProfile-Slot-o	OBJECT-TYPE
	SYNTAX	INTEGER
	ACCESS	read-only
	STATUS	mandatory
	DESCRIPTION	""
	::= { miboC3InterfaceProfileEntry 2 }

    oC3InterfaceProfile-Item-o	OBJECT-TYPE
	SYNTAX	INTEGER
	ACCESS	read-only
	STATUS	mandatory
	DESCRIPTION	""
	::= { miboC3InterfaceProfileEntry 3 }

    oC3InterfaceProfile-Name	OBJECT-TYPE
	SYNTAX	DisplayString
	ACCESS	read-write
	STATUS	mandatory
	DESCRIPTION	"Name of Channelized OC3 Interface profile"
	::= { miboC3InterfaceProfileEntry 4 }

    oC3InterfaceProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboC3InterfaceProfileEntry 5 }

    oC3InterfaceProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboC3InterfaceProfileEntry 6 }

    oC3InterfaceProfile-PhysicalAddress-ItemNumber	OBJECT-TYPE
	SYNTAX	INTEGER
	ACCESS	read-write
	STATUS	mandatory
	DESCRIPTION	"A number that specifies an addressable entity within the context of shelf and slot."
	::= { miboC3InterfaceProfileEntry 7 }

    oC3InterfaceProfile-LimControl-PrimaryLpm	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"Which LPM is the primary control for the interface"
	::= { miboC3InterfaceProfileEntry 8 }

    oC3InterfaceProfile-LimControl-ActiveLine	OBJECT-TYPE
	SYNTAX	INTEGER {
		    workingLine (1),
		    protectionLine (2),
		    backupLine (3)
		}
	ACCESS	read-write
	STATUS	mandatory
	DESCRIPTION	"Administrative request for current active line or line interface"
	::= { miboC3InterfaceProfileEntry 9 }

    oC3InterfaceProfile-LineParams-Name	OBJECT-TYPE
	SYNTAX	DisplayString
	ACCESS	read-write
	STATUS	mandatory
	DESCRIPTION	"Name of STM network line."
	::= { miboC3InterfaceProfileEntry 10 }

    oC3InterfaceProfile-LineParams-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboC3InterfaceProfileEntry 11 }

    oC3InterfaceProfile-LineParams-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboC3InterfaceProfileEntry 12 }

    oC3InterfaceProfile-LineParams-PhysicalAddress-ItemNumber	OBJECT-TYPE
	SYNTAX	INTEGER
	ACCESS	read-write
	STATUS	mandatory
	DESCRIPTION	"A number that specifies an addressable entity within the context of shelf and slot."
	::= { miboC3InterfaceProfileEntry 13 }

    oC3InterfaceProfile-LineParams-Enabled	OBJECT-TYPE
	SYNTAX	INTEGER {
		    no (1),
		    yes (2)
		}
	ACCESS	read-write
	STATUS	mandatory
	DESCRIPTION	"TRUE if the link is enabled, otherwise FALSE."
	::= { miboC3InterfaceProfileEntry 14 }

    oC3InterfaceProfile-LineParams-AuPointer	OBJECT-TYPE
	SYNTAX	INTEGER {
		    au3Pointer (2),
		    au4Pointer (3)
		}
	ACCESS	read-write
	STATUS	mandatory
	DESCRIPTION	"The AU pointer used by this STM-1 link."
	::= { miboC3InterfaceProfileEntry 15 }

    oC3InterfaceProfile-LineParams-Signaling	OBJECT-TYPE
	SYNTAX	INTEGER {
		    sonet (2),
		    sdh (3),
		    japan (4)
		}
	ACCESS	read-write
	STATUS	mandatory
	DESCRIPTION	"The STM signaling to use on this STM link."
	::= { miboC3InterfaceProfileEntry 20 }

    oC3InterfaceProfile-LineParams-LoopTiming	OBJECT-TYPE
	SYNTAX	INTEGER {
		    no (1),
		    yes (2)
		}
	ACCESS	read-write
	STATUS	mandatory
	DESCRIPTION	"TRUE if the line is to use loop timing, otherwise FALSE."
	::= { miboC3InterfaceProfileEntry 16 }

    oC3InterfaceProfile-LineParams-Loopback	OBJECT-TYPE
	SYNTAX	INTEGER {
		    noLoopback (1),
		    lineLoopback (2),
		    localLoopback (3)
		}
	ACCESS	read-write
	STATUS	mandatory
	DESCRIPTION	"Loopback mode"
	::= { miboC3InterfaceProfileEntry 17 }

    oC3InterfaceProfile-LineParams-ApsConfigName	OBJECT-TYPE
	SYNTAX	DisplayString
	ACCESS	read-write
	STATUS	mandatory
	DESCRIPTION	"APS Config Profile name, specifies APS configuration profile that defines a protection group for this line."
	::= { miboC3InterfaceProfileEntry 19 }

    oC3InterfaceProfile-Action-o	OBJECT-TYPE
	SYNTAX	INTEGER {
		    noAction (1),
		    createProfile (2),
		    deleteProfile (3)
		}
	ACCESS	read-write
	STATUS	mandatory
	DESCRIPTION	""
	::= { miboC3InterfaceProfileEntry 18 }


	-- The miboC3InterfaceProfile__path_params table
	--
	-- This table contains parameters for the miboC3InterfaceProfile__path_params profile
	--

    miboC3InterfaceProfile-PathParamsTable	OBJECT-TYPE
	SYNTAX		SEQUENCE OF MiboC3InterfaceProfile-PathParamsEntry
	ACCESS		not-accessible
	STATUS		mandatory
	DESCRIPTION	"A list of miboC3InterfaceProfile__path_params profile entries."
	::= { miboC3InterfaceProfile 2 }

    miboC3InterfaceProfile-PathParamsEntry	OBJECT-TYPE
	SYNTAX		MiboC3InterfaceProfile-PathParamsEntry
	ACCESS		not-accessible
	STATUS		mandatory
	DESCRIPTION	"A miboC3InterfaceProfile__path_params entry containing objects that
			 maps to the parameters of miboC3InterfaceProfile__path_params profile."
	INDEX		{ oC3InterfaceProfile-PathParams-Shelf-o, oC3InterfaceProfile-PathParams-Slot-o, oC3InterfaceProfile-PathParams-Item-o, oC3InterfaceProfile-PathParams-Index-o }
	::= { miboC3InterfaceProfile-PathParamsTable 1 }

    MiboC3InterfaceProfile-PathParamsEntry ::=
	SEQUENCE {
	    oC3InterfaceProfile-PathParams-Shelf-o
		INTEGER,
	    oC3InterfaceProfile-PathParams-Slot-o
		INTEGER,
	    oC3InterfaceProfile-PathParams-Item-o
		INTEGER,
	    oC3InterfaceProfile-PathParams-Index-o
		INTEGER,
	    oC3InterfaceProfile-PathParams-Name
		DisplayString,
	    oC3InterfaceProfile-PathParams-Stm0Profile-Name
		DisplayString,
	    oC3InterfaceProfile-PathParams-Stm0Profile-PhysicalAddress-Shelf
		INTEGER,
	    oC3InterfaceProfile-PathParams-Stm0Profile-PhysicalAddress-Slot
		INTEGER,
	    oC3InterfaceProfile-PathParams-Stm0Profile-PhysicalAddress-ItemNumber
		INTEGER,
	    oC3InterfaceProfile-PathParams-Stm0Profile-Enabled
		INTEGER,
	    oC3InterfaceProfile-PathParams-Stm0Profile-TributaryMapping
		INTEGER,
	    oC3InterfaceProfile-PathParams-Ds3Profile-Name
		DisplayString,
	    oC3InterfaceProfile-PathParams-Ds3Profile-PhysicalAddress-Shelf
		INTEGER,
	    oC3InterfaceProfile-PathParams-Ds3Profile-PhysicalAddress-Slot
		INTEGER,
	    oC3InterfaceProfile-PathParams-Ds3Profile-PhysicalAddress-ItemNumber
		INTEGER,
	    oC3InterfaceProfile-PathParams-Ds3Profile-Enabled
		INTEGER,
	    oC3InterfaceProfile-PathParams-Ds3Profile-FrameType
		INTEGER,
	    oC3InterfaceProfile-PathParams-Ds3Profile-LineLength
		INTEGER,
	    oC3InterfaceProfile-PathParams-Ds3Profile-Loopback
		INTEGER,
	    oC3InterfaceProfile-PathParams-Ds3Profile-StatusChangeTrapEnable
		INTEGER
	}

    oC3InterfaceProfile-PathParams-Shelf-o	OBJECT-TYPE
	SYNTAX	INTEGER
	ACCESS	read-only
	STATUS	mandatory
	DESCRIPTION	""
	::= { miboC3InterfaceProfile-PathParamsEntry 1 }

    oC3InterfaceProfile-PathParams-Slot-o	OBJECT-TYPE
	SYNTAX	INTEGER
	ACCESS	read-only
	STATUS	mandatory
	DESCRIPTION	""
	::= { miboC3InterfaceProfile-PathParamsEntry 2 }

    oC3InterfaceProfile-PathParams-Item-o	OBJECT-TYPE
	SYNTAX	INTEGER
	ACCESS	read-only
	STATUS	mandatory
	DESCRIPTION	""
	::= { miboC3InterfaceProfile-PathParamsEntry 3 }

    oC3InterfaceProfile-PathParams-Index-o	OBJECT-TYPE
	SYNTAX	INTEGER
	ACCESS	read-only
	STATUS	mandatory
	DESCRIPTION	""
	::= { miboC3InterfaceProfile-PathParamsEntry 4 }

    oC3InterfaceProfile-PathParams-Name	OBJECT-TYPE
	SYNTAX	DisplayString
	ACCESS	read-write
	STATUS	mandatory
	DESCRIPTION	"Name of Channelized STS1 Link profile"
	::= { miboC3InterfaceProfile-PathParamsEntry 5 }

    oC3InterfaceProfile-PathParams-Stm0Profile-Name	OBJECT-TYPE
	SYNTAX	DisplayString
	ACCESS	read-write
	STATUS	mandatory
	DESCRIPTION	"Name of Channelized SONET/SDH Path profile"
	::= { miboC3InterfaceProfile-PathParamsEntry 6 }

    oC3InterfaceProfile-PathParams-Stm0Profile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboC3InterfaceProfile-PathParamsEntry 7 }

    oC3InterfaceProfile-PathParams-Stm0Profile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboC3InterfaceProfile-PathParamsEntry 8 }

    oC3InterfaceProfile-PathParams-Stm0Profile-PhysicalAddress-ItemNumber	OBJECT-TYPE
	SYNTAX	INTEGER
	ACCESS	read-write
	STATUS	mandatory
	DESCRIPTION	"A number that specifies an addressable entity within the context of shelf and slot."
	::= { miboC3InterfaceProfile-PathParamsEntry 9 }

    oC3InterfaceProfile-PathParams-Stm0Profile-Enabled	OBJECT-TYPE
	SYNTAX	INTEGER {
		    no (1),
		    yes (2)
		}
	ACCESS	read-write
	STATUS	mandatory
	DESCRIPTION	"TRUE if the link is enabled, otherwise FALSE."
	::= { miboC3InterfaceProfile-PathParamsEntry 10 }

    oC3InterfaceProfile-PathParams-Stm0Profile-TributaryMapping	OBJECT-TYPE
	SYNTAX	INTEGER {
		    vc11AsyncMapping (2),
		    vc11ByteSyncMapping (3),
		    vc12AsyncMapping (5),
		    vc12ByteSyncMapping (6),
		    vc3AsyncMapping (8)
		}
	ACCESS	read-write
	STATUS	mandatory
	DESCRIPTION	"The VT/VC mapping to be performed by this link"
	::= { miboC3InterfaceProfile-PathParamsEntry 11 }

    oC3InterfaceProfile-PathParams-Ds3Profile-Name	OBJECT-TYPE
	SYNTAX	DisplayString
	ACCESS	read-write
	STATUS	mandatory
	DESCRIPTION	"Name of DS3 line."
	::= { miboC3InterfaceProfile-PathParamsEntry 12 }

    oC3InterfaceProfile-PathParams-Ds3Profile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboC3InterfaceProfile-PathParamsEntry 13 }

    oC3InterfaceProfile-PathParams-Ds3Profile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboC3InterfaceProfile-PathParamsEntry 14 }

    oC3InterfaceProfile-PathParams-Ds3Profile-PhysicalAddress-ItemNumber	OBJECT-TYPE
	SYNTAX	INTEGER
	ACCESS	read-write
	STATUS	mandatory
	DESCRIPTION	"A number that specifies an addressable entity within the context of shelf and slot."
	::= { miboC3InterfaceProfile-PathParamsEntry 15 }

    oC3InterfaceProfile-PathParams-Ds3Profile-Enabled	OBJECT-TYPE
	SYNTAX	INTEGER {
		    no (1),
		    yes (2)
		}
	ACCESS	read-write
	STATUS	mandatory
	DESCRIPTION	"TRUE if the line is enabled, otherwise FALSE."
	::= { miboC3InterfaceProfile-PathParamsEntry 16 }

    oC3InterfaceProfile-PathParams-Ds3Profile-FrameType	OBJECT-TYPE
	SYNTAX	INTEGER {
		    m13 (1),
		    cBitParity (2)
		}
	ACCESS	read-write
	STATUS	mandatory
	DESCRIPTION	"Determines the DS3 frame format, also known as the DS3 application."
	::= { miboC3InterfaceProfile-PathParamsEntry 17 }

    oC3InterfaceProfile-PathParams-Ds3Profile-LineLength	OBJECT-TYPE
	SYNTAX	INTEGER {
		    n-0225 (1),
		    n-226450 (2)
		}
	ACCESS	read-write
	STATUS	mandatory
	DESCRIPTION	"The length in feet of the Rx and Tx lines to a DSX-3 cross connect. Double these values for direct connection."
	::= { miboC3InterfaceProfile-PathParamsEntry 18 }

    oC3InterfaceProfile-PathParams-Ds3Profile-Loopback	OBJECT-TYPE
	SYNTAX	INTEGER {
		    noLoopback (1),
		    lineLoopback (2),
		    localLoopback (3)
		}
	ACCESS	read-write
	STATUS	mandatory
	DESCRIPTION	"Loopback mode."
	::= { miboC3InterfaceProfile-PathParamsEntry 19 }

    oC3InterfaceProfile-PathParams-Ds3Profile-StatusChangeTrapEnable	OBJECT-TYPE
	SYNTAX	INTEGER {
		    no (1),
		    yes (2)
		}
	ACCESS	read-write
	STATUS	mandatory
	DESCRIPTION	"When set to No, do not send dsx3LineStatusChangeTrapEnable trap. If Yes, send traps. The default is No."
	::= { miboC3InterfaceProfile-PathParamsEntry 21 }


	-- The miboC3InterfaceProfile__path_params__master_ds1_index table
	--
	-- This table contains parameters for the miboC3InterfaceProfile__path_params__master_ds1_index profile
	--

    miboC3InterfaceProfile-PathParams-MasterDs1IndexTable	OBJECT-TYPE
	SYNTAX		SEQUENCE OF MiboC3InterfaceProfile-PathParams-MasterDs1IndexEntry
	ACCESS		not-accessible
	STATUS		mandatory
	DESCRIPTION	"A list of miboC3InterfaceProfile__path_params__master_ds1_index profile entries."
	::= { miboC3InterfaceProfile 20 }

    miboC3InterfaceProfile-PathParams-MasterDs1IndexEntry	OBJECT-TYPE
	SYNTAX		MiboC3InterfaceProfile-PathParams-MasterDs1IndexEntry
	ACCESS		not-accessible
	STATUS		mandatory
	DESCRIPTION	"A miboC3InterfaceProfile__path_params__master_ds1_index entry containing objects that
			 maps to the parameters of miboC3InterfaceProfile__path_params__master_ds1_index profile."
	INDEX		{ oC3InterfaceProfile-PathParams-MasterDs1Index-Shelf-o, oC3InterfaceProfile-PathParams-MasterDs1Index-Slot-o, oC3InterfaceProfile-PathParams-MasterDs1Index-Item-o, oC3InterfaceProfile-PathParams-MasterDs1Index-Index-o, oC3InterfaceProfile-PathParams-MasterDs1Index-Index1-o }
	::= { miboC3InterfaceProfile-PathParams-MasterDs1IndexTable 1 }

    MiboC3InterfaceProfile-PathParams-MasterDs1IndexEntry ::=
	SEQUENCE {
	    oC3InterfaceProfile-PathParams-MasterDs1Index-Shelf-o
		INTEGER,
	    oC3InterfaceProfile-PathParams-MasterDs1Index-Slot-o
		INTEGER,
	    oC3InterfaceProfile-PathParams-MasterDs1Index-Item-o
		INTEGER,
	    oC3InterfaceProfile-PathParams-MasterDs1Index-Index-o
		INTEGER,
	    oC3InterfaceProfile-PathParams-MasterDs1Index-Index1-o
		INTEGER,
	    oC3InterfaceProfile-PathParams-MasterDs1Index
		INTEGER
	}

    oC3InterfaceProfile-PathParams-MasterDs1Index-Shelf-o	OBJECT-TYPE
	SYNTAX	INTEGER
	ACCESS	read-only
	STATUS	mandatory
	DESCRIPTION	""
	::= { miboC3InterfaceProfile-PathParams-MasterDs1IndexEntry 1 }

    oC3InterfaceProfile-PathParams-MasterDs1Index-Slot-o	OBJECT-TYPE
	SYNTAX	INTEGER
	ACCESS	read-only
	STATUS	mandatory
	DESCRIPTION	""
	::= { miboC3InterfaceProfile-PathParams-MasterDs1IndexEntry 2 }

    oC3InterfaceProfile-PathParams-MasterDs1Index-Item-o	OBJECT-TYPE
	SYNTAX	INTEGER
	ACCESS	read-only
	STATUS	mandatory
	DESCRIPTION	""
	::= { miboC3InterfaceProfile-PathParams-MasterDs1IndexEntry 3 }

    oC3InterfaceProfile-PathParams-MasterDs1Index-Index-o	OBJECT-TYPE
	SYNTAX	INTEGER
	ACCESS	read-only
	STATUS	mandatory
	DESCRIPTION	""
	::= { miboC3InterfaceProfile-PathParams-MasterDs1IndexEntry 4 }

    oC3InterfaceProfile-PathParams-MasterDs1Index-Index1-o	OBJECT-TYPE
	SYNTAX	INTEGER
	ACCESS	read-only
	STATUS	mandatory
	DESCRIPTION	""
	::= { miboC3InterfaceProfile-PathParams-MasterDs1IndexEntry 5 }

    oC3InterfaceProfile-PathParams-MasterDs1Index	OBJECT-TYPE
	SYNTAX	INTEGER
	ACCESS	read-write
	STATUS	mandatory
	DESCRIPTION	"The item index of the Master T1/E1 profile to use on the DS1 link."
	::= { miboC3InterfaceProfile-PathParams-MasterDs1IndexEntry 6 }

END
