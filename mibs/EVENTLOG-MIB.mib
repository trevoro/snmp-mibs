-- This MIB has all the information the user needs about a generated event.   
   
          EVENTLOG-MIB  
   
          DEFINITIONS ::= BEGIN  
   
          IMPORTS 
		      MODULE-IDENTITY, OBJECT-TYPE 
			   FROM SNMPv2-SMI   
		      eventlog   
			   FROM CORIOLIS-MIB    
		      IpAddress  
            FROM RFC1155-SMI;      
   
          eventlogMIB MODULE-IDENTITY  
          LAST-UPDATED "0010300000Z"   
          ORGANIZATION "Coriolis Networks"   
          CONTACT-INFO  
          " Srivathsan Srinivasagopalan   
   
          Postal: 330 Codman Hill Road,   
          Boxboro MA, 01719.  
   
          Tel: +1 978 264 1904   
          Fax: +1 978 264 1929   
   
          E-mail: sri@coriolisnet.com" 
          DESCRIPTION   
          " The MIB module for event log "   
          ::= { eventlog 1 }  
                        
          -- The event log table 
   
          eventlogTable OBJECT-TYPE 
	         SYNTAX 	   SEQUENCE OF EventlogEntry 
	         MAX-ACCESS  not-accessible  
	         STATUS	   current 
	         DESCRIPTION 
		         "A table containing information about a generated event." 
	         ::= { eventlog 2 }   
   
	       eventlogEntry    OBJECT-TYPE  
		      SYNTAX	      EventlogEntry    
		      MAX-ACCESS     not-accessible
		      STATUS	      current
		      DESCRIPTION
		         "Entry in the table for a single transport channel"
		      INDEX	{ eventlogEventID }
		      ::= {eventlogTable 1 }

	       EventlogEntry ::= SEQUENCE {
		      eventlogName 		         OCTET STRING,
            eventlogDesc               OCTET STRING,
            eventlogSeverity    	      OCTET STRING,  
		      eventlogTime    		      OCTET STRING,
		      eventlogSrcIpAddr  		   IpAddress,
            eventlogCorEventIpAddr 	   IpAddress,
            eventlogEventID            INTEGER,
            eventlogCorEventID         INTEGER
		      }

	       eventlogName	OBJECT-TYPE
		      SYNTAX	   OCTET STRING   
		      MAX-ACCESS	read-only
		      STATUS	   current
		      DESCRIPTION
		         "Name of the event being generated."
		      ::= { eventlogEntry 1 }

	       eventlogDesc	OBJECT-TYPE
		      SYNTAX	   OCTET STRING   
		      MAX-ACCESS	read-only
		      STATUS	   current
		      DESCRIPTION
		         "Description of the event being generated."
		      ::= { eventlogEntry 2 }

	       eventlogSeverity	OBJECT-TYPE
		      SYNTAX	      OCTET STRING
		      MAX-ACCESS	   read-only
		      STATUS	      current
		      DESCRIPTION
		         "Categoryof the event being generated. The various severities are:
                  null severity                 = 0
                  clear event (lowest severity) = 1
                  informational event           = 2
                  warning event                 = 3
                  minor error                   = 4
                  major error                   = 5
                  critical error                = 6"
		      ::= { eventlogEntry 3 }

	       eventlogTime	OBJECT-TYPE
		      SYNTAX	   OCTET STRING
		      MAX-ACCESS	read-only
		      STATUS	   current
		      DESCRIPTION
		         "Absolute time when the event occured."
		      ::= { eventlogEntry 4 }

	       eventlogSrcIpAddr	OBJECT-TYPE
		      SYNTAX	         IpAddress
		      MAX-ACCESS	      read-only
		      STATUS	         current
		      DESCRIPTION
		         "IP address of the source generating the event."
		      ::= { eventlogEntry 5 }

	       eventlogCorEventIpAddr	OBJECT-TYPE
		      SYNTAX		         IpAddress
		      MAX-ACCESS		      read-only
		      STATUS		         current
		      DESCRIPTION
		         "IpAddress of the correlated event."
		      ::= { eventlogEntry 6 }

	       eventlogEventID	   OBJECT-TYPE
		      SYNTAX		      INTEGER	
		      MAX-ACCESS		   read-only
		      STATUS		      current
		      DESCRIPTION
		         "Event ID of the event being generated."
		      ::= { eventlogEntry 7 }

	       eventlogCorEventID	OBJECT-TYPE
		      SYNTAX		      INTEGER	
		      MAX-ACCESS		   read-only
		      STATUS		      current
		      DESCRIPTION
		         "Correlated event ID of the event being generated."
		      ::= { eventlogEntry 8 }

		  END
