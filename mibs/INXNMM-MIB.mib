INXNMM-MIB

DEFINITIONS ::= BEGIN
--
-- MIB Definition File for the Racal Datacom INXNMM Network Management Module.  
--                                  Release 1.1
--
IMPORTS
		DisplayString FROM SNMPv2-TC
        OBJECT-TYPE, NetworkAddress, IpAddress,
        Counter, Gauge, TimeTicks
                  FROM RFC1155-SMI;


internet        OBJECT IDENTIFIER ::= { iso org(3) dod(6) 1 }
experimental    OBJECT IDENTIFIER ::= { internet 3 }
private         OBJECT IDENTIFIER ::= { internet 4 }
enterprises     OBJECT IDENTIFIER ::= { private 1 }
interlan        OBJECT IDENTIFIER ::= { enterprises 28 }


dot3            OBJECT IDENTIFIER ::= { experimental 3 }

riTelnet        OBJECT IDENTIFIER ::= { interlan 3 }
riBoot          OBJECT IDENTIFIER ::= { interlan 16 }
riThresh        OBJECT IDENTIFIER ::= { interlan 17 }
riSystem        OBJECT IDENTIFIER ::= { interlan 18 }
riTsRates       OBJECT IDENTIFIER ::= { interlan 22 }
riLdcNmm        OBJECT IDENTIFIER ::= { interlan 10 }
riPort          OBJECT IDENTIFIER ::= { interlan 13 }

riHotFail       OBJECT IDENTIFIER ::= { riLdcNmm 14 }

riProducts      OBJECT IDENTIFIER ::= { interlan 1 }
riProdLdc       OBJECT IDENTIFIER ::= { riProducts 3 }
riPLdcNMM        OBJECT IDENTIFIER ::= { riProdLdc 1 }

--      nullSpecific OBJECT IDENTIFIER ::= { 0 0 }

               -- object types

-- ******************************************************************
-- Ethernet interface MIB Group. This is based on an early version of
-- the Internet Draft for this MIB. 
-- ******************************************************************

dot3Table OBJECT-TYPE
	SYNTAX SEQUENCE OF Dot3Entry
	ACCESS not-accessible
	STATUS mandatory
		--% ALIAS "INX-NMM Interface Table"
	DESCRIPTION
		"A list of the INX-NMM Ethernet interface's operational
attributes, such as whether it is configured for multicast receive
and the status of the MAC sublayer .
You cannot access this variable; it is only a table marker in the
MIB."
	::= { dot3 1 }

dot3Entry OBJECT-TYPE
	SYNTAX Dot3Entry
	ACCESS not-accessible
	STATUS mandatory
		--% ALIAS "Interface Table Entry"
	DESCRIPTION
		"An entry in the INX-NMM Interface table.  (See the
previous variable, INX-NMM Interface Table, for an explanation of
this table.)
You cannot access this variable; it is only a table marker in the
MIB.  The following variables are entries in the table:

Interface Table Index
MAC Initialization Status
MAC Operational Status
Multicast Receive Status
Nonaligned Frames Recd
FCS Errored Frames Received"
	INDEX	{ dot3Index }
	::= { dot3Table 1 }

Dot3Entry ::= SEQUENCE {




    dot3Index
        INTEGER,
    dot3InitializeMAC
        INTEGER,
    dot3MACSubLayerStatus
        INTEGER,
    dot3MulticastReceiveEnabled
        INTEGER,
    dot3AlignmentErrors
        Counter,
    dot3FCSErrors
        Counter }

dot3Index OBJECT-TYPE
	SYNTAX INTEGER 
	ACCESS read-only
	STATUS mandatory
		--% ALIAS "Interface Table Index"
		--% GROUP INX-NMM-Interface-Table
	DESCRIPTION
		"The value assigned to the INX-NMM Ethernet interface. 
Because the INX-NMM has only one interface, this variable always returns 1."
	::= { dot3Entry 1 }

dot3InitializeMAC OBJECT-TYPE
	SYNTAX INTEGER {
				initialize(1)
			}
		ACCESS read-write
	STATUS mandatory
		--% ALIAS "MAC Initialization Status"
		--% GROUP INX-NMM-Interface-Table
	DESCRIPTION
		"The initialization status of the MAC and PLS subsystems
of the interface.  Because the MAC and PLS subsystems on the INX-NMM are 
initialized at power-up and remain so, this variable always returns 
initialized(1)."
	::= { dot3Entry 2 }

dot3MACSubLayerStatus OBJECT-TYPE
	SYNTAX INTEGER {
				enabled(1)
			}
	ACCESS read-write
	STATUS mandatory
		--% ALIAS "MAC Operational Status"
		--% GROUP INX-NMM-Interface-Table
	DESCRIPTION
		"The operational status of the MAC sublayer, i.e.,
whether it is ready to transmit and receive frames.  Because this
sublayer is always active in the INX-NMM, this variable always
returns enabled(1)."
	::= { dot3Entry 3 }

dot3MulticastReceiveEnabled OBJECT-TYPE
	SYNTAX INTEGER {
				true(1)
			}
		ACCESS read-write
	STATUS mandatory
		--% ALIAS "Multicast Receive Status"
		--% GROUP INX-NMM-Interface-Table
	DESCRIPTION
		"The Multicast Receive status, i.e., whether the INX-NMM
is configured to receive frames with a multicast address.  Because
Multicast Receive is always enabled on the INX-NMM, this variable
always returns true(1)."
	::= { dot3Entry 4 }

dot3AlignmentErrors OBJECT-TYPE
	SYNTAX Counter
	ACCESS read-only
	STATUS mandatory
		--% ALIAS "Nonaligned Frames Recd"
		--% GROUP Interface-Receive-Table
	DESCRIPTION
		"The number of frames received on the interface that are
not an integral number of octets in length (i.e.,  the number of
bits they contain is not a multiple of eight) and do not pass the
FCS check.  This condition indicates that the frames were corrupted
during transmission."
	::= { dot3Entry 5 }

dot3FCSErrors OBJECT-TYPE
	SYNTAX Counter
	ACCESS read-only
	STATUS mandatory
		--% ALIAS "FCS Errored Frames Received"
		--% GROUP Interface-Receive-Table
	DESCRIPTION
		"The number of frames received on the interface that are
an integral number of octets in length (i.e., the number of bits
they contain is a multiple of eight) that do not pass the FCS
check, indicating that the frames were corrupted during
transmission."
	::= { dot3Entry 6 }

dot3TxTable OBJECT-TYPE
	SYNTAX SEQUENCE OF Dot3TxEntry
	ACCESS not-accessible
	STATUS mandatory
		--% ALIAS "Interface Transmit Table"
	DESCRIPTION
		"A list of transmit errors and statistics for the INX-NMM
Ethernet interface.  You cannot access this variable; it is only a table
marker in the MIB."
	::= { dot3 2 }

dot3TxEntry OBJECT-TYPE
	SYNTAX Dot3TxEntry
	ACCESS not-accessible
	STATUS mandatory
		--% ALIAS "Interface Transmit Entry"
	DESCRIPTION
		"An entry in the Interface Transmit table.  (See the
previous variable, Interface Transmit Table, for an explanation of
this table.)  You cannot access this variable; it is only a table marker 
in the MIB.  The following variables are entries in the table:

Interface Transmit Index
Single Collisions Transmitted
Multiple Collisions Xmitted
Total SQE Test Errors"
	INDEX	{ dot3TxIndex }
	::= { dot3TxTable 1 }

Dot3TxEntry ::= SEQUENCE {
    dot3TxIndex
        INTEGER,
    dot3TxSingleCollisionFrames
        Counter,
    dot3TxMultipleCollisionFrames
        Counter,
    dot3TxSQETestErrors
        Counter }

dot3TxIndex OBJECT-TYPE
	SYNTAX INTEGER 
	ACCESS read-only
	STATUS mandatory
		--% ALIAS "Interface Transmit Index"
		--% GROUP Interface-Transmit-Table
	DESCRIPTION
		"The value assigned to the INX-NMM Ethernet interface. 
Because the INX-NMM has only one interface, this variable always
returns 1."
	::= { dot3TxEntry 1 }

dot3TxSingleCollisionFrames OBJECT-TYPE
	SYNTAX Counter
	ACCESS read-only
	STATUS mandatory
		--% ALIAS "Single Collisions Transmitted"
		--% GROUP Interface-Transmit-Table
	DESCRIPTION
		"The number of frames that were successfully transmitted
after experiencing one and only one collision."
	::= { dot3TxEntry 2 }

dot3TxMultipleCollisionFrames OBJECT-TYPE
	SYNTAX Counter
	ACCESS read-only
	STATUS mandatory
		--% ALIAS "Multiple Collisions Xmitted"
		--% GROUP Interface-Transmit-Table
	DESCRIPTION
		"The number of frames that were successfully transmitted
after experiencing more than one collision."
	::= { dot3TxEntry 3 }


dot3TxSQETestErrors OBJECT-TYPE
	SYNTAX Counter 
	ACCESS read-only
	STATUS mandatory
		--% ALIAS "Total SQE Test Errors"
		--% GROUP Interface-Transmit-Table
	DESCRIPTION
		"The number of times that the SQE TEST ERROR message has
been generated by this interface's PLS sublayer.  The PLS sublayer
generates an SQE test error message when the Signal-Quality-Error
test fails.  The Signal-Quality-Error test verifies good data
transmission.
The INX-NMM does not generate SQE test error messages, so this
variable always returns 0."
	::= { dot3TxEntry 4 }

dot3XRxTable OBJECT-TYPE
	SYNTAX SEQUENCE OF Dot3XRxEntry
	ACCESS not-accessible
	STATUS mandatory
		--% ALIAS "Interface Receive Table"
	DESCRIPTION
		"A list of receive errors and statistics for the INX-NMM
Ethernet interface.  You cannot access this variable; it is only a table 
marker in the MIB."
	::= { dot3 3 }

dot3XRxEntry OBJECT-TYPE
	SYNTAX Dot3XRxEntry
	ACCESS not-accessible
	STATUS mandatory
		--% ALIAS "Interface Receive Entry"
	DESCRIPTION
		"An entry in the Interface Receive table.  (See the
previous variable, Interface Receive Table, for an explanation of
this table.)
You cannot access this variable; it is only a table marker in the
MIB.  The following variables are entries in the table:

Interface Receive Index
Too Long Frames Recd
In-Range Length Errors Recd
Out-Range Length Errors Recd
MAC Errors Received
Autopartition Status
Autopartition Disconnects 
Last Good Source Address Recd
Source Address Changes Count"
	INDEX	{ dot3XRxIndex }
	::= { dot3XRxTable 1 }

Dot3XRxEntry ::= SEQUENCE {
    dot3XRxIndex
        INTEGER,
    dot3XRxFrameTooLongs
        Counter,
    dot3XRxInRangeLengthErrors
        Counter,
    dot3XRxOutOfRangeLengthFields
        Counter,
    dot3XRxInternalMACReceiveErrors
        Counter,
    dot3XRxAutoPartitionStatus
        INTEGER,
    dot3XRxAutoPartitionLog
        Counter,
    dot3XRxLastSourceAddress
        OCTET STRING,
    dot3XRxSourceAddressLog
        Counter
    }

dot3XRxIndex OBJECT-TYPE
	SYNTAX INTEGER 
	ACCESS read-only
	STATUS mandatory
		--% ALIAS "Interface Receive Index"
		--% GROUP Interface-Receive-Table
	DESCRIPTION
		"The value assigned to the INX-NMM Ethernet interface. 
Because the INX-NMM has only one interface, this variable always
returns 1."
	::= { dot3XRxEntry 1 }

dot3XRxFrameTooLongs OBJECT-TYPE
	SYNTAX Counter
	ACCESS read-only
	STATUS mandatory
		--% ALIAS "Too Long Frames Recd"
		--% GROUP Interface-Receive-Table
	DESCRIPTION
		"The number of frames received on the interface that
exceed the maximum permitted frame size, i.e., 1012 octets."
	::= { dot3XRxEntry 2 }

dot3XRxInRangeLengthErrors OBJECT-TYPE
	SYNTAX Counter 
	ACCESS read-only
	STATUS mandatory
		--% ALIAS "In-Range Length Errors Recd"
		--% GROUP Interface-Receive-Table
	DESCRIPTION
		"The number of in-range length errors received.  IEEE
802.3 frames contain a length field, indicating the length of the
frame.  If the value in the length field and the actual length of
the frame do not match, even if the length of the frame is within
802.3 parameters, the receiving device returns an in-range error. 
The INX-NMM receives Ethernet frames that do not have a length in
the length field.  It therefore cannot detect this error, and this
variable always returns 0."
	::= { dot3XRxEntry 3 }

dot3XRxOutOfRangeLengthFields OBJECT-TYPE
	SYNTAX Counter 
	ACCESS read-only
	STATUS mandatory
		--% ALIAS "Out-Range Length Errors Recd"
		--% GROUP Interface-Receive-Table
	DESCRIPTION
		"The number of out-of-range length errors received.  IEEE
802.3 frames contain a length field, indicating the length of the
frame.  If the length of the frame is outside 802.3 parameters, the
receiving device returns an out-of-range error.  The INX-NMM
receives Ethernet frames that do not have a length in the length
field.  It therefore cannot detect this error, and this variable
always returns 0."
	::= { dot3XRxEntry 4 }

dot3XRxInternalMACReceiveErrors OBJECT-TYPE
	SYNTAX Counter
	ACCESS read-only
	STATUS mandatory
		--% ALIAS "MAC Errors Received"
		--% GROUP Interface-Receive-Table
	DESCRIPTION
		"The number of frames the interface could not receive
because of an internal MAC sublayer receive error.  This variable
returns frames not counted by the Too Long Frames Received,
Nonaligned Frames Received, FCS Errored Frames Received, In-Range
Length Errors Recd, and Out-Range Length Errors Recd variables."
	::= { dot3XRxEntry 5 }

dot3XRxAutoPartitionStatus OBJECT-TYPE
	SYNTAX INTEGER
	ACCESS read-write
	STATUS mandatory
		--% ALIAS "Autopartition Status"
		--% GROUP Interface-Receive-Table
	DESCRIPTION
		"The autopartition status of the INX-NMM.  Devices that
support autopartitioning have the ability to autonomously
disconnect from the network when they sense trouble, e.g., a device
with a jabber condition.  Because the INX-NMM interface does not
support autopartitioning, this variable always returns 2, and may
only be set to 2."
	::= { dot3XRxEntry 6 }

dot3XRxAutoPartitionLog OBJECT-TYPE
	SYNTAX Counter 
	ACCESS read-only
	STATUS mandatory
		--% ALIAS "Autopartition Disconnects"
		--% GROUP Interface-Receive-Table
	DESCRIPTION
		"The number of autopartitions the INX-NMM has performed. 
Devices that support autopartitioning maintain a log of the number
of times they disconnected from the network.  Because the INX-NMM
interface does not support auto-partitioning, this variable always
returns 0."
	::= { dot3XRxEntry 7 }

dot3XRxLastSourceAddress OBJECT-TYPE
	SYNTAX OCTET STRING
	ACCESS read-only
	STATUS mandatory
		--% ALIAS "Last Good Source Address Recd"
		--% GROUP Interface-Receive-Table
	DESCRIPTION
		"The source address of the last frame successfully
received.  Because this value changes too often to be useful, the
INX-NMM interface does not record the last source address of
received frames; therefore, this variable always returns a string
of 0s."
	::= { dot3XRxEntry 8 }

dot3XRxSourceAddressLog OBJECT-TYPE
	SYNTAX Counter 
	ACCESS read-only
	STATUS mandatory
		--% ALIAS "Source Address Changes Count"
		--% GROUP Interface-Receive-Table
	DESCRIPTION
		"The number of times that the value of Last Good Source
Address has changed.  The INX-NMM interface does not log source
address changes; therefore, this variable always returns 0."
	::= { dot3XRxEntry 9 }

dot3XTxTable OBJECT-TYPE
	SYNTAX SEQUENCE OF Dot3XTxEntry
	ACCESS not-accessible
	STATUS mandatory
		--% ALIAS "Interface Xmit Error/Stat Table"
	DESCRIPTION
		"A list of transmit errors and statistics for the INX-NMM
Ethernet interface.
You cannot access this variable; it is only a table marker in the
MIB."
	::= { dot3 4 }

dot3XTxEntry OBJECT-TYPE
	SYNTAX Dot3XTxEntry
	ACCESS not-accessible
	STATUS mandatory
		--% ALIAS "Interface Xmit Error/Stat Entry"
	DESCRIPTION
		"An entry in the Interface Xmit Error/Stat table.  (See
the previous variable, Interface Xmit Error/Stat Table, for an
explanation of this table.)
You cannot access this variable; it is only a table marker in the
MIB.  The following variables are entries in the table:

Interface Xmit Error/Stat Index
Interface Transmit Status
Transmissions Deferred
Late Collisions Detected
Excessive Collisions Detected
MAC Transmit Errors
Carrier Sense Errors
Deferred Frames
TDR Status"
	INDEX	{ dot3XTxIndex }
	::= { dot3XTxTable 1 }

Dot3XTxEntry ::= SEQUENCE {
    dot3XTxIndex
        INTEGER,
    dot3XTxEnabled
        INTEGER,
    dot3XTxDeferredTransmissions
        Counter,
    dot3XTxLateCollisions
        Counter,
    dot3XTxExcessiveCollisions
        Counter,
    dot3XTxInternalMACTransmitErrors
        Counter,
    dot3XTxCarrierSenseErrors
        Counter,
    dot3XTxExcessiveDeferrals
        Counter,
    dot3XTxTDR
        Gauge }

dot3XTxIndex OBJECT-TYPE
	SYNTAX INTEGER 
	ACCESS read-only
	STATUS mandatory
		--% ALIAS "Interface Xmit Error/Stat Index"
		--% GROUP Interface-Xmit-Error/Stat-Table
	DESCRIPTION
		"The value assigned to the INX-NMM Ethernet interface. 
Because the INX-NMM has only one interface, this variable always
returns 1."
	::= { dot3XTxEntry 1 }

dot3XTxEnabled OBJECT-TYPE
	SYNTAX INTEGER {
					true(1)
				}
	ACCESS read-write
	STATUS mandatory
		--% ALIAS "Interface Transmit Status"
		--% GROUP Interface-Xmit-Error/Stat-Table
	DESCRIPTION
		"The transmit status of the interface, i.e., whether it
is able to transmit frames.  Because transmit is always enabled on
the INX-NMM, this variable always returns true(1)."
	::= { dot3XTxEntry 2 }

dot3XTxDeferredTransmissions OBJECT-TYPE
	SYNTAX Counter 
	ACCESS read-only
	STATUS mandatory
		--% ALIAS "Transmissions Deferred"
		--% GROUP Interface-Xmit-Error/Stat-Table
	DESCRIPTION
		"The number of times the INX-NMM deferred transmission
of data because it sensed traffic on the network.  Because the
INX-NMM does not record deferrals, this variable always returns 0."
	::= { dot3XTxEntry 3 }

dot3XTxLateCollisions OBJECT-TYPE
	SYNTAX Counter 
	ACCESS read-only
	STATUS mandatory
		--% ALIAS "Late Collisions Detected"
		--% GROUP Interface-Xmit-Error/Stat-Table
	DESCRIPTION
		"The number of times that a collision has been detected
on this bus later than 512 bit times from frame start.  This count
is not maintained by the INX-NMM, so this variable always returns
0."
	::= { dot3XTxEntry 4 }

dot3XTxExcessiveCollisions OBJECT-TYPE
	SYNTAX Counter 
	ACCESS read-only
	STATUS mandatory
		--% ALIAS "Excessive Collisions Detected"
		--% GROUP Interface-Xmit-Error/Stat-Table
	DESCRIPTION
		"The number of frames the interface could not transmit
because of excessive collisions."
	::= { dot3XTxEntry 5 }

dot3XTxInternalMACTransmitErrors OBJECT-TYPE
	SYNTAX Counter
	ACCESS read-only
	STATUS mandatory
		--% ALIAS "MAC Transmit Errors"
		--% GROUP Interface-Xmit-Error/Stat-Table
	DESCRIPTION
		"The number of frames the interface could not transmit
because of an internal MAC sublayer transmit error.  This variable
counts frames not counted by the Late Collisions Detected,
Excessive Collisions Detected, Carrier Sense Errors, and Deferred
Frames variables."
	::= { dot3XTxEntry 6 }

dot3XTxCarrierSenseErrors OBJECT-TYPE
	SYNTAX Counter
	ACCESS read-only
	STATUS mandatory
		--% ALIAS "Carrier Sense Errors"
		--% GROUP Interface-Xmit-Error/Stat-Table
	DESCRIPTION
		"The number of times that the carrier-sense condition was
lost or never asserted when the INX-NMM attempted to transmit a
frame on the interface.
This count is incrememted at most once per transmission attempt,
even if the carrier-sense condition fluctuates during the transmit
attempt."
	::= { dot3XTxEntry 7 }

dot3XTxExcessiveDeferrals OBJECT-TYPE
	SYNTAX Counter 
	ACCESS read-only
	STATUS mandatory
		--% ALIAS "Deferred Frames"
		--% GROUP Interface-Xmit-Error/Stat-Table
	DESCRIPTION
		"The number of frames the INX-NMM deferred transmitting
for an excessive period of time.  Because the INX-NMM interface
does not record deferrals, this variable always returns 0."
	::= { dot3XTxEntry 8 }

dot3XTxTDR OBJECT-TYPE
	SYNTAX Gauge 
	ACCESS read-only
	STATUS mandatory
		--% ALIAS "TDR Status"
		--% GROUP Interface-Xmit-Error/Stat-Table
	DESCRIPTION
		"The status of Time Domain Reflectometry (TDR) on the
INX-NMM.  TDR is the ability of a device to check the viability of
a cable by sending a signal to the end of the cable.  The INX-NMM
interface does not support Time Domain Reflectometry, so this
variable always returns 0."
	::= { dot3XTxEntry 9 }

dot3CollTable OBJECT-TYPE
        SYNTAX SEQUENCE OF Dot3CollEntry
        ACCESS not-accessible
        STATUS mandatory
		--% ALIAS "Collision Frequency Table"
	DESCRIPTION
		"A histogram representing the frequency of collisions on
the interface. In the Collision Frequency histogram, one dimension of each
cell represents Collisions per Frame, and the other dimension represents
Collision Frequency.
You cannot access this variable; it is only a table marker in the MIB."
        ::= { dot3 5 }

dot3CollEntry OBJECT-TYPE
        SYNTAX Dot3CollEntry
        ACCESS not-accessible
        STATUS mandatory
		--% ALIAS "Collision Frequency Entry"
	DESCRIPTION
		"An entry in the Collision Frequency table. (See the
previous variable, Collision Frequency Table, for an explanation
of this table.)
You cannot access this variable; it is only a table marker in the
MIB. The following variables are entries in the table:

Collision Frequency Index
Collisions per Frame
Collision Frequency"
	INDEX	{ dot3CollIndex, dot3CollCount }
        ::= { dot3CollTable 1 }

Dot3CollEntry ::= SEQUENCE {
    dot3CollIndex
        INTEGER,
    dot3CollCount
        INTEGER (1..15),
    dot3CollFrequency
        Counter }

dot3CollIndex OBJECT-TYPE
        SYNTAX INTEGER 
        ACCESS read-only
        STATUS mandatory
		--% ALIAS "Collision Frequency Index"
		--% GROUP Collision-Frequency-Table
	DESCRIPTION
		"The value assigned to the INX-NMM Ethernet interface. 
Because the INX-NMM has only one interface, this variable always
returns 1."
        ::= { dot3CollEntry 1 }

dot3CollCount OBJECT-TYPE
        SYNTAX INTEGER (1..15)
        ACCESS read-only
        STATUS mandatory
		--% ALIAS "Collisions per Frame"
		--% GROUP Collision-Frequency-Table
	DESCRIPTION
		"The number of media collisions per frame indicated by
one cell in the collision histogram.  The INX-NMM tracks the number
of collisions up to 15."
        ::= { dot3CollEntry 2 }

dot3CollFrequency OBJECT-TYPE
        SYNTAX Counter
        ACCESS read-only
        STATUS mandatory
		--% ALIAS "Collision Frequency"
		--% GROUP Collision-Frequency-Table
	DESCRIPTION
		"The number of frames that were transmitted after
experiencing exactly Collisions per Frame collisions on the INX-NMM
Ethernet interface (see the previous variable)."
        ::= { dot3CollEntry 3 }


-- ***********************************************************************
-- 
-- Following objects are from the Racal Datacom Boot Specification Group.  
-- 
-- ***********************************************************************

riNumBoots OBJECT-TYPE
	SYNTAX INTEGER 
	ACCESS read-write
	STATUS mandatory
		--% ALIAS "Number of Boot Table Entries"
		--% GROUP Racal-InterLan-Boot-Group
	DESCRIPTION
		"The number of entries in the Boot table.  There is one
entry for the INX-NMM's operating software image file, and one
entry for the Chassis Management Protocol (CMP) image file, so this
variable always returns 2, and can only be set to 2."
	::={ riBoot 1 }

riBootServiceOffered OBJECT-TYPE
	SYNTAX INTEGER {
				false(1),
                                true(2)
				}
	ACCESS read-write
	STATUS mandatory
		--% ALIAS "Boot Service Available"
		--% GROUP Racal-InterLan-Boot-Group
	DESCRIPTION " The setting of this variable determines whether
this INX-NMM can provide boot operating system images to other
INX-NMM, returning true(2) if it can and false(1) if it cannot."
	::={ riBoot 2 }

riBootTable OBJECT-TYPE
	SYNTAX SEQUENCE OF RiBootEntry
	ACCESS not-accessible
	STATUS mandatory
		--% ALIAS "Boot Table"
	DESCRIPTION
		"The Boot table contains boot information.
You cannot access this variable; it is only a table marker in the
MIB."
	::= { riBoot 3 }

riBootEntry OBJECT-TYPE
	SYNTAX RiBootEntry
	ACCESS not-accessible
	STATUS mandatory
		--% ALIAS "Boot Table Entry"
	DESCRIPTION
		"This variable returns a particular boot specification,
i.e., an entry in the Boot table.  (See the previous variable, Boot
Table, for an explanation of this table).
You cannot access this variable; it is only a table marker in the
MIB.  The following variables are entries in the table:

Boot Table Index
Boot File Name
Boot Server IP Address
Boot File Version
Gateway IP Address"
	INDEX	{ riBootIndex }
	::={ riBootTable 1 }

RiBootEntry ::= SEQUENCE {
     riBootIndex
          INTEGER,
     riBootFileName
          OCTET STRING,
     riBootIPAddress
          IpAddress,
     riBootVersion
          INTEGER,
     riBootGateway
          IpAddress }

riBootIndex OBJECT-TYPE
	SYNTAX INTEGER (1..2)
	ACCESS read-only
	STATUS mandatory
		--% ALIAS "Boot Table Index"
		--% GROUP Boot-Table
	DESCRIPTION
		"This variable returns a unique value for each entry in
the Boot table.  It returns 1 for  the Chassis Management Protocol
file and 2 for the operating software image file."
	::= { riBootEntry 1 }

riBootFileName OBJECT-TYPE
	SYNTAX OCTET STRING
	ACCESS read-write
	STATUS mandatory
		--% ALIAS "Boot File Name"
		--% GROUP Boot-Table
	DESCRIPTION
		"The name of the operating software image file on the
Featurecard or TFTP boot server from which you want to load the
image."
	::= { riBootEntry 3 }

riBootIPAddress OBJECT-TYPE
	SYNTAX IpAddress
	ACCESS read-write
	STATUS mandatory
		--% ALIAS "Boot Server IP Address"
		--% GROUP Boot-Table
	DESCRIPTION
		"The Internet address of the boot server from which you
want to load the software to the INX-NMM.
Note:  There is only one boot server IP address for all entries in
the Boot table.  If you change the address for one entry, all other
entries will reflect the change as well."
	::= { riBootEntry 6 }

riBootVersion OBJECT-TYPE
	SYNTAX INTEGER
	ACCESS read-write
	STATUS mandatory
		--% ALIAS "Boot File Version"
		--% GROUP Boot-Table
	DESCRIPTION
		"The revision level of the operating software image file
on the Featurecard or TFTP boot server from which you want to load
the image."
	::= { riBootEntry 7 }

riBootGateway OBJECT-TYPE
	SYNTAX IpAddress
	ACCESS read-write
	STATUS mandatory
		--% ALIAS "Gateway IP Address"
		--% GROUP Boot-Table
	DESCRIPTION
		"The Internet address of the gateway the INX-NMM must use
to get to the boot server, if applicable.

Note:  There is only one gateway address for all entries in the
Boot table.  If you change the address for one entry, all other
entries will reflect the change as well."
     ::= { riBootEntry 8 }

-- ***********************************************************************
-- 
-- Following objects are from the Racal Datacom Proprietary System
-- MIB group 
-- 
-- ***********************************************************************

riSystemHardwareRev OBJECT-TYPE
	SYNTAX DisplayString
	ACCESS read-only
	STATUS mandatory
		--% ALIAS "INX-NMM Hardware Rev"
		--% GROUP Racal-InterLan-System-Group
	DESCRIPTION
		"The hardware revision level of the INX-NMM."
	::={ riSystem 1 }

riSystemFirmwareRev OBJECT-TYPE
	SYNTAX DisplayString
	ACCESS read-only
	STATUS mandatory
		--% ALIAS "INX-NMM Firmware Rev"
		--% GROUP Racal-InterLan-System-Group
	DESCRIPTION
		"The firmware revision level of the INX-NMM."
	::={ riSystem 2 }

riSystemSoftwareRev OBJECT-TYPE
	SYNTAX DisplayString
	ACCESS read-only
	STATUS mandatory
		--% ALIAS "INX-NMM Software Rev"
		--% GROUP Racal-InterLan-System-Group
	DESCRIPTION
		"The software revision level of the INX-NMM."
	::={ riSystem 3 }

riSystemSerialNumber OBJECT-TYPE
	SYNTAX DisplayString
	ACCESS read-only
	STATUS mandatory
		--% ALIAS "INX-NMM Serial Number"
		--% GROUP Racal-InterLan-System-Group
	DESCRIPTION
		"The serial number of the INX-NMM."
	::={ riSystem 4 }

riSystemReset OBJECT-TYPE
	SYNTAX INTEGER {
					notreset(1),
					resetupdate(3)
				}
	ACCESS read-write
	STATUS mandatory
		--% ALIAS "INX-NMM Reset Status"
		--% GROUP Racal-InterLan-System-Group
	DESCRIPTION
		"The reset status of the INX-NMM.  The reset types are
o resetupdate(3) saves the current configuration in NVRAM and then
  resets the INX-NMM.  This value is returned while a reset is in
  progress.
o notreset(1) is returned when the INX-NMM is not being reset. 

Setting this variable to notreset(1) will not abort an outstanding
resetupdate(3)."
	::={ riSystem 5 }

riSystemTicksPerSecond OBJECT-TYPE
	SYNTAX INTEGER 
	ACCESS read-only
	STATUS mandatory
		--% ALIAS "Internal Clock Ticks/Second"
		--% GROUP Racal-InterLan-System-Group
	DESCRIPTION
		"The number of internal clock ticks that occur each
second on the INX-NMM, which is 100."
	::= { riSystem 12 }

riSystemRateInterval OBJECT-TYPE
	SYNTAX INTEGER 
	ACCESS read-write
	STATUS mandatory
		--% ALIAS "Rate Interval"
		--% GROUP Racal-InterLan-System-Group
	DESCRIPTION
		"How often, in seconds, any rate statistic maintained by
the INX-NMM is checked.  The default is 20 seconds."
	::= { riSystem 13 }

riSystemNVRamWriteCount OBJECT-TYPE
	SYNTAX Counter
	ACCESS read-only
	STATUS mandatory
		--% ALIAS "NVRAM Change Count"
		--% GROUP Racal-InterLan-System-Group
	DESCRIPTION
		"The number of times that the NVRAM has been changed."
	::= { riSystem 15 }

-- ************************************************************
--
-- Racal Datacom proprietary telnet group.
--
-- ************************************************************

tnCount OBJECT-TYPE
     SYNTAX    Counter 
     ACCESS    read-only
     STATUS    mandatory
		--% ALIAS "Telnet Sessions Initiated"
		--% GROUP Racal-InterLan-Telnet-Group
	DESCRIPTION
		"The number of telnet sessions that have been initiated
from the INX-NMM.  Because the INX-NMM doesn't initiate sessions,
this variable always returns 0."
     ::={ riTelnet 1 }

tnTable OBJECT-TYPE
     SYNTAX    SEQUENCE OF TnEntry
     ACCESS    not-accessible
     STATUS    mandatory
		--% ALIAS "Telnet Session Table"
	DESCRIPTION
		"Contains telnet session-specific information that is
appropriate to either the server or client side of a session.  
You cannot access this variable; it is only a table marker in the
MIB."
     ::={ riTelnet 2 }

tnEntry OBJECT-TYPE
     SYNTAX    TnEntry
     ACCESS    not-accessible
     STATUS    mandatory
		--% ALIAS "Telnet Session Table Entry"
	DESCRIPTION
		"An entry in the Telnet Session table. (See the previous
variable, Telnet Session Table, for an explanation of this table.) 
There is one entry in the table for each active telnet session.
You cannot access this variable; it is only a table marker in the
MIB.  The following variables are entries in the table:

Telnet Port Identifier
Local IP Addr of TCP Cxn
Remote IP Addr of TCP Cxn
Local Port of TCP Connection
Remote Port of TCP Connection
Up Time at Session Start
Session Options On
Telnet Session State
Telnet User ID"
	INDEX	{ tnLocalIpAddress, tnLocalPort, 
		  tnRemoteIpAddress, tnRemotePort}
     ::= { tnTable 1 }

TnEntry ::= SEQUENCE {
          tnPort
               INTEGER,
          tnLocalIpAddress
               IpAddress,
          tnRemoteIpAddress
               IpAddress,
          tnLocalPort
               INTEGER (0..65535),
          tnRemotePort
               INTEGER (0..65535),
          tnUpTime
               TimeTicks,
          tnOptionsOn
               OCTET STRING,
          tnState
               INTEGER,
          tnUserId
               OCTET STRING
--          tnNextType
--             INTEGER,
--          tnNextName
--               OBJECT IDENTIFIER
          }                        

tnPort OBJECT-TYPE
     SYNTAX    INTEGER 
     ACCESS    read-only
     STATUS    mandatory
		--% ALIAS "Telnet Port Identifier"
		--% GROUP Telnet-Session-Table
	DESCRIPTION
		"An internal index in the INX-NMM."
     ::= { tnEntry 1 }

tnLocalIpAddress OBJECT-TYPE
     SYNTAX    IpAddress
     ACCESS    read-only
     STATUS    mandatory
		--% ALIAS "Local IP Addr of TCP Cxn"
		--% GROUP Telnet-Session-Table 
	DESCRIPTION
		"The local IP address of the TCP connection that this
telnet session is using.  The value of this variable is the same
as the value of the Connection Local Address variable for the TCP
connection this telnet session is using."
     ::= { tnEntry 2 }

tnRemoteIpAddress OBJECT-TYPE
     SYNTAX    IpAddress
     ACCESS    read-only
     STATUS    mandatory
		--% ALIAS "Remote IP Addr of TCP Cxn"
		--% GROUP Telnet-Session-Table
	DESCRIPTION
		"The remote IP address of the TCP connection that this
telnet session is using.  The value of this variable is the same
as the value of the Connection Remote Address variable for the TCP
connection this telnet session is using."
     ::= { tnEntry 3 }

tnLocalPort OBJECT-TYPE
     SYNTAX    INTEGER (0..65535)
     ACCESS    read-only
     STATUS    mandatory
		--% ALIAS "Local Port of TCP Connection"
		--% GROUP Telnet-Session-Table
	DESCRIPTION
		"The local port of the TCP connection that this telnet
session is using. The value of this variable is the same as the
value of the Connection Local Port Number variable for the TCP
connection this telnet session is using."
     ::= { tnEntry 4 }

tnRemotePort OBJECT-TYPE
     SYNTAX    INTEGER (0..65535)
     ACCESS    read-only
     STATUS    mandatory
		--% ALIAS "Remote Port of TCP Connection"
		--% GROUP Telnet-Session-Table
	DESCRIPTION
		"The remote port of the TCP connection that this telnet
session is using.  The value of this variable is the same as the
value of the Connection Remote Port Number variable for the TCP
connection this telnet session is using."
     ::= { tnEntry 5 }

tnUpTime OBJECT-TYPE
     SYNTAX    TimeTicks
     ACCESS    read-only
     STATUS    mandatory
		--% ALIAS "Up Time at Session Start"
		--% GROUP Racal-InterLan-Telnet-Group
	DESCRIPTION
		"The value of INX-NMM Up Time at the time the telnet
session was established."
     ::= { tnEntry 6 }

tnOptionsOn OBJECT-TYPE
     SYNTAX    OCTET STRING
     ACCESS    read-only
     STATUS    mandatory
		--% ALIAS "Session Options On"
		--% GROUP Racal-InterLan-Telnet-Group
	DESCRIPTION
		"Indicates which options are on/enabled in the will/do
state.  Each octet in the string contains the numerical value of
an option that is on.  For example, if a session had options 1, 4,
10, 15, and 20 on, then this variable would be 5 octets long, and
the octets would contain the values 1, 4, 10, 15, and 20.  The
option values in the octet string can be in any order."
     ::= { tnEntry 7 }

tnState OBJECT-TYPE
     SYNTAX    INTEGER {
               serverActive(1)
               }
     ACCESS    read-only
     STATUS    mandatory
		--% ALIAS "Telnet Session State"
		--% GROUP Racal-InterLan-Telnet-Group
	DESCRIPTION
		"Shows the state of the session.  This variable always
returns serverActive(1), which indicates that the INX-NMM is the
telnet server and that a session is active, i.e., the user has
logged in to this end of the connection."
     ::= { tnEntry 8 }

tnUserId OBJECT-TYPE
     SYNTAX    OCTET STRING
     ACCESS    read-only
     STATUS    mandatory
		--% ALIAS "Telnet User ID"
		--% GROUP Racal-InterLan-Telnet-Group
	DESCRIPTION
		"The identification of the actual user at that end of the
telnet session.  The INX-NMM always returns a null string for this
variable, because the concept of a user ID is not relevant to the
INX-NMM."
     ::= { tnEntry 9 }

--tnNextType OBJECT-TYPE
--     SYNTAX    INTEGER {
--                    none(1),
--                    other(2),
--                    local(3),
--                    telnet(4),
--                    dummy(5)
--               }
--     ACCESS    read-only
--     STATUS    mandatory
		--% ALIAS "Protocol Type of Next Session"
		--% GROUP Racal-InterLan-Telnet-Group
--	DESCRIPTION
--		"&description"
--     ::= { tnEntry 12 }
--
--tnNextName OBJECT-TYPE
--     SYNTAX    OBJECT IDENTIFIER
--     ACCESS    read-only
--     STATUS    mandatory
		--% ALIAS "Name of Next Session"
		--% GROUP Racal-InterLan-Telnet-Group
--	DESCRIPTION
--		"&description"
--     ::= { tnEntry 13 }

-- ******************************************
--
-- The NMM Group - starting with the
-- basic chassis management objects.
--
-- ******************************************

riLdcHardwareRev OBJECT-TYPE
	SYNTAX    DisplayString
	ACCESS    read-only
	STATUS    mandatory
		--% ALIAS "INX-CMM Hardware Rev"
		--% GROUP INX-NMM-Basic-Chassis-Mgmt-group
	DESCRIPTION
		"The hardware revision level of the INX-CMM, which this
variable returns as a hexadecimal display string.
Note: This is NOT the hardware revision level of the INX-NMM
module."
	::={ riLdcNmm 1 }

riLdcFirmwareRev OBJECT-TYPE
	SYNTAX    DisplayString
	ACCESS    read-only
	STATUS    mandatory
		--% ALIAS "INX-CMM Firmware Rev"
		--% GROUP INX-NMM-Basic-Chassis-Mgmt-group
	DESCRIPTION
		"The firmware revision level of the INX-CMM, i.e., the
revision level of the INX-CMM PROMs.
Note: This is NOT the firmware revision level of the INX-NMM
module."
	::={ riLdcNmm 2 }

riLdcChassisSoftwareRev OBJECT-TYPE
	SYNTAX    DisplayString 
	ACCESS    read-only
	STATUS    mandatory
		--% ALIAS "INX-CMM Software Rev"
		--% GROUP INX-NMM-Basic-Chassis-Mgmt-group
	DESCRIPTION
		"The software revision level of higher-level INX-CMM
software.  Currently, there is no higher-level software on the INX-CMM; all
its software is contained in the INX-CMM PROMS, whose revision
level is returned by the previous variable, riLdcFirmwareRev.
Because there is no higher-level software on the INX-CMM, this
variable returns 0.
Note: This is NOT the software revision level of the INX-NMM
module."
	::={ riLdcNmm 3 }

riLdcChassisSerialNumber OBJECT-TYPE
	SYNTAX    DisplayString
	ACCESS    read-only
	STATUS    mandatory
		--% ALIAS "INX-CMM Serial Number"
		--% GROUP INX-NMM-Basic-Chassis-Mgmt-group
	DESCRIPTION
		"The logic module serial number of the INX-CMM."
	::={ riLdcNmm 4 }

riLdcChassisStatus OBJECT-TYPE
	SYNTAX    INTEGER {
					reset(1),
					enabled(6),
					disabled(7),
					other(200)
				}
	ACCESS    read-write
	STATUS    mandatory
		--% ALIAS "Chassis Module State"
		--% GROUP INX-NMM-Basic-Chassis-Mgmt-group
	DESCRIPTION
		"The state of the modules in the chassis.

This variable returns enabled(6) if any module in the chassis is
set to enabled(6). It returns disabled(7) when all modules, excluding the 
INX-NMM, are set to disabled(7).
To reboot all modules in the chassis, including the INX-NMM, set
this variable to reset(1).  Wait two minutes after changing boot
parameters for any module in the chassis before setting this
variable to reset(1).  This ensures that your configuration updates
have been stored in NVRAM. You cannot set this variable to other(200)."
	::={ riLdcNmm 5 }

riLdcChassisSlotCount OBJECT-TYPE
	SYNTAX    INTEGER
	ACCESS    read-only
	STATUS    mandatory
		--% ALIAS "Slots Available"
		--% GROUP INX-NMM-Basic-Chassis-Mgmt-group
	DESCRIPTION
		"The total number of slots available in the chassis for
INTERNExT modules.  The INX5000-3 contains 3 slots, and the INX5000-12 
contains 13 slots."
	::={ riLdcNmm 6 }

riLdcNumPowerSupplies OBJECT-TYPE
	SYNTAX    INTEGER (1..2)
	ACCESS    read-only
	STATUS    mandatory
		--% ALIAS "Power Supplies Available"
		--% GROUP INX-NMM-Basic-Chassis-Mgmt-group
	DESCRIPTION
		"The number of power supplies that are installed in the
INTERNExT chassis.  This variable returns either 1 or 2, because
the INX5000-3 requires one power supply module, and the INX5000-12
can operate with either one or two power supply modules installed."
	::={ riLdcNmm 7 }

riLdcNumBusMons OBJECT-TYPE
	SYNTAX    INTEGER 
	ACCESS    read-only
	STATUS    mandatory
		--% ALIAS "Bus Monitor Entries"
		--% GROUP INX-NMM-Basic-Chassis-Mgmt-group
	DESCRIPTION
		"The number of entries in the Bus Monitor table, which
contains statistics for the internal INTERNExT chassis buses.  This
variable always returns 2, because the chassis contains two
internal Ethernet buses, Bus A and Bus B."
	::={ riLdcNmm 8 }

riLdcNumFans OBJECT-TYPE
	SYNTAX    INTEGER
	ACCESS    read-only
	STATUS    mandatory
		--% ALIAS "Fan Status Entries"
		--% GROUP INX-NMM-Basic-Chassis-Mgmt-group
	DESCRIPTION
		"The number of entries in the Fan Status table, which
contains information about the chassis fans.  This variable returns
either 1 or 4, because the INX5000-3 requires one fan to operate,
and the INX5000-12 requires four."
	::={ riLdcNmm 9 }

riLdcChassisSlotTable OBJECT-TYPE
	SYNTAX    SEQUENCE OF RiLdcSlotEntry
	ACCESS    not-accessible
	STATUS    mandatory
		--% ALIAS "Chassis Slot Table"
	DESCRIPTION 	
		"The Slot table contains information on the contents of
each INTERNExT chassis slot. You cannot access this variable; it is only a 
table marker in the MIB."
	::={ riLdcNmm 10 }

riLdcSlotEntry OBJECT-TYPE
	SYNTAX    RiLdcSlotEntry
	ACCESS    not-accessible
	STATUS    mandatory
		--% ALIAS "Chassis Slot Entry"
	DESCRIPTION
		"An entry in the Slot table.  (See the previous variable,
Chassis Slot Table, for an explanation of this table.)
You cannot access this variable; it is only a table marker in the
MIB.  The following variables are entries in the table:

Chassis Slot Index
Logic Module Object ID
Desired Logic Module State
Current Logic Module State
Logic Module Bus
Logic Module Hardware Rev
Logic Module Firmware Rev
Logic Module Software Rev
Logic Module Serial Number
Slot Diagnostic Results
Slot Diagnostic Code
Logic Module Detection Time
Slot Temperature Status
Connectivity Module Type
Connectivity Module Rev
Connectivity Module Serial Number
Connectivity Module State
Connectivity Module Bus
Media Type Setting
Sonic Bus
Slot Module Type
Set INX-NMM to Standby"
 	INDEX	{ riLdcSlotIndex }
	::={ riLdcChassisSlotTable 1 }

RiLdcSlotEntry ::= SEQUENCE {
			riLdcSlotIndex
				INTEGER,
			riLdcSlotContents
				OBJECT IDENTIFIER,
			riLdcSlotAdminStatus
				INTEGER,
			riLdcSlotOperStatus
				INTEGER,
			riLdcSlotBus
				INTEGER,
			riLdcSlotHwRev
				DisplayString,
			riLdcSlotFwRev
				DisplayString,
			riLdcSlotSwRev
				DisplayString,
			riLdcSlotSerialNumber
				DisplayString,
			riLdcSlotDiagnostic
				INTEGER,
			riLdcSlotDiagnosticCode
				OCTET STRING,
			riLdcSlotResetTime
				TimeTicks,
			riLdcSlotTempCondition
				INTEGER,
			riLdcSlotConnectivityType
				OBJECT IDENTIFIER,
			riLdcSlotConnectivityRev
				DisplayString,
			riLdcSlotConnectivitySerialNumber
				DisplayString,
			riLdcSlotConnectivityState
				INTEGER,
			riLdcSlotConnectivityBus
				INTEGER,
			riLdcSlotConnectivityMedia
				INTEGER,
			riLdcSlotSonicBus
				INTEGER,
			riLdcSlotModuleType
				INTEGER,
			riLdcSlotStandbyNMM
				INTEGER
		}

riLdcSlotIndex OBJECT-TYPE
	SYNTAX	INTEGER
	ACCESS	read-only
	STATUS	mandatory
		--% ALIAS "Chassis Slot Index"
		--% GROUP Chassis-Slot-Table
	DESCRIPTION
		"A unique value for each slot in the chassis.  The value
ranges from 1 to n, where n is the number of slots in the chassis.
This variable returns 14 for the CMM slot in the INX5000-12, and
4 for the CMM slot in the INX5000-3."
	::={ riLdcSlotEntry 1 }

riLdcSlotContents OBJECT-TYPE
	SYNTAX    OBJECT IDENTIFIER
	ACCESS    read-only
	STATUS    mandatory
		--% ALIAS "Logic Module Object ID"
		--% GROUP Chassis-Slot-Table
	DESCRIPTION
		"The type of logic module that is in the slot, as
specified below.  If the slot is empty, this variable returns 0.0.

1.3.6.1.4.1.28.1.3.1.1      INX-NMM
1.3.6.1.4.1.28.1.3.2.1      INX-10BT
1.3.6.1.4.1.28.1.3.3.1      INX-FOIRL
1.3.6.1.4.1.28.1.3.4.1      INX-NTS
1.3.6.1.4.1.28.1.3.6.1      INX-CMM
1.3.6.1.4.1.28.1.3.5.1      INX-LBR
1.3.6.1.4.1.28.1.3.5.2      INX-RBR
0.0                         No module in slot."
	::={ riLdcSlotEntry 2 }

riLdcSlotAdminStatus OBJECT-TYPE
	SYNTAX    INTEGER {
				reboot(1),
				enabled(6),
				disabled(7),
				empty(31),
				booting(34),
				other(200)
			}
	ACCESS    read-write
	STATUS    mandatory
		--% ALIAS "Desired Logic Module State"
		--% GROUP Chassis-Slot-Table
	DESCRIPTION
		"The state of the logic module in the slot.
To enable or disable a logic module, first set this variable to
enabled(6) or disabled(7), then reboot the module by setting the
variable to reboot(1).
Only reboot(1), enabled(6), and disabled(7) are settable values.
If you try to set the state of the INX-CMM with this variable, the
value is accepted but has no effect.  To set the state of the
INX-CMM, use the Chassis Module State variable. If you try to set this 
variable for an empty slot, a badValue error is returned. When read, 
the variable returns the same status as Current Logic Module State."
	::={ riLdcSlotEntry 3 }

riLdcSlotOperStatus OBJECT-TYPE
	SYNTAX    INTEGER {
				enabled(6),
				disabled(7),
				empty(31),
				booting(34),
				other(200)
			}
	ACCESS    read-only
	STATUS    mandatory
		--% ALIAS "Current Logic Module State"
		--% GROUP Chassis-Slot-Table
	DESCRIPTION
		"The current state of the logic module in the slot.
empty(31) indicates that there is nothing in the slot; other(200)
indicates that the module in the slot has an undefined  status."
	::={ riLdcSlotEntry 4 }

riLdcSlotBus OBJECT-TYPE
	SYNTAX    INTEGER {
				bus-a(2),
				bus-b(3),
				other(200)
			}
	ACCESS    read-write
	STATUS    mandatory
		--% ALIAS "Logic Module Bus"
		--% GROUP Chassis-Slot-Table
	DESCRIPTION
		"The internal Ethernet bus connected to the NIC of the
logic module.  The values have the following meanings:
o bus-a(2) indicates that the NIC is connected to Bus A.
o bus-b(3) indicates that the NIC is connected to Bus B.
o other(200) indicates that the slot is empty.

After you set this variable, you must reboot the module with the
Desired Logic Module State variable for the new setting to take
effect.  If you set this variable and then read it without
rebooting, the old setting is returned.
If you set one of these values for the INX-CMM or INX-LBR, it is
accepted but has no effect on the INX-CMM's or INX-LBR's operation,
because it has no bus connection and the INX-LBR is not currently
configurable from the INX-NMM"
	::={ riLdcSlotEntry 5 }

riLdcSlotHwRev OBJECT-TYPE
	SYNTAX    DisplayString
	ACCESS    read-only
	STATUS    mandatory
		--% ALIAS "Logic Module Hardware Rev"
		--% GROUP Chassis-Slot-Table
	DESCRIPTION
		"The hardware revision level of the logic module in the
slot, returned as a hexadecimal string.  If the slot is empty, the
variable returns 0."
	::={ riLdcSlotEntry 6 }

riLdcSlotFwRev OBJECT-TYPE
	SYNTAX    DisplayString
	ACCESS    read-only
	STATUS    mandatory
		--% ALIAS "Logic Module Firmware Rev"
		--% GROUP Chassis-Slot-Table
	DESCRIPTION
		"The firmware revision level of the logic module in the
slot.  If the slot contains no module, or if the module contains
no firmware, the variable returns 0."
	::={ riLdcSlotEntry 7 }

riLdcSlotSwRev OBJECT-TYPE
	SYNTAX    DisplayString
	ACCESS    read-only
	STATUS    mandatory
		--% ALIAS "Logic Module Software Rev"
		--% GROUP Chassis-Slot-Table
	DESCRIPTION
		"The revision level of the operating software image of
the logic module in the slot.  If the slot contains no module, or
the module has no software, the variable returns 0."
	::={ riLdcSlotEntry 8 }

riLdcSlotSerialNumber OBJECT-TYPE
	SYNTAX    DisplayString
	ACCESS    read-only
	STATUS    mandatory
		--% ALIAS "Logic Module Serial Number"
		--% GROUP Chassis-Slot-Table
	DESCRIPTION
		"The serial number of the logic module in the slot.  If
the slot is empty, the variable returns 0."
	::={ riLdcSlotEntry 9 }

riLdcSlotDiagnostic OBJECT-TYPE
	SYNTAX    INTEGER {
				pass(92),
				fail(93),
				other(200)
			}
	ACCESS    read-only
	STATUS    mandatory
		--% ALIAS "Slot Diagnostic Results"
		--% GROUP Chassis-Slot-Table
	DESCRIPTION
		"The results of the internal startup (i.e.,
nondestructive) diagnostics for the logic and connectivity modules
in a slot.  This variable returns either pass(92) or fail(93),
indicating the general results of the diagnostic tests.  If the
variable returns fail(93), see the next variable, Slot Diagnostic
Code, for information about which test failed."
	::={ riLdcSlotEntry 10 }

riLdcSlotDiagnosticCode OBJECT-TYPE
	SYNTAX    OCTET STRING
	ACCESS    read-only
	STATUS    mandatory
		--% ALIAS "Slot Diagnostic Code"
		--% GROUP Chassis-Slot-Table
	DESCRIPTION
		"Diagnostic results, returned as an octet string."
	::={ riLdcSlotEntry 11 }

riLdcSlotResetTime OBJECT-TYPE
	SYNTAX    TimeTicks
	ACCESS    read-only
	STATUS    mandatory
		--% ALIAS "Logic Module Detection Time"
		--% GROUP Chassis-Slot-Table
	DESCRIPTION
		"The value of INX-NMM Up Time (i.e., the length of time
since the INX-NMM was last initialized) when the INX-NMM detected
the presence of a logic module in this slot.  This variable returns
0 in two cases:  if the slot is empty, and if the slot contains an
INX-NMM, because the INX-NMM detects its own presence immediately."
	::={ riLdcSlotEntry 12 }

riLdcSlotTempCondition OBJECT-TYPE
	SYNTAX    INTEGER {
				unknown(60),
				ok(61),
				too-hot(62)
			}
	ACCESS    read-only
	STATUS    mandatory
		--% ALIAS "Slot Temperature Status"
		--% GROUP Chassis-Slot-Table
	DESCRIPTION
		"The temperature status of the slot.  When the slot is
empty or when the module in the slot is in some other failure or
error state, this variable returns unknown(60)."
	::={ riLdcSlotEntry 13 }

riLdcSlotConnectivityType OBJECT-TYPE
	SYNTAX    OBJECT IDENTIFIER
	ACCESS    read-only
	STATUS    mandatory
		--% ALIAS "Connectivity Module Type"
		--% GROUP Chassis-Slot-Table
	DESCRIPTION
		"The type of connectivity module that is in the slot, as
specified below. If there is no connectivity module in this slot, or the 
type cannot be determined, then this variable returns 0.0.

1.3.6.1.4.1.28.1.3.2.1.1.1     10BT-RJ45
1.3.6.1.4.1.28.1.3.2.1.2.1     10BT-TELCO
1.3.6.1.4.1.28.1.3.3.1.1.1     FOIRL-FST
1.3.6.1.4.1.28.1.3.4.1.1.1     NTS-RJ45
1.3.6.1.4.1.28.1.3.4.1.2.1     NTS-TELCO
1.3.6.1.4.1.28.1.3.5.2.1.1     INX-V35
1.3.6.1.4.1.28.1.3.5.2.1.2     INX-X21
1.3.6.1.4.1.28.1.3.6.1.1.1     INX-AUI
1.3.6.1.4.1.28.1.3.6.1.2.1     INX-FST
0.0                            No module in slot."
	::={ riLdcSlotEntry 14 }

riLdcSlotConnectivityRev OBJECT-TYPE
	SYNTAX    DisplayString
	ACCESS    read-only
	STATUS    mandatory
		--% ALIAS "Connectivity Module Rev"
		--% GROUP Chassis-Slot-Table
	DESCRIPTION
		"The hardware revision of the connectivity module in the
slot, returned as a hexadecimal string.  If the slot is empty, then
this variable returns 0."
	::={ riLdcSlotEntry 15 }

riLdcSlotConnectivitySerialNumber OBJECT-TYPE
	SYNTAX    DisplayString
	ACCESS    read-only
	STATUS    mandatory
		--% ALIAS "Connectivity Module Serial Number"
		--% GROUP Chassis-Slot-Table
	DESCRIPTION
		"The serial number of the connectivity module in the
slot. This variable returns a null string for INX-10BT RJ45 and INX-10BT
Telco connectivity modules, because these modules are not equipped
with identification ROM.  If the slot is empty, then this variable
returns 0."
	::={ riLdcSlotEntry 16 }

riLdcSlotConnectivityState OBJECT-TYPE
	SYNTAX    INTEGER {
				disabled(10),
				enabled(19),
				other(200)
			}
	ACCESS    read-write
	STATUS    mandatory
		--% ALIAS "Connectivity Module State"
		--% GROUP Chassis-Slot-Table
	DESCRIPTION
		"The state of the connectivity module in the slot.

You can enable or disable only INX-AUI and INX-FST connectivity
modules with this variable. INX-10BT, INX-NTS and FOIRL-FST
connectivity modules always return enabled(19), and cannot be set
to disabled(10). other(200) is returned for empty slots; you cannot 
set this value."
	::={ riLdcSlotEntry 17 }

riLdcSlotConnectivityBus OBJECT-TYPE
	SYNTAX    INTEGER {
				bus-a(8),
				bus-b(9),
				other(200)
			}
	ACCESS    read-write
	STATUS    mandatory
		--% ALIAS "Connectivity Module Bus"
		--% GROUP Chassis-Slot-Table
	DESCRIPTION
		"The bus connected to an INX-AUI or INX-FST connectivity
module.
o bus-a(8) indicates that the INX-AUI or INX-FST is connected to
  Bus A.
o bus-b(9) indicates that INX-AUI or INX-FST is connected to Bus
  B.
o other(200) indicates that the connectivity module is not an
  INX-AUI or INX-FST; you cannot set this value."
	::={ riLdcSlotEntry 18 }

riLdcSlotConnectivityMedia  OBJECT-TYPE
	SYNTAX    INTEGER {
				backbone-thick(11),
				backbone-thin(12),
				backbone-fiber(13),
				nts-telco(17),
				nts-rj45(18),
				bt-10-telco(33),
				bt-10-rj45(34),
				foirl-fiber(49),
				bridge-v35(81),
				bridge-x21(82),
				other(200)
			}
	ACCESS    read-write
	STATUS    mandatory
		--% ALIAS "Media Type Setting"
		--% GROUP Chassis-Slot-Table
	DESCRIPTION
	"The INX media type for the connectivity module located in this slot.
o backbone thick(11) indicates that the media type of the INX-AUI or INX-FST
  is set for connection to an external transceiver.
o backbone-thin(12) indicates that the media type of the INX-AUI is set for 
  connection to Thin Ethernet.
o backbone-fiber(13) indicates that the media type of the INX-FST is set for 
  connection to fiber-optic cable.
o NTS-TELCO(17) and NTS-RJ45(18) are the connectivity modules for
  the INX-NTS logic module.  The NTS-RJ45 has 16 RJ-45 ports,
  numbered 1 through 16, top to bottom.  The NTS-TELCO has two 50-pin
  telco connectors.
o 10BT-TELCO(33) and 10BT-RJ45(34) are the connectivity modules for
  the INX-10BT logic module.  The 10BT-RJ45 has 12 RJ-45 twisted pair
  transceiver ports.  The 10BT-TELCO has one 50-pin telco connector.
o FOIRL-FST(49) is the connectivity module for the INX-FOIRL,
  containing 6 pairs of ST fiber-optic connectors for connection to
  six ports.
o BRIDGE-V35(81) and BRIDGE-X21U(82) are the connectivity modules
  for the INX-RBR.
o other(200) indicates that the connectivity module is not an
  INX-AUI or INX-FST; you cannot set this value."
	::={ riLdcSlotEntry 19 }

riLdcSlotSonicBus  OBJECT-TYPE
	SYNTAX    INTEGER {
				bus-a(15),
				bus-b(16),
				other(200)
			}
	ACCESS    read-write
	STATUS    mandatory
		--% ALIAS "Sonic Bus"
		--% GROUP Chassis-Slot-Table
	DESCRIPTION
		"The internal Ethernet bus that the INX-NMM SONIC is
monitoring.
o bus-a(15) indicates that the SONIC is monitoring Bus A.
o bus-b(16) indicates that the SONIC is monitoring Bus B.
o other(200) indicates that the logic module is not an INX-NMM; you
  cannot set this value.

After you set this variable, you must reboot the module with the
Desired Logic Module State variable for the new setting to take
effect.  If you set this variable and then read it without
rebooting, the old setting is returned."
	::={ riLdcSlotEntry 20 }

riLdcSlotModuleType  OBJECT-TYPE
	SYNTAX    INTEGER {
			inx-nmm(1),
			inx-nts(2),
			inx-10bt(3),
			inx-cmm(4),
			inx-rbr(5),
			inx-foirl(6),
			inx-lbr(7),
			empty(31),
			other(200)
			}
	ACCESS    read-only
	STATUS    mandatory
		--% ALIAS "Module Type"
		--% GROUP Chassis-Slot-Table
	DESCRIPTION
		"The type of logic module in the specified slot.  This
variable returns the same information as Logic Module Object ID,
but in integer form, rather than as object identifiers."
	::={ riLdcSlotEntry 21 }

riLdcSlotStandbyNMM OBJECT-TYPE
	SYNTAX    INTEGER {
			standby-NMM(3),
			non-standby-NMM(4),
			other(200)
			}
	ACCESS    read-write
	STATUS    mandatory
		--% ALIAS "Standby NMM"
		--% GROUP Chassis-Slot-Table
	DESCRIPTION
		"Whether this INX-NMM is in standby mode.  For this
INX-NMM to be the master, this variable must be set to
non-standby-NMM(4) and the Desired Logic Module State variable must
be set to enabled(6).  For this INX-NMM to be the slave, this
variable must be set to non-standby-NMM(4) and the MDSU, Desired
Logic Module State variable must be set to disabled(7). If this variable 
is set to standby-NMM(3), this INX-NMM is in standby mode; the setting of 
this variable overrides the setting of the Desired Logic Module State 
variable. This variable returns other(200) when read if the module in this
slot is not an INX-NMM."
	::={ riLdcSlotEntry 22 }

-- Power supply table

riLdcPowerSupplyTable OBJECT-TYPE
	SYNTAX    SEQUENCE OF RiLdcPSEntry
	ACCESS    not-accessible
	STATUS    mandatory
		--% ALIAS "Power Supply Table"
	DESCRIPTION
		"The Power Supply table contains information on the
INTERNExT chassis power supplies.
You cannot access this variable; it is only a table marker in the
MIB."
	::={ riLdcNmm 11 }

riLdcPSEntry OBJECT-TYPE
	SYNTAX    RiLdcPSEntry
	ACCESS    not-accessible
	STATUS    mandatory
		--% ALIAS "Power Supply Table Entry"
	DESCRIPTION
		"An entry in the Power Supply table.  (See the previous
variable, Power Supply Table, for an explanation of this table.)
You cannot access this variable; it is only a table marker in the
MIB.  The following variables are entries in the table:

Power Supply Table Index
Power Supply State"
	INDEX	{ riLdcPSIndex }
	::={ riLdcPowerSupplyTable 1 }

RiLdcPSEntry ::= SEQUENCE {
				riLdcPSIndex
					INTEGER,
--				riLdcPSAdminStatus
--					INTEGER,
				riLdcPSActualStatus
					INTEGER
			  }

riLdcPSIndex OBJECT-TYPE
	SYNTAX    INTEGER
	ACCESS    read-only
	STATUS    mandatory
		--% ALIAS "Power Supply Table Index"
		--% GROUP Power-Supply-Table
	DESCRIPTION
		"A unique value for each power supply in the chassis. 
Values range from 1 to n, where n is the number of available
positions for power supplies in the chassis.  There is one position
for a power supply module in the INX5000-3, and two positions for
power supply modules in the INX5000-12."
	::={ riLdcPSEntry 1 }

--riLdcPSAdminStatus OBJECT-TYPE
--	SYNTAX    INTEGER {
--					backup(3),
--					empty(4),
--					off(71),
--					active(72),
--					other(200)
--			   }
--	ACCESS    read-write
--	STATUS    mandatory
		--% ALIAS "Desired Power Supply State"
		--% GROUP Power-Supply-Table
--	DESCRIPTION
--		"&description"
--	::= { riLdcPSEntry 2 }

riLdcPSActualStatus OBJECT-TYPE
	SYNTAX    INTEGER {
				off(71),
				active(72),
				other(200)
			}
	ACCESS    read-only
	STATUS    mandatory
		--% ALIAS "Power Supply State"
		--% GROUP Power-Supply-Table
	DESCRIPTION
		"The current operational state of the power supply.  The
values and their meanings are as follows:
o off(71) indicates that the power supply in this position is not
  supplying power.  Warning:  Do not remove the power entry module
  until you have another one to replace it.  All modules, except the
  INX-NMM and INX-CMM, power down automatically within five minutes
  after the top power entry module is removed.
o active(72) indicates that the power supply in this position is
  active and supplying power to the chassis, and all conditions in
  the power supply are optimal (i.e., no fault has been detected in
  the power supply).
o other(200) indicates that this position is empty."
	::= { riLdcPSEntry 3 }

-- Internal Ethernet Bus Monitoring table

riLdcBusMonTable OBJECT-TYPE
	SYNTAX    SEQUENCE OF RiLdcBusMonEntry
	ACCESS    not-accessible
	STATUS    mandatory
		--% ALIAS "Bus Monitor Table"
	DESCRIPTION
		"The Bus Monitor table maintains traffic statistics on
the internal buses of the INTERNExT chassis. 
You cannot access this variable; it is only a table marker in the
MIB."
	::={ riLdcNmm 12 }

riLdcBusMonEntry OBJECT-TYPE
	SYNTAX    RiLdcBusMonEntry
	ACCESS    not-accessible
	STATUS    mandatory
		--% ALIAS "Bus Monitor Table Entry"
	DESCRIPTION
		"Entries in the Bus Monitor table provide statistical
information on the activities of the internal Ethernet buses.  (See
the previous variable, Bus Monitor Table, for an explanation of
this table.)
You cannot access this variable; it is only a table marker in the
MIB.  The following variables are entries in the table:

Bus Monitor Table Index
Monitored Bus
Frames Received
Frames Received Rate
Octets Recd
Octets Received Rate
Multicast Frames Received
Multicast Frames Received Rate
Broadcast Frames Received
Broadcast Frames Received Rate
Normal Collisions
Normal Collisions Rate
Late Collisions
Late Collisions Rate
CRC Errored Frames Received 
CRC Errored Frames Recd Rate
Collision Fragments Received
Collision Fragments Received Rate
Short Frames Received
Short Frames Received Rate
In-Range Errors Received 
In-Range Errors Received Rate
Out-Range Errors Received
Out-Range Errors Received Rate
Too Long Frames Received
Too Long Frames Received Rate
Nonaligned Frames Received
Nonaligned Frames Recd Rate
Missed Frames Received
Missed Frames Received Rate
Bad Frames Received
Bad Frames Received Rate
Peak Bus Utilization
Peak Bus Utilization Time
Current Bus Utilization"
	INDEX	{ riLdcBusMonIndex }
	::={ riLdcBusMonTable 1 }

RiLdcBusMonEntry ::= SEQUENCE {
					riLdcBusMonIndex
						INTEGER,
					riLdcBusMonBus
						INTEGER,
					riLdcBusMonFramesReceivedOK
						Counter,
					riLdcBusMonFramesReceivedOKRate
						Gauge,
					riLdcBusMonOctetsReceivedOK
						Counter,
					riLdcBusMonOctetsReceivedOKRate
						Gauge,
					riLdcBusMonMCastFramesReceivedOK
						Counter,
					riLdcBusMonMCastFramesReceivedOKRate
						Gauge,
					riLdcBusMonBCastFramesReceivedOK
						Counter,
					riLdcBusMonBCastFramesReceivedOKRate
						Gauge,
					riLdcBusMonCollisions
						Counter,
					riLdcBusMonCollisionsRate
						Gauge,
					riLdcBusMonLateCollisions
						Counter,
					riLdcBusMonLateCollisionsRate
						Gauge,
					riLdcBusMonCRCErrors
						Counter,
					riLdcBusMonCRCErrorsRate
						Gauge,
					riLdcBusMonPygmies
						Counter,
					riLdcBusMonPygmiesRate
						Gauge,
					riLdcBusMonShortFrames
						Counter,
					riLdcBusMonShortFramesRate
						Gauge,
					riLdcBusMonInRangeLengthErrors
						Counter,
					riLdcBusMonInRangeLengthErrorsRate
						Gauge,
					riLdcBusMonOutOfRangeLengthErrors
						Counter,
					riLdcBusMonOutOfRangeLengthErrorsRate
						Gauge,
					riLdcBusMonFramesTooLong
						Counter,
					riLdcBusMonFramesTooLongRate
						Gauge,
					riLdcBusMonAlignmentErrors
						Counter,
					riLdcBusMonAlignmentErrorsRate
						Gauge,
					riLdcBusMonMissedPackets
						Counter,
					riLdcBusMonMissedPacketsRate
						Gauge,
					riLdcBusMonErrorFrames
						Counter,
					riLdcBusMonErrorFramesRate
						Gauge,
					riLdcBusMonUtilPeak
						Gauge,
					riLdcBusMonUtilPeakTime
						TimeTicks,
					riLdcBusMonUtilCurrent
						Gauge
				}

riLdcBusMonIndex OBJECT-TYPE
	SYNTAX    INTEGER
	ACCESS    read-only
	STATUS    mandatory
		--% ALIAS "Bus Monitor Table Index"
		--% GROUP Bus-Monitor-Table
	DESCRIPTION
		"A unique value for each table entry.  The value ranges
from 1 to the value of Bus Monitor Entries. 1 for Bus A, 2 for Bus
B"
	::={ riLdcBusMonEntry 1 }

riLdcBusMonBus OBJECT-TYPE
	SYNTAX    INTEGER {
					bus-a(15),
					bus-b(16)
				}
	ACCESS    read-only
	STATUS    mandatory
		--% ALIAS "Monitored Bus"
		--% GROUP Bus-Monitor-Table
	DESCRIPTION
		"The internal Ethernet bus associated with this entry. 
The INTERNExT chassis contains two internal Ethernet buses, Bus A
and Bus B."
	::={ riLdcBusMonEntry 2 }

riLdcBusMonFramesReceivedOK OBJECT-TYPE
	SYNTAX    Counter 
	ACCESS    read-only
	STATUS    mandatory
		--% ALIAS "Frames Received"
		--% GROUP Bus-Monitor-Table
	DESCRIPTION
		"The number of frames received successfully off the bus
by the SONIC.  This value does not include frames received with
FCS, length, or alignment errors, or frames lost due to internal
errors."
	::={ riLdcBusMonEntry 3 }

riLdcBusMonFramesReceivedOKRate OBJECT-TYPE
	SYNTAX    Gauge 
	ACCESS    read-only
	STATUS    mandatory
		--% ALIAS "Frames Received Rate"
		--% GROUP Bus-Monitor-Table
	DESCRIPTION
		"The rate of frames received successfully off the bus by
the SONIC.  This value does not include frames received with FCS,
length, or alignment errors, or frames lost due to internal
errors."
	::={ riLdcBusMonEntry 4 }

riLdcBusMonOctetsReceivedOK OBJECT-TYPE
	SYNTAX    Counter 
	ACCESS    read-only
	STATUS    mandatory
		--% ALIAS "Octets Recd"
		--% GROUP Bus-Monitor-Table
	DESCRIPTION
		"The number of octets associated with the frames included
in Frames Received."
	::={ riLdcBusMonEntry 5 }

riLdcBusMonOctetsReceivedOKRate OBJECT-TYPE
	SYNTAX    Gauge
	ACCESS    read-only
	STATUS    mandatory
		--% ALIAS "Octets Received Rate"
		--% GROUP Bus-Monitor-Table
	DESCRIPTION
		"The rate of octets associated with the frames included
in Frames Received."
	::={ riLdcBusMonEntry 6 }

riLdcBusMonMCastFramesReceivedOK OBJECT-TYPE
	SYNTAX    Counter
	ACCESS    read-only
	STATUS    mandatory
		--% ALIAS "Multicast Frames Received"
		--% GROUP Bus-Monitor-Table
	DESCRIPTION
		"The number of frames received successfully off this bus
that have an Ethernet multicast destination address."
	::={ riLdcBusMonEntry 7 }

riLdcBusMonMCastFramesReceivedOKRate OBJECT-TYPE
	SYNTAX    Gauge 
	ACCESS    read-only
	STATUS    mandatory
		--% ALIAS "Multicast Frames Received Rate"
		--% GROUP Bus-Monitor-Table
	DESCRIPTION
		"The rate of frames received successfully off this bus
that have an Ethernet multicast destination address."
	::={ riLdcBusMonEntry 8 }

riLdcBusMonBCastFramesReceivedOK OBJECT-TYPE
	SYNTAX    Counter
	ACCESS    read-only
	STATUS    mandatory
		--% ALIAS "Broadcast Frames Received"
		--% GROUP Bus-Monitor-Table
	DESCRIPTION
		"The number of frames received successfully off this bus
that have a broadcast destination address."
	::={ riLdcBusMonEntry 9 }

riLdcBusMonBCastFramesReceivedOKRate OBJECT-TYPE
	SYNTAX    Gauge 
	ACCESS    read-only
	STATUS    mandatory
		--% ALIAS "Broadcast Frames Received Rate"
		--% GROUP Bus-Monitor-Table
	DESCRIPTION
		"The rate of frames received successfully off of this bus
that have a broadcast destination address."
	::={ riLdcBusMonEntry 10 }

riLdcBusMonCollisions  OBJECT-TYPE
	SYNTAX    Counter
	ACCESS    read-only
	STATUS    mandatory
		--% ALIAS "Normal Collisions"
		--% GROUP Bus-Monitor-Table
	DESCRIPTION
		"The number of collisions detected on this bus that
occurred within 512 bit times from frame start.  (Collisions are
normal for networks with high utilization.)"
	::={ riLdcBusMonEntry 11 }

riLdcBusMonCollisionsRate  OBJECT-TYPE
	SYNTAX    Gauge 
	ACCESS    read-only
	STATUS    mandatory
		--% ALIAS "Normal Collisions Rate"
		--% GROUP Bus-Monitor-Table
	DESCRIPTION
		"The rate of collisions detected on this bus that
occurred within 512 bit times from frame start."
	::={ riLdcBusMonEntry 12 }

riLdcBusMonLateCollisions  OBJECT-TYPE
	SYNTAX    Counter
	ACCESS    read-only
	STATUS    mandatory
		--% ALIAS "Late Collisions"
		--% GROUP Bus-Monitor-Table
	DESCRIPTION
		"The number of times that a collision has been detected
on this bus later than 512 bit times from frame start.  A late
collision is counted twice, both as a collision and as a late
collision."
	::={ riLdcBusMonEntry 13 }

riLdcBusMonLateCollisionsRate  OBJECT-TYPE
	SYNTAX    Gauge 
	ACCESS    read-only
	STATUS    mandatory
		--% ALIAS "Late Collisions Rate"
		--% GROUP Bus-Monitor-Table
	DESCRIPTION
		"The rate of times that a collision has been detected on
this bus later than 512 bit times from frame start.  A late
collision is counted twice, both as a collision and as a late
collision."
	::={ riLdcBusMonEntry 14 }

riLdcBusMonCRCErrors  OBJECT-TYPE
	SYNTAX    Counter
	ACCESS    read-only
	STATUS    mandatory
		--% ALIAS "CRC Errored Frames Received"
		--% GROUP Bus-Monitor-Table
	DESCRIPTION
		"The number of frames received off this bus that are an
integral number of octets in length (the number of bits they
contain is a multiple of eight) and that do not pass the FCS
check."
	::={ riLdcBusMonEntry 15 }

riLdcBusMonCRCErrorsRate  OBJECT-TYPE
	SYNTAX    Gauge
	ACCESS    read-only
	STATUS    mandatory
		--% ALIAS "CRC Errored Frames Recd Rate"
		--% GROUP Bus-Monitor-Table
	DESCRIPTION
		"The rate of frames received off this bus that are an
integral number of octets in length (i.e., the number of bits they
contain is a multiple of eight) and that do not pass the FCS
check."
	::={ riLdcBusMonEntry 16 }

riLdcBusMonPygmies  OBJECT-TYPE
	SYNTAX    Counter
	ACCESS    read-only
	STATUS    mandatory
		--% ALIAS "Collision Fragments Received"
		--% GROUP Bus-Monitor-Table
	DESCRIPTION
		"The number of collision fragments (frames less than 96
bits long) received on this bus."
	::={ riLdcBusMonEntry 17 }

riLdcBusMonPygmiesRate  OBJECT-TYPE
	SYNTAX    Gauge 
	ACCESS    read-only
	STATUS    mandatory
		--% ALIAS "Collision Fragments Received Rate"
		--% GROUP Bus-Monitor-Table
	DESCRIPTION
		"The rate of collision fragments (frames less than 96
bits long) received on this bus."
	::={ riLdcBusMonEntry 18 }

riLdcBusMonShortFrames  OBJECT-TYPE
	SYNTAX    Counter
	ACCESS    read-only
	STATUS    mandatory
		--% ALIAS "Short Frames Received"
		--% GROUP Bus-Monitor-Table
	DESCRIPTION
		"The number of frames received on this bus that are
between 8 and 63 octets long."
	::={ riLdcBusMonEntry 19 }

riLdcBusMonShortFramesRate  OBJECT-TYPE
	SYNTAX    Gauge 
	ACCESS    read-only
	STATUS    mandatory
		--% ALIAS "Short Frames Received Rate"
		--% GROUP Bus-Monitor-Table
	DESCRIPTION
		"The rate of frames received on this bus that are between
8 and 63 octets long."
	::={ riLdcBusMonEntry 20 }

riLdcBusMonInRangeLengthErrors  OBJECT-TYPE
	SYNTAX    Counter 
	ACCESS    read-only
	STATUS    mandatory
		--% ALIAS "In-Range Errors Received"
		--% GROUP Bus-Monitor-Table
	DESCRIPTION
		"Number of in-range errors received on this bus.  IEEE
802.3 frames contain a length field, indicating the length of the
frame.  If the value in the length field and the actual length of
the frame do not match, even if the length of the frame is within
802.3 parameters, the receiving device returns an in-range error."
	::={ riLdcBusMonEntry 21 }

riLdcBusMonInRangeLengthErrorsRate  OBJECT-TYPE
	SYNTAX    Gauge 
	ACCESS    read-only
	STATUS    mandatory
		--% ALIAS "In-Range Errors Received Rate"
		--% GROUP Bus-Monitor-Table
	DESCRIPTION
		"Rate of in-range errors received on this bus.  IEEE
802.3 frames contain a length field, indicating the length of the
frame.  If the value in the length field and the actual length of
the frame do not match, even if the length of the frame is within
802.3 parameters, the receiving device returns an in-range error."
	::={ riLdcBusMonEntry 22 }

riLdcBusMonOutOfRangeLengthErrors  OBJECT-TYPE
	SYNTAX    Counter
	ACCESS    read-only
	STATUS    mandatory
		--% ALIAS "Out-Range Errors Received"
		--% GROUP Bus-Monitor-Table
	DESCRIPTION
		"Number of out-of-range errors received on this bus. 
IEEE 802.3 frames contain a length field, indicating the length of
the frame.  If the length of the frame is outside of 802.3
parameters, the receiving device returns an out-of-range error. 
Because the INX-NMM receives frames that do not have a length
field, it cannot detect this error, and this variable always
returns 0."
	::={ riLdcBusMonEntry 23 }

riLdcBusMonOutOfRangeLengthErrorsRate  OBJECT-TYPE
	SYNTAX    Gauge 
	ACCESS    read-only
	STATUS    mandatory
		--% ALIAS "Out-Range Errors Received Rate"
		--% GROUP Bus-Monitor-Table
	DESCRIPTION
		"Rate of out-of-range errors received on this bus.  IEEE
802.3 frames contain a length field, indicating the length of the
frame.  If the length of the frame is outside of 802.3 parameters,
the receiving device returns an out-of-range error.  Because the
INX-NMM receives frames that do not have a length field, it cannot
detect this error, and this variable always returns 0."
	::={ riLdcBusMonEntry 24 }

riLdcBusMonFramesTooLong  OBJECT-TYPE
	SYNTAX    Counter
	ACCESS    read-only
	STATUS    mandatory
		--% ALIAS "Too Long Frames Received"
		--% GROUP Bus-Monitor-Table
	DESCRIPTION
		"The number of frames received on this bus that are
greater than 1520 octets long, but not greater than 5msec in
duration (which would indicate a jabber condition)."
	::={ riLdcBusMonEntry 25 }

riLdcBusMonFramesTooLongRate  OBJECT-TYPE
	SYNTAX    Gauge 
	ACCESS    read-only
	STATUS    mandatory
		--% ALIAS "Too Long Frames Received Rate"
		--% GROUP Bus-Monitor-Table
	DESCRIPTION
		"The rate of frames received on this bus that are greater
than 1520 octets long, but not greater than 5 msec in duration
(which would indicate a jabber condition)."
	::={ riLdcBusMonEntry 26 }

riLdcBusMonAlignmentErrors  OBJECT-TYPE
	SYNTAX    Counter
	ACCESS    read-only
	STATUS    mandatory
		--% ALIAS "Nonaligned Frames Received"
		--% GROUP Bus-Monitor-Table
	DESCRIPTION
		"The number of frames received on this bus that are not
an integral number of octets in length (i.e., the number of bits
they contain is not a multiple of eight).  These frames will not
pass the FCS check but are counted as FCS errors."
	::={ riLdcBusMonEntry 27 }

riLdcBusMonAlignmentErrorsRate  OBJECT-TYPE
	SYNTAX    Gauge 
	ACCESS    read-only
	STATUS    mandatory
		--% ALIAS "Nonaligned Frames Recd Rate"
		--% GROUP Bus-Monitor-Table
	DESCRIPTION
		"The rate of frames received on this bus that are not an
integral number of octets in length.  (These frames will not pass
the FCS check but are not counted as FCS errors.)"
	::={ riLdcBusMonEntry 28 }

riLdcBusMonMissedPackets OBJECT-TYPE
	SYNTAX   Counter
	ACCESS   read-only
	STATUS   mandatory
		--% ALIAS "Missed Frames Received"
		--% GROUP Bus-Monitor-Table
	DESCRIPTION
		"The number of frames received while the INX-NMM receive
state is disabled.  The receive state usually becomes disabled
because a network error condition has created a situation where
resources are limited."
	::= { riLdcBusMonEntry 29 }

riLdcBusMonMissedPacketsRate OBJECT-TYPE
	SYNTAX   Gauge 
	ACCESS   read-only
	STATUS   mandatory
		--% ALIAS "Missed Frames Received Rate"
		--% GROUP Bus-Monitor-Table
	DESCRIPTION
		"The rate of frames received while the INX-NMM receive
state is disabled.  The receive state usually becomes disabled
because a network error condition has created a situation where
resources are limited."
	::= { riLdcBusMonEntry 30 }

riLdcBusMonErrorFrames OBJECT-TYPE
	SYNTAX   Counter
	ACCESS   read-only
	STATUS   mandatory
		--% ALIAS "Bad Frames Received"
		--% GROUP Bus-Monitor-Table
	DESCRIPTION
		"The total number of frames received with CRC, alignment,
or length errors."
	::= { riLdcBusMonEntry 31 }

riLdcBusMonErrorFramesRate OBJECT-TYPE
	SYNTAX   Gauge 
	ACCESS   read-only
	STATUS   mandatory
		--% ALIAS "Bad Frames Received Rate"
		--% GROUP Bus-Monitor-Table
	DESCRIPTION
		"The rate of frames received with CRC, alignment, or
length errors."
	::= { riLdcBusMonEntry 32 }

riLdcBusMonUtilPeak OBJECT-TYPE
	SYNTAX   Gauge
	ACCESS   read-write
	STATUS   mandatory
		--% ALIAS "Peak Bus Utilization"
		--% GROUP Bus-Monitor-Table
	DESCRIPTION
		--% GROUP Interface-Receive-Table
		"The highest utilization  of the 10MBit/sec Ethernet
network detected since NMM boot (eg. 27% Peak Utilization =
2.7Mbits/sec).  To clear this value and the UtilPeakTime, set this
object to 0"
	::= { riLdcBusMonEntry 33 }

riLdcBusMonUtilPeakTime OBJECT-TYPE
	SYNTAX   TimeTicks
	ACCESS   read-only
	STATUS   mandatory
		--% ALIAS "Peak Bus Utilization Time Ago"
		--% GROUP Bus-Monitor-Table
	DESCRIPTION
		"The NMM Uptime when the UtilPeak was detected."
	::= { riLdcBusMonEntry 34 }

riLdcBusMonUtilCurrent OBJECT-TYPE
	SYNTAX   Gauge
	ACCESS   read-only
	STATUS   mandatory
		--% ALIAS "Utility Current"
		--% GROUP Bus-Monitor-Table
	DESCRIPTION
		"The current utilization  of the 10MBit/sec Ethernet
network. (eg. 15% Current Utilization = 1.5Mbits/sec)."
	::= { riLdcBusMonEntry 35 }

-- Fan status table

riLdcFanTable OBJECT-TYPE
	SYNTAX    SEQUENCE OF RiLdcFanEntry
	ACCESS    not-accessible
	STATUS    mandatory
		--% ALIAS "Fan Status Table"
	DESCRIPTION
		"The Fan Status table lists the status of all fans in the
chassis.
You cannot access this variable; it is only a table marker in the
MIB."
	::={ riLdcNmm 13 }

riLdcFanEntry OBJECT-TYPE
	SYNTAX    RiLdcFanEntry
	ACCESS    not-accessible
	STATUS    mandatory
		--% ALIAS "Fan Status Table Entry"
	DESCRIPTION
		"Status information on a single fan, i.e., an entry in
the Fan Status table.   (See the previous variable, Fan Status
Table, for an explanation of this table.)
You cannot access this variable; it is only a table marker in the
MIB.  The following variables are entries in the table:

Fan Status Table Index
Fan Status"
	INDEX	{ riLdcFanIndex }
	::={ riLdcFanTable 1 }

RiLdcFanEntry ::= SEQUENCE {
					riLdcFanIndex
						INTEGER,
					riLdcFanStatus
						INTEGER
				}

riLdcFanIndex OBJECT-TYPE
	SYNTAX    INTEGER
	ACCESS    read-only
	STATUS    mandatory
		--% ALIAS "Fan Status Table Index"
		--% GROUP Fan-Status-Table
	DESCRIPTION
		"A unique value for each Fan Status Table entry.  The
value ranges from 1 to the value of Fan Status Entries.  The fans
are numbered from left to right as you are facing the chassis."
	::={ riLdcFanEntry 1 }

riLdcFanStatus OBJECT-TYPE
	SYNTAX    INTEGER {
					off(81),
					on(82),
					other(200)
				}
	ACCESS    read-only
	STATUS    mandatory
		--% ALIAS "Fan Status"
		--% GROUP Fan-Status-Table
	DESCRIPTION
		"The status of the fan.  This variable returns on(82) if
the fan is operating, and off(81) if it is not operating."
	::={ riLdcFanEntry 2 }

-- ***************************************
--
--  RI NMM Hot Fail Group
--
-- ***************************************
--
--
--       INX-NMM Hot     This group contains all the variables that
--       Failover Group  relate to recovery from network
--                       component failures.  The first eight
--                       variables in the group make up your primary
--                       and backup backbone connectivity module
--                       configuration.  The remaining variables allow
--                       you to enable/disable and monitor the status
--                       of the Hot Failover Algorithm.

riLdcHfAPrimaryAui OBJECT-TYPE
	SYNTAX    INTEGER
	ACCESS    read-write
	STATUS    mandatory
		--% ALIAS "Bus A Primary Backbone Slot Number"
		--% GROUP Hot-Fail-Table
	DESCRIPTION
		"The number of the slot in which the primary Bus A
backbone connectivity module for the chassis is installed.(CMM Slot
is recommended)"
	::={ riHotFail 1 }

riLdcHfAPrimaryMedia OBJECT-TYPE
	SYNTAX    INTEGER {
			backbone-thick(11),
			backbone-thin(12),
			backbone-fiber(13)
			}
	ACCESS    read-write
	STATUS    mandatory
		--% ALIAS "Bus A Primary Backbone Media"
		--% GROUP Hot-Fail-Table
	DESCRIPTION
		"The media type of the primary Bus A backbone
connectivity module for the chassis.  This variable returns
backbone-thick(11) if the module is configured to be connected to
the backbone network via a transceiver cable; backbone-thin(12) if
the module is configured to be connected to the backbone via a Thin
Ethernet coaxial cable; and backbone-fiber(13) if it is configured
for connection to the backbone via fiber-optic cabling."
	::={ riHotFail 2 }

riLdcHfBPrimaryAui OBJECT-TYPE
	SYNTAX    INTEGER
	ACCESS    read-write
	STATUS    mandatory
		--% ALIAS "Bus B Primary Backbone Slot Number"
		--% GROUP Hot-Fail-Table
	DESCRIPTION
		"The number of the slot in which the primary Bus B
backbone connectivity module for the chassis is installed.  You can
set this variable to not configured(200) if you do not want a
backup configuration for Bus B.
You cannot set this variable to the slot number of the INX-CMM."
	::={ riHotFail 3 }

riLdcHfBPrimaryMedia OBJECT-TYPE
	SYNTAX    INTEGER {
			backbone-thick(11),
			backbone-thin(12),
			backbone-fiber(13)
			}
	ACCESS    read-write
	STATUS    mandatory
		--% ALIAS "Bus B Primary Backbone Media"
		--% GROUP Hot-Fail-Table
	DESCRIPTION
		"The media type of the primary Bus B backbone
connectivity module for the chassis.  This variable returns
backbone-thick(11) if the module is configured to be connected to
the backbone netswork via a transceiver cable; 
backbone-thin(12) if the module is configured to be connected to
the backbone via a Thin Ethernet coaxial cable; and
backbone-fiber(13) if it is configured for connection to the
backbone via fiber-optic cabling."
	::={ riHotFail 4 }

riLdcHfABackupAui OBJECT-TYPE
	SYNTAX    INTEGER
	ACCESS    read-write
	STATUS    mandatory
		--% ALIAS "Bus A Backup Backbone Slot Number"
		--% GROUP Hot-Fail-Table
	DESCRIPTION
		"The number of the slot in which the backup Bus A
backbone connectivity module for the chassis is installed.
Note:  If you do not want to enable hot failover, but want to know
when an event that would have caused it occurs, you can set this
variable and Bus A Primary Backbone Slot # to the same value, 
and Bus A Primary Backbone Media and Bus A Backup Backbone Media to 
the same value.  Hot failover will not occur, but if there is a 
failure of a network component, the Hot Failover trap is generated 
(if it can be transmitted on the network)."

	::={ riHotFail 5 }

riLdcHfABackupMedia OBJECT-TYPE
	SYNTAX    INTEGER {
			backbone-thick(11),
			backbone-thin(12),
			backbone-fiber(13)
			}
	ACCESS    read-write
	STATUS    mandatory
		--% ALIAS "Bus A Backup Backbone Media"
		--% GROUP Hot-Fail-Table
	DESCRIPTION
		"The media type of the backup Bus A backbone connectivity
module for the chassis.  This variable returns backbone-thick(11)
if the module is configured to be connected to the backbone
netswork via a transceiver cable; backbone-thin(12) if the module
is configured to be connected to the backbone via a Thin Ethernet
coaxial cable; and backbone-fiber(13) if it is configured for
connection to the backbone via fiber-optic cabling."
	::={ riHotFail 6 }

riLdcHfBBackupAui OBJECT-TYPE
	SYNTAX    INTEGER
	ACCESS    read-write
	STATUS    mandatory
		--% ALIAS "Bus B Backup Backbone Slot Number"
		--% GROUP Hot-Fail-Table
	DESCRIPTION
		"The number of the slot in which the backup Bus B
backbone connectivity module for the chassis is installed.  You can
set this variable to not-configured(200) if you do not want a
backup configuration slot number for Bus B.
You cannot set this variable to the slot number of the INX-CMM."
	::={ riHotFail 7 }

riLdcHfBBackupMedia OBJECT-TYPE
	SYNTAX    INTEGER {
			backbone-thick(11),
			backbone-thin(12),
			backbone-fiber(13)
			}
	ACCESS    read-write
	STATUS    mandatory
		--% ALIAS "Bus B Backup Backbone Media"
		--% GROUP Hot-Fail-Table
	DESCRIPTION
		"The media type of the backup Bus B backbone connectivity
module for the chassis.  This variable returns backbone-thick(11)
if the module is configured to be connected to the backbone
netswork via a transceiver cable; backbone-thin(12) if the module
is configured to be connected to the backbone via a Thin Ethernet
coaxial cable; and backbone-fiber(13) if it is configured for
connection to the backbone via fiber-optic cabling."
	::={ riHotFail 8 }

riLdcHfIntState OBJECT-TYPE
	SYNTAX    INTEGER {
			enabled(1),
			disabled(2),
			dis-no-A-config(3),
			dis-no-B-config(4),
                        dis-A-B-conflict(5),
                        dis-zero-frequency(6),
                        dis-no-backbone(7)
			}
	ACCESS    read-write
	STATUS    mandatory
		--% ALIAS "Internal Failover Detection"
		--% GROUP Hot-Fail-Table
	DESCRIPTION
		"The current state of internal hot failover detection for
both Bus A and Bus B.  Setting this variable to enabled(1) invokes
internal hot failover detection/monitoring and enables the chassis
to the primary hot failover configuration.
To modify the internal polling frequency or the internal retry
limit, you must first set this variable to disabled(2), make the
modification (with the Internal Polling Frequency or Maximum
Polling Retries variable), and then set this variable to
enabled(1).  Under certain conditions, enabling can fail; when this
happens, a General Error status is returned. 
(Refer to the ASN file, Racal-INXNMM for detailed error definitions)"
-- One of the following values is returned following a General Error:
-- dis-no-A-config(3) is returned when either the primary or backup
-- configuration for Bus A contains an invalid slot number. See the
-- Bus A Primary Backbone Slot # and Bus A Backup Backbone Slot #
-- variables.
-- dis-no-B-config(4) is returned when only one NMM is found in the
-- chassis and its NIC is configured for Bus B and the Bus B Hot
-- Failover configuration is NONE for the Primary and Backup Backbone
-- Slot Numbers.
-- dis-A-B-conflict(5) is returned when the primary slot number for
-- Bus A is identical to either the Bus B primary slot number or the
-- Bus B backup slot number.  See the Bus A Primary Backbone Slot #,
-- Bus B Primary Backbone Slot #, and Bus B Backup Backbone Slot #
-- variables.
-- dis-zero-frequency(6) is returned when the polling frequency is set
-- to 0.  See the Internal Polling Frequency variable.
-- dis-no-backbone(7) is returned when the slot listed in the
-- configuration does not have a backbone connectivity module in it.
-- See the Bus A Primary Backbone Slot #, Bus A Backup Backbone Slot
-- #, Bus B Primary Backbone Slot #, and Bus B Backup Backbone Slot# variables.
	::={ riHotFail 9 }

riLdcHfIntPollFreq OBJECT-TYPE
	SYNTAX    INTEGER (1..255)
	ACCESS    read-write
	STATUS    mandatory
		--% ALIAS "Internal Polling Frequency"
		--% GROUP Hot-Fail-Table
	DESCRIPTION
		"The frequency, in seconds, with which the INX-NMM master
and slave modules attempt to transmit a self-addressed packet onto
the bus for which their NIC is configured (i.e., the communication
bus).  The range of valid values is 1-255 seconds, and the default
is 60 seconds."
	::={ riHotFail 10 }

riLdcHfIntRetries OBJECT-TYPE
	SYNTAX    INTEGER (1..255)
	ACCESS    read-write
	STATUS    mandatory
		--% ALIAS "Internal Maximum Polling Retries"
		--% GROUP Hot-Fail-Table
	DESCRIPTION
		"The number of polling transmits (see the previous
variable, Internal Polling Frequency) that must fail before
internal failover is invoked.  The range of valid values is 1 -
255, and the default is 3."
	::={ riHotFail 11 }

riLdcHfExtState OBJECT-TYPE
	SYNTAX    INTEGER {
			enabled(1),
			disabled(2),
			dis-no-A-config(3),
			dis-no-B-config(4),
                        dis-A-B-conflict(5),
                        dis-zero-frequency(6),
                        dis-no-backbone(7),
                        dis-zero-p1-addr(8), 
                        dis-wrong-ext-bus(9)
			}
	ACCESS    read-write
	STATUS    mandatory
		--% ALIAS "External Failover Detection State"
		--% GROUP Hot-Fail-Table
	DESCRIPTION
		"The current state of external hot failover detection. 
External hot failover detection is only available for the bus on
which the master INX-NMM's NIC is configured.  Setting this
variable to enabled(1) invokes external hot failover
detection/monitoring.
In addition to the status returned by the riLdcHfIntState object,
the following two failures descriptions are returned if an
enable(1) fails with a General Error.
dis-zero-p1-addr(8) is returned when the  Ping 1 address is set to
0.0.0.0.  See the Ext Failover Detection/Ping 1 variable.
dis-wrong-ext-bus(9) is returned when the master NIC is on Bus B
and the primary or backup configuration for Bus B is invalid.  See
the Bus B Primary Backbone Slot #, Bus B Backup Backbone Slot #,
Bus B Primary Backbone Media, and Bus B Backup Backbone Media
variables."
	::={ riHotFail 12 }

riLdcHfExtPing1 OBJECT-TYPE
	SYNTAX    IpAddress
	ACCESS    read-write
	STATUS    mandatory
		--% ALIAS "External Failover Detection/Ping 1"
		--% GROUP Hot-Fail-Table
	DESCRIPTION
		"The IP adress of the node to which the master INX-NMM
will ping to detect external cable failures.  The master INX-NMM
wil send the pings on the bus for which its NIC is configured. 
Only that bus can have external hot failure detection in use.
Setting this value to 0.0.0.0 disables external hot failover
detection by making it impossible to set External Failover
Detection to enabled."
	::={ riHotFail 13 }

riLdcHfExtPing2 OBJECT-TYPE
	SYNTAX	  IpAddress
	ACCESS    read-write
	STATUS    mandatory
		--% ALIAS "External Failover Detection/Ping 2"
		--% GROUP Hot-Fail-Table
	DESCRIPTION 
                " The IP address of a second node to ping should
the first host not respond (see the previous variable, Ext Failover
Detection/Ping 1).  This eliminates the false hot failover
detections that occur when the ping1 host is rebooting at the time
the ping is made.  
The INX-NMM only tries to ping this address once the ping address
reverts to the one specified by Ext Failover Detection/Ping 1.  As
with Ext Failover Detection/Ping1, set this variable to the address
of the node to which the master INX-NMM will ping to detect
external cable failures.  
The master INX-NMM sends the pings on the bus for which its NIC is
configured (i.e., the value of Logic Module Bus).
If you set this variable to 0.0.0.0, external hot failover
detection is enabled, but only Ext Failover Detection/Ping1 is
used."
	::={ riHotFail 14 }

riLdcHfExtPollFreq OBJECT-TYPE
	SYNTAX    INTEGER (1..255)
	ACCESS    read-write
	STATUS    mandatory
		--% ALIAS "External Ping Frequency"
		--% GROUP Hot-Fail-Table
	DESCRIPTION " The frequency, in seconds, with which the master
INX-NMM pings the address specified by Ext Failover Detection/Ping
1 or Ext Failover Detection/Ping 2.  The range of valid values is
1 - 255 seconds, and the default is 15 seconds."

	::={ riHotFail 15 }

riLdcHfExtResponseTmo OBJECT-TYPE
	SYNTAX    INTEGER (1..60)
	ACCESS    read-write
	STATUS    mandatory
		--% ALIAS "Ping Response Timeout"
		--% GROUP Hot-Fail-Table
	DESCRIPTION " The number of seconds the INX-NMM waits for a
response to the ping before the ping is considered failed.  The
range of valid values is 1 - 60 seconds, and the default is three
seconds."
	::={ riHotFail 16 }

riLdcHfExtRetries OBJECT-TYPE
	SYNTAX    INTEGER (1..255)
	ACCESS    read-write
	STATUS    mandatory
		--% ALIAS "Ping Retries"
		--% GROUP Hot-Fail-Table
	DESCRIPTION " The number of pings to the host specified by Ext
Failover Detection/Ping 1 that must fail before external failover
is invoked.  The range is 1 - 255, and the default is 3."
	::={ riHotFail 17 }

riLdcHfHysteresis OBJECT-TYPE
	SYNTAX    INTEGER (1..3600)
	ACCESS    read-write
	STATUS    mandatory
		--% ALIAS "Hysteresis Count"
		--% GROUP Hot-Fail-Table
	DESCRIPTION " The number of seconds required between failovers
from the backup configuration to the primary configuration. This
hysteresis time eliminates the continuous hot failing from one
network to another that can occur if there is an intermittent failure 
on one of the networks.  There is no hysteresis time when failing the
primary configuration to the backup configuration."
	::={ riHotFail 18 }

riLdcHfTable OBJECT-TYPE
	SYNTAX    SEQUENCE OF RiLdcHfEntry
	ACCESS    not-accessible
	STATUS    mandatory
		--% ALIAS "Hot Failover Status Table"
	DESCRIPTION "  The Hot Failover Status table contains
information on the hot failover status of each internal bus."
	::={ riHotFail 19 }

riLdcHfEntry OBJECT-TYPE
	SYNTAX    RiLdcHfEntry
	ACCESS    not-accessible
	STATUS    mandatory
		--% ALIAS "Hot Fail Entry"
	DESCRIPTION
		"Statistical information for the Hot Failover functions.
(See the previous variable, Hot Fail Table, for an explanation of
this table.)

Hot Failover Status Index
Current Configuration
Time of Last Failover
Internal Failover Count
External Failover Count
Primary Config Failover Cause
Backup Config Failover Cause
Internal Transmit Status
Internal Transmit Failures
AUI Autopartition Status
Bus Autopartitions
Bus Clock Status
Bus Clock Failures
Configuration Status
Configuration Changes
Ping 1 Host Status
Ping 1 Host Failures
Ping 2 Host Status
Ping 2 Host Failures"
	INDEX	{ riLdcHfIndex }
	::={ riLdcHfTable 1 }

RiLdcHfEntry ::= SEQUENCE {
			riLdcHfIndex
				INTEGER,
			riLdcHfPrimBkupState
				INTEGER,
			riLdcHfLastFailover
				TimeTicks,
			riLdcHfIntFailovers
				Counter,
			riLdcHfExtFailovers
				Counter,
			riLdcHfPrimReason
				INTEGER,
			riLdcHfBkupReason
				INTEGER,
			riLdcHfIntTxStatus
				INTEGER,
			riLdcHfIntTxFailures
				Counter,
			riLdcHfAutopartState
				INTEGER,
			riLdcHfBusAutopartitions
				Counter,
			riLdcHfBusClockStatus
				INTEGER,
			riLdcHfBusClockFailures
				Counter,
			riLdcHfBusConfigStatus
				INTEGER,
			riLdcHfBusConfigChanges
				Counter,
			riLdcHfExtPing1Status
				INTEGER,
			riLdcHfExtPing1Failures
				Counter,
			riLdcHfExtPing2Status
				INTEGER,
			riLdcHfExtPing2Failures
				Counter
			}

riLdcHfIndex OBJECT-TYPE
	SYNTAX    INTEGER (1..2)
	ACCESS    read-only
	STATUS    mandatory
		--% ALIAS "Hot Failover Status Index"
		--% GROUP Hot-Fail-Status
	DESCRIPTION " A unique value for each bus entry in the Hot
Failover Status table, i.e., Bus A or Bus B.  This variable returns
1 for Bus A and 2 for Bus B."
	::={ riLdcHfEntry 1 }


riLdcHfPrimBkupState OBJECT-TYPE
	SYNTAX    INTEGER {
			using-prim-config(1),
			using-bkup-config(2),
			not-in-use(200)
			}
	ACCESS    read-only
	STATUS    mandatory
		--% ALIAS "Current Configuration"
		--% GROUP Hot-Fail-Status
	DESCRIPTION " Whether this bus is currently operating with its
primary configuration or its backup configuration.  The returned
value of this variable depends on the settings of the first eight
variables in the Hot Failover group:  Bus A Primary Backbone Slot #, 
Bus A Primary Backbone Media, Bus B Primary Backbone Slot #, Bus B 
Primary Backbone Media, Bus A Backup Backbone Slot #, Bus A Backup 
Backbone Media, Bus B Backup Backbone Slot #, and Bus B Backup Backbone Media.
This variable returns not-in-use(200) if both internal and external
hot failover detection are disabled for this bus, or if there is
a problem in the configuration for the bus, which might be due to
contradictory settings of some of the variables 
in the Hot Failover group."
	::={ riLdcHfEntry 2 }

riLdcHfLastFailover OBJECT-TYPE
	SYNTAX    TimeTicks
	ACCESS    read-only
	STATUS    mandatory
		--% ALIAS "Time of Last Failover"
		--% GROUP Hot-Fail-Status
	DESCRIPTION " The value of INX-NMM Up Time (the sysUpTime
variable in the System group for the INX-NMM) at the time the last
failover for this bus occurred.  By subtracting this value from the
current INX-NMM UP Time value, you can tell how long ago the failover 
occurred."
	::={ riLdcHfEntry 3 }

riLdcHfIntFailovers OBJECT-TYPE
	SYNTAX    Counter
	ACCESS    read-only
	STATUS    mandatory
		--% ALIAS "Internal Failover Count"
		--% GROUP Hot-Fail-Status
	DESCRIPTION " The number of internal hot failovers invoked for
this bus since the last boot of the INX-NMM."
	::={ riLdcHfEntry 4 }

riLdcHfExtFailovers OBJECT-TYPE
	SYNTAX    Counter
	ACCESS    read-only
	STATUS    mandatory
		--% ALIAS "External Failover Count"
		--% GROUP Hot-Fail-Status
	DESCRIPTION "The number of external hot failovers invoked for
this bus since the last boot of the INX-NMM."
	::={ riLdcHfEntry 5 }

riLdcHfPrimReason OBJECT-TYPE
	SYNTAX    INTEGER {
			nofailover(1),
			autopartitioned(3),
			bus-clock-failure(4),
			internal-tx-failure(5),
			external-ping-failure(6),
			config-change(7)
			}
	ACCESS    read-only
	STATUS    mandatory
		--% ALIAS "Primary Config Failover Cause"
		--% GROUP Hot-Fail-Status
	DESCRIPTION " The reason that an initial failover or automatic
configuration change was invoked following a fault detected in the
primary configuration.  This variable returns nofailover(1) if no
failover has occurred or if the bus is not configured.  It returns 
autopartitioned(3) if the reason for the failure is that the bus backbone 
module has autopartitioned, bus-clock-failure(4) if the cause is an internal
chassis bus clock failure, internal-tx-failure(5) if the cause
is an internal transmit failure, external-ping-failure(6) if the
cause is the failure of a ping attempt, and config-change(7) if the
backbone modules had to be reset during the current configuration
if another backbone was enabled by a means other than hot failover 
(for example, with the Connectivity Module Bus variable)."
	::={ riLdcHfEntry 6 }

riLdcHfBkupReason OBJECT-TYPE
	SYNTAX    INTEGER {
			nofailover(1),
			autopartitioned(3),
			bus-clock-failure(4),
			internal-tx-failure(5),
			external-ping-failure(6),
			config-change(7)
			}
	ACCESS    read-only
	STATUS    mandatory
		--% ALIAS "Backup Config Failover Cause"
		--% GROUP Hot-Fail-Status
	DESCRIPTION " The reason that an initial failover or automatic
Bacbone re-configuration was invoked following a fault detected in
the backup configuration.  This variable returns nofailover(1) if
no failover has occurred or if the bus is not configured.
It returns autopartitioned(3) if the reason for the failure is that
the bus backbone module has autopartitioned, bus-clock-failure(4)
if the cause is an internal chassis bus clock failure,
internal-tx-failure(5) if the cause is an internal transmit failure, 
external-ping-failure(6) if the cause is the failure of a ping attempt, 
and config-change(7) if the backbone modules had to be reset during the current configuration
if another backbone was enabled by a means other than hot failover 
(for example, with the Connectivity Module Bus variable)."
	::={ riLdcHfEntry 7 }

riLdcHfIntTxStatus OBJECT-TYPE
	SYNTAX    INTEGER {
			internal-bus-OK(1),
			lost-crs(2),
			excess-collisions(3),
			other-tx-error(4),
			not-in-use(200)
			}
	ACCESS    read-only
	STATUS    mandatory
		--% ALIAS "Internal Transmit Status"
		--% GROUP Hot-Fail-Status
	DESCRIPTION " This variable returns the transmit status of the
internal detection scheme for this bus.  It returns
internal-bus-OK(1) if internal transmits are succeeding and no
other bus errors are evident.  If internal transmits are not succeeding or 
there is another bus error, it returns a value that tells you what the 
problem is, i.e., lost-crs(2), excess-collisions(3), or other-tx-error(4).
If internal detection is not enabled, this variable returns
not-in-use(200)."
	::={ riLdcHfEntry 8 }

riLdcHfIntTxFailures OBJECT-TYPE
	SYNTAX    Counter
	ACCESS    read-only
	STATUS    mandatory
		--% ALIAS "Internal Transmit Failures"
		--% GROUP Hot-Fail-Status
	DESCRIPTION " The number of internal transmit failures that
have occurred on this bus since the last boot of the INX-NMM."
	::={ riLdcHfEntry 9 }

riLdcHfAutopartState OBJECT-TYPE
	SYNTAX    INTEGER {
			aui-OK(1),
			aui-autopartitioned(2),
			not-configured(200)
			}
	ACCESS    read-only
	STATUS    mandatory
		--% ALIAS "AUI Autopartition Status"
		--% GROUP Hot-Fail-Status
	DESCRIPTION " The state of the backbone connectivity module
for this bus, i.e., whether it is currently autopartitioned. This
variable returns aui-OK(1) if the module is not autopartitioned, and 
aui-autopartitioned(2) if it is.  It returns other(200) if either 
Bus B Primary Backbone Slot # or Bus B Backup Backbone Slot # is set 
to not configured(200)."
	::={ riLdcHfEntry 10 }

riLdcHfBusAutopartitions OBJECT-TYPE
	SYNTAX    Counter
	ACCESS    read-only
	STATUS    mandatory
		--% ALIAS "Bus Autopartitions"
		--% GROUP Hot-Fail-Status
	DESCRIPTION " The number of times this bus has autopartitioned
since the last boot of the INX-NMM.  This count is the number of
autopartitions of the backbone connectivity module.
Note:  This count does not include any port that is connected to
this bus through a concentrator module."
	::={ riLdcHfEntry 11 }

riLdcHfBusClockStatus OBJECT-TYPE
	SYNTAX    INTEGER {
			bus-clock-ok(1),
			bus-clock-failed(2)
			}
	ACCESS    read-only
	STATUS    mandatory
		--% ALIAS "Bus Clock Status"
		--% GROUP Hot-Fail-Status
	DESCRIPTION " The status of this bus's master clock, which is
provided by the backbone connectivity module.  This variable
returns busclockok(1) if the clock is functioning normally, and
busclockfailed(2) if it is not."
	::={ riLdcHfEntry 12 }

riLdcHfBusClockFailures OBJECT-TYPE
	SYNTAX    Counter
	ACCESS    read-only
	STATUS    mandatory
		--% ALIAS "Bus Clock Failures"
		--% GROUP Hot-Fail-Status
	DESCRIPTION " The number times this bus's clock has failed
since the last reboot of the INX-NMM."
	::={ riLdcHfEntry 13 }

riLdcHfBusConfigStatus OBJECT-TYPE
	SYNTAX    INTEGER {
                          config-ok(1),
                          two-backbones-enabled(2),
                          no-backbones-enabled(3)
                          }
	ACCESS    read-only
	STATUS    mandatory
		--% ALIAS "Configuration Status"
		--% GROUP Hot-Fail-Status
	DESCRIPTION " The current status of the backbone connectivity
module's configuration."
	::={ riLdcHfEntry 14 }

riLdcHfBusConfigChanges OBJECT-TYPE
	SYNTAX    Counter
	ACCESS    read-only
	STATUS    mandatory
		--% ALIAS "Configuration ChangesStatus"
		--% GROUP Hot-Fail-Status
	DESCRIPTION " The number of times the backbone modules were
reconfigured to the primary configuration because a mismatch of
that configuration with the actual physical backbone configuration
or an illegal configuration was detected. Hot Failover detects this 
change and fails to the primary configuration."
	::={ riLdcHfEntry 15 }

riLdcHfExtPing1Status OBJECT-TYPE
	SYNTAX    INTEGER {
			external-bus-OK(1),
			host-unreachable(2),
			not-configured(200)
			}
	ACCESS    read-only
	STATUS    mandatory
		--% ALIAS "Ping 1 Host Status"
		--% GROUP Hot-Fail-Status
	DESCRIPTION " The ping 1 host (i.e., the value of Ext Failover
Det'n/Ping 1 Addr) status for the external detection scheme.  This
variable returns external-bus-OK(1) if the INX-NMM is able to ping
the external host, and host-unreachable(2) if it cannot. 
If external failover detection is not enabled, this variable returns 
not-in-use(200)."
	::={ riLdcHfEntry 16 }

riLdcHfExtPing1Failures OBJECT-TYPE
	SYNTAX    Counter
	ACCESS    read-only
	STATUS    mandatory
		--% ALIAS "Ping 1 Host Failures"
		--% GROUP Hot-Fail-Status
	DESCRIPTION " The number of ping 1 host (i.e.,the value of Ext
Failover Det'n/Ping 1 Addr) status failures for the external
detection scheme since the last boot of the INX-NMM."
	::={ riLdcHfEntry 17 }

riLdcHfExtPing2Status OBJECT-TYPE
	SYNTAX    INTEGER {
			external-bus-OK(1),
			host-unreachable(2),
			not-configured(200)
			}
	ACCESS    read-only
	STATUS    mandatory
		--% ALIAS "Ping 2 Host Status"
		--% GROUP Hot-Fail-Status
	DESCRIPTION " The ping 2 host (i.e., the value of Ext Failover
Det'n/Ping 2 Addr) status for the external detection scheme.  This
variable returns external-bus-OK(1) if the INX-NMM is able to ping
the external host, and host-unreachable(2) if it cannot.  If external 
failover detection is not enabled, or if Ext Failover Detection/Ping 2 
is set to 0.0.0.0, this variable returns not-in-use(200)."
	::={ riLdcHfEntry 18 }

riLdcHfExtPing2Failures OBJECT-TYPE
	SYNTAX    Counter
	ACCESS    read-only
	STATUS    mandatory
		--% ALIAS "Ping 2 Host Failures"
		--% GROUP Hot-Fail-Status
	DESCRIPTION " The number of ping 2 (i.e., the value of Ext
Failover Det'n/Ping 2 Addr) host status failures for the external
detection scheme since the last boot of the INX-NMM."
	::={ riLdcHfEntry 19 }

-- ***************************************
--
--  RI Ethernet Port Group
--
-- ***************************************

riPortTable OBJECT-TYPE
	SYNTAX    SEQUENCE OF RiPortEntry
	ACCESS    not-accessible
	STATUS    mandatory
		--% ALIAS "Port Table"
	DESCRIPTION
		"Statistical information about the INX-10BT and INX-FOIRL
module ports.
You cannot access this variable; it is only a table marker in the MIB.
Note:  If there is no INX-10BT or INX-FOIRL module in the slot for
which you are trying to get information, that slot is not
accessible and the variable returns ;MIB Object Not Found."
	::={ riPort 1 }

riPortEntry OBJECT-TYPE
	SYNTAX    RiPortEntry
	ACCESS    not-accessible
	STATUS    mandatory
		--% ALIAS "Port Table Entry"
	DESCRIPTION
		"Statistical information for a single Ethernet port,
i.e., an entry in the Port table.  (See the previous variable, Port
Table, for an explanation of this table.)
You cannot access this variable; it is only a table marker in the
MIB.  The following variables are entries in the table:

Slot Number
Port Number
Port State
Frames Rec'd
Frames Rec'd Rate
Octets Rec'd
Octets Rec'd Rate
Multicast Frames Rec'd
Multicast Frames Rec'd Rate
Broadcast Frames Rec'd
Broadcast Frames Rec'd Rate
Collisions
Collisions Rate
CRC Errored Frames Rec'd
CRC Errored Frames Rec'd Rate
Short Frames Rec'd
Short Frames Rec'd Rate
In-Range Errors Rec'd
In-Range Errors Rec'd Rate
Out-Range Errors Rec'd
Out-Range Errors Rec'd Rate
Too Long Frames Rec'd
Too Long Frames Rec'd Rate
Nonaligned Frames Rec'd
Nonaligned Frames Rec'd Rate
Autopartitions
Autopartitions Rate
Transmit Clock Violations
Transmit Clock Violations Rate
Last Good Source Address
Source Address Changes
Source Address Changes Rate
Link Disconnects
Link Disconnects Rate
Late Collision Count
Late Collision Rate
Jabber Lockups
Jabber Lockups Rate
Port Link Status"
	INDEX	{ riPortSlotNumber, riPortPortNumber }
	::={ riPortTable 1 }

RiPortEntry ::= SEQUENCE {
					riPortSlotNumber
						INTEGER,
					riPortPortNumber
						INTEGER,
					riPortState
						INTEGER,
					riPortFramesReceivedOK
						Counter,
					riPortFramesReceivedOKRate
						Gauge,
					riPortOctetsReceivedOK
						Counter,
					riPortOctetsReceivedOKRate
						Gauge,
					riPortMulticastFramesReceivedOK
						Counter,
					riPortMulticastFramesReceivedOKRate
						Gauge,
					riPortBroadcastFramesReceivedOK
						Counter,
					riPortBroadcastFramesReceivedOKRate
						Gauge,
					riPortCollisions
						Counter,
					riPortCollisionsRate
						Gauge,
					riPortCRCErrors
						Counter,
					riPortCRCErrorsRate
						Gauge,
					riPortShortFrames
						Counter,
					riPortShortFramesRate
						Gauge,
					riPortInRangeLengthErrors
						Counter,
					riPortInRangeLengthErrorsRate
						Gauge,
					riPortOutOfRangeLengthErrors
						Counter,
					riPortOutOfRangeLengthErrorsRate
						Gauge,
					riPortFramesTooLong
						Counter,
					riPortFramesTooLongRate
						Gauge,
					riPortAlignmentErrors
						Counter,
					riPortAlignmentErrorsRate
						Gauge,
					riPortAutoPartitions
						Counter,
					riPortAutoPartitionsRate
						Gauge,
					riPortTransmitClockViolations
						Counter,
					riPortTransmitClockViolationsRate
						Gauge,
					riPortLastSourceAddress
						OCTET STRING,
					riPortSourceAddressChanges
						Counter,
					riPortSourceAddressChangesRate
						Gauge,
					riPortLinkIntegrityChanges
						Counter,
					riPortLinkIntegrityChangesRate
						Gauge,
					riPortLateCollisions
						Counter,
					riPortLateCollisionsRate
						Gauge,
					riPortMauJabberLockups
						Counter,
					riPortMauJabberLockupsRate
						Gauge,
					riPortLinkStatus
						INTEGER
				}

riPortSlotNumber OBJECT-TYPE
	SYNTAX    INTEGER
	ACCESS    read-only
	STATUS    mandatory
		--% ALIAS "Slot Number"
		--% GROUP Port-Table
	DESCRIPTION
		"A unique value for each slot in the chassis that
contains an INX-10BT or INX-FOIRL module.  Values range from 1 to
n, where n is the maximum number of INX-10BT and INX-FOIRL modules
that can be contained in a single chassis.  This variable
identifies the slot in the chassis that contains the media module
that contains the port.

Values are only returned for slots containing INX-10BT and
INX-FOIRL modules."
	::={ riPortEntry 1 }

riPortPortNumber OBJECT-TYPE
	SYNTAX    INTEGER (1..12)
	ACCESS    read-only
	STATUS    mandatory
		--% ALIAS "Port Number"
		--% GROUP Port-Table
	DESCRIPTION
		"A unique value for each port on the INX-10BT or
INX-FOIRL module that contains this port.  The value ranges from
1 to n, where n is the total number of ports on the module."
	::={ riPortEntry 2 }

riPortState OBJECT-TYPE
	SYNTAX    INTEGER {
					auto-partitioned(3),
					enabled(4),
					disabled(5),
					other(200),
					empty(41)
				}
	ACCESS    read-write
	STATUS    mandatory
		--% ALIAS "Port State"
		--% GROUP Port-Table
	DESCRIPTION
		"The state of the port.

o empty(41) indicates that there is nothing in the slot.  You
  cannot set the variable to this value
o auto-partitioned(3) indicates that the port has auto-partitioned.
o enabled(4) indicates that frames can pass through the port.
o disabled(5) indicates that the port is turned off - no frames are
  allowed to pass through the port.
o other(200) indicates that the port is not in any of the other
  three states.  You cannot set the variable to this value.

You can only set this variable to enabled(4) or disabled(5).  If
you try to access a slot not containing an INX-10BT or INX-FOIRL
module, you receive an object not found error message."
	::={ riPortEntry 3 }

riPortFramesReceivedOK OBJECT-TYPE
	SYNTAX    Counter
	ACCESS    read-only
	STATUS    mandatory
		--% ALIAS "Frames Rec'd"
		--% GROUP Port-Table
	DESCRIPTION
		"The number of frames successfully received through this
port.  This count does not include frames received with FCS,
length, or alignment errors, or frames lost due to internal
errors."
	::={ riPortEntry 4 }

riPortFramesReceivedOKRate OBJECT-TYPE
	SYNTAX    Gauge 
	ACCESS    read-only
	STATUS    mandatory
		--% ALIAS "Frames Rec'd Rate"
		--% GROUP Port-Table
	DESCRIPTION
		"The rate of frames/sec that have been successfully
received through this port.  This count does not include frames
received with FCS, length, or alignment errors, or frames lost due
to internal errors."
	::={ riPortEntry 5 }

riPortOctetsReceivedOK OBJECT-TYPE
	SYNTAX    Counter
	ACCESS    read-only
	STATUS    mandatory
		--% ALIAS "Octets Rec'd"
		--% GROUP Port-Table
	DESCRIPTION
		"The number of octets associated with the frames included
in Frames Received."
	::={ riPortEntry 6 }

riPortOctetsReceivedOKRate OBJECT-TYPE
	SYNTAX    Gauge 
	ACCESS    read-only
	STATUS    mandatory
		--% ALIAS "Octets Rec'd Rate"
		--% GROUP Port-Table
	DESCRIPTION
		"The rate of octets/sec associated with the frames
included in Frames Received."
	::={ riPortEntry 7 }

riPortMulticastFramesReceivedOK OBJECT-TYPE
	SYNTAX    Counter
	ACCESS    read-only
	STATUS    mandatory
		--% ALIAS "Multicast Frames Rec'd"
		--% GROUP Port-Table
	DESCRIPTION
		"The number of frames that had a multicast destination
address sent by the device attached to this port."
	::={ riPortEntry 8 }

riPortMulticastFramesReceivedOKRate OBJECT-TYPE
	SYNTAX    Gauge
	ACCESS    read-only
	STATUS    mandatory
		--% ALIAS "Multicast Frames Rec'd Rate"
		--% GROUP Port-Table
	DESCRIPTION
		"The rate of frames/sec sent by the device attached to
this port that had a multicast destination address."
	::={ riPortEntry 9 }

riPortBroadcastFramesReceivedOK OBJECT-TYPE
	SYNTAX    Counter
	ACCESS    read-only
	STATUS    mandatory
		--% ALIAS "Broadcast Frames Rec'd"
		--% GROUP Port-Table
	DESCRIPTION
		"The number of frames that had a broadcast destination
address sent by the device attached to this port."
	::={ riPortEntry 10 }

riPortBroadcastFramesReceivedOKRate OBJECT-TYPE
	SYNTAX    Gauge 
	ACCESS    read-only
	STATUS    mandatory
		--% ALIAS "Broadcast Frames Rec'd Rate"
		--% GROUP Port-Table
	DESCRIPTION
		"The rate of frames/sec sent by the device attached to
this port that had a broadcast destination address."
	::={ riPortEntry 11 }

riPortCollisions  OBJECT-TYPE
	SYNTAX    Counter
	ACCESS    read-only
	STATUS    mandatory
		--% ALIAS "Collisions"
		--% GROUP Port-Table
	DESCRIPTION
		"The number of collisions within 512 bit times from frame
start detected when the device attached to this port attempted to
transmit.  (Collisions are normal for networks with high
utilization.)"
	::={ riPortEntry 12 }

riPortCollisionsRate  OBJECT-TYPE
	SYNTAX    Gauge 
	ACCESS    read-only
	STATUS    mandatory
		--% ALIAS "Collisions Rate"
		--% GROUP Port-Table
	DESCRIPTION
		"The rate of collisions/sec within 512 bit times from
frame start detected when the device attached to this port
attempted to transmit."
	::={ riPortEntry 13 }

riPortCRCErrors  OBJECT-TYPE
	SYNTAX    Counter
	ACCESS    read-only
	STATUS    mandatory
		--% ALIAS "CRC Errored Frames Rec`d"
		--% GROUP Port-Table
	DESCRIPTION
		"The number of frames sent by the device attached to this
port that are an integral number of octets in length (i.e., the
number of bits they contain is a multiple of eight) and do not pass
the FCS check."
	::={ riPortEntry 14 }

riPortCRCErrorsRate  OBJECT-TYPE
	SYNTAX    Gauge 
	ACCESS    read-only
	STATUS    mandatory
		--% ALIAS "CRC Errored Frames Rec'd Rate"
		--% GROUP Port-Table
	DESCRIPTION
		"The rate of frames/sec sent by the device attached to
this port that are an integral number of octets in length and do
not pass the FCS check."
	::={ riPortEntry 15 }

riPortShortFrames  OBJECT-TYPE
	SYNTAX    Counter
	ACCESS    read-only
	STATUS    mandatory
		--% ALIAS "Short Frames Rec'd"
		--% GROUP Port-Table
	DESCRIPTION
		"The number of frames sent by the device attached to this
port that are 8-63 octets long."
	::={ riPortEntry 16 }

riPortShortFramesRate  OBJECT-TYPE
	SYNTAX    Gauge 
	ACCESS    read-only
	STATUS    mandatory
		--% ALIAS "Short Frames Rec'd Rate"
		--% GROUP Port-Table
	DESCRIPTION
		"The rate of frames/sec sent by the device attached to
this port that are 8-63 octets long."
	::={ riPortEntry 17 }

riPortInRangeLengthErrors  OBJECT-TYPE
	SYNTAX    Counter 
	ACCESS    read-only
	STATUS    mandatory
		--% ALIAS "In-Range Errors Rec'd"
		--% GROUP Port-Table
	DESCRIPTION
		"The number of in-range errors sent by the device
attached to this port.  IEEE 802.3  frames contain a length field,
indicating the length of the frame.  If the value in the length
field and the actual length of the frame do not match, even if the
length of the frame is within 802.3 parameters, the receiving
device returns an in-range error.  Because the INX-NMM receives
Ethernet frames that do not have a length field, it cannot detect
this error, and this variable always returns 0."
	::={ riPortEntry 18 }

riPortInRangeLengthErrorsRate  OBJECT-TYPE
	SYNTAX    Gauge 
	ACCESS    read-only
	STATUS    mandatory
		--% ALIAS "In-Range Errors Rec'd Rate"
		--% GROUP Port-Table
	DESCRIPTION
		"The rate of in-range errors sent by the device attached
to this port.  IEEE 802.3 frames contain a length field, indicating
the length of the frame.  If the value in the length field and the
actual length of the frame do not match, even if the length of the
frame is within 802.3 parameters, the receiving device returns an
in-range error.Because the INX-NMM receives Ethernet frames that
do not have a length field, it cannot detect this error, and this
variable always returns 0."
	::={ riPortEntry 19 }

riPortOutOfRangeLengthErrors  OBJECT-TYPE
	SYNTAX    Counter 
	ACCESS    read-only
	STATUS    mandatory
		--% ALIAS "Out-Range Errors Rec'd"
		--% GROUP Port-Table
	DESCRIPTION
		"The number of out-of-range errors sent by the device
attached to this port.  IEEE 802.3 frames contain a length field,
indicating the length of the frame.  If the length of the frame is
outside of 802.3 parameters, the receiving device returns an
out-of-range error.  Because the INX-NMM receives Ethernet frames
that do not have a length field, it cannot detect this error, and
this variable always returns 0."
	::={ riPortEntry 20 }

riPortOutOfRangeLengthErrorsRate  OBJECT-TYPE
	SYNTAX    Gauge 
	ACCESS    read-only
	STATUS    mandatory
		--% ALIAS "Out-Range Errors Rec'd Rate"
		--% GROUP Port-Table
	DESCRIPTION
		"The rate of out-of-range errors sent by the device
attached to this port.  IEEE 802.3 frames contain a length field,
indicating the length of the frame.  If the length of the frame is
outside of 802.3 parameters, the receiving device returns an
out-of-range error.Because the INX-NMM receives Ethernet frames
that do not have a length field, it cannot detect this error, and
this variable always returns 0."
	::={ riPortEntry 21 }

riPortFramesTooLong  OBJECT-TYPE
	SYNTAX    Counter
	ACCESS    read-only
	STATUS    mandatory
		--% ALIAS "Too Long Frames Rec'd"
		--% GROUP Port-Table
	DESCRIPTION
		"The number of frames sent by the device attached to this
port that were greater than 1520 octets long, but not greater than
5 msec in duration (which would indicate a jabber condition)."
	::={ riPortEntry 22 }

riPortFramesTooLongRate  OBJECT-TYPE
	SYNTAX    Gauge 
	ACCESS    read-only
	STATUS    mandatory
		--% ALIAS "Too Long Frames Rec'd Rate"
		--% GROUP Port-Table
	DESCRIPTION
		"The rate of frames/sec sent by the device attached to
this port that were greater than 1520 octets long, but not greater
than 5 msec in duration (which would indicate a jabber condition)."
	::={ riPortEntry 23 }

riPortAlignmentErrors  OBJECT-TYPE
	SYNTAX    Counter
	ACCESS    read-only
	STATUS    mandatory
		--% ALIAS "Nonaligned Frames Rec'd"
		--% GROUP Port-Table
	DESCRIPTION
		"The number of frames sent by the device attached to this
port that were not an integral number of octets in length (i.e.,
the number of bits they contain is not a multiple of eight).  These
frames will not pass the FCS check but are not counted as FCS
errors."
	::={ riPortEntry 24 }

riPortAlignmentErrorsRate  OBJECT-TYPE
	SYNTAX    Gauge 
	ACCESS    read-only
	STATUS    mandatory
		--% ALIAS "Nonaligned Frames Rec'd Rate"
		--% GROUP Port-Table
	DESCRIPTION
		"The rate of frames/sec sent by the device attached to
this port that were not an integral number of octets in length. 
(These frames will not pass the FCS check but are not counted as
FCS errors.) of the INX-NMM, this variable always returns 0."
	::={ riPortEntry 25 }

riPortAutoPartitions  OBJECT-TYPE
	SYNTAX    Counter
	ACCESS    read-only
	STATUS    mandatory
		--% ALIAS "Autopartitions"
		--% GROUP Port-Table
	DESCRIPTION
		"The number of times that the port was automatically
partitioned from the network because of an error detected by the
INX-10BT or INX-FOIRL module.  Autopartitions can be caused by a
long collision (between 100 microseconds and 3 milliseconds), or
by 31 consecutive collisions (collisions shorter than 100
microseconds that occurred less than 512 bit times after frame
start)."
	::={ riPortEntry 26 }

riPortAutoPartitionsRate  OBJECT-TYPE
	SYNTAX    Gauge 
	ACCESS    read-only
	STATUS    mandatory
		--% ALIAS "Autopartitions Rate"
		--% GROUP Port-Table
	DESCRIPTION
		"The rate of times/sec that the port was automatically
partitioned from the network because of an error detected by the
INX-10BT or INX-FOIRL module."
	::={ riPortEntry 27 }

riPortTransmitClockViolations OBJECT-TYPE
	SYNTAX    Counter
	ACCESS    read-only
	STATUS    mandatory
		--% ALIAS "Transmit Clock Violations"
		--% GROUP Port-Table
	DESCRIPTION
		"The number of times that the device attached to the port
transmits, but its frame cannot be decoded by the module because
of a timing error.  The timing error is usually caused by an error
in the device's transmit logic."
	::={ riPortEntry 28 }

riPortTransmitClockViolationsRate OBJECT-TYPE
	SYNTAX    Gauge 
	ACCESS    read-only
	STATUS    mandatory
		--% ALIAS "Transmit Clock Violations Rate"
		--% GROUP Port-Table
	DESCRIPTION
		"The rate of times/sec that the device attached to the
port transmits, but its frame cannot be decoded by the module
because of a timing error.  The timing error is usually caused by
an error in the device's transmit logic."
	::={ riPortEntry 29 }

riPortLastSourceAddress OBJECT-TYPE
	SYNTAX    OCTET STRING
	ACCESS    read-only
	STATUS    mandatory
		--% ALIAS "Last Good Source Address"
		--% GROUP Port-Table
	DESCRIPTION
		"The Ethernet source address of the last uncorrupted
frame sent by the device attached to this port."
	::={ riPortEntry 30 }

riPortSourceAddressChanges OBJECT-TYPE
	SYNTAX    Counter
	ACCESS    read-only
	STATUS    mandatory
		--% ALIAS "Source Address Changes"
		--% GROUP Port-Table
	DESCRIPTION
		"The number of times the Ethernet source address of a
frame transmitted by the device attached to the port has changed
from one frame to the next frame.  If the port is attached to a
bridge, this count will be very high."
	::={ riPortEntry 31 }

riPortSourceAddressChangesRate OBJECT-TYPE
	SYNTAX    Gauge 
	ACCESS    read-only
	STATUS    mandatory
		--% ALIAS "Source Address Changes Rate"
		--% GROUP Port-Table
	DESCRIPTION
		"The rate of times/sec the Ethernet source address of a
frame transmitted by the device attached to the port has changed
from one frame to the next frame."
	::={ riPortEntry 32 }

riPortLinkIntegrityChanges OBJECT-TYPE
	SYNTAX    Counter
	ACCESS    read-only
	STATUS    mandatory
		--% ALIAS "Link Disconnects"
		--% GROUP Port-Table
	DESCRIPTION
		"The total number of times the device attached to the
port has been disconnected or reconnected.  When an INX-10BT or
INX-FOIRL module is booted, it has a link integrity of 0 for all
ports."
	::={ riPortEntry 33 }

riPortLinkIntegrityChangesRate OBJECT-TYPE
	SYNTAX    Gauge 
	ACCESS    read-only
	STATUS    mandatory
		--% ALIAS "Link Disconnects Rate"
		--% GROUP Port-Table
	DESCRIPTION
		"The rate of times the device attached to the port has
been disconnected or reconnected.  When an INX-10BT or INX-FOIRL
module is booted, it has a link integrity of 0 for all ports."
	::={ riPortEntry 34 }

riPortLateCollisions  OBJECT-TYPE
	SYNTAX    Counter
	ACCESS    read-only
	STATUS    mandatory
		--% ALIAS "Late Collision Count"
		--% GROUP Port-Table
	DESCRIPTION
		"The number of times that a collision has been detected
on this port later than 512 bit times from frame start.  A late
collision is counted twice, as both a collision and as a late
collision."
	::={ riPortEntry 35 }

riPortLateCollisionsRate  OBJECT-TYPE
	SYNTAX    Gauge 
	ACCESS    read-only
	STATUS    mandatory
		--% ALIAS "Late Collision Rate"
		--% GROUP Port-Table
	DESCRIPTION
		"The rate of the times/sec that a collision has been
detected on this port later than 512 bit times from frame start. 
A late collision is counted twice, as both a collision and as a
late collision."
	::={ riPortEntry 36 }

riPortMauJabberLockups  OBJECT-TYPE
	SYNTAX    Counter
	ACCESS    read-only
	STATUS    mandatory
		--% ALIAS "Jabber Lockups"
		--% GROUP Port-Table
	DESCRIPTION
		"The number of times the port detects that the attached
device is transmitting continuously for more than six ms."
	::={ riPortEntry 37 }

riPortMauJabberpLockupsRate  OBJECT-TYPE
	SYNTAX    Gauge 
	ACCESS    read-only
	STATUS    mandatory
		--% ALIAS "Jabber Lockups Rate"
		--% GROUP Port-Table
	DESCRIPTION
		"The rate of times/sec the port detects that the attached
device is transmitting for more than 6 ms."
	::={ riPortEntry 38 }

riPortLinkStatus OBJECT-TYPE
	SYNTAX INTEGER {
			link-status-led-on(1), 
			link-status-led-off(2),
			other(200)
			}
	ACCESS    read-only
	STATUS    mandatory
		--% ALIAS "Port Link Status"
		--% GROUP Port-Table
	DESCRIPTION
		" Whether an active device is  attached to this port.  
The device's MAU should generate a 100-ns pulse every 8 to 16 msec.  This 
pulse is detected by the INX-10BT or INX-FOIRL when it polls the port.  If 
the pulse is detected, this variable returns link-status-led-on(1). If the 
pulse is not detected, this variable returns link-status-led-off(2)."
	::={ riPortEntry 39 }

--
-- Racal Datacom Threshold Group
--
riThCount OBJECT-TYPE
     SYNTAX    Gauge
     ACCESS    read-only
     STATUS    mandatory
		--% ALIAS "Active Entries in Thresh Table"
		--% GROUP Racal-InterLan-Threshold-Group
	DESCRIPTION
		"the number of active entries in the threshold table."
     ::= { riThresh 1 }

riThMaxCount OBJECT-TYPE
     SYNTAX    INTEGER 
     ACCESS    read-only
     STATUS    mandatory
		--% ALIAS "Max Allowed Active Thresholds"
		--% GROUP Racal-InterLan-Threshold-Group
	DESCRIPTION
		"The maximum number of active thresholds allowed."
     ::= { riThresh 2 }

riThUniqueIndex OBJECT-TYPE
     SYNTAX    INTEGER
     ACCESS    read-write
     STATUS    mandatory
		--% ALIAS "Create/Read Threshold Entry"
		--% GROUP Racal-InterLan-Threshold-Group
	DESCRIPTION
		"Setting this variable creates a new entry in the
Threshold table.  You must type a number for the entry when you set
this variable, but the INX-NMM assigns the actual entry number;
that number is the one returned in the response to the set command. 
If you read this variable, it returns the number of the most
recently generated threshold entry."
     ::= { riThresh 3 }

riThInterval OBJECT-TYPE
     SYNTAX    INTEGER
     ACCESS    read-write
     STATUS    mandatory
		--% ALIAS "How Often Thresholds Checked"
		--% GROUP Racal-InterLan-Threshold-Group
	DESCRIPTION
		"How often, in seconds, thresholds exceeded are checked. 
To  disable threshold checking, set this variable to 0."
     ::= { riThresh 4 }

--
-- Threshold Table
--

riThTable OBJECT-TYPE
     SYNTAX    SEQUENCE OF RiThEntry
     ACCESS    not-accessible
     STATUS    mandatory
		--% ALIAS "Threshold Table"
	DESCRIPTION
		"A table containing information about the thresholds that
have been set.
You cannot access this variable; it is only a table marker in the
MIB."
     ::={ riThresh 5 }

riThEntry OBJECT-TYPE
     SYNTAX    RiThEntry
     ACCESS    not-accessible
     STATUS    mandatory
		--% ALIAS "Threshold Table Entry"
	DESCRIPTION
		"An entry in the Threshold table.  (See the previous
variable, Threshold Table, for an explanation of this table).
You cannot access this variable; it is only a table marker in the
MIB.  The following variables are entries in the table:

	Threshold Table Index
	Threshold Status
	Threshold Object ID
	Threshold Value
	Threshold Hysteresis
	Direction of Approach to Thresh
	Threshold Trigger Count
	Threshold Community Name
	Threshold Eth Addr Destination
	Threshold IP Addr Destination"

	INDEX	{ riThIndex }
     ::= { riThTable 1 }

RiThEntry ::= SEQUENCE {
          riThIndex
               INTEGER,
          riThStatus
               INTEGER,
	  riThObject
	       OBJECT IDENTIFIER,
	  riThThreshold
		INTEGER,
	  riThHysteresis
		INTEGER,
	  riThDirection
		INTEGER,
	  riThTriggeredCount
		Counter,
	  riThCommunity
		OCTET STRING,
	  riThPhysDestination
		OCTET STRING,
	  riThIPDestination
		IpAddress
          }                        

riThIndex OBJECT-TYPE
     SYNTAX    INTEGER
     ACCESS    read-only
     STATUS    mandatory
		--% ALIAS "Threshold Table Index"
		--% GROUP Threshold-Table
	DESCRIPTION
		"A unique value for each threshold."
     ::= { riThEntry 1 }

riThStatus OBJECT-TYPE
     SYNTAX    INTEGER {
			delete(1),
			unset(2),
			armed(3),
			safety(4)
			}
     ACCESS    read-write
     STATUS    mandatory
		--% ALIAS "Threshold Status"
		--% GROUP Threshold-Table
	DESCRIPTION
		"The current status of the threshold.
o delete(1) deletes the threshold entry specified.
o unset(2) means that the threshold is newly created, currently
  being configured, or disabled.
o armed(3) means that the threshold is active and generates a trap
  PDU when it is triggered.
o safety(4) means that the threshold is active, but does not
  generate trap PDUs."
     ::= { riThEntry 2 }

riThObject OBJECT-TYPE
     SYNTAX    OBJECT IDENTIFIER
     ACCESS    read-write
     STATUS    mandatory
		--% ALIAS "Threshold Object ID"
		--% GROUP Threshold-Table
	DESCRIPTION
		"The complete object identifier of the variable on which
this threshold is set.
Threshold Object ID can be set only for Counter or Gauge variables. 
If you attempt to set a threshold for a variable of any other type,
you receive a badValue error."
     ::= { riThEntry 3 }

riThThreshold OBJECT-TYPE
     SYNTAX    INTEGER
     ACCESS    read-write
     STATUS    mandatory
		--% ALIAS "Threshold Value"
		--% GROUP Threshold-Table
	DESCRIPTION
		"The threshold value for the variable identified by
Threshold Object ID.  If this particular variable is a gauge, then
whenever its value rises above or drops below (depending on the
setting of the Direction of Approach to Thresh variable) the value
of Threshold Value, the threshold is considered to have been
triggered.  If this particular variable is a counter, then whenever
its value increments by the value of Threshold Value, the threshold
is considered to have been triggered."
     ::= { riThEntry 4 }

riThHysteresis OBJECT-TYPE
     SYNTAX    INTEGER
     ACCESS    read-write
     STATUS    mandatory
		--% ALIAS "Threshold Hysteresis"
		--% GROUP Threshold-Table
	DESCRIPTION
		"The hysteresis value for the threshold.  After a
variable's threshold is triggered, the value of the variable must
either drop below or rise above a certain value (depending on the
setting of the Direction of Approach to Thresh variable), the
hysteresis, before another trigger can be recognized. For example, 
if you set the threshold for module temperature to 80, the threshold 
is triggered the first time the temperature rises above 80.  If you 
also set the hysteresis for this threshold to 60, the threshold will 
only be triggered again if the temperature drops below 60, and then 
rises past 80.  If the temperature drops from 80 to 70, and then goes 
back to 80, the threshold is not triggered. If the hysteresis value is 
less than the threshold value, the variable's value must drop below the 
hysteresis before another trigger is recognized.  If the hysteresis value 
is greater than the threshold value, the variable's value must rise above 
the hysteresis before another trigger is recognized. The value of the 
hysteresis depends on the value of the threshold and whether the value of 
the variable is rising or falling; therefore, set this variable in conjunction
with both the Threshold Value and Direction of Approach to Thresh variables.
This variable is relevant only to thresholds set on Gauge variables."
     ::= { riThEntry 5 }

riThDirection OBJECT-TYPE
     SYNTAX    INTEGER {
			up(1),
			down(2)
			}
     ACCESS    read-write
     STATUS    mandatory
		--% ALIAS "Direction of Approach to Thresh"
		--% GROUP Threshold-Table
	DESCRIPTION
		"The direction in which a change in a Gauge variable's
value causes a threshold to trigger.
If its direction is up, a trigger occurs when the variable's value
rises above the threshold value.  In this case, the hysteresis must
be less than or equal to the threshold value.
If its direction is down, a trigger occurs when the variable's
value falls below the threshold value.  In this case, the
hysteresis must be greater than or equal to the threshold value.
This variable is relevant only to thresholds set on Gauge
variables."
     ::= { riThEntry 6 }

riThTriggeredCount OBJECT-TYPE
     SYNTAX    Counter
     ACCESS    read-only
     STATUS    mandatory
		--% ALIAS "Threshold Trigger Count"
		--% GROUP Threshold-Table
	DESCRIPTION
		"The number of times that this threshold has been
triggered."
     ::= { riThEntry 7 }

riThCommunity OBJECT-TYPE
     SYNTAX    OCTET STRING
     ACCESS    read-write
     STATUS    mandatory
		--% ALIAS "Threshold Community Name"
		--% GROUP Threshold-Table
	DESCRIPTION
		"The community name to place in the authentication header
of the trap PDU.  This variable specifies the community to which
the trap is to be sent when a threshold is triggered."
     ::= { riThEntry 8 }

riThPhysDestination OBJECT-TYPE
     SYNTAX    OCTET STRING
     ACCESS    read-write
     STATUS    mandatory
		--% ALIAS "Threshold Eth Addr Destination"
		--% GROUP Threshold-Table
	DESCRIPTION
		"The Ethernet address of the node to which the trap is
to be sent when the threshold is triggered."
     ::= { riThEntry 9 }

riThIPDestination OBJECT-TYPE
     SYNTAX    IpAddress
     ACCESS    read-write
     STATUS    mandatory
		--% ALIAS "Threshold IP Addr Destination"
		--% GROUP Threshold-Table
	DESCRIPTION
		"The IP address of the node to which the trap is to be
sent when the threshold is triggered."
     ::= { riThEntry 10 }

--
-- Racal Datacom Rate Group
--

riRateTxSingleCollisionFrames OBJECT-TYPE
     SYNTAX    Gauge
     ACCESS    read-only
     STATUS    mandatory
		--% ALIAS "Single Collision Frame Rate"
		--% GROUP Racal-InterLan-Rate-Group
	DESCRIPTION
		"The rate of frames that were successfully transmitted
after experiencing one and only one collision.
This variable corresponds to the Single Collisions Transmitted
variable in the dot3 group."
     ::= { riTsRates 1 }

riRateTxMultipleCollisionFrames OBJECT-TYPE
     SYNTAX    Gauge
     ACCESS    read-only
     STATUS    mandatory
		--% ALIAS "Multiple Collision Frame Rate"
		--% GROUP Racal-InterLan-Rate-Group
	DESCRIPTION
		"The rate of frames that were successfully transmitted
after experiencing more than one collision.
This variable corresponds to the Multiple Collisions Xmitted
variable in the dot3 group."
     ::= { riTsRates 2 }

riRateTxDeferredTransmissions OBJECT-TYPE
     SYNTAX    Gauge 
     ACCESS    read-only
     STATUS    mandatory
		--% ALIAS "Deferred Transmission Rate"
		--% GROUP Racal-InterLan-Rate-Group
	DESCRIPTION
		"The rate of times the INX-NMM deferred transmission of
data because it sensed traffic on the network.  Because the INX-NMM
does not record deferrals, this variable always returns 0.
This variable corresponds to the Transmissions Deferred variable
in the dot3 group."
     ::= { riTsRates 3 }

riRateTxLateCollisions OBJECT-TYPE
     SYNTAX    Gauge 
     ACCESS    read-only
     STATUS    mandatory
		--% ALIAS "Transmit Late Collision Rate"
		--% GROUP Racal-InterLan-Rate-Group
	DESCRIPTION
		"The rate of times that a collision has been detected on
this bus later than 512 bit times from frame start.  This count is
not maintained by the INX-NMM, so this variable always returns 0.
This variable corresponds to the Late Collisions Detected variable
in the dot3 group."
     ::= { riTsRates 4 }

riRateTxInternalMACTransmitErrors OBJECT-TYPE
     SYNTAX    Gauge
     ACCESS    read-only
     STATUS    mandatory
		--% ALIAS "Internal MAC Xmit Error Rate"
		--% GROUP Racal-InterLan-Rate-Group
	DESCRIPTION
		"The rate of frames the interface could not transmit
because of an internal MAC sublayer transmit error.

This variable corresponds to the MAC Transmit Errors variable in
the dot3 group."
     ::= { riTsRates 5 }

riRateTxCarrierSenseErrors OBJECT-TYPE
     SYNTAX    Gauge
     ACCESS    read-only
     STATUS    mandatory
		--% ALIAS "Carrier Sense Error Rate"
		--% GROUP Racal-InterLan-Rate-Group
	DESCRIPTION
		"The rate of times that the carrier-sense condition was
lost or never asserted when the INX-NMM attempted to transmit a
frame on the interface.
This variable corresponds to the Carrier Sense Errors variable in
the dot3 group."
     ::= { riTsRates 6 }

riRateTxExcessiveDeferrals OBJECT-TYPE
     SYNTAX    Gauge
     ACCESS    read-only
     STATUS    mandatory
		--% ALIAS "Excessive Deferral Rate"
		--% GROUP Racal-InterLan-Rate-Group
	DESCRIPTION
		"The rate of frames the INX-NMM deferred transmitting for
an excessive period of time.  Because the INX-NMM interface does
not record deferrals, this variable always returns 0.
This variable corresponds to the Deferred Frames variable in the
dot3 group."
     ::= { riTsRates 7 }

riRateRxInternalMACReceiveErrors OBJECT-TYPE
     SYNTAX    Gauge
     ACCESS    read-only
     STATUS    mandatory
		--% ALIAS "Internl MAC Receive Error Rate"
		--% GROUP Racal-InterLan-Rate-Group
	DESCRIPTION
		"The rate of frames the interface could not receive
because of an internal MAC sublayer receive error.

This variable corresponds to the MAC Errors Received variable in
the dot3 group."
     ::= { riTsRates 8 }

riRateRxFCSErrors OBJECT-TYPE
     SYNTAX    Gauge
     ACCESS    read-only
     STATUS    mandatory
		--% ALIAS "FCS Error Rate"
		--% GROUP Racal-InterLan-Rate-Group
	DESCRIPTION
		"The rate of frames received on the interface that are
an integral number of octets in length (i.e., the number of bits
they contain is a multiple of eight) that do not pass the FCS
check, indicating that the frames were corrupted during
transmission.
This variable corresponds to the FCS Errored Frames Received
variable in the dot3 group."
     ::= { riTsRates 9 }

riRateRxAlignmentErrors OBJECT-TYPE
     SYNTAX    Gauge
     ACCESS    read-only
     STATUS    mandatory
		--% ALIAS "Alignment Error Rate"
		--% GROUP Racal-InterLan-Rate-Group
	DESCRIPTION
		"The rate of frames received on the interface that are
not an integral number of octets in length (i.e., the number of
bits they contain is not a multiple of eight) and do not pass the
FCS check.  This indicates that the frames were corrupted during
transmission.
This variable corresponds to the Nonaligned Frames Recd variable
in the dot3 group."
     ::= { riTsRates 10 }

riRateRxInRangeLengthErrors OBJECT-TYPE
     SYNTAX    Gauge 
     ACCESS    read-only
     STATUS    mandatory
		--% ALIAS "In-Range Length Error Rate"
		--% GROUP Racal-InterLan-Rate-Group
	DESCRIPTION
		"The rate of in-range length errors received.  IEEE 802.3
frames contain a length field, indicating the length of the frame. 
If the value in the length field and the actual length of the frame
do not match, even if the length of the frame is within 802.3
parameters, the receiving device returns an in-range error.  The
INX-NMM receives Ethernet fr
This variable corresponds to the In-Range Length Errors Recd
variable in the dot3 group."
     ::= { riTsRates 11 }

riRateRxOutofRangeLengthFields OBJECT-TYPE
     SYNTAX    Gauge 
     ACCESS    read-only
     STATUS    mandatory
		--% ALIAS "Out of Range Length Field Rate"
		--% GROUP Racal-InterLan-Rate-Group
	DESCRIPTION
		"The rate of out-of-range length errors received.  IEEE
802.3 frames contain a length field, indicating the length of the
frame.  If the length of the frame is outside 802.3 parameters, the
receiving device returns an out-of-range error.  The INX-NMM
receives Ethernet frames that do not have a length field.  It
therefore cannot detect this error, 
This variable corresponds to the Out-Range Length Errors Recd
variable in the dot3 group."
     ::= { riTsRates 12 }

riRateRxFrameTooLongs OBJECT-TYPE
     SYNTAX    Gauge
     ACCESS    read-only
     STATUS    mandatory
		--% ALIAS "Frame Too Long Rate"
		--% GROUP Racal-InterLan-Rate-Group
	DESCRIPTION
		"The rate of frames received on the interface that exceed
the maximum permitted frame size, i.e., 1012 octets.
This variable corresponds to the Too Long Frames Recd variable in
the dot3 group."
     ::= { riTsRates 13 }

END
