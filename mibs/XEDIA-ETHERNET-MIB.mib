XEDIA-ETHERNET-MIB DEFINITIONS ::= BEGIN

IMPORTS
    MODULE-IDENTITY, OBJECT-TYPE, Counter32
        FROM SNMPv2-SMI
    MODULE-COMPLIANCE, OBJECT-GROUP
        FROM SNMPv2-CONF
    dot3StatsEntry
        FROM EtherLike-MIB
    xediaMibs
        FROM XEDIA-REG
    ;

xediaEthernetMIB MODULE-IDENTITY
    LAST-UPDATED "9701102155Z" -- January 10, 1997
    ORGANIZATION "Xedia Corp."
    CONTACT-INFO
        "support@xedia.com"
    DESCRIPTION
        "This module defines proprietary objects that extend those in
        IETF's the Ethernet-Like Interface MIB."
    ::= { xediaMibs 3 }


-- ================================================================
-- Top-level organization of the MIB
-- ================================================================

xdot3Objects        OBJECT IDENTIFIER ::= { xediaEthernetMIB 1 }
xdot3Conformance    OBJECT IDENTIFIER ::= { xediaEthernetMIB 2 } 

-- ================================================================
-- Object Definitions
-- ================================================================

--
-- Xedia Ethernet Statistics Table
--

xdot3StatsTable OBJECT-TYPE
    SYNTAX      SEQUENCE OF Xdot3StatsEntry
    MAX-ACCESS  not-accessible
    STATUS      current
    DESCRIPTION
        "Additional Xedia proprietary statistics for ethernet-like
        interfaces."
    ::= { xdot3Objects 1 }

xdot3StatsEntry OBJECT-TYPE
    SYNTAX      Xdot3StatsEntry
    MAX-ACCESS  not-accessible
    STATUS      current
    DESCRIPTION
        "Additional Xedia proprietary statistics for single
        ethernet-like interface."
    AUGMENTS    { dot3StatsEntry }
    ::= { xdot3StatsTable 1 }

Xdot3StatsEntry ::= SEQUENCE {
    xdot3StatsOutUnderflows         Counter32,
    xdot3StatsOutNoCarriers         Counter32,
    xdot3StatsOutCarrierLosses      Counter32,
    xdot3StatsOutJabberTimeouts     Counter32,
    xdot3StatsOutTotalCollisions    Counter32,
    xdot3StatsInDescriptorErrors    Counter32,
    xdot3StatsInRunts               Counter32,
    xdot3StatsInTotalCollisions     Counter32,
    xdot3StatsInDribbles            Counter32,
    xdot3StatsInOverflows           Counter32,
    xdot3StatsInV1EthFrames         Counter32,
    xdot3StatsInV2Dot3Frames        Counter32,
    xdot3StatsInMissedFrames        Counter32,
    xdot3NegotiatedConfigSpeed      INTEGER,
    xdot3NegotiatedConfigDuplexMode INTEGER,
    xdot3NegotiatedFlowControl      INTEGER,
    xdot3IfOperStatus               INTEGER
}

xdot3StatsOutUnderflows OBJECT-TYPE
    SYNTAX      Counter32
    MAX-ACCESS  read-only
    STATUS      current
    DESCRIPTION
        "A count of frames not transmitted on a particular interface
        because of underflow. An underflow occurs when the driver does
        not keep up with the hardware's transmit speed in providing
        buffers."
    ::= { xdot3StatsEntry 1 }

xdot3StatsOutNoCarriers OBJECT-TYPE
    SYNTAX      Counter32
    MAX-ACCESS  read-only
    STATUS      current
    DESCRIPTION
        "The number of times that the carrier signal from the
        transceiver was not present when a frame was to be transmitted."
    ::= { xdot3StatsEntry 2 }

xdot3StatsOutCarrierLosses OBJECT-TYPE
    SYNTAX      Counter32
    MAX-ACCESS  read-only
    STATUS      current
    DESCRIPTION
        "The number of times the carrier was lost during
        transmission."
    ::= { xdot3StatsEntry 3 }

xdot3StatsOutJabberTimeouts OBJECT-TYPE
    SYNTAX      Counter32
    MAX-ACCESS  read-only
    STATUS      current
    DESCRIPTION
        "The number of times a transmission was aborted because the
        jabber timer timed out."
    ::= { xdot3StatsEntry 4 }

xdot3StatsOutTotalCollisions OBJECT-TYPE
    SYNTAX      Counter32
    MAX-ACCESS  read-only
    STATUS      current
    DESCRIPTION
        "The total number of collisions that have occurred while
        transmitting on this interface."
    ::= { xdot3StatsEntry 5 }

xdot3StatsInDescriptorErrors OBJECT-TYPE
    SYNTAX      Counter32
    MAX-ACCESS  read-only
    STATUS      current
    DESCRIPTION
        "The number of frames that were truncated because they did not
        fit within the current desriptor buffers."
    ::= { xdot3StatsEntry 6 }

xdot3StatsInRunts OBJECT-TYPE
    SYNTAX      Counter32
    MAX-ACCESS  read-only
    STATUS      current
    DESCRIPTION
        "The number of runt frames. A runt frame may have been damaged
        by collision or premature termination before the collision
        window had passed."
    ::= { xdot3StatsEntry 7 }

xdot3StatsInTotalCollisions OBJECT-TYPE
    SYNTAX      Counter32
    MAX-ACCESS  read-only
    STATUS      current
    DESCRIPTION
        "The number of collisions detected on incoming frames."
    ::= { xdot3StatsEntry 8 }

xdot3StatsInDribbles OBJECT-TYPE
    SYNTAX      Counter32
    MAX-ACCESS  read-only
    STATUS      current
    DESCRIPTION
        "The number of frames which were not a multiple of 8 bytes."
    ::= { xdot3StatsEntry 9 }

xdot3StatsInOverflows OBJECT-TYPE
    SYNTAX      Counter32
    MAX-ACCESS  read-only
    STATUS      current
    DESCRIPTION
        "The number of frames that were truncated due to FIFO
        overflow. This indicates a hardware problem (as opposed to
        MissedFrames which indicates the software did not keep up)."
    ::= { xdot3StatsEntry 10 }

xdot3StatsInV1EthFrames OBJECT-TYPE
    SYNTAX      Counter32
    MAX-ACCESS  read-only
    STATUS      current
    DESCRIPTION
        "The number of Ethernet-type (version 1) frames."
    ::= { xdot3StatsEntry 11 }

xdot3StatsInV2Dot3Frames OBJECT-TYPE
    SYNTAX      Counter32
    MAX-ACCESS  read-only
    STATUS      current
    DESCRIPTION
        "The number of 802.3-type (version 2) frames."
    ::= { xdot3StatsEntry 12 }

xdot3StatsInMissedFrames OBJECT-TYPE
    SYNTAX      Counter32
    MAX-ACCESS  read-only
    STATUS      current
    DESCRIPTION
        "The number of frames that were received by the hardware but
        that were not picked up by the driver."
    ::= { xdot3StatsEntry 13 }

xdot3NegotiatedConfigSpeed OBJECT-TYPE
    SYNTAX      INTEGER {
                    mbps10(1),
                    mbps100(2),
                    gbps1(3),
                    unknown(4)
                }
    MAX-ACCESS  read-only
    STATUS      current
    DESCRIPTION
        "The negotiated configured speed of the interface when the 
         auto negotiates mode is enable." 
    ::= { xdot3StatsEntry 14 }

xdot3NegotiatedConfigDuplexMode OBJECT-TYPE
    SYNTAX      INTEGER {
                    full(1),
                    half(2),
                    unknown(3)
                }
    MAX-ACCESS  read-only
    STATUS      current
    DESCRIPTION
        "The negotiated configured duplex mode of the interface."
    ::= { xdot3StatsEntry 15 } 

xdot3NegotiatedFlowControl OBJECT-TYPE
    SYNTAX      INTEGER {
                    disabled(1),
                    enabledXmit(2),
                    enabledRcv(3),
                    enabledXmitAndRcv(4),
                    unknown(5)
                }
    MAX-ACCESS  read-only
    STATUS      current
    DESCRIPTION 
         "The negotiated configured flow control parameters." 
    ::= { xdot3StatsEntry 16 }

xdot3IfOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
         "This is a reference object (from the ifmib.mi2's 
          ifOperStatus) reports the current operational states
          of the interface for the auto-negotiate configuration 
          purpose." 
    ::= { xdot3StatsEntry 17 }

--
-- Xedia Ethernet Config Table
--

-- The IETF MAU MIB covers some of this. (Everything but
-- CaptureEffectResol and Tx/RxRingSize?) Can we use that instead?

xdot3ConfigTable OBJECT-TYPE
    SYNTAX      SEQUENCE OF Xdot3ConfigEntry
    MAX-ACCESS  not-accessible
    STATUS      current
    DESCRIPTION
        "Xedia proprietary configuration parameters for ethernet-like
        interfaces."
    ::= { xdot3Objects 2 }

xdot3ConfigEntry OBJECT-TYPE
    SYNTAX      Xdot3ConfigEntry
    MAX-ACCESS  not-accessible
    STATUS      current
    DESCRIPTION
        "Xedia proprietary configuration parameters for single
        ethernet-like interface."
    AUGMENTS    { dot3StatsEntry }
    ::= { xdot3ConfigTable 1 }

Xdot3ConfigEntry ::= SEQUENCE {
    xdot3ConfigSpeed                INTEGER,
    xdot3ConfigDuplexMode           INTEGER,
    xdot3ConfigMedia                INTEGER,
    xdot3ConfigCaptureEffectResol   INTEGER,
    xdot3ConfigAutoNegotiate        INTEGER
--  xdot3ConfigAutoAbilities        INTEGER 
}

xdot3ConfigSpeed OBJECT-TYPE
    SYNTAX      INTEGER {
                    mbps10(1), 
                    mbps100(2),
                    gbps1(3)
                }
    MAX-ACCESS  read-write
    STATUS      current
    DESCRIPTION
        "The configured speed of the interface. This may be set by the
        administrator or may be the result of auto-negotiation."
    DEFVAL      { mbps100 }
    ::= { xdot3ConfigEntry 1 }

xdot3ConfigDuplexMode OBJECT-TYPE
    SYNTAX      INTEGER {
                    full(1), 
                    half(2)
                }
    MAX-ACCESS  read-write
    STATUS      current
    DESCRIPTION
        "The configured mode of the interface."
    DEFVAL      { half }
    ::= { xdot3ConfigEntry 2 }

xdot3ConfigMedia OBJECT-TYPE
    SYNTAX      INTEGER { 
                    tx(1), 
                    fx(2),
                    sx(3),
                    lx(4)
                }
    MAX-ACCESS  read-only
    STATUS      current
    DESCRIPTION
        "The media type of the interface. The value 'tx(1)' indicates
        copper, 'fx(2)' indicates 850 nm multi-mode fiber, 'sx(3)'
        indicates 850 nm multi-mode fiber and lx(4) indicates 1300 nm
        single-mode or multi-mode fiber."
    ::= { xdot3ConfigEntry 3 }

xdot3ConfigCaptureEffectResol OBJECT-TYPE
    SYNTAX      INTEGER {
                    enabled(1),
                    disabled(2)
                }
    MAX-ACCESS  read-write
    STATUS      current
    DESCRIPTION
        "This object controls whether a non-standard backoff algorithm 
        is used for collision handling in order to avoid 'capture
        effect'. Capture effect occurs when two stations transmit in
        such a way that, because of collision backoff, one station
        captures the channel for an unfair amount of time (and the
        line may remain idle for a long time after that station stops
        transmitting because of the second station increasing its
        backoff time.) The value of 'enabled(1)' indicates the
        enhanced algorithm will be use. The value 'disabled(2)' is the
        default and indicates the standard backoff algorithm is used."
    DEFVAL      { disabled }
    ::= { xdot3ConfigEntry 4 }

xdot3ConfigAutoNegotiate OBJECT-TYPE
    SYNTAX      INTEGER {
                    enabled(1),
                    disabled(2)
                }
    MAX-ACCESS  read-write
    STATUS      current
    DESCRIPTION
       "This object controls whether to negotiate the speed and
        duplex mode for 10/100 fast ethernet; and negotiate duplex
        mode and MAC control for gigabit ethernet interface."
    DEFVAL      { enabled } 
    ::= { xdot3ConfigEntry 5 }

--xdot3ConfigAutoAbilites OBJECT-TYPE
--    SYNTAX      INTEGER {
--                    100full(1),
--                    100half(2),
--                     10full(3),
--                     10half(4)
--                }
--    MAX-ACCESS  read-write
--    STATUS      current
-- ***** the description needs some work if this object is ever turned on...
--    DESCRIPTION
--      "This object represents the administarively-configured
--       the auto-negotiation abilities of speed and deuplex
--       mode configuration. If auto-negotiation is implemented
--       and enabled for the MAU attached to this interface,
--       the auto-negotiation follows this setting."
--    DEFVAL      { 100full }
--    ::= { xdot3ConfigEntry 6 }

-- ================================================================
-- Conformance Information
-- ================================================================

xdot3Compliances    OBJECT IDENTIFIER ::= { xdot3Conformance 1 }
xdot3Groups         OBJECT IDENTIFIER ::= { xdot3Conformance 2 }

--
-- Compliance Statements
--

xdot3Compliance MODULE-COMPLIANCE
    STATUS      current
    DESCRIPTION
        "The compliance statement for all agents that support this
        MIB. A compliant agent implements all objects defined in this
        MIB."
    MODULE  -- this module
    MANDATORY-GROUPS {
        xdot3Group
    }
    ::= { xdot3Compliances 1 }

--
-- Object Groups
--

xdot3Group OBJECT-GROUP
    OBJECTS {
        xdot3StatsOutUnderflows,
        xdot3StatsOutNoCarriers,
        xdot3StatsOutCarrierLosses,
        xdot3StatsOutJabberTimeouts,
        xdot3StatsOutTotalCollisions,
        xdot3StatsInDescriptorErrors,
        xdot3StatsInRunts,
        xdot3StatsInTotalCollisions,
        xdot3StatsInDribbles,
        xdot3StatsInOverflows,
        xdot3StatsInV1EthFrames,
        xdot3StatsInV2Dot3Frames,
        xdot3StatsInMissedFrames,
        xdot3ConfigSpeed,
        xdot3ConfigDuplexMode,
        xdot3ConfigMedia,
        xdot3ConfigCaptureEffectResol,
        xdot3ConfigAutoNegotiate,
        xdot3NegotiatedConfigSpeed,
        xdot3NegotiatedConfigDuplexMode,
        xdot3NegotiatedFlowControl,
        xdot3IfOperStatus 
    }
    STATUS      current
    DESCRIPTION
        "The set of all accessible objects in this MIB."
    ::= { xdot3Groups 1 }


END
