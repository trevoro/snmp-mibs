SEI-SMI DEFINITIONS ::= BEGIN

IMPORTS
	MODULE-IDENTITY, enterprises, 
	OBJECT-TYPE,
	Integer32,
	Gauge32, 
	IpAddress, 
	NOTIFICATION-TYPE
		FROM SNMPv2-SMI 
	TRAP-TYPE
		FROM RFC-1215
	SnmpAdminString
		FROM SNMP-FRAMEWORK-MIB
	sysName FROM RFC1213-MIB;
   
	sei MODULE-IDENTITY
 		LAST-UPDATED    "200406080000Z"  -- June 08, 2004
		ORGANIZATION "System Engineering International"
 		CONTACT-INFO
	"  	System Engineering International
 
        Postal:	5115 Pegasus Ct., Suite Q
        		Frederick, MD 21704
				USA

		Tel:	+1 301 694 9601

		E-mail:	tdiamond@seipower.com"
  
        DESCRIPTION
		"The Enterprise Number for System Engineering International"

		REVISION    "200406080000Z"  -- June 08, 2004
		DESCRIPTION "Initial version."
	::= { enterprises 20364 } -- assigned by IANA

juiceBoxPse OBJECT IDENTIFIER ::= { sei 1 }

juiceBoxObjects OBJECT IDENTIFIER ::= { juiceBoxPse 1 }

-- Juice Box Objects

	juiceBoxPortTable OBJECT-TYPE
		SYNTAX      SEQUENCE OF JuiceBoxPortEntry
		MAX-ACCESS  not-accessible
		STATUS      current
		DESCRIPTION
           "A table of objects that display and control the power
            characteristics of an individual port on a Juice Box
            Midspan Power Hub. Values of all read-write objects in 
            this table are persistent at restart/reboot."
	::= { juiceBoxObjects 1 }

	juiceBoxPortEntry  OBJECT-TYPE
		SYNTAX      JuiceBoxPortEntry  
		MAX-ACCESS  not-accessible
		STATUS      current
		DESCRIPTION
			"A set of objects that display and control the power
			characteristics of a Juice Box Midspan Power Hub port."
		INDEX    { juiceBoxPortIndex  }
	::= { juiceBoxPortTable 1 }

	JuiceBoxPortEntry ::= SEQUENCE {
		juiceBoxPortIndex
			Integer32,
		juiceBoxPortDetectionSetting
			INTEGER,
		juiceBoxPortMaxPower
			INTEGER, 
		juiceBoxPortDescription
			SnmpAdminString,         
		juiceBoxPortStatus
			INTEGER,
		juiceBoxPortClassifications
			INTEGER, 
		juiceBoxPortPowerDelivered
			Gauge32
  }

	juiceBoxPortIndex OBJECT-TYPE
		SYNTAX      Integer32 (1..2147483647)
		MAX-ACCESS  not-accessible
		STATUS      current
		DESCRIPTION
           "This variable uniquely identifies the port within 
           the Juice Box Midspan Power Hub."
	::= { juiceBoxPortEntry 1 }

	juiceBoxPortDetectionSetting OBJECT-TYPE
	SYNTAX INTEGER   {
		disabled(1),
		ieee8023afonly(2),
		ieee8023afandlegacy(3),
		forcedon(4)
     }
    MAX-ACCESS read-write
    STATUS current
    DESCRIPTION
        "Describes the type of PD detection performed by the port.
         A value of disabled(1) means that no PD detection is performed.  If a port
         	currently delivering power is set to disabled(1), power will be removed 
         	from the port. 
         A value of ieee802.3afonly(2) means only PDs with valid signatures
	 		as defined by ieee 802.3af will be detected and powered.
         A value of ieee8023afandlegacy(3) means that PDs with 802.3af and legacy
	 		signatures will be detected and powered.
         A value of forcedon(4) means the port is powered without regard to detection status.
         	A setting of forcedon(4) is not persistent and must be re-asserted after restart/reboot"
    ::= { juiceBoxPortEntry 2 }

	juiceBoxPortMaxPower OBJECT-TYPE
	SYNTAX INTEGER   {
		max1W(1),
		max2W(2),
		max3W(3),
		max4W(4),
		max5W(5),
		max6W(6),
		max7W(7),
		max8W(8),
		max9W(9),
		max10W(10),
		max11W(11),
		max12W(12),
		max13W(13),
		max14W(14),
		max15W(15)		
     }
    MAX-ACCESS read-write
    STATUS current
    DESCRIPTION
        "Describes the maximum power setting for the port in watts.
		This setting is used by to calculate Allocated Power.
		It is only used if the port is classified as Class 0 or Legacy."
     ::= { juiceBoxPortEntry 3 }

	juiceBoxPortDescription OBJECT-TYPE
	SYNTAX SnmpAdminString
	MAX-ACCESS read-write
	STATUS current
	DESCRIPTION
        "A manager will set the value of this variable to indicate
         the type of powered device that is connected to the port.
         The default value supplied by the agent if no value has
         ever been set is PORT x where x is the port number"
	::= { juiceBoxPortEntry 4 }

	juiceBoxPortStatus OBJECT-TYPE
    SYNTAX INTEGER   {
         disabled(1),
         deliveringPower(2),
	     startupFault(3),
	     overCurrentFault(4),
	     short(5),
	     open(6),
	     rsignatureHi(7),
	     rsignatureLow(8),
	     invalidDetect(9),
         disconnect(10),
         powerup(12),
	     overPowerWarning(13),
	     overPowerFault(14),
	     insufficientPower(15)
     }
	MAX-ACCESS read-only
	STATUS current
	DESCRIPTION
       "Describes the status of the port.
         A value of disabled(1) means that juiceBoxPortDetectionSetting for the port
         	is set to disabled. No PD detection will be performed. 
         A value of deliveringPower(2) means the port is delivering power within 
         	operational parameters.
         A value of startupFault(3) means that port failed to power up properly.
         A value of overCurrentFault(4) means the port current was greater than the 
         	350mA maximum value specified by IEEE 802.3af. 
         A value of short(5) means an short circuit was discovered during PD detection.
         A value of open(6) means an open circuit was discovered during PD detection.
         A value of rsignatureHi(7) means a resistance greater than the valid signature 
         	specified by IEEE 802.3af was discovered during PD detection.
         A value of rsignatureLow(8) means a resistance less than the valid signature 
         	specified by IEEE 802.3af was discovered during PD detection.
         A value of invalidDetect(9) means an invalid signature as
         	specified by IEEE 802.3af was discovered during PD detection.
         A value of disconnect(10) means that the port current was less than the 
         	10mA mininum value specified by IEEE 802.3af required to maintain power.
         A value of powerup(12) means the port is in the process of being powered.
         A value of overPowerWarning(13) means the port is delivering power greater 
         	than the maximum value for its Class or the value set with juiceBoxPortMaxPower.
         A value of overPowerFault(14) means the port was shut down because the power delivered
         	was at least 1 Watt greater than the maximum value for its Class or the value set 
         	with juiceBoxPortMaxPower. 
         A value of insufficientPower(15) means the port could not be powered because
         	there is insuffiecent power capability remaining to fully power the port."
  	::= { juiceBoxPortEntry 5 }


	juiceBoxPortClassifications OBJECT-TYPE
	SYNTAX INTEGER   {
               class0(1),
               class1(2),
               class2(3),
               class3(4),
               class4(5),
	       	   legacy(6)
     }
    MAX-ACCESS read-only
    STATUS current
    DESCRIPTION
        "Classification is a way to identify a Powered Device according to 
        its power consumption. 
        
        The meaning of the classification labels is defined in the
        IEEE specification.

       	This variable is valid only while a PD is being powered,
        that is, while the attribute juiceBoxPortStatus is reporting 
        the enumeration deliveringPower or overpowerWarning."
	::= { juiceBoxPortEntry 6 }

	juiceBoxPortPowerDelivered OBJECT-TYPE
		SYNTAX      Gauge32
		UNITS      "milliWatts"
		MAX-ACCESS  read-only
		STATUS      current
		DESCRIPTION
		"Measured usage power of port expressed in milliWatts. 
		
		This variable is valid only while a PD is being powered,
        that is, while the attribute juiceBoxPortStatus is reporting 
        the enumeration deliveringPower or overPowerWarning.
        
        If an overPowerFault has occured on the port, the power level that 
        caused the fault is indicated"
	::= { juiceBoxPortEntry 7 }

juiceBoxMainObjects       OBJECT IDENTIFIER ::= { juiceBoxObjects 2 }

	juiceBoxMainSystemVoltage OBJECT-TYPE
		SYNTAX      Gauge32
		UNITS      "milliVolts"
		MAX-ACCESS  read-only
		STATUS      current
		DESCRIPTION
			"Measured system voltage in millivolts ."
	::= { juiceBoxMainObjects 1 }

	juiceBoxMainTemperature OBJECT-TYPE
		SYNTAX      Gauge32
		UNITS      "degrees C"
		MAX-ACCESS  read-only
		STATUS      current
		DESCRIPTION
			"Measured internal temperature in degrees C."
	::= { juiceBoxMainObjects 2 }
  
	juiceBoxMainPowerAvailable OBJECT-TYPE
		SYNTAX      Gauge32  (1..65535)
		UNITS      "Watts"
		MAX-ACCESS  read-only
		STATUS      current
		DESCRIPTION
			"The nominal power of the JuiceBox expressed in Watts."
	::= { juiceBoxMainObjects 3 }
 
	juiceBoxMainPowerDelivered OBJECT-TYPE
		SYNTAX      Gauge32
		UNITS      "Watts"
		MAX-ACCESS  read-only
		STATUS      current
		DESCRIPTION
               "Total Power Delivered to the PDs."
	::= { juiceBoxMainObjects 4 }

	juiceBoxMainAllocatedPower OBJECT-TYPE
		SYNTAX      Gauge32
		UNITS      "Watts"
		MAX-ACCESS  read-only
		STATUS      current
		DESCRIPTION
               "Total Power Allocated to the PDs.  This value is calculated base
               on the Classification of the PDs powered by the Juice Box.  If the PD
               classified as Class 0 or Legacy, the juiceBoxPortMaxPower setting for
               the port is used."
	::= { juiceBoxMainObjects 5 }
 
	juiceBoxMainAllocatedPowerThreshold OBJECT-TYPE
		SYNTAX      Integer32  (1..99)
		UNITS      "%"
		MAX-ACCESS  read-write
		STATUS      current
		DESCRIPTION
               "The usage threshold expressed in percents for
                comparing the alocated power and initiating
                an alarm (trap) if the threshold is exceeded."
	::= { juiceBoxMainObjects 6 }
 
	juiceBoxMainTrapDestinationIPAddr OBJECT-TYPE
		SYNTAX     IpAddress
		MAX-ACCESS read-write
		STATUS     current
		DESCRIPTION
 			"A read/write IP address.  This is the address to which 
 			the agent sends traps.  The value is initialized as 0.0.0.0.
 			Traps will not be sent until a new value is entered"
	::= { juiceBoxMainObjects 7 }

      juiceBoxMainTrapReXmitPeriod OBJECT-TYPE
		SYNTAX      Integer32  (1..3600)
		UNITS      "seconds"
		MAX-ACCESS  read-write
		STATUS      current
		DESCRIPTION
 			"The period of time in seconds after which a trap will be 
            re-transmitted if the fault condition is still present"
	::= { juiceBoxMainObjects 8 }
 
	juiceBoxMainGlobalPortDetectionSetting OBJECT-TYPE
		SYNTAX INTEGER   {
			disabled(1),
			ieee8023afonly(2),
			ieee8023afandlegacy(3),
			forcedon(4)
     }
    MAX-ACCESS read-write
    STATUS current
    DESCRIPTION
        "Sets the PortDetectionSetting for all the Juice Box ports to the
        selected value. 
          
        Describes the type of PD detection performed by the port.
         A value of disabled(1) means that no PD detection is performed.  If a port
         	currently delivering power is set to disabled(1), power will be removed 
         	from the port. 
         A value of ieee802.3afonly(2) means only PDs with valid signatures
	 		as defined by ieee 802.3af will be detected and powered.
         A value of ieee8023afandlegacy(3) means that PDs with 802.3af and legacy
	 		signatures will be detected and powered.
         A value of forcedon(4) means the port is powered without regard to detection status.
         	A setting of forcedon(4) is not persistent and must be re-asserted after restart/reboot"
     ::= { juiceBoxMainObjects 9 }

	juiceBoxMainGlobalPortMaxPower OBJECT-TYPE
    	SYNTAX INTEGER   {
			max1W(1),
			max2W(2),	
			max3W(3),
			max4W(4),
			max5W(5),
			max6W(6),
			max7W(7),
			max8W(8),
			max9W(9),
			max10W(10),
			max11W(11),
			max12W(12),
			max13W(13),
			max14W(14),
			max15W(15)		
    	 }
    	MAX-ACCESS read-write
    	STATUS current
    	DESCRIPTION
    	    "Used to set PortMaxPower for all ports to the same value.
    	  	Describes the maximum power setting for the port in watts.
			This setting is used by to calculate Allocated Power.
			It is only used if the port is classified as Class 0 or Legacy."
    ::= { juiceBoxMainObjects 10 }

	juiceBoxMainNetworkControllerFirmware OBJECT-TYPE
		SYNTAX SnmpAdminString
		MAX-ACCESS read-only
		STATUS current
		DESCRIPTION
        "Firmware Version of the JuiceBox Network Controller."
	::= { juiceBoxMainObjects 11 }

	juiceBoxMainSystemControllerFirmware OBJECT-TYPE
		SYNTAX SnmpAdminString
		MAX-ACCESS read-only
		STATUS current
		DESCRIPTION
		"Firmware Version of the JuiceBox SystemController."
	::= { juiceBoxMainObjects 12 }

-- Juice Box Trap Definitions

	juiceBoxPortStatusChange TRAP-TYPE
		ENTERPRISE sei
		VARIABLES {sysName,	juiceBoxPortIndex, juiceBoxPortStatus}
		DESCRIPTION
			"This trap will be sent anytime the status of a Juice Box port 
			changes."
			
			--#TYPE "%s, PORT %d STATUS IS %d"
			--#ARGUMENTS {0,1,2}
			--#STATE OPERATIONAL
		::= 20


  	juiceBoxAllocatedPowerThresholdReached TRAP-TYPE
		ENTERPRISE sei
		VARIABLES {sysName,	juiceBoxMainAllocatedPower, juiceBoxMainPowerDelivered}
		DESCRIPTION
			"This trap is sent when the Allocated Power is greater than the percentage
			threshold set juiceBoxMainAllocatedPowerThreshold."
			
			--#TYPE "Juice Box Allocated Power Threshold Trap"
			--#SUMMARY "%s, POWER ALLOCATED = %d, POWER DELIVERED = %d"
			--#ARGUMENTS {0,1,2}
			--#STATE OPERATIONAL
		::= 10



  
  
END
