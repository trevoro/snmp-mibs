Nortel-Magellan-Passport-DisdnNISMIB
DEFINITIONS ::= BEGIN



IMPORTS

      OBJECT-TYPE
   FROM RFC-1212

      passportMIBs
   FROM Nortel-Magellan-Passport-UsefulDefinitionsMIB

      DisplayString,
      StorageType,
      RowStatus,
      Unsigned32
   FROM Nortel-Magellan-Passport-StandardTextualConventionsMIB

      NonReplicated,
      Link
   FROM Nortel-Magellan-Passport-TextualConventionsMIB

      dataSigChanIndex,
      dataSigChan
   FROM Nortel-Magellan-Passport-DataIsdnMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DisdnNIS Enterprise MIB."

disdnNISMIB OBJECT IDENTIFIER ::= { passportMIBs 127 }










-- DataSigChan/n Nis
-- The Nis component defines the operational characteristics of the 
-- signalling channel's connection to the external equipment.

dataSigChanNis OBJECT IDENTIFIER ::= { dataSigChan 13 }



dataSigChanNisRowStatusTable OBJECT-TYPE
   SYNTAX     SEQUENCE OF DataSigChanNisRowStatusEntry
   ACCESS     not-accessible
   STATUS     mandatory
   DESCRIPTION
     "This entry controls the addition and deletion of 
      dataSigChanNis components."
::= { dataSigChanNis 1 }

dataSigChanNisRowStatusEntry OBJECT-TYPE
   SYNTAX     DataSigChanNisRowStatusEntry
   ACCESS     not-accessible
   STATUS     mandatory
   DESCRIPTION
     "A single entry in the table represents a single 
      dataSigChanNis component."
   INDEX {
      dataSigChanIndex,
      dataSigChanNisIndex }
::= { dataSigChanNisRowStatusTable 1 }

DataSigChanNisRowStatusEntry ::= SEQUENCE {
   dataSigChanNisRowStatus
      RowStatus,
   dataSigChanNisComponentName
      DisplayString,
   dataSigChanNisStorageType
      StorageType,
   dataSigChanNisIndex
      NonReplicated }

dataSigChanNisRowStatus OBJECT-TYPE
   SYNTAX     RowStatus 
   ACCESS     read-write
   STATUS     mandatory
   DESCRIPTION
     "This variable is used as the basis for SNMP naming of
      dataSigChanNis components.
      These components can be added and deleted."
::= { dataSigChanNisRowStatusEntry 1 }

dataSigChanNisComponentName OBJECT-TYPE
   SYNTAX     DisplayString 
   ACCESS     read-only
   STATUS     mandatory
   DESCRIPTION
     "This variable provides the component's string name for
      use with the ASCII Console Interface"
::= { dataSigChanNisRowStatusEntry 2 }

dataSigChanNisStorageType OBJECT-TYPE
   SYNTAX     StorageType 
   ACCESS     read-only
   STATUS     mandatory
   DESCRIPTION
     "This variable represents the storage type value for the
      dataSigChanNis tables."
::= { dataSigChanNisRowStatusEntry 4 }

dataSigChanNisIndex OBJECT-TYPE
   SYNTAX     NonReplicated 
   ACCESS     not-accessible
   STATUS     mandatory
   DESCRIPTION
     "This variable represents the index for the dataSigChanNis tables."
::= { dataSigChanNisRowStatusEntry 10 }

dataSigChanNisL2Table OBJECT-TYPE
   SYNTAX     SEQUENCE OF DataSigChanNisL2Entry
   ACCESS     not-accessible
   STATUS     mandatory
   DESCRIPTION
     "This group represents the provisionable Layer 2 attributes of the 
      Q931 CCITT protocol."
::= { dataSigChanNis 11 }

dataSigChanNisL2Entry OBJECT-TYPE
   SYNTAX     DataSigChanNisL2Entry
   ACCESS     not-accessible
   STATUS     mandatory
   DESCRIPTION
     "An entry in the dataSigChanNisL2Table."
   INDEX {
      dataSigChanIndex,
      dataSigChanNisIndex }
::= { dataSigChanNisL2Table 1 }

DataSigChanNisL2Entry ::= SEQUENCE {
   dataSigChanNisT23
      Unsigned32,
   dataSigChanNisT200
      Unsigned32,
   dataSigChanNisN200
      Unsigned32,
   dataSigChanNisT203
      Unsigned32,
   dataSigChanNisN201
      Unsigned32,
   dataSigChanNisCircuitSwitchedK
      Unsigned32 }

dataSigChanNisT23 OBJECT-TYPE
   SYNTAX     Unsigned32 (1..15)
   ACCESS     read-write
   STATUS     mandatory
   DESCRIPTION
     "This attribute specifies the layer2 enable request timer."
   DEFVAL     { 10 }
::= { dataSigChanNisL2Entry 1 }

dataSigChanNisT200 OBJECT-TYPE
   SYNTAX     Unsigned32 (1..20)
   ACCESS     read-write
   STATUS     mandatory
   DESCRIPTION
     "This attribute specifies the maximum time between a layer 2 frame 
      and its acknowledgement"
   DEFVAL     { 2 }
::= { dataSigChanNisL2Entry 2 }

dataSigChanNisN200 OBJECT-TYPE
   SYNTAX     Unsigned32 (1..8)
   ACCESS     read-write
   STATUS     mandatory
   DESCRIPTION
     "This attribute specifies the maximum number of re-transmissions of 
      a layer2 frame."
   DEFVAL     { 3 }
::= { dataSigChanNisL2Entry 3 }

dataSigChanNisT203 OBJECT-TYPE
   SYNTAX     Unsigned32 (2..40)
   ACCESS     read-write
   STATUS     mandatory
   DESCRIPTION
     "This attribute specifies the maximum time that a no layer 2 traffic 
      situation can last. Expiry triggers a check on whether the far end is 
      a live."
   DEFVAL     { 10 }
::= { dataSigChanNisL2Entry 4 }

dataSigChanNisN201 OBJECT-TYPE
   SYNTAX     Unsigned32 (4..260)
   ACCESS     read-write
   STATUS     mandatory
   DESCRIPTION
     "This attribute specifies the maximum number of octets in an 
      information field."
   DEFVAL     { 260 }
::= { dataSigChanNisL2Entry 5 }

dataSigChanNisCircuitSwitchedK OBJECT-TYPE
   SYNTAX     Unsigned32 (1..632)
   ACCESS     read-write
   STATUS     mandatory
   DESCRIPTION
     "This attribute specifies the maximum number of frames for B 
      channel use."
   DEFVAL     { 7 }
::= { dataSigChanNisL2Entry 6 }

dataSigChanNisProvTable OBJECT-TYPE
   SYNTAX     SEQUENCE OF DataSigChanNisProvEntry
   ACCESS     not-accessible
   STATUS     mandatory
   DESCRIPTION
     "This group defines the general options of the d-channel signalling 
      link."
::= { dataSigChanNis 13 }

dataSigChanNisProvEntry OBJECT-TYPE
   SYNTAX     DataSigChanNisProvEntry
   ACCESS     not-accessible
   STATUS     mandatory
   DESCRIPTION
     "An entry in the dataSigChanNisProvTable."
   INDEX {
      dataSigChanIndex,
      dataSigChanNisIndex }
::= { dataSigChanNisProvTable 1 }

DataSigChanNisProvEntry ::= SEQUENCE {
   dataSigChanNisSide
      INTEGER }

dataSigChanNisSide OBJECT-TYPE
   SYNTAX     INTEGER  {
                 network(1),
                 user(2) }
   ACCESS     read-write
   STATUS     mandatory
   DESCRIPTION
     "This attribute specifies whether the layer 2 HDLC interface is the 
      network or user side of the connection."
   DEFVAL     { user }
::= { dataSigChanNisProvEntry 1 }

dataSigChanNisOperTable OBJECT-TYPE
   SYNTAX     SEQUENCE OF DataSigChanNisOperEntry
   ACCESS     not-accessible
   STATUS     mandatory
   DESCRIPTION
     "This group provides the operational attributes for the signalling 
      protocol."
::= { dataSigChanNis 15 }

dataSigChanNisOperEntry OBJECT-TYPE
   SYNTAX     DataSigChanNisOperEntry
   ACCESS     not-accessible
   STATUS     mandatory
   DESCRIPTION
     "An entry in the dataSigChanNisOperTable."
   INDEX {
      dataSigChanIndex,
      dataSigChanNisIndex }
::= { dataSigChanNisOperTable 1 }

DataSigChanNisOperEntry ::= SEQUENCE {
   dataSigChanNisActiveChannels
      Unsigned32,
   dataSigChanNisPeakActiveChannels
      Unsigned32,
   dataSigChanNisDChanStatus
      INTEGER }

dataSigChanNisActiveChannels OBJECT-TYPE
   SYNTAX     Unsigned32 (0..128)
   ACCESS     read-only
   STATUS     mandatory
   DESCRIPTION
     "This attribute indicates the number of currently active channels. 
      This includes data and voice channels."
   DEFVAL     { 0 }
::= { dataSigChanNisOperEntry 1 }

dataSigChanNisPeakActiveChannels OBJECT-TYPE
   SYNTAX     Unsigned32 (0..128)
   ACCESS     read-only
   STATUS     mandatory
   DESCRIPTION
     "This attribute indicates the maximum number of channels that have 
      been active on this signalling channel during the last polling period."
   DEFVAL     { 0 }
::= { dataSigChanNisOperEntry 4 }

dataSigChanNisDChanStatus OBJECT-TYPE
   SYNTAX     INTEGER  {
                 outOfService(0),
                 establishing(1),
                 established(2),
                 enabling(3),
                 inService(4),
                 restarting(5) }
   ACCESS     read-only
   STATUS     mandatory
   DESCRIPTION
     "This attribute indicates the state of the D-channel. 
      outOfService means that there is no layer 2 or layer 3 connectivity 
      to the PBX.
      establishing means that the signalling channel is attempting to stage 
      the layer 2.
      established means that the layer 2 is enabled. If the signalling 
      channel stays in the established state, then it is waiting for a restart 
      from the PBX.
      enabling means that the resources for processing calls are being 
      initialized. If the signalling channel stays in the enabling state then 
      it is waiting for a restart acknowledgement from the PBX. 
      inService means that the resources for processing calls are 
      available. 
      restarting means that the resources for call processing are being rei-
      initialized."
::= { dataSigChanNisOperEntry 7 }

dataSigChanNisToolsTable OBJECT-TYPE
   SYNTAX     SEQUENCE OF DataSigChanNisToolsEntry
   ACCESS     not-accessible
   STATUS     mandatory
   DESCRIPTION
     "This group contains a series of operational attributes which turn on 
      and off several kinds of tracing."
::= { dataSigChanNis 16 }

dataSigChanNisToolsEntry OBJECT-TYPE
   SYNTAX     DataSigChanNisToolsEntry
   ACCESS     not-accessible
   STATUS     mandatory
   DESCRIPTION
     "An entry in the dataSigChanNisToolsTable."
   INDEX {
      dataSigChanIndex,
      dataSigChanNisIndex }
::= { dataSigChanNisToolsTable 1 }

DataSigChanNisToolsEntry ::= SEQUENCE {
   dataSigChanNisTracing
      OCTET STRING }

dataSigChanNisTracing OBJECT-TYPE
   SYNTAX     OCTET STRING (SIZE (1))
   ACCESS     read-write
   STATUS     mandatory
   DESCRIPTION
     "This attribute defines which types of tracing are active for this 
      signalling channel.  The tracing messages are sent to the debug 
      stream. To see the messages the agentQueue attribute in Col/debug 
      must be greater than 0 and a Telnet NMIS session must list the 
      debug stream in in its data streams (ex. set nmis telnet session/1 
      dataStreams debug). Different types of tracing can be enabled 
      simultaneously. 
      Note that tracing consumes additional CPU resources and will slow 
      down call processing on a heavily loaded card.  If there is message 
      block exhaustion tracing will be suspended for a period and then 
      automatically reenabled.  An alarm is generated on tracing 
      suspension and resumption.  This mechanism protects the function 
      processor against excessive numbers of tracing messages.
      
      Types of tracing include: 
      protocolErrors - get details of any protocol errors which are 
      occuring. Protocol errors are also reported in summary form as 
      alarms. 
      q931Summary - Summary of the Q.931 messages on the signalling 
      link, including certain call details (calling number, called number, 
      release codes). 
      q931Hex - Q.931 messages displayed in hex format.  Useful to 
      determine protocol compliance in case of errors reported on local or 
      remote ends.
      q931Symbolic - Q.931 messages parsed to give maximum detail.  
      Useful for understanding content of messages flowing on the link.
      portHex - Messages in hex format being sent and received on the 
      link.

      Description of bits:
      protocolErrors(0)
      q931Summary(1)
      q931Hex(2)
      q931Symbolic(3)
      portHex(4)"
::= { dataSigChanNisToolsEntry 1 }


-- 
-- DataSigChan/n ts014 Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length). The Framer component also provides a provisionable 
-- attribute which binds the application component to a specific 
-- hardware component.
-- 
-- The Framer component contains operational attributes for link 
-- interface datapath statistics (such as frame counts and aborts).
-- 

dataSigChanNisFramer OBJECT IDENTIFIER ::= { dataSigChanNis 2 }



dataSigChanNisFramerRowStatusTable OBJECT-TYPE
   SYNTAX     SEQUENCE OF DataSigChanNisFramerRowStatusEntry
   ACCESS     not-accessible
   STATUS     mandatory
   DESCRIPTION
     "This entry controls the addition and deletion of 
      dataSigChanNisFramer components."
::= { dataSigChanNisFramer 1 }

dataSigChanNisFramerRowStatusEntry OBJECT-TYPE
   SYNTAX     DataSigChanNisFramerRowStatusEntry
   ACCESS     not-accessible
   STATUS     mandatory
   DESCRIPTION
     "A single entry in the table represents a single 
      dataSigChanNisFramer component."
   INDEX {
      dataSigChanIndex,
      dataSigChanNisIndex,
      dataSigChanNisFramerIndex }
::= { dataSigChanNisFramerRowStatusTable 1 }

DataSigChanNisFramerRowStatusEntry ::= SEQUENCE {
   dataSigChanNisFramerRowStatus
      RowStatus,
   dataSigChanNisFramerComponentName
      DisplayString,
   dataSigChanNisFramerStorageType
      StorageType,
   dataSigChanNisFramerIndex
      NonReplicated }

dataSigChanNisFramerRowStatus OBJECT-TYPE
   SYNTAX     RowStatus 
   ACCESS     read-only
   STATUS     mandatory
   DESCRIPTION
     "This variable is used as the basis for SNMP naming of
      dataSigChanNisFramer components.
      These components cannot be added nor deleted."
::= { dataSigChanNisFramerRowStatusEntry 1 }

dataSigChanNisFramerComponentName OBJECT-TYPE
   SYNTAX     DisplayString 
   ACCESS     read-only
   STATUS     mandatory
   DESCRIPTION
     "This variable provides the component's string name for
      use with the ASCII Console Interface"
::= { dataSigChanNisFramerRowStatusEntry 2 }

dataSigChanNisFramerStorageType OBJECT-TYPE
   SYNTAX     StorageType 
   ACCESS     read-only
   STATUS     mandatory
   DESCRIPTION
     "This variable represents the storage type value for the
      dataSigChanNisFramer tables."
::= { dataSigChanNisFramerRowStatusEntry 4 }

dataSigChanNisFramerIndex OBJECT-TYPE
   SYNTAX     NonReplicated 
   ACCESS     not-accessible
   STATUS     mandatory
   DESCRIPTION
     "This variable represents the index for the dataSigChanNisFramer tables."
::= { dataSigChanNisFramerRowStatusEntry 10 }

dataSigChanNisFramerProvTable OBJECT-TYPE
   SYNTAX     SEQUENCE OF DataSigChanNisFramerProvEntry
   ACCESS     not-accessible
   STATUS     mandatory
   DESCRIPTION
     "This group contains the base provisioning data for the Framer 
      component. Application or hardware interface specific provisioning 
      data is contained in other provisionable Framer groups."
::= { dataSigChanNisFramer 10 }

dataSigChanNisFramerProvEntry OBJECT-TYPE
   SYNTAX     DataSigChanNisFramerProvEntry
   ACCESS     not-accessible
   STATUS     mandatory
   DESCRIPTION
     "An entry in the dataSigChanNisFramerProvTable."
   INDEX {
      dataSigChanIndex,
      dataSigChanNisIndex,
      dataSigChanNisFramerIndex }
::= { dataSigChanNisFramerProvTable 1 }

DataSigChanNisFramerProvEntry ::= SEQUENCE {
   dataSigChanNisFramerInterfaceName
      Link }

dataSigChanNisFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dataSigChanNisFramerProvEntry 1 }

dataSigChanNisFramerStateTable OBJECT-TYPE
   SYNTAX     SEQUENCE OF DataSigChanNisFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dataSigChanNisFramer 12 }

dataSigChanNisFramerStateEntry OBJECT-TYPE
   SYNTAX     DataSigChanNisFramerStateEntry
   ACCESS     not-accessible
   STATUS     mandatory
   DESCRIPTION
     "An entry in the dataSigChanNisFramerStateTable."
   INDEX {
      dataSigChanIndex,
      dataSigChanNisIndex,
      dataSigChanNisFramerIndex }
::= { dataSigChanNisFramerStateTable 1 }

DataSigChanNisFramerStateEntry ::= SEQUENCE {
   dataSigChanNisFramerAdminState
      INTEGER,
   dataSigChanNisFramerOperationalState
      INTEGER,
   dataSigChanNisFramerUsageState
      INTEGER }

dataSigChanNisFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dataSigChanNisFramerStateEntry 1 }

dataSigChanNisFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dataSigChanNisFramerStateEntry 2 }

dataSigChanNisFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dataSigChanNisFramerStateEntry 3 }

dataSigChanNisFramerStatsTable OBJECT-TYPE
   SYNTAX     SEQUENCE OF DataSigChanNisFramerStatsEntry
   ACCESS     not-accessible
   STATUS     mandatory
   DESCRIPTION
     "This group contains the operational statistics data for a Framer 
      component."
::= { dataSigChanNisFramer 13 }

dataSigChanNisFramerStatsEntry OBJECT-TYPE
   SYNTAX     DataSigChanNisFramerStatsEntry
   ACCESS     not-accessible
   STATUS     mandatory
   DESCRIPTION
     "An entry in the dataSigChanNisFramerStatsTable."
   INDEX {
      dataSigChanIndex,
      dataSigChanNisIndex,
      dataSigChanNisFramerIndex }
::= { dataSigChanNisFramerStatsTable 1 }

DataSigChanNisFramerStatsEntry ::= SEQUENCE {
   dataSigChanNisFramerFrmToIf
      Unsigned32,
   dataSigChanNisFramerFrmFromIf
      Unsigned32,
   dataSigChanNisFramerOctetFromIf
      Unsigned32,
   dataSigChanNisFramerAborts
      Unsigned32,
   dataSigChanNisFramerCrcErrors
      Unsigned32,
   dataSigChanNisFramerLrcErrors
      Unsigned32,
   dataSigChanNisFramerNonOctetErrors
      Unsigned32,
   dataSigChanNisFramerOverruns
      Unsigned32,
   dataSigChanNisFramerUnderruns
      Unsigned32,
   dataSigChanNisFramerLargeFrmErrors
      Unsigned32 }

dataSigChanNisFramerFrmToIf OBJECT-TYPE
   SYNTAX     Unsigned32 (0..4294967295)
   ACCESS     read-only
   STATUS     mandatory
   DESCRIPTION
     "This attribute counts the number of frames transmitted to the link 
      interface by Framer.
      This count wraps to zero after reaching its maximum value."
   DEFVAL     { 0 }
::= { dataSigChanNisFramerStatsEntry 1 }

dataSigChanNisFramerFrmFromIf OBJECT-TYPE
   SYNTAX     Unsigned32 (0..4294967295)
   ACCESS     read-only
   STATUS     mandatory
   DESCRIPTION
     "This attribute counts the number of frames received from the link 
      interface by Framer.
      This count wraps to zero after reaching its maximum value."
   DEFVAL     { 0 }
::= { dataSigChanNisFramerStatsEntry 2 }

dataSigChanNisFramerOctetFromIf OBJECT-TYPE
   SYNTAX     Unsigned32 (0..4294967295)
   ACCESS     read-only
   STATUS     mandatory
   DESCRIPTION
     "The number of bytes received from the link interface by Framer."
   DEFVAL     { 0 }
::= { dataSigChanNisFramerStatsEntry 3 }

dataSigChanNisFramerAborts OBJECT-TYPE
   SYNTAX     Unsigned32 (0..4294967295)
   ACCESS     read-only
   STATUS     mandatory
   DESCRIPTION
     "This attribute counts the total number of aborts received.
      This count wraps to zero after reaching its maximum value."
   DEFVAL     { 0 }
::= { dataSigChanNisFramerStatsEntry 4 }

dataSigChanNisFramerCrcErrors OBJECT-TYPE
   SYNTAX     Unsigned32 (0..4294967295)
   ACCESS     read-only
   STATUS     mandatory
   DESCRIPTION
     "This attribute counts the total number of frames with CRC errors.
      This count wraps to zero after reaching its maximum value."
   DEFVAL     { 0 }
::= { dataSigChanNisFramerStatsEntry 5 }

dataSigChanNisFramerLrcErrors OBJECT-TYPE
   SYNTAX     Unsigned32 (0..4294967295)
   ACCESS     read-only
   STATUS     mandatory
   DESCRIPTION
     "This attribute counts the total number of frames with LRC errors.
      This count wraps to zero after reaching its maximum value."
   DEFVAL     { 0 }
::= { dataSigChanNisFramerStatsEntry 6 }

dataSigChanNisFramerNonOctetErrors OBJECT-TYPE
   SYNTAX     Unsigned32 (0..4294967295)
   ACCESS     read-only
   STATUS     mandatory
   DESCRIPTION
     "This attribute counts the total number of frames that were non octet 
      aligned.
      This count wraps to zero after reaching its maximum value."
   DEFVAL     { 0 }
::= { dataSigChanNisFramerStatsEntry 7 }

dataSigChanNisFramerOverruns OBJECT-TYPE
   SYNTAX     Unsigned32 (0..4294967295)
   ACCESS     read-only
   STATUS     mandatory
   DESCRIPTION
     "This attribute counts the total number of frames received from the 
      link for which overruns occurred.
      This count wraps to zero after reaching its maximum value."
   DEFVAL     { 0 }
::= { dataSigChanNisFramerStatsEntry 8 }

dataSigChanNisFramerUnderruns OBJECT-TYPE
   SYNTAX     Unsigned32 (0..4294967295)
   ACCESS     read-only
   STATUS     mandatory
   DESCRIPTION
     "This attribute counts the total number of frames transmitted to the 
      link for which underruns occurred.
      This count wraps to zero after reaching its maximum value."
   DEFVAL     { 0 }
::= { dataSigChanNisFramerStatsEntry 9 }

dataSigChanNisFramerLargeFrmErrors OBJECT-TYPE
   SYNTAX     Unsigned32 (0..4294967295)
   ACCESS     read-only
   STATUS     mandatory
   DESCRIPTION
     "This attribute counts the total number of frames received which 
      were too large. The frame was longer than 500 bytes.
      This count wraps to zero after reaching its maximum value."
   DEFVAL     { 0 }
::= { dataSigChanNisFramerStatsEntry 10 }




-- 
-- Version and Compliance statements
-- 



-- Object-Group Statement:
-- A list of all current accessible leaf objects.

-- OBJECTS { dataSigChanNisFramerOctetFromIf,
--           dataSigChanNisT203,
--           dataSigChanNisFramerFrmToIf,
--           dataSigChanNisDChanStatus,
--           dataSigChanNisFramerAdminState,
--           dataSigChanNisFramerLrcErrors,
--           dataSigChanNisFramerOverruns,
--           dataSigChanNisFramerAborts,
--           dataSigChanNisFramerRowStatus,
--           dataSigChanNisFramerLargeFrmErrors,
--           dataSigChanNisTracing,
--           dataSigChanNisFramerStorageType,
--           dataSigChanNisRowStatus,
--           dataSigChanNisN201,
--           dataSigChanNisT23,
--           dataSigChanNisFramerNonOctetErrors,
--           dataSigChanNisPeakActiveChannels,
--           dataSigChanNisFramerUsageState,
--           dataSigChanNisStorageType,
--           dataSigChanNisFramerComponentName,
--           dataSigChanNisN200,
--           dataSigChanNisFramerFrmFromIf,
--           dataSigChanNisFramerInterfaceName,
--           dataSigChanNisComponentName,
--           dataSigChanNisCircuitSwitchedK,
--           dataSigChanNisFramerUnderruns,
--           dataSigChanNisSide,
--           dataSigChanNisFramerCrcErrors,
--           dataSigChanNisActiveChannels,
--           dataSigChanNisFramerOperationalState,
--           dataSigChanNisT200 }
-- STATUS  mandatory
-- DESCRIPTION
--   "A list of all current accessible leaf objects."

disdnNISGroup OBJECT IDENTIFIER ::= { disdnNISMIB 1 }
disdnNISGroupBE OBJECT IDENTIFIER ::= { disdnNISGroup 5 }
disdnNISGroupBE00 OBJECT IDENTIFIER ::= { disdnNISGroupBE 1 }
disdnNISGroupBE00A OBJECT IDENTIFIER ::= { disdnNISGroupBE00 2 }



-- Agent-Capabilities Statement:

-- PRODUCT-RELEASE "Passport Release 7.0 DisdnNIS."
-- STATUS          mandatory
-- DESCRIPTION     "DisdnNIS MIB: MIB Version BE00A,
--                  Software Version BG00S4C."
-- SUPPORTS        Nortel-Magellan-Passport-DisdnNISMIB
--    INCLUDES     { disdnNISGroupBE00A }

disdnNISCapabilities OBJECT IDENTIFIER ::= { disdnNISMIB 3 }
disdnNISCapabilitiesBE OBJECT IDENTIFIER ::= { disdnNISCapabilities 5 }
disdnNISCapabilitiesBE00 OBJECT IDENTIFIER ::= { disdnNISCapabilitiesBE 1 }
disdnNISCapabilitiesBE00A OBJECT IDENTIFIER ::= { disdnNISCapabilitiesBE00 2 }





END
