TERM-PROT-MIB DEFINITIONS ::= BEGIN
	IMPORTS
          OBJECT-TYPE, MODULE-IDENTITY, Integer32, IpAddress
                   FROM SNMPv2-SMI
          RowStatus, DisplayString
                   FROM SNMPv2-TC
          common, UsrConfigStatus
                  FROM USR-DEFINITIONS-MIB;
usrTermProt MODULE-IDENTITY
        LAST-UPDATED "200208231615Z"
        ORGANIZATION "CommWorks Corporation, a 3Com Company"
        CONTACT-INFO "Customer Support"
        DESCRIPTION
           "The commWorks enterprise defined MIB objects  for Terminal
            Protocols Process."
       ::= { common 18 }
--      REVISION "200208231615Z"
--      DESCRIPTION "Clarified usage and labels for usrTermProtTelnetEscEnabled
--          usrTermProtTelnetShowTryingMsg, usrTermProtTelnetClientAccess,
--          usrTelnetTerminalDownloadMode, usrTermProtRloginEscEnabled,
--          usrTermProtTelnetShowDisconnect."
--      REVISION "200205051800Z"
--      DESCRIPTION "Converted to SNMPv2"
-- Begin managed object definitions here...
usrTermProtCFMStatusFlag OBJECT-TYPE
	SYNTAX		UsrConfigStatus
	MAX-ACCESS		read-write
	STATUS		    current
	DESCRIPTION
		"This variable controls saving and loading of configuration
		information for the Terminal Protocols Module. The value can 
		be set to either save or load by a management station. The other
		values indicate if any configuration operation and what type
		is in progress."
::= { usrTermProt 1 }
usrTermProtCfgFileName OBJECT-TYPE
	SYNTAX      DisplayString
	MAX-ACCESS      read-only
	STATUS          current
	DESCRIPTION		
		"The name of a ConfigFile to read/write  permanent database records.
		 If the value of this object is an empty string, then the Terminal
		 Protocols module uses the default name `@file://TermProt.cfg'. "
::= { usrTermProt 2 }
usrTermProtConnectedMsg OBJECT-TYPE
	SYNTAX      DisplayString
	MAX-ACCESS      read-write
	STATUS          current
	DESCRIPTION		
		"The string which is displayed when a ClearTCP client session
		is connected to the remote TCP host. If the value of this object
		is an empty string, the Terminal Protocols module uses a 
		default of CONNECTED"
	--CONFIGURABLE
::= { usrTermProt 3 }
usrTermProtTelnetEscEnabled OBJECT-TYPE
	SYNTAX          INTEGER {
                        enabled(1),
                        disabled(2)
                        }
	MAX-ACCESS      read-write
	STATUS          current
	DESCRIPTION		
		"If set to DISABLED, this object prevents all Telnet Clients
		from using the escape character during a session. If they
		enter that character, it will be sent as regular text. If
		set to ENABLED, the user will be permitted to enter the
		escape character to use the local Telnet command line."
	--CONFIGURABLE
::= { usrTermProt 4 }
usrTermProtAllowManageUsers OBJECT-TYPE
        SYNTAX  INTEGER {
                        manage-off(0),
                        manage-on (1)
                        }
        MAX-ACCESS  read-write
        STATUS      current
        DESCRIPTION
                "This variable turns on/off the ability to manage the system
                 through telnet server connections."
        --CONFIGURABLE
::= { usrTermProt 5 }
usrTermProtTelnetShowTryingMsg  OBJECT-TYPE
	SYNTAX          INTEGER {
                        enabled(1),
                        disabled(2)
                        }
        MAX-ACCESS  read-write
        STATUS      current
        DESCRIPTION
                "This variable turns on/off the trying status message for 
                 telnet to terminal servers."
        --CONFIGURABLE
::= { usrTermProt 6 }
usrTermProtTelnetClientAccess OBJECT-TYPE
	SYNTAX          INTEGER {
                        enabled(1),
                        disabled(2)
                        }
	MAX-ACCESS      read-write
	STATUS          current
	DESCRIPTION		
		"This indicates whether to use the client access table.
		 By default, this value will be disabled.
		If set to enabled, the users can telnet into the HARC only
		from ip addresses added in the client access table. If the value
		if set to disabled, the client access table is not referred to."
	--CONFIGURABLE
::= { usrTermProt 7 }
usrTelnetAccessTable OBJECT-TYPE
		SYNTAX  SEQUENCE OF UsrTelnetAccessEntry
         	MAX-ACCESS  not-accessible
         	STATUS      current
         	DESCRIPTION
            "The Telnet access table"
::= { usrTermProt 8 }
usrTelnetAccessEntry OBJECT-TYPE
         	SYNTAX  UsrTelnetAccessEntry
         	MAX-ACCESS  not-accessible
         	STATUS      current
         	DESCRIPTION
            ""
         INDEX   { usrTelnetAccessIpAddr }
::= { usrTelnetAccessTable 1 }
UsrTelnetAccessEntry ::=
         	SEQUENCE {
         	usrTelnetAccessIpAddr IpAddress,
         	usrTelnetAccessIpMask IpAddress,
         	usrTelnetAccessStatus INTEGER
         }
usrTelnetAccessIpAddr OBJECT-TYPE
         	SYNTAX  IpAddress
         	MAX-ACCESS  not-accessible
         	STATUS      current
         	DESCRIPTION
            "The IP Address of the station allowed for telnet into HiPerARC."
::= { usrTelnetAccessEntry 1 }
usrTelnetAccessStatus OBJECT-TYPE
	 	SYNTAX   INTEGER {
			add(1),
			normal(2),
			delete(3)
			}
         	MAX-ACCESS   read-write
         	STATUS       current
         	DESCRIPTION
            "The status of the entry for this address."
          --CONFIGURABLE
::= { usrTelnetAccessEntry 2 }
usrTelnetAccessIpMask OBJECT-TYPE
         	SYNTAX  IpAddress
         	MAX-ACCESS  read-write
         	STATUS      current
         	DESCRIPTION
            "The IP Address of the station allowed for telnet into HiPerARC."
        --CONFIGURABLE
::= { usrTelnetAccessEntry 3 }
usrTelnetTerminalDownloadMode OBJECT-TYPE
			SYNTAX      INTEGER {
                            enabled(1),
                            disabled(2)
                            }
			MAX-ACCESS  read-write
         	STATUS      current
         	DESCRIPTION
            "Will cause telnet client on non-23 port disable ECHO in local
			 and remote side"
        --CONFIGURABLE
::= { usrTermProt 9 }
usrTermProtRloginEscEnabled OBJECT-TYPE
    SYNTAX          INTEGER {
                        enabled(1),
                        disabled(2)
                        }
    MAX-ACCESS      read-write
    STATUS          current
    DESCRIPTION
        "If set to disabled, this object prevents all Rlogin Clients
        from using the escape character during a session. If they
        enter that character, it will be sent as regular text. If
        set to enabled, the user will be permitted to enter the
        escape character to use the local Telnet command line."
    --CONFIGURABLE
::= { usrTermProt 10 }
usrTermProtTelnetShowDisconnect  OBJECT-TYPE
   	SYNTAX      INTEGER {
                    enabled(1),
                    disabled(2)
                    }
    MAX-ACCESS  read-write
    STATUS      current
    DESCRIPTION
            "This variable enabled/disables the disconnect message for 
             telnet/cleartcp connections "
        --CONFIGURABLE
::= { usrTermProt 11 }
usrCTCPEncryptionTable OBJECT-TYPE
	SYNTAX SEQUENCE OF UsrCTCPEncryptionEntry
	MAX-ACCESS not-accessible
	STATUS     current
	DESCRIPTION
		"The table of cleartcp encryption ids and keys. "
::= { usrTermProt 12 }
usrTermProtTelnetBannerFile  OBJECT-TYPE
	SYNTAX      OCTET STRING
        MAX-ACCESS  read-write
        STATUS      current
        DESCRIPTION
                " Banner text displayed to admin users telneting to the system"
        --CONFIGURABLE
::= { usrTermProt 13 }
usrCTCPEncryptionEntry OBJECT-TYPE
	SYNTAX UsrCTCPEncryptionEntry
	MAX-ACCESS not-accessible
	STATUS     current
	DESCRIPTION
                "A (conceptual) entry for one encryption id and key."
	INDEX { usrCTCPEncryptionId }
::= { usrCTCPEncryptionTable 1 }
UsrCTCPEncryptionEntry ::= SEQUENCE {
	usrCTCPEncryptionId		DisplayString,
	usrCTCPEncryptionKey	Integer32,
        usrCTCPEncryptionStatus     RowStatus
	}
usrCTCPEncryptionId OBJECT-TYPE
	SYNTAX		DisplayString
	MAX-ACCESS          not-accessible
	STATUS		    current
	DESCRIPTION
		"The logical identifier of the encryption id-key Table. "
::= { usrCTCPEncryptionEntry 1 }
usrCTCPEncryptionKey OBJECT-TYPE
	SYNTAX		Integer32
	MAX-ACCESS      read-write
	STATUS		    current
	DESCRIPTION
		"Key number corresponds to the encryption-id in the table"
	--CONFIGURABLE
::= { usrCTCPEncryptionEntry 2 }
usrCTCPEncryptionStatus OBJECT-TYPE
	SYNTAX		RowStatus
	MAX-ACCESS      read-write
	STATUS		    current
	DESCRIPTION
		"The status of this row of the CTCP Encryption Table. "
	--CONFIGURABLE
::= { usrCTCPEncryptionEntry 3 }
END     -- End of TERM-PROT-MIB DEFINITIONS
-- ************************************************************************
--
--    usr_fr.mib - The Commworks Frame Relay MIB module
--
-- Author:         <Ginny Walker>
--
