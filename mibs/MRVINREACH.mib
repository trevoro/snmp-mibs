-- varfix Fri Jun 28 10:13:33 EDT 2002 user: sse
-- File created using agent2concat
-- By: sse
-- Date: Fri Jun 28 10:11:32 EDT 2002


MRVINREACH DEFINITIONS ::= BEGIN

--
-- FILE: /users/sse/mibs/src/rfc/rfc1155.smi
--

-- Changes to rfc1155 (SMI):
--      Removed EXPORTS.
--      Added explicit definitions of ccitt, null, iso, org, and dod.
--      Commented out OBJECT-TYPE macro definition (since will use
--        the definition from RFC1212).
--      Commented out definitions of syntax types and replaced
--        with SMIC directives to enable them.



        -- no IMPORTS
		  
IMPORTS
	OBJECT-TYPE, TimeTicks, Gauge, Counter, NetworkAddress, IpAddress
		FROM RFC1155-SMI
	TRAP-TYPE
		FROM RFC-1215		  
;

        -- Define OIDs
        ccitt        OBJECT IDENTIFIER ::= { 0 }
        null         OBJECT IDENTIFIER ::= { ccitt 0 }

        iso          OBJECT IDENTIFIER ::= { 1 }
        org          OBJECT IDENTIFIER ::= { iso 3 }
        dod          OBJECT IDENTIFIER ::= { org 6 }
        internet     OBJECT IDENTIFIER ::= { dod 1 }
        directory    OBJECT IDENTIFIER ::= { internet 1 }
        mgmt         OBJECT IDENTIFIER ::= { internet 2 }
        experimental OBJECT IDENTIFIER ::= { internet 3 }
        private      OBJECT IDENTIFIER ::= { internet 4 }
        enterprises  OBJECT IDENTIFIER ::= { private 1 }

        -- Make builtin items known
--        SMI NetworkAddress
--        SMI IpAddress
--        SMI Counter
--        SMI Gauge
--        SMI TimeTicks
--        SMI Opaque


        -- definition of object types

        --    OBJECT-TYPE MACRO ::=
        --    BEGIN
        --        TYPE NOTATION ::= "SYNTAX" type (TYPE ObjectSyntax)
        --                          "ACCESS" Access
        --                          "STATUS" Status
        --        VALUE NOTATION ::= value (VALUE ObjectName)
        --
        --        Access ::= "read-only"
        --                        | "read-write"
        --                        | "write-only"
        --                        | "not-accessible"
        --        Status ::= "mandatory"
        --                        | "optional"
        --                        | "obsolete"
        --    END
        --
        -- names of objects in the MIB
        --
        --       ObjectName ::= OBJECT IDENTIFIER
        --
        -- syntax of objects in the MIB
        --
        --       ObjectSyntax ::=
        --           CHOICE {
        --               simple
        --                   SimpleSyntax,
               -- note that simple SEQUENCEs are not directly
               -- mentioned here to keep things simple (i.e.,
               -- prevent mis-use).  However, application-wide
               -- types which are IMPLICITly encoded simple
               -- SEQUENCEs may appear in the following CHOICE
        --
        --               application-wide
        --                   ApplicationSyntax
        --           }
        --
        --          SimpleSyntax ::=
        --              CHOICE {
        --                  number INTEGER,
        --                  string OCTET STRING,
        --                  object OBJECT IDENTIFIER,
        --                  empty  NULL
        --              }
        --
        --          ApplicationSyntax ::=
        --              CHOICE {
        --                  address NetworkAddress,
        --                  counter Counter,
        --                  gauge Gauge,
        --                  ticks TimeTicks,
        --                  arbitrary Opaque
                  -- other application-wide types, as they are
                  -- defined, will be added here
        --              }
        --
        --
                  -- application-wide types

        --          NetworkAddress ::=
        --              CHOICE {
        --                  internet IpAddress
        --              }
        --
        --          IpAddress ::=
        --              [APPLICATION 0]
        --                  IMPLICIT OCTET STRING (SIZE (4))
        --
        --          Counter ::=
        --              [APPLICATION 1]
        --                  IMPLICIT INTEGER (0..4294967295)
        --
        --          Gauge ::=
        --              [APPLICATION 2]
        --                  IMPLICIT INTEGER (0..4294967295)
        --
        --          TimeTicks ::=
        --              [APPLICATION 3]
        --                  IMPLICIT INTEGER (0..4294967295)
        --
        --          Opaque ::=
        --              [APPLICATION 4]
        --                  IMPLICIT OCTET STRING

--
-- FILE: /users/sse/mibs/src/rfc/rfc1212.smi
--

-- changes to rfc1212 (Concise MIB OBJECT-TYPE definition):
--      Removed IMPORTS.
--      Commented out OBJECT-TYPE macro definition and replaced
--        with SMIC directive to enable it.




    -- Make builtin items known
--    SMI OBJECT-TYPE


        --  OBJECT-TYPE MACRO ::=
        --  BEGIN
        --      TYPE NOTATION ::=
                                          -- must conform to
                                          -- RFC1155's ObjectSyntax
        --                        "SYNTAX" type(ObjectSyntax)
        --                        "ACCESS" Access
        --                        "STATUS" Status
        --                        DescrPart
        --                        ReferPart
        --                        IndexPart
        --                        DefValPart
        --      VALUE NOTATION ::= value (VALUE ObjectName)
        --
        --      Access ::= "read-only"
        --                      | "read-write"
        --                      | "write-only"
        --                      | "not-accessible"
        --      Status ::= "mandatory"
        --                      | "optional"
        --                      | "obsolete"
        --                      | "deprecated"
        --
        --      DescrPart ::=
        --                 "DESCRIPTION" value (description DisplayString)
        --                      | empty
        --
        --      ReferPart ::=
        --                 "REFERENCE" value (reference DisplayString)
        --                      | empty
        --
        --      IndexPart ::=
        --                 "INDEX" "{" IndexTypes "}"
        --                      | empty
        --      IndexTypes ::=
        --                 IndexType | IndexTypes "," IndexType
        --      IndexType ::=
                                  -- if indexobject, use the SYNTAX
                                  -- value of the correspondent
                                  -- OBJECT-TYPE invocation
        --                 value (indexobject ObjectName)
                                  -- otherwise use named SMI type
                                  -- must conform to IndexSyntax below
        --                      | type (indextype)
        --
        --      DefValPart ::=
        --                 "DEFVAL" "{" value (defvalue ObjectSyntax) "}"
        --                      | empty
        --  END
        --
        --  IndexSyntax ::=
        --      CHOICE {
        --          number
        --              INTEGER (0..MAX),
        --          string
        --              OCTET STRING,
        --          object
        --              OBJECT IDENTIFIER,
        --          address
        --              NetworkAddress,
        --          ipAddress
        --              IpAddress
        --      }

--
-- FILE: /users/sse/mibs/src/rfc/rfc1213.mib
--

-- Changes to rfc1213 (MIB-II):
--      No changes needed.




          --  This MIB module uses the extended OBJECT-TYPE macro as
          --  defined in [14];


          --  MIB-II (same prefix as MIB-I)

          mib-2      OBJECT IDENTIFIER ::= { mgmt 1 }

          -- textual conventions

          DisplayString ::=
              OCTET STRING
          -- This data type is used to model textual information taken
          -- from the NVT ASCII character set.  By convention, objects
          -- with this syntax are declared as having
          --
          --      SIZE (0..255)

          PhysAddress ::=
              OCTET STRING
          -- This data type is used to model media addresses.  For many
          -- types of media, this will be in a binary representation.
          -- For example, an ethernet address would be represented as
          -- a string of 6 octets.


          -- groups in MIB-II

          system       OBJECT IDENTIFIER ::= { mib-2 1 }

          interfaces   OBJECT IDENTIFIER ::= { mib-2 2 }

          at           OBJECT IDENTIFIER ::= { mib-2 3 }

          ip           OBJECT IDENTIFIER ::= { mib-2 4 }

          icmp         OBJECT IDENTIFIER ::= { mib-2 5 }

          tcp          OBJECT IDENTIFIER ::= { mib-2 6 }

          udp          OBJECT IDENTIFIER ::= { mib-2 7 }

          egp          OBJECT IDENTIFIER ::= { mib-2 8 }

          -- historical (some say hysterical)
          -- cmot      OBJECT IDENTIFIER ::= { mib-2 9 }

          transmission OBJECT IDENTIFIER ::= { mib-2 10 }

          snmp         OBJECT IDENTIFIER ::= { mib-2 11 }


          -- the System group

          -- Implementation of the System group is mandatory for all
          -- systems.  If an agent is not configured to have a value
          -- for any of these variables, a string of length 0 is
          -- returned.

          sysDescr OBJECT-TYPE
              SYNTAX  DisplayString (SIZE (0..255))
              ACCESS  read-only
              STATUS  mandatory
              DESCRIPTION
                      "A textual description of the entity.  This value
                      should include the full name and version
                      identification of the system's hardware type,
                      software operating-system, and networking
                      software.  It is mandatory that this only contain
                      printable ASCII characters."
              ::= { system 1 }

          sysObjectID OBJECT-TYPE
              SYNTAX  OBJECT IDENTIFIER
              ACCESS  read-only
              STATUS  mandatory
              DESCRIPTION
                      "The vendor's authoritative identification of the
                      network management subsystem contained in the
                      entity.  This value is allocated within the SMI
                      enterprises subtree (1.3.6.1.4.1) and provides an
                      easy and unambiguous means for determining `what
                      kind of box' is being managed.  For example, if
                      vendor `Flintstones, Inc.' was assigned the
                      subtree 1.3.6.1.4.1.4242, it could assign the
                      identifier 1.3.6.1.4.1.4242.1.1 to its `Fred
                      Router'."
              ::= { system 2 }

          sysUpTime OBJECT-TYPE
              SYNTAX  TimeTicks
              ACCESS  read-only
              STATUS  mandatory
              DESCRIPTION
                      "The time (in hundredths of a second) since the
                      network management portion of the system was last
                      re-initialized."
              ::= { system 3 }

          sysContact OBJECT-TYPE
              SYNTAX  DisplayString (SIZE (0..255))
              ACCESS  read-write
              STATUS  mandatory
              DESCRIPTION
                      "The textual identification of the contact person
                      for this managed node, together with information
                      on how to contact this person."
              ::= { system 4 }

          sysName OBJECT-TYPE
              SYNTAX  DisplayString (SIZE (0..255))
              ACCESS  read-write
              STATUS  mandatory
              DESCRIPTION
                      "An administratively-assigned name for this
                      managed node.  By convention, this is the node's
                      fully-qualified domain name."
              ::= { system 5 }

          sysLocation OBJECT-TYPE
              SYNTAX  DisplayString (SIZE (0..255))
              ACCESS  read-write
              STATUS  mandatory
              DESCRIPTION
                      "The physical location of this node (e.g.,
                      `telephone closet, 3rd floor')."
              ::= { system 6 }

          sysServices OBJECT-TYPE
              SYNTAX  INTEGER (0..127)
              ACCESS  read-only
              STATUS  mandatory
              DESCRIPTION
                      "A value which indicates the set of services that
                      this entity primarily offers.

                      The value is a sum.  This sum initially takes the
                      value zero, Then, for each layer, L, in the range
                      1 through 7, that this node performs transactions
                      for, 2 raised to (L - 1) is added to the sum.  For
                      example, a node which performs primarily routing
                      functions would have a value of 4 (2^(3-1)).  In
                      contrast, a node which is a host offering
                      application services would have a value of 72
                      (2^(4-1) + 2^(7-1)).  Note that in the context of
                      the Internet suite of protocols, values should be
                      calculated accordingly:

                           layer  functionality
                               1  physical (e.g., repeaters)
                               2  datalink/subnetwork (e.g., bridges)
                               3  internet (e.g., IP gateways)
                               4  end-to-end  (e.g., IP hosts)
                               7  applications (e.g., mail relays)

                      For systems including OSI protocols, layers 5 and
                      6 may also be counted."
              ::= { system 7 }


          -- the Interfaces group

          -- Implementation of the Interfaces group is mandatory for
          -- all systems.

          ifNumber OBJECT-TYPE
              SYNTAX  INTEGER
              ACCESS  read-only
              STATUS  mandatory
              DESCRIPTION
                      "The number of network interfaces (regardless of
                      their current state) present on this system."
              ::= { interfaces 1 }


          -- the Interfaces table

          -- The Interfaces table contains information on the entity's
          -- interfaces.  Each interface is thought of as being
          -- attached to a `subnetwork'.  Note that this term should
          -- not be confused with `subnet' which refers to an
          -- addressing partitioning scheme used in the Internet suite
          -- of protocols.

          ifTable OBJECT-TYPE
              SYNTAX  SEQUENCE OF IfEntry
              ACCESS  not-accessible
              STATUS  mandatory
              DESCRIPTION
                      "A list of interface entries.  The number of
                      entries is given by the value of ifNumber."
              ::= { interfaces 2 }

          ifEntry OBJECT-TYPE
              SYNTAX  IfEntry
              ACCESS  not-accessible
              STATUS  mandatory
              DESCRIPTION
                      "An interface entry containing objects at the
                      subnetwork layer and below for a particular
                      interface."
              INDEX   { ifIndex }
              ::= { ifTable 1 }

          IfEntry ::=
              SEQUENCE {
                  ifIndex
                      INTEGER,
                  ifDescr
                      DisplayString,
                  ifType
                      INTEGER,
                  ifMtu
                      INTEGER,
                  ifSpeed
                      Gauge,
                  ifPhysAddress
                      PhysAddress,
                  ifAdminStatus
                      INTEGER,
                  ifOperStatus
                      INTEGER,
                  ifLastChange
                      TimeTicks,
                  ifInOctets
                      Counter,
                  ifInUcastPkts
                      Counter,
                  ifInNUcastPkts
                      Counter,
                  ifInDiscards
                      Counter,
                  ifInErrors
                      Counter,
                  ifInUnknownProtos
                      Counter,
                  ifOutOctets
                      Counter,
                  ifOutUcastPkts
                      Counter,
                  ifOutNUcastPkts
                      Counter,
                  ifOutDiscards
                      Counter,
                  ifOutErrors
                      Counter,
                  ifOutQLen
                      Gauge,
                  ifSpecific
                      OBJECT IDENTIFIER
              }

          ifIndex OBJECT-TYPE
              SYNTAX  INTEGER
              ACCESS  read-only
              STATUS  mandatory
              DESCRIPTION
                      "A unique value for each interface.  Its value
                      ranges between 1 and the value of ifNumber.  The
                      value for each interface must remain constant at
                      least from one re-initialization of the entity's
                      network management system to the next re-
                      initialization."
              ::= { ifEntry 1 }

          ifDescr OBJECT-TYPE
              SYNTAX  DisplayString (SIZE (0..255))
              ACCESS  read-only
              STATUS  mandatory
              DESCRIPTION
                      "A textual string containing information about the
                      interface.  This string should include the name of
                      the manufacturer, the product name and the version
                      of the hardware interface."
              ::= { ifEntry 2 }

          ifType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32)
                      }
              ACCESS  read-only
              STATUS  mandatory
              DESCRIPTION
                      "The type of interface, distinguished according to
                      the physical/link protocol(s) immediately `below'
                      the network layer in the protocol stack."
              ::= { ifEntry 3 }

          ifMtu OBJECT-TYPE
              SYNTAX  INTEGER
              ACCESS  read-only
              STATUS  mandatory
              DESCRIPTION
                      "The size of the largest datagram which can be
                      sent/received on the interface, specified in
                      octets.  For interfaces that are used for
                      transmitting network datagrams, this is the size
                      of the largest network datagram that can be sent
                      on the interface."
              ::= { ifEntry 4 }

          ifSpeed OBJECT-TYPE
              SYNTAX  Gauge
              ACCESS  read-only
              STATUS  mandatory
              DESCRIPTION
                      "An estimate of the interface's current bandwidth
                      in bits per second.  For interfaces which do not
                      vary in bandwidth or for those where no accurate
                      estimation can be made, this object should contain
                      the nominal bandwidth."
              ::= { ifEntry 5 }

          ifPhysAddress OBJECT-TYPE
              SYNTAX  PhysAddress
              ACCESS  read-only
              STATUS  mandatory
              DESCRIPTION
                      "The interface's address at the protocol layer
                      immediately `below' the network layer in the
                      protocol stack.  For interfaces which do not have
                      such an address (e.g., a serial line), this object
                      should contain an octet string of zero length."
              ::= { ifEntry 6 }

          ifAdminStatus OBJECT-TYPE
              SYNTAX  INTEGER {
                          up(1),       -- ready to pass packets
                          down(2),
                          testing(3)   -- in some test mode
                      }
              ACCESS  read-write
              STATUS  mandatory
              DESCRIPTION
                      "The desired state of the interface.  The
                      testing(3) state indicates that no operational
                      packets can be passed."
              ::= { ifEntry 7 }

          ifOperStatus OBJECT-TYPE
              SYNTAX  INTEGER {
                          up(1),       -- ready to pass packets
                          down(2),
                          testing(3)   -- in some test mode
                      }
              ACCESS  read-only
              STATUS  mandatory
              DESCRIPTION
                      "The current operational state of the interface.
                      The testing(3) state indicates that no operational
                      packets can be passed."
              ::= { ifEntry 8 }

          ifLastChange OBJECT-TYPE
              SYNTAX  TimeTicks
              ACCESS  read-only
              STATUS  mandatory
              DESCRIPTION
                      "The value of sysUpTime at the time the interface
                      entered its current operational state.  If the
                      current state was entered prior to the last re-
                      initialization of the local network management
                      subsystem, then this object contains a zero
                      value."
              ::= { ifEntry 9 }

          ifInOctets OBJECT-TYPE
              SYNTAX  Counter
              ACCESS  read-only
              STATUS  mandatory
              DESCRIPTION
                      "The total number of octets received on the
                      interface, including framing characters."
              ::= { ifEntry 10 }

          ifInUcastPkts OBJECT-TYPE
              SYNTAX  Counter
              ACCESS  read-only
              STATUS  mandatory
              DESCRIPTION
                      "The number of subnetwork-unicast packets
                      delivered to a higher-layer protocol."
              ::= { ifEntry 11 }

          ifInNUcastPkts OBJECT-TYPE
              SYNTAX  Counter
              ACCESS  read-only
              STATUS  mandatory
              DESCRIPTION
                      "The number of non-unicast (i.e., subnetwork-
                      broadcast or subnetwork-multicast) packets
                      delivered to a higher-layer protocol."
              ::= { ifEntry 12 }

          ifInDiscards OBJECT-TYPE
              SYNTAX  Counter
              ACCESS  read-only
              STATUS  mandatory
              DESCRIPTION
                      "The number of inbound packets which were chosen
                      to be discarded even though no errors had been
                      detected to prevent their being deliverable to a
                      higher-layer protocol.  One possible reason for
                      discarding such a packet could be to free up
                      buffer space."
              ::= { ifEntry 13 }

          ifInErrors OBJECT-TYPE
              SYNTAX  Counter
              ACCESS  read-only
              STATUS  mandatory
              DESCRIPTION
                      "The number of inbound packets that contained
                      errors preventing them from being deliverable to a
                      higher-layer protocol."
              ::= { ifEntry 14 }
          ifInUnknownProtos OBJECT-TYPE
              SYNTAX  Counter
              ACCESS  read-only
              STATUS  mandatory
              DESCRIPTION
                      "The number of packets received via the interface
                      which were discarded because of an unknown or
                      unsupported protocol."
              ::= { ifEntry 15 }

          ifOutOctets OBJECT-TYPE
              SYNTAX  Counter
              ACCESS  read-only
              STATUS  mandatory
              DESCRIPTION
                      "The total number of octets transmitted out of the
                      interface, including framing characters."
              ::= { ifEntry 16 }

          ifOutUcastPkts OBJECT-TYPE
              SYNTAX  Counter
              ACCESS  read-only
              STATUS  mandatory
              DESCRIPTION
                      "The total number of packets that higher-level
                      protocols requested be transmitted to a
                      subnetwork-unicast address, including those that
                      were discarded or not sent."
              ::= { ifEntry 17 }

          ifOutNUcastPkts OBJECT-TYPE
              SYNTAX  Counter
              ACCESS  read-only
              STATUS  mandatory
              DESCRIPTION
                      "The total number of packets that higher-level
                      protocols requested be transmitted to a non-
                      unicast (i.e., a subnetwork-broadcast or
                      subnetwork-multicast) address, including those
                      that were discarded or not sent."
              ::= { ifEntry 18 }

          ifOutDiscards OBJECT-TYPE
              SYNTAX  Counter
              ACCESS  read-only
              STATUS  mandatory
              DESCRIPTION
                      "The number of outbound packets which were chosen
                      to be discarded even though no errors had been
                      detected to prevent their being transmitted.  One
                      possible reason for discarding such a packet could
                      be to free up buffer space."
              ::= { ifEntry 19 }

          ifOutErrors OBJECT-TYPE
              SYNTAX  Counter
              ACCESS  read-only
              STATUS  mandatory
              DESCRIPTION
                      "The number of outbound packets that could not be
                      transmitted because of errors."
              ::= { ifEntry 20 }

          ifOutQLen OBJECT-TYPE
              SYNTAX  Gauge
              ACCESS  read-only
              STATUS  mandatory
              DESCRIPTION
                      "The length of the output packet queue (in
                      packets)."
              ::= { ifEntry 21 }

          ifSpecific OBJECT-TYPE
              SYNTAX  OBJECT IDENTIFIER
              ACCESS  read-only
              STATUS  mandatory
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { ifEntry 22 }


          -- the Address Translation group

          -- Implementation of the Address Translation group is
          -- mandatory for all systems.  Note however that this group
          -- is deprecated by MIB-II. That is, it is being included
          -- solely for compatibility with MIB-I nodes, and will most
          -- likely be excluded from MIB-III nodes.  From MIB-II and
          -- onwards, each network protocol group contains its own
          -- address translation tables.

          -- The Address Translation group contains one table which is
          -- the union across all interfaces of the translation tables
          -- for converting a NetworkAddress (e.g., an IP address) into
          -- a subnetwork-specific address.  For lack of a better term,
          -- this document refers to such a subnetwork-specific address
          -- as a `physical' address.

          -- Examples of such translation tables are: for broadcast
          -- media where ARP is in use, the translation table is
          -- equivalent to the ARP cache; or, on an X.25 network where
          -- non-algorithmic translation to X.121 addresses is
          -- required, the translation table contains the
          -- NetworkAddress to X.121 address equivalences.

          atTable OBJECT-TYPE
              SYNTAX  SEQUENCE OF AtEntry
              ACCESS  not-accessible
              STATUS  deprecated
              DESCRIPTION
                      "The Address Translation tables contain the
                      NetworkAddress to `physical' address equivalences.
                      Some interfaces do not use translation tables for
                      determining address equivalences (e.g., DDN-X.25
                      has an algorithmic method); if all interfaces are
                      of this type, then the Address Translation table
                      is empty, i.e., has zero entries."
              ::= { at 1 }

          atEntry OBJECT-TYPE
              SYNTAX  AtEntry
              ACCESS  not-accessible
              STATUS  deprecated
              DESCRIPTION
                      "Each entry contains one NetworkAddress to
                      `physical' address equivalence."
              INDEX   { atIfIndex,
                        atNetAddress }
              ::= { atTable 1 }

          AtEntry ::=
              SEQUENCE {
                  atIfIndex
                      INTEGER,
                  atPhysAddress
                      PhysAddress,
                  atNetAddress
                      NetworkAddress
              }

          atIfIndex OBJECT-TYPE
              SYNTAX  INTEGER
              ACCESS  read-write
              STATUS  deprecated
              DESCRIPTION
                      "The interface on which this entry's equivalence
                      is effective.  The interface identified by a
                      particular value of this index is the same
                      interface as identified by the same value of
                      ifIndex."
              ::= { atEntry 1 }

          atPhysAddress OBJECT-TYPE
              SYNTAX  PhysAddress
              ACCESS  read-write
              STATUS  deprecated
              DESCRIPTION
                      "The media-dependent `physical' address.

                      Setting this object to a null string (one of zero
                      length) has the effect of invaliding the
                      corresponding entry in the atTable object.  That
                      is, it effectively dissasociates the interface
                      identified with said entry from the mapping
                      identified with said entry.  It is an
                      implementation-specific matter as to whether the
                      agent removes an invalidated entry from the table.
                      Accordingly, management stations must be prepared
                      to receive tabular information from agents that
                      corresponds to entries not currently in use.
                      Proper interpretation of such entries requires
                      examination of the relevant atPhysAddress object."
              ::= { atEntry 2 }

          atNetAddress OBJECT-TYPE
              SYNTAX  NetworkAddress
              ACCESS  read-write
              STATUS  deprecated
              DESCRIPTION
                      "The NetworkAddress (e.g., the IP address)
                      corresponding to the media-dependent `physical'
                      address."
              ::= { atEntry 3 }


          -- the IP group

          -- Implementation of the IP group is mandatory for all
          -- systems.

          ipForwarding OBJECT-TYPE
              SYNTAX  INTEGER {
                          forwarding(1),    -- acting as a gateway
                          not-forwarding(2) -- NOT acting as a gateway
                      }
              ACCESS  read-write
              STATUS  mandatory
              DESCRIPTION
                      "The indication of whether this entity is acting
                      as an IP gateway in respect to the forwarding of
                      datagrams received by, but not addressed to, this
                      entity.  IP gateways forward datagrams.  IP hosts
                      do not (except those source-routed via the host).

                      Note that for some managed nodes, this object may
                      take on only a subset of the values possible.
                      Accordingly, it is appropriate for an agent to
                      return a `badValue' response if a management
                      station attempts to change this object to an
                      inappropriate value."
              ::= { ip 1 }

          ipDefaultTTL OBJECT-TYPE
              SYNTAX  INTEGER
              ACCESS  read-write
              STATUS  mandatory
              DESCRIPTION
                      "The default value inserted into the Time-To-Live
                      field of the IP header of datagrams originated at
                      this entity, whenever a TTL value is not supplied
                      by the transport layer protocol."
              ::= { ip 2 }

          ipInReceives OBJECT-TYPE
              SYNTAX  Counter
              ACCESS  read-only
              STATUS  mandatory
              DESCRIPTION
                      "The total number of input datagrams received from
                      interfaces, including those received in error."
              ::= { ip 3 }

          ipInHdrErrors OBJECT-TYPE
              SYNTAX  Counter
              ACCESS  read-only
              STATUS  mandatory
              DESCRIPTION
                      "The number of input datagrams discarded due to
                      errors in their IP headers, including bad
                      checksums, version number mismatch, other format
                      errors, time-to-live exceeded, errors discovered
                      in processing their IP options, etc."
              ::= { ip 4 }

          ipInAddrErrors OBJECT-TYPE
              SYNTAX  Counter
              ACCESS  read-only
              STATUS  mandatory
              DESCRIPTION
                      "The number of input datagrams discarded because
                      the IP address in their IP header's destination
                      field was not a valid address to be received at
                      this entity.  This count includes invalid
                      addresses (e.g., 0.0.0.0) and addresses of
                      unsupported Classes (e.g., Class E).  For entities
                      which are not IP Gateways and therefore do not
                      forward datagrams, this counter includes datagrams
                      discarded because the destination address was not
                      a local address."
              ::= { ip 5 }

          ipForwDatagrams OBJECT-TYPE
              SYNTAX  Counter
              ACCESS  read-only
              STATUS  mandatory
              DESCRIPTION
                      "The number of input datagrams for which this
                      entity was not their final IP destination, as a
                      result of which an attempt was made to find a
                      route to forward them to that final destination.
                      In entities which do not act as IP Gateways, this
                      counter will include only those packets which were
                      Source-Routed via this entity, and the Source-
                      Route option processing was successful."
              ::= { ip 6 }

          ipInUnknownProtos OBJECT-TYPE
              SYNTAX  Counter
              ACCESS  read-only
              STATUS  mandatory
              DESCRIPTION
                      "The number of locally-addressed datagrams
                      received successfully but discarded because of an
                      unknown or unsupported protocol."
              ::= { ip 7 }

          ipInDiscards OBJECT-TYPE
              SYNTAX  Counter
              ACCESS  read-only
              STATUS  mandatory
              DESCRIPTION
                      "The number of input IP datagrams for which no
                      problems were encountered to prevent their
                      continued processing, but which were discarded
                      (e.g., for lack of buffer space).  Note that this
                      counter does not include any datagrams discarded
                      while awaiting re-assembly."
              ::= { ip 8 }

          ipInDelivers OBJECT-TYPE
              SYNTAX  Counter
              ACCESS  read-only
              STATUS  mandatory
              DESCRIPTION
                      "The total number of input datagrams successfully
                      delivered to IP user-protocols (including ICMP)."
              ::= { ip 9 }

          ipOutRequests OBJECT-TYPE
              SYNTAX  Counter
              ACCESS  read-only
              STATUS  mandatory
              DESCRIPTION
                      "The total number of IP datagrams which local IP
                      user-protocols (including ICMP) supplied to IP in
                      requests for transmission.  Note that this counter
                      does not include any datagrams counted in
                      ipForwDatagrams."
              ::= { ip 10 }

          ipOutDiscards OBJECT-TYPE
              SYNTAX  Counter
              ACCESS  read-only
              STATUS  mandatory
              DESCRIPTION
                      "The number of output IP datagrams for which no
                      problem was encountered to prevent their
                      transmission to their destination, but which were
                      discarded (e.g., for lack of buffer space).  Note
                      that this counter would include datagrams counted
                      in ipForwDatagrams if any such packets met this
                      (discretionary) discard criterion."
              ::= { ip 11 }

          ipOutNoRoutes OBJECT-TYPE
              SYNTAX  Counter
              ACCESS  read-only
              STATUS  mandatory
              DESCRIPTION
                      "The number of IP datagrams discarded because no
                      route could be found to transmit them to their
                      destination.  Note that this counter includes any
                      packets counted in ipForwDatagrams which meet this
                      `no-route' criterion.  Note that this includes any
                      datagarms which a host cannot route because all of
                      its default gateways are down."
              ::= { ip 12 }

          ipReasmTimeout OBJECT-TYPE
              SYNTAX  INTEGER
              ACCESS  read-only
              STATUS  mandatory
              DESCRIPTION
                      "The maximum number of seconds which received
                      fragments are held while they are awaiting
                      reassembly at this entity."
              ::= { ip 13 }

          ipReasmReqds OBJECT-TYPE
              SYNTAX  Counter
              ACCESS  read-only
              STATUS  mandatory
              DESCRIPTION
                      "The number of IP fragments received which needed
                      to be reassembled at this entity."
              ::= { ip 14 }

          ipReasmOKs OBJECT-TYPE
              SYNTAX  Counter
              ACCESS  read-only
              STATUS  mandatory
              DESCRIPTION
                      "The number of IP datagrams successfully re-
                      assembled."
              ::= { ip 15 }

          ipReasmFails OBJECT-TYPE
              SYNTAX  Counter
              ACCESS  read-only
              STATUS  mandatory
              DESCRIPTION
                      "The number of failures detected by the IP re-
                      assembly algorithm (for whatever reason: timed
                      out, errors, etc).  Note that this is not
                      necessarily a count of discarded IP fragments
                      since some algorithms (notably the algorithm in
                      RFC 815) can lose track of the number of fragments
                      by combining them as they are received."
              ::= { ip 16 }

          ipFragOKs OBJECT-TYPE
              SYNTAX  Counter
              ACCESS  read-only
              STATUS  mandatory
              DESCRIPTION
                      "The number of IP datagrams that have been
                      successfully fragmented at this entity."
              ::= { ip 17 }

          ipFragFails OBJECT-TYPE
              SYNTAX  Counter
              ACCESS  read-only
              STATUS  mandatory
              DESCRIPTION
                      "The number of IP datagrams that have been
                      discarded because they needed to be fragmented at
                      this entity but could not be, e.g., because their
                      Don't Fragment flag was set."
              ::= { ip 18 }

          ipFragCreates OBJECT-TYPE
              SYNTAX  Counter
              ACCESS  read-only
              STATUS  mandatory
              DESCRIPTION
                      "The number of IP datagram fragments that have
                      been generated as a result of fragmentation at
                      this entity."
              ::= { ip 19 }

          -- the IP address table

          -- The IP address table contains this entity's IP addressing
          -- information.

          ipAddrTable OBJECT-TYPE
              SYNTAX  SEQUENCE OF IpAddrEntry
              ACCESS  not-accessible
              STATUS  mandatory
              DESCRIPTION
                      "The table of addressing information relevant to
                      this entity's IP addresses."
              ::= { ip 20 }

          ipAddrEntry OBJECT-TYPE
              SYNTAX  IpAddrEntry
              ACCESS  not-accessible
              STATUS  mandatory
              DESCRIPTION
                      "The addressing information for one of this
                      entity's IP addresses."
              INDEX   { ipAdEntAddr }
              ::= { ipAddrTable 1 }

          IpAddrEntry ::=
              SEQUENCE {
                  ipAdEntAddr
                      IpAddress,
                  ipAdEntIfIndex
                      INTEGER,
                  ipAdEntNetMask
                      IpAddress,
                  ipAdEntBcastAddr
                      INTEGER,
                  ipAdEntReasmMaxSize
                      INTEGER (0..65535)
              }

          ipAdEntAddr OBJECT-TYPE
              SYNTAX  IpAddress
              ACCESS  read-only
              STATUS  mandatory
              DESCRIPTION
                      "The IP address to which this entry's addressing
                      information pertains."
              ::= { ipAddrEntry 1 }

          ipAdEntIfIndex OBJECT-TYPE
              SYNTAX  INTEGER
              ACCESS  read-only
              STATUS  mandatory
              DESCRIPTION
                      "The index value which uniquely identifies the
                      interface to which this entry is applicable.  The
                      interface identified by a particular value of this
                      index is the same interface as identified by the
                      same value of ifIndex."
              ::= { ipAddrEntry 2 }

          ipAdEntNetMask OBJECT-TYPE
              SYNTAX  IpAddress
              ACCESS  read-only
              STATUS  mandatory
              DESCRIPTION
                      "The subnet mask associated with the IP address of
                      this entry.  The value of the mask is an IP
                      address with all the network bits set to 1 and all
                      the hosts bits set to 0."
              ::= { ipAddrEntry 3 }

          ipAdEntBcastAddr OBJECT-TYPE
              SYNTAX  INTEGER
              ACCESS  read-only
              STATUS  mandatory
              DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
              ::= { ipAddrEntry 4 }

          ipAdEntReasmMaxSize OBJECT-TYPE
              SYNTAX  INTEGER (0..65535)
              ACCESS  read-only
              STATUS  mandatory
              DESCRIPTION
                      "The size of the largest IP datagram which this
                      entity can re-assemble from incoming IP fragmented
                      datagrams received on this interface."
              ::= { ipAddrEntry 5 }

          -- the IP routing table

          -- The IP routing table contains an entry for each route
          -- presently known to this entity.

          ipRouteTable OBJECT-TYPE
              SYNTAX  SEQUENCE OF IpRouteEntry
              ACCESS  not-accessible
              STATUS  mandatory
              DESCRIPTION
                      "This entity's IP Routing table."
              ::= { ip 21 }

          ipRouteEntry OBJECT-TYPE
              SYNTAX  IpRouteEntry
              ACCESS  not-accessible
              STATUS  mandatory
              DESCRIPTION
                      "A route to a particular destination."
              INDEX   { ipRouteDest }
              ::= { ipRouteTable 1 }

          IpRouteEntry ::=
              SEQUENCE {
                  ipRouteDest
                      IpAddress,
                  ipRouteIfIndex
                      INTEGER,
                  ipRouteMetric1
                      INTEGER,
                  ipRouteMetric2
                      INTEGER,
                  ipRouteMetric3
                      INTEGER,
                  ipRouteMetric4
                      INTEGER,
                  ipRouteNextHop
                      IpAddress,
                  ipRouteType
                      INTEGER,
                  ipRouteProto
                      INTEGER,
                  ipRouteAge
                      INTEGER,
                  ipRouteMask
                      IpAddress,
                  ipRouteMetric5
                      INTEGER,
                  ipRouteInfo
                      OBJECT IDENTIFIER
              }

          ipRouteDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
              ::= { ipRouteEntry 1 }

          ipRouteIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { ipRouteEntry 2 }

          ipRouteMetric1 OBJECT-TYPE
              SYNTAX  INTEGER
              ACCESS  read-write
              STATUS  mandatory
              DESCRIPTION
                      "The primary routing metric for this route.  The
                      semantics of this metric are determined by the
                      routing-protocol specified in the route's
                      ipRouteProto value.  If this metric is not used,
                      its value should be set to -1."
              ::= { ipRouteEntry 3 }

          ipRouteMetric2 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 4 }

          ipRouteMetric3 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 5 }

          ipRouteMetric4 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 6 }

          ipRouteNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
              ::= { ipRouteEntry 7 }

          ipRouteType OBJECT-TYPE
              SYNTAX  INTEGER {
                          other(1),        -- none of the following

                          invalid(2),      -- an invalidated route
                                           -- route to directly

                          direct(3),       -- connected (sub-)network

                                           -- route to a non-local
                          indirect(4)      -- host/network/sub-network
                      }
              ACCESS  read-write
              STATUS  mandatory
              DESCRIPTION
                      "The type of route.  Note that the values
                      direct(3) and indirect(4) refer to the notion of
                      direct and indirect routing in the IP
                      architecture.

                      Setting this object to the value invalid(2) has
                      the effect of invalidating the corresponding entry
                      in the ipRouteTable object.  That is, it
                      effectively dissasociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { ipRouteEntry 8 }

          ipRouteProto OBJECT-TYPE
              SYNTAX  INTEGER {
                          other(1),       -- none of the following

                                          -- non-protocol information,
                                          -- e.g., manually configured
                          local(2),       -- entries

                                          -- set via a network
                          netmgmt(3),     -- management protocol

                                          -- obtained via ICMP,
                          icmp(4),        -- e.g., Redirect

                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14)
                      }
              ACCESS  read-only
              STATUS  mandatory
              DESCRIPTION
                      "The routing mechanism via which this route was
                      learned.  Inclusion of values for gateway routing
                      protocols is not intended to imply that hosts
                      should support those protocols."
              ::= { ipRouteEntry 9 }

          ipRouteAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { ipRouteEntry 10 }

          ipRouteMask OBJECT-TYPE
              SYNTAX  IpAddress
              ACCESS  read-write
              STATUS  mandatory
              DESCRIPTION
                      "Indicate the mask to be logical-ANDed with the
                      destination address before being compared to the
                      value in the ipRouteDest field.  For those systems
                      that do not support arbitrary subnet masks, an
                      agent constructs the value of the ipRouteMask by
                      determining whether the value of the correspondent
                      ipRouteDest field belong to a class-A, B, or C
                      network, and then using one of:

                           mask           network
                           255.0.0.0      class-A
                           255.255.0.0    class-B
                           255.255.255.0  class-C

                      If the value of the ipRouteDest is 0.0.0.0 (a
                      default route), then the mask value is also
                      0.0.0.0.  It should be noted that all IP routing
                      subsystems implicitly use this mechanism."
              ::= { ipRouteEntry 11 }

          ipRouteMetric5 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 12 }

          ipRouteInfo OBJECT-TYPE
              SYNTAX  OBJECT IDENTIFIER
              ACCESS  read-only
              STATUS  mandatory
              DESCRIPTION
                      "A reference to MIB definitions specific to the
                      particular routing protocol which is responsible
                      for this route, as determined by the value
                      specified in the route's ipRouteProto value.  If
                      this information is not present, its value should
                      be set to the OBJECT IDENTIFIER { 0 0 }, which is
                      a syntatically valid object identifier, and any
                      conformant implementation of ASN.1 and BER must be
                      able to generate and recognize this value."
              ::= { ipRouteEntry 13 }


          -- the IP Address Translation table

          -- The IP address translation table contain the IpAddress to
          -- `physical' address equivalences.  Some interfaces do not
          -- use translation tables for determining address
          -- equivalences (e.g., DDN-X.25 has an algorithmic method);
          -- if all interfaces are of this type, then the Address
          -- Translation table is empty, i.e., has zero entries.

          ipNetToMediaTable OBJECT-TYPE
              SYNTAX  SEQUENCE OF IpNetToMediaEntry
              ACCESS  not-accessible
              STATUS  mandatory
              DESCRIPTION
                      "The IP Address Translation table used for mapping
                      from IP addresses to physical addresses."
              ::= { ip 22 }

          ipNetToMediaEntry OBJECT-TYPE
              SYNTAX  IpNetToMediaEntry
              ACCESS  not-accessible
              STATUS  mandatory
              DESCRIPTION
                      "Each entry contains one IpAddress to `physical'
                      address equivalence."
              INDEX   { ipNetToMediaIfIndex,
                        ipNetToMediaNetAddress }
              ::= { ipNetToMediaTable 1 }

          IpNetToMediaEntry ::=
              SEQUENCE {
                  ipNetToMediaIfIndex
                      INTEGER,
                  ipNetToMediaPhysAddress
                      PhysAddress,
                  ipNetToMediaNetAddress
                      IpAddress,
                  ipNetToMediaType
                      INTEGER
              }

          ipNetToMediaIfIndex OBJECT-TYPE
              SYNTAX  INTEGER
              ACCESS  read-write
              STATUS  mandatory
              DESCRIPTION
                      "The interface on which this entry's equivalence
                      is effective.  The interface identified by a
                      particular value of this index is the same
                      interface as identified by the same value of
                      ifIndex."
              ::= { ipNetToMediaEntry 1 }

          ipNetToMediaPhysAddress OBJECT-TYPE
              SYNTAX  PhysAddress
              ACCESS  read-write
              STATUS  mandatory
              DESCRIPTION
                      "The media-dependent `physical' address."
              ::= { ipNetToMediaEntry 2 }

          ipNetToMediaNetAddress OBJECT-TYPE
              SYNTAX  IpAddress
              ACCESS  read-only
              STATUS  mandatory
              DESCRIPTION
                      "The IpAddress corresponding to the media-
                      dependent `physical' address."
              ::= { ipNetToMediaEntry 3 }

          ipNetToMediaType OBJECT-TYPE
              SYNTAX  INTEGER {
                          other(1),        -- none of the following
                          invalid(2),      -- an invalidated mapping
                          dynamic(3),
                          static(4)
                      }
              ACCESS  read-write
              STATUS  mandatory
              DESCRIPTION
                      "The type of mapping.

                      Setting this object to the value invalid(2) has
                      the effect of invalidating the corresponding entry
                      in the ipNetToMediaTable.  That is, it effectively
                      dissasociates the interface identified with said
                      entry from the mapping identified with said entry.
                      It is an implementation-specific matter as to
                      whether the agent removes an invalidated entry
                      from the table.  Accordingly, management stations
                      must be prepared to receive tabular information
                      from agents that corresponds to entries not
                      currently in use.  Proper interpretation of such
                      entries requires examination of the relevant
                      ipNetToMediaType object."
              ::= { ipNetToMediaEntry 4 }


          -- additional IP objects

          ipRoutingDiscards OBJECT-TYPE
              SYNTAX  Counter
              ACCESS  read-only
              STATUS  mandatory
              DESCRIPTION
                      "The number of routing entries which were chosen
                      to be discarded even though they are valid.  One
                      possible reason for discarding such an entry could
                      be to free-up buffer space for other routing
                      entries."
              ::= { ip 23 }


          -- the ICMP group

          -- Implementation of the ICMP group is mandatory for all
          -- systems.

          icmpInMsgs OBJECT-TYPE
              SYNTAX  Counter
              ACCESS  read-only
              STATUS  mandatory
              DESCRIPTION
                      "The total number of ICMP messages which the
                      entity received.  Note that this counter includes
                      all those counted by icmpInErrors."
              ::= { icmp 1 }

          icmpInErrors OBJECT-TYPE
              SYNTAX  Counter
              ACCESS  read-only
              STATUS  mandatory
              DESCRIPTION
                      "The number of ICMP messages which the entity
                      received but determined as having ICMP-specific
                      errors (bad ICMP checksums, bad length, etc.)."
              ::= { icmp 2 }

          icmpInDestUnreachs OBJECT-TYPE
              SYNTAX  Counter
              ACCESS  read-only
              STATUS  mandatory
              DESCRIPTION
                      "The number of ICMP Destination Unreachable
                      messages received."
              ::= { icmp 3 }

          icmpInTimeExcds OBJECT-TYPE
              SYNTAX  Counter
              ACCESS  read-only
              STATUS  mandatory
              DESCRIPTION
                      "The number of ICMP Time Exceeded messages
                      received."
              ::= { icmp 4 }

          icmpInParmProbs OBJECT-TYPE
              SYNTAX  Counter
              ACCESS  read-only
              STATUS  mandatory
              DESCRIPTION
                      "The number of ICMP Parameter Problem messages
                      received."
              ::= { icmp 5 }

          icmpInSrcQuenchs OBJECT-TYPE
              SYNTAX  Counter
              ACCESS  read-only
              STATUS  mandatory
              DESCRIPTION
                      "The number of ICMP Source Quench messages
                      received."
              ::= { icmp 6 }

          icmpInRedirects OBJECT-TYPE
              SYNTAX  Counter
              ACCESS  read-only
              STATUS  mandatory
              DESCRIPTION
                      "The number of ICMP Redirect messages received."
              ::= { icmp 7 }

          icmpInEchos OBJECT-TYPE
              SYNTAX  Counter
              ACCESS  read-only
              STATUS  mandatory
              DESCRIPTION
                      "The number of ICMP Echo (request) messages
                      received."
              ::= { icmp 8 }

          icmpInEchoReps OBJECT-TYPE
              SYNTAX  Counter
              ACCESS  read-only
              STATUS  mandatory
              DESCRIPTION
                      "The number of ICMP Echo Reply messages received."
              ::= { icmp 9 }

          icmpInTimestamps OBJECT-TYPE
              SYNTAX  Counter
              ACCESS  read-only
              STATUS  mandatory
              DESCRIPTION
                      "The number of ICMP Timestamp (request) messages
                      received."
              ::= { icmp 10 }

          icmpInTimestampReps OBJECT-TYPE
              SYNTAX  Counter
              ACCESS  read-only
              STATUS  mandatory
              DESCRIPTION
                      "The number of ICMP Timestamp Reply messages
                      received."
              ::= { icmp 11 }

          icmpInAddrMasks OBJECT-TYPE
              SYNTAX  Counter
              ACCESS  read-only
              STATUS  mandatory
              DESCRIPTION
                      "The number of ICMP Address Mask Request messages
                      received."
              ::= { icmp 12 }

          icmpInAddrMaskReps OBJECT-TYPE
              SYNTAX  Counter
              ACCESS  read-only
              STATUS  mandatory
              DESCRIPTION
                      "The number of ICMP Address Mask Reply messages
                      received."
              ::= { icmp 13 }

          icmpOutMsgs OBJECT-TYPE
              SYNTAX  Counter
              ACCESS  read-only
              STATUS  mandatory
              DESCRIPTION
                      "The total number of ICMP messages which this
                      entity attempted to send.  Note that this counter
                      includes all those counted by icmpOutErrors."
              ::= { icmp 14 }

          icmpOutErrors OBJECT-TYPE
              SYNTAX  Counter
              ACCESS  read-only
              STATUS  mandatory
              DESCRIPTION
                      "The number of ICMP messages which this entity did
                      not send due to problems discovered within ICMP
                      such as a lack of buffers.  This value should not
                      include errors discovered outside the ICMP layer
                      such as the inability of IP to route the resultant
                      datagram.  In some implementations there may be no
                      types of error which contribute to this counter's
                      value."
              ::= { icmp 15 }

          icmpOutDestUnreachs OBJECT-TYPE
              SYNTAX  Counter
              ACCESS  read-only
              STATUS  mandatory
              DESCRIPTION
                      "The number of ICMP Destination Unreachable
                      messages sent."
              ::= { icmp 16 }

          icmpOutTimeExcds OBJECT-TYPE
              SYNTAX  Counter
              ACCESS  read-only
              STATUS  mandatory
              DESCRIPTION
                      "The number of ICMP Time Exceeded messages sent."
              ::= { icmp 17 }

          icmpOutParmProbs OBJECT-TYPE
              SYNTAX  Counter
              ACCESS  read-only
              STATUS  mandatory
              DESCRIPTION
                      "The number of ICMP Parameter Problem messages
                      sent."
              ::= { icmp 18 }

          icmpOutSrcQuenchs OBJECT-TYPE
              SYNTAX  Counter
              ACCESS  read-only
              STATUS  mandatory
              DESCRIPTION
                      "The number of ICMP Source Quench messages sent."
              ::= { icmp 19 }

          icmpOutRedirects OBJECT-TYPE
              SYNTAX  Counter
              ACCESS  read-only
              STATUS  mandatory
              DESCRIPTION
                      "The number of ICMP Redirect messages sent.  For a
                      host, this object will always be zero, since hosts
                      do not send redirects."
              ::= { icmp 20 }

          icmpOutEchos OBJECT-TYPE
              SYNTAX  Counter
              ACCESS  read-only
              STATUS  mandatory
              DESCRIPTION
                      "The number of ICMP Echo (request) messages sent."
              ::= { icmp 21 }

          icmpOutEchoReps OBJECT-TYPE
              SYNTAX  Counter
              ACCESS  read-only
              STATUS  mandatory
              DESCRIPTION
                      "The number of ICMP Echo Reply messages sent."
              ::= { icmp 22 }

          icmpOutTimestamps OBJECT-TYPE
              SYNTAX  Counter
              ACCESS  read-only
              STATUS  mandatory
              DESCRIPTION
                      "The number of ICMP Timestamp (request) messages
                      sent."
              ::= { icmp 23 }

          icmpOutTimestampReps OBJECT-TYPE
              SYNTAX  Counter
              ACCESS  read-only
              STATUS  mandatory
              DESCRIPTION
                      "The number of ICMP Timestamp Reply messages
                      sent."
              ::= { icmp 24 }

          icmpOutAddrMasks OBJECT-TYPE
              SYNTAX  Counter
              ACCESS  read-only
              STATUS  mandatory
              DESCRIPTION
                      "The number of ICMP Address Mask Request messages
                      sent."
              ::= { icmp 25 }

          icmpOutAddrMaskReps OBJECT-TYPE
              SYNTAX  Counter
              ACCESS  read-only
              STATUS  mandatory
              DESCRIPTION
                      "The number of ICMP Address Mask Reply messages
                      sent."
              ::= { icmp 26 }


          -- the TCP group

          -- Implementation of the TCP group is mandatory for all
          -- systems that implement the TCP.

          -- Note that instances of object types that represent
          -- information about a particular TCP connection are
          -- transient; they persist only as long as the connection
          -- in question.

          tcpRtoAlgorithm OBJECT-TYPE
              SYNTAX  INTEGER {
                          other(1),    -- none of the following

                          constant(2), -- a constant rto
                          rsre(3),     -- MIL-STD-1778, Appendix B
                          vanj(4)      -- Van Jacobson's algorithm [10]
                      }
              ACCESS  read-only
              STATUS  mandatory
              DESCRIPTION
                      "The algorithm used to determine the timeout value
                      used for retransmitting unacknowledged octets."
              ::= { tcp 1 }

          tcpRtoMin OBJECT-TYPE
              SYNTAX  INTEGER
              ACCESS  read-only
              STATUS  mandatory
              DESCRIPTION
                      "The minimum value permitted by a TCP
                      implementation for the retransmission timeout,
                      measured in milliseconds.  More refined semantics
                      for objects of this type depend upon the algorithm
                      used to determine the retransmission timeout.  In
                      particular, when the timeout algorithm is rsre(3),
                      an object of this type has the semantics of the
                      LBOUND quantity described in RFC 793."
              ::= { tcp 2 }


          tcpRtoMax OBJECT-TYPE
              SYNTAX  INTEGER
              ACCESS  read-only
              STATUS  mandatory
              DESCRIPTION
                      "The maximum value permitted by a TCP
                      implementation for the retransmission timeout,
                      measured in milliseconds.  More refined semantics
                      for objects of this type depend upon the algorithm
                      used to determine the retransmission timeout.  In
                      particular, when the timeout algorithm is rsre(3),
                      an object of this type has the semantics of the
                      UBOUND quantity described in RFC 793."
              ::= { tcp 3 }

          tcpMaxConn OBJECT-TYPE
              SYNTAX  INTEGER
              ACCESS  read-only
              STATUS  mandatory
              DESCRIPTION
                      "The limit on the total number of TCP connections
                      the entity can support.  In entities where the
                      maximum number of connections is dynamic, this
                      object should contain the value -1."
              ::= { tcp 4 }

          tcpActiveOpens OBJECT-TYPE
              SYNTAX  Counter
              ACCESS  read-only
              STATUS  mandatory
              DESCRIPTION
                      "The number of times TCP connections have made a
                      direct transition to the SYN-SENT state from the
                      CLOSED state."
              ::= { tcp 5 }

          tcpPassiveOpens OBJECT-TYPE
              SYNTAX  Counter
              ACCESS  read-only
              STATUS  mandatory
              DESCRIPTION
                      "The number of times TCP connections have made a
                      direct transition to the SYN-RCVD state from the
                      LISTEN state."
              ::= { tcp 6 }

          tcpAttemptFails OBJECT-TYPE
              SYNTAX  Counter
              ACCESS  read-only
              STATUS  mandatory
              DESCRIPTION
                      "The number of times TCP connections have made a
                      direct transition to the CLOSED state from either
                      the SYN-SENT state or the SYN-RCVD state, plus the
                      number of times TCP connections have made a direct
                      transition to the LISTEN state from the SYN-RCVD
                      state."
              ::= { tcp 7 }

          tcpEstabResets OBJECT-TYPE
              SYNTAX  Counter
              ACCESS  read-only
              STATUS  mandatory
              DESCRIPTION
                      "The number of times TCP connections have made a
                      direct transition to the CLOSED state from either
                      the ESTABLISHED state or the CLOSE-WAIT state."
              ::= { tcp 8 }

          tcpCurrEstab OBJECT-TYPE
              SYNTAX  Gauge
              ACCESS  read-only
              STATUS  mandatory
              DESCRIPTION
                      "The number of TCP connections for which the
                      current state is either ESTABLISHED or CLOSE-
                      WAIT."
              ::= { tcp 9 }

          tcpInSegs OBJECT-TYPE
              SYNTAX  Counter
              ACCESS  read-only
              STATUS  mandatory
              DESCRIPTION
                      "The total number of segments received, including
                      those received in error.  This count includes
                      segments received on currently established
                      connections."
              ::= { tcp 10 }

          tcpOutSegs OBJECT-TYPE
              SYNTAX  Counter
              ACCESS  read-only
              STATUS  mandatory
              DESCRIPTION
                      "The total number of segments sent, including
                      those on current connections but excluding those
                      containing only retransmitted octets."
              ::= { tcp 11 }

          tcpRetransSegs OBJECT-TYPE
              SYNTAX  Counter
              ACCESS  read-only
              STATUS  mandatory
              DESCRIPTION
                      "The total number of segments retransmitted - that
                      is, the number of TCP segments transmitted
                      containing one or more previously transmitted
                      octets."
              ::= { tcp 12 }


          -- the TCP Connection table

          -- The TCP connection table contains information about this
          -- entity's existing TCP connections.

          tcpConnTable OBJECT-TYPE
              SYNTAX  SEQUENCE OF TcpConnEntry
              ACCESS  not-accessible
              STATUS  mandatory
              DESCRIPTION
                      "A table containing TCP connection-specific
                      information."
              ::= { tcp 13 }

          tcpConnEntry OBJECT-TYPE
              SYNTAX  TcpConnEntry
              ACCESS  not-accessible
              STATUS  mandatory
              DESCRIPTION
                      "Information about a particular current TCP
                      connection.  An object of this type is transient,
                      in that it ceases to exist when (or soon after)
                      the connection makes the transition to the CLOSED
                      state."
              INDEX   { tcpConnLocalAddress,
                        tcpConnLocalPort,
                        tcpConnRemAddress,
                        tcpConnRemPort }
              ::= { tcpConnTable 1 }

          TcpConnEntry ::=
              SEQUENCE {
                  tcpConnState
                      INTEGER,
                  tcpConnLocalAddress
                      IpAddress,
                  tcpConnLocalPort
                      INTEGER (0..65535),
                  tcpConnRemAddress
                      IpAddress,
                  tcpConnRemPort
                      INTEGER (0..65535)
              }

          tcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              ACCESS  read-write
              STATUS  mandatory
              DESCRIPTION
                      "The state of this TCP connection.

                      The only value which may be set by a management
                      station is deleteTCB(12).  Accordingly, it is
                      appropriate for an agent to return a `badValue'
                      response if a management station attempts to set
                      this object to any other value.

                      If a management station sets this object to the
                      value deleteTCB(12), then this has the effect of
                      deleting the TCB (as defined in RFC 793) of the
                      corresponding connection on the managed node,
                      resulting in immediate termination of the
                      connection.

                      As an implementation-specific option, a RST
                      segment may be sent from the managed node to the
                      other TCP endpoint (note however that RST segments
                      are not sent reliably)."
              ::= { tcpConnEntry 1 }

          tcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { tcpConnEntry 2 }

          tcpConnLocalPort OBJECT-TYPE
              SYNTAX  INTEGER (0..65535)
              ACCESS  read-only
              STATUS  mandatory
              DESCRIPTION
                      "The local port number for this TCP connection."
              ::= { tcpConnEntry 3 }

          tcpConnRemAddress OBJECT-TYPE
              SYNTAX  IpAddress
              ACCESS  read-only
              STATUS  mandatory
              DESCRIPTION
                      "The remote IP address for this TCP connection."
              ::= { tcpConnEntry 4 }

          tcpConnRemPort OBJECT-TYPE
              SYNTAX  INTEGER (0..65535)
              ACCESS  read-only
              STATUS  mandatory
              DESCRIPTION
                      "The remote port number for this TCP connection."
              ::= { tcpConnEntry 5 }


          -- additional TCP objects

          tcpInErrs OBJECT-TYPE
              SYNTAX  Counter
              ACCESS  read-only
              STATUS  mandatory
              DESCRIPTION
                      "The total number of segments received in error
                      (e.g., bad TCP checksums)."
              ::= { tcp 14 }

          tcpOutRsts OBJECT-TYPE
              SYNTAX  Counter
              ACCESS  read-only
              STATUS  mandatory
              DESCRIPTION
                      "The number of TCP segments sent containing the
                      RST flag."
              ::= { tcp 15 }


          -- the UDP group

          -- Implementation of the UDP group is mandatory for all
          -- systems which implement the UDP.

          udpInDatagrams OBJECT-TYPE
              SYNTAX  Counter
              ACCESS  read-only
              STATUS  mandatory
              DESCRIPTION
                      "The total number of UDP datagrams delivered to
                      UDP users."
              ::= { udp 1 }

          udpNoPorts OBJECT-TYPE
              SYNTAX  Counter
              ACCESS  read-only
              STATUS  mandatory
              DESCRIPTION
                      "The total number of received UDP datagrams for
                      which there was no application at the destination
                      port."
              ::= { udp 2 }

          udpInErrors OBJECT-TYPE
              SYNTAX  Counter
              ACCESS  read-only
              STATUS  mandatory
              DESCRIPTION
                      "The number of received UDP datagrams that could
                      not be delivered for reasons other than the lack
                      of an application at the destination port."
              ::= { udp 3 }

          udpOutDatagrams OBJECT-TYPE
              SYNTAX  Counter
              ACCESS  read-only
              STATUS  mandatory
              DESCRIPTION
                      "The total number of UDP datagrams sent from this
                      entity."
              ::= { udp 4 }


          -- the UDP Listener table

          -- The UDP listener table contains information about this
          -- entity's UDP end-points on which a local application is
          -- currently accepting datagrams.

          udpTable OBJECT-TYPE
              SYNTAX  SEQUENCE OF UdpEntry
              ACCESS  not-accessible
              STATUS  mandatory
              DESCRIPTION
                      "A table containing UDP listener information."
              ::= { udp 5 }

          udpEntry OBJECT-TYPE
              SYNTAX  UdpEntry
              ACCESS  not-accessible
              STATUS  mandatory
              DESCRIPTION
                      "Information about a particular current UDP
                      listener."
              INDEX   { udpLocalAddress, udpLocalPort }
              ::= { udpTable 1 }

          UdpEntry ::=
              SEQUENCE {
                  udpLocalAddress
                      IpAddress,
                  udpLocalPort
                      INTEGER (0..65535)
              }

          udpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { udpEntry 1 }

          udpLocalPort OBJECT-TYPE
              SYNTAX  INTEGER (0..65535)
              ACCESS  read-only
              STATUS  mandatory
              DESCRIPTION
                      "The local port number for this UDP listener."
              ::= { udpEntry 2 }


          -- the EGP group

          -- Implementation of the EGP group is mandatory for all
          -- systems which implement the EGP.

          egpInMsgs OBJECT-TYPE
              SYNTAX  Counter
              ACCESS  read-only
              STATUS  mandatory
              DESCRIPTION
                      "The number of EGP messages received without
                      error."
              ::= { egp 1 }

          egpInErrors OBJECT-TYPE
              SYNTAX  Counter
              ACCESS  read-only
              STATUS  mandatory
              DESCRIPTION
                      "The number of EGP messages received that proved
                      to be in error."
              ::= { egp 2 }

          egpOutMsgs OBJECT-TYPE
              SYNTAX  Counter
              ACCESS  read-only
              STATUS  mandatory
              DESCRIPTION
                      "The total number of locally generated EGP
                      messages."
              ::= { egp 3 }

          egpOutErrors OBJECT-TYPE
              SYNTAX  Counter
              ACCESS  read-only
              STATUS  mandatory
              DESCRIPTION
                      "The number of locally generated EGP messages not
                      sent due to resource limitations within an EGP
                      entity."
              ::= { egp 4 }


          -- the EGP Neighbor table

          -- The EGP neighbor table contains information about this
          -- entity's EGP neighbors.

          egpNeighTable OBJECT-TYPE
              SYNTAX  SEQUENCE OF EgpNeighEntry
              ACCESS  not-accessible
              STATUS  mandatory
              DESCRIPTION
                      "The EGP neighbor table."
              ::= { egp 5 }

          egpNeighEntry OBJECT-TYPE
              SYNTAX  EgpNeighEntry
              ACCESS  not-accessible
              STATUS  mandatory
              DESCRIPTION
                      "Information about this entity's relationship with
                      a particular EGP neighbor."
              INDEX   { egpNeighAddr }
              ::= { egpNeighTable 1 }

          EgpNeighEntry ::=
              SEQUENCE {
                  egpNeighState
                      INTEGER,
                  egpNeighAddr
                      IpAddress,
                  egpNeighAs
                      INTEGER,
                  egpNeighInMsgs
                      Counter,
                  egpNeighInErrs
                      Counter,
                  egpNeighOutMsgs
                      Counter,
                  egpNeighOutErrs
                      Counter,
                  egpNeighInErrMsgs
                      Counter,
                  egpNeighOutErrMsgs
                      Counter,
                  egpNeighStateUps
                      Counter,
                  egpNeighStateDowns
                      Counter,
                  egpNeighIntervalHello
                      INTEGER,
                  egpNeighIntervalPoll
                      INTEGER,
                  egpNeighMode
                      INTEGER,
                  egpNeighEventTrigger
                      INTEGER
              }

          egpNeighState OBJECT-TYPE
              SYNTAX  INTEGER {
                          idle(1),
                          acquisition(2),
                          down(3),
                          up(4),
                          cease(5)
                      }
              ACCESS  read-only
              STATUS  mandatory
              DESCRIPTION
                      "The EGP state of the local system with respect to
                      this entry's EGP neighbor.  Each EGP state is
                      represented by a value that is one greater than
                      the numerical value associated with said state in
                      RFC 904."
              ::= { egpNeighEntry 1 }

          egpNeighAddr OBJECT-TYPE
              SYNTAX  IpAddress
              ACCESS  read-only
              STATUS  mandatory
              DESCRIPTION
                      "The IP address of this entry's EGP neighbor."
              ::= { egpNeighEntry 2 }

          egpNeighAs OBJECT-TYPE
              SYNTAX  INTEGER
              ACCESS  read-only
              STATUS  mandatory
              DESCRIPTION
                      "The autonomous system of this EGP peer.  Zero
                      should be specified if the autonomous system
                      number of the neighbor is not yet known."
              ::= { egpNeighEntry 3 }

          egpNeighInMsgs OBJECT-TYPE
              SYNTAX  Counter
              ACCESS  read-only
              STATUS  mandatory
              DESCRIPTION
                      "The number of EGP messages received without error
                      from this EGP peer."
              ::= { egpNeighEntry 4 }

          egpNeighInErrs OBJECT-TYPE
              SYNTAX  Counter
              ACCESS  read-only
              STATUS  mandatory
              DESCRIPTION
                      "The number of EGP messages received from this EGP
                      peer that proved to be in error (e.g., bad EGP
                      checksum)."
              ::= { egpNeighEntry 5 }

          egpNeighOutMsgs OBJECT-TYPE
              SYNTAX  Counter
              ACCESS  read-only
              STATUS  mandatory
              DESCRIPTION
                      "The number of locally generated EGP messages to
                      this EGP peer."
              ::= { egpNeighEntry 6 }

          egpNeighOutErrs OBJECT-TYPE
              SYNTAX  Counter
              ACCESS  read-only
              STATUS  mandatory
              DESCRIPTION
                      "The number of locally generated EGP messages not
                      sent to this EGP peer due to resource limitations
                      within an EGP entity."
              ::= { egpNeighEntry 7 }

          egpNeighInErrMsgs OBJECT-TYPE
              SYNTAX  Counter
              ACCESS  read-only
              STATUS  mandatory
              DESCRIPTION
                      "The number of EGP-defined error messages received
                      from this EGP peer."
              ::= { egpNeighEntry 8 }

          egpNeighOutErrMsgs OBJECT-TYPE
              SYNTAX  Counter
              ACCESS  read-only
              STATUS  mandatory
              DESCRIPTION
                      "The number of EGP-defined error messages sent to
                      this EGP peer."
              ::= { egpNeighEntry 9 }

          egpNeighStateUps OBJECT-TYPE
              SYNTAX  Counter
              ACCESS  read-only
              STATUS  mandatory
              DESCRIPTION
                      "The number of EGP state transitions to the UP
                      state with this EGP peer."
              ::= { egpNeighEntry 10 }

          egpNeighStateDowns OBJECT-TYPE
              SYNTAX  Counter
              ACCESS  read-only
              STATUS  mandatory
              DESCRIPTION
                      "The number of EGP state transitions from the UP
                      state to any other state with this EGP peer."
              ::= { egpNeighEntry 11 }

          egpNeighIntervalHello OBJECT-TYPE
              SYNTAX  INTEGER
              ACCESS  read-only
              STATUS  mandatory
              DESCRIPTION
                      "The interval between EGP Hello command
                      retransmissions (in hundredths of a second).  This
                      represents the t1 timer as defined in RFC 904."
              ::= { egpNeighEntry 12 }

          egpNeighIntervalPoll OBJECT-TYPE
              SYNTAX  INTEGER
              ACCESS  read-only
              STATUS  mandatory
              DESCRIPTION
                      "The interval between EGP poll command
                      retransmissions (in hundredths of a second).  This
                      represents the t3 timer as defined in RFC 904."
              ::= { egpNeighEntry 13 }

          egpNeighMode OBJECT-TYPE
              SYNTAX  INTEGER { active(1), passive(2) }
              ACCESS  read-only
              STATUS  mandatory
              DESCRIPTION
                      "The polling mode of this EGP entity, either
                      passive or active."
              ::= { egpNeighEntry 14 }

          egpNeighEventTrigger OBJECT-TYPE
              SYNTAX  INTEGER { start(1), stop(2) }
              ACCESS  read-write
              STATUS  mandatory
              DESCRIPTION
                      "A control variable used to trigger operator-
                      initiated Start and Stop events.  When read, this
                      variable always returns the most recent value that
                      egpNeighEventTrigger was set to.  If it has not
                      been set since the last initialization of the
                      network management subsystem on the node, it
                      returns a value of `stop'.

                      When set, this variable causes a Start or Stop
                      event on the specified neighbor, as specified on
                      pages 8-10 of RFC 904.  Briefly, a Start event
                      causes an Idle peer to begin neighbor acquisition
                      and a non-Idle peer to reinitiate neighbor
                      acquisition.  A stop event causes a non-Idle peer
                      to return to the Idle state until a Start event
                      occurs, either via egpNeighEventTrigger or
                      otherwise."
              ::= { egpNeighEntry 15 }


          -- additional EGP objects

          egpAs OBJECT-TYPE
              SYNTAX  INTEGER
              ACCESS  read-only
              STATUS  mandatory
              DESCRIPTION
                      "The autonomous system number of this EGP entity."
              ::= { egp 6 }


          -- the Transmission group

          -- Based on the transmission media underlying each interface
          -- on a system, the corresponding portion of the Transmission
          -- group is mandatory for that system.

          -- When Internet-standard definitions for managing
          -- transmission media are defined, the transmission group is
          -- used to provide a prefix for the names of those objects.

          -- Typically, such definitions reside in the experimental
          -- portion of the MIB until they are "proven", then as a
          -- part of the Internet standardization process, the
          -- definitions are accordingly elevated and a new object
          -- identifier, under the transmission group is defined. By
          -- convention, the name assigned is:
          --
          --     type OBJECT IDENTIFIER    ::= { transmission number }
          --
          -- where "type" is the symbolic value used for the media in
          -- the ifType column of the ifTable object, and "number" is
          -- the actual integer value corresponding to the symbol.


          -- the SNMP group

          -- Implementation of the SNMP group is mandatory for all
          -- systems which support an SNMP protocol entity.  Some of
          -- the objects defined below will be zero-valued in those
          -- SNMP implementations that are optimized to support only
          -- those functions specific to either a management agent or
          -- a management station.  In particular, it should be
          -- observed that the objects below refer to an SNMP entity,
          -- and there may be several SNMP entities residing on a
          -- managed node (e.g., if the node is hosting acting as
          -- a management station).

          snmpInPkts OBJECT-TYPE
              SYNTAX  Counter
              ACCESS  read-only
              STATUS  mandatory
              DESCRIPTION
                      "The total number of Messages delivered to the
                      SNMP entity from the transport service."
              ::= { snmp 1 }

          snmpOutPkts OBJECT-TYPE
              SYNTAX  Counter
              ACCESS  read-only
              STATUS  mandatory
              DESCRIPTION
                      "The total number of SNMP Messages which were
                      passed from the SNMP protocol entity to the
                      transport service."
              ::= { snmp 2 }

          snmpInBadVersions OBJECT-TYPE
              SYNTAX  Counter
              ACCESS  read-only
              STATUS  mandatory
              DESCRIPTION
                      "The total number of SNMP Messages which were
                      delivered to the SNMP protocol entity and were for
                      an unsupported SNMP version."
              ::= { snmp 3 }

          snmpInBadCommunityNames OBJECT-TYPE
              SYNTAX  Counter
              ACCESS  read-only
              STATUS  mandatory
              DESCRIPTION
                      "The total number of SNMP Messages delivered to
                      the SNMP protocol entity which used a SNMP
                      community name not known to said entity."
              ::= { snmp 4 }

          snmpInBadCommunityUses OBJECT-TYPE
              SYNTAX  Counter
              ACCESS  read-only
              STATUS  mandatory
              DESCRIPTION
                      "The total number of SNMP Messages delivered to
                      the SNMP protocol entity which represented an SNMP
                      operation which was not allowed by the SNMP
                      community named in the Message."
              ::= { snmp 5 }

          snmpInASNParseErrs OBJECT-TYPE
              SYNTAX  Counter
              ACCESS  read-only
              STATUS  mandatory
              DESCRIPTION
                      "The total number of ASN.1 or BER errors
                      encountered by the SNMP protocol entity when
                      decoding received SNMP Messages."
              ::= { snmp 6 }

          -- { snmp 7 } is not used

          snmpInTooBigs OBJECT-TYPE
              SYNTAX  Counter
              ACCESS  read-only
              STATUS  mandatory
              DESCRIPTION
                      "The total number of SNMP PDUs which were
                      delivered to the SNMP protocol entity and for
                      which the value of the error-status field is
                      `tooBig'."
              ::= { snmp 8 }

          snmpInNoSuchNames OBJECT-TYPE
              SYNTAX  Counter
              ACCESS  read-only
              STATUS  mandatory
              DESCRIPTION
                      "The total number of SNMP PDUs which were
                      delivered to the SNMP protocol entity and for
                      which the value of the error-status field is
                      `noSuchName'."
              ::= { snmp 9 }

          snmpInBadValues OBJECT-TYPE
              SYNTAX  Counter
              ACCESS  read-only
              STATUS  mandatory
              DESCRIPTION
                      "The total number of SNMP PDUs which were
                      delivered to the SNMP protocol entity and for
                      which the value of the error-status field is
                      `badValue'."
              ::= { snmp 10 }

          snmpInReadOnlys OBJECT-TYPE
              SYNTAX  Counter
              ACCESS  read-only
              STATUS  mandatory
              DESCRIPTION
                      "The total number valid SNMP PDUs which were
                      delivered to the SNMP protocol entity and for
                      which the value of the error-status field is
                      `readOnly'.  It should be noted that it is a
                      protocol error to generate an SNMP PDU which
                      contains the value `readOnly' in the error-status
                      field, as such this object is provided as a means
                      of detecting incorrect implementations of the
                      SNMP."
              ::= { snmp 11 }

          snmpInGenErrs OBJECT-TYPE
              SYNTAX  Counter
              ACCESS  read-only
              STATUS  mandatory
              DESCRIPTION
                      "The total number of SNMP PDUs which were
                      delivered to the SNMP protocol entity and for
                      which the value of the error-status field is
                      `genErr'."
              ::= { snmp 12 }

          snmpInTotalReqVars OBJECT-TYPE
              SYNTAX  Counter
              ACCESS  read-only
              STATUS  mandatory
              DESCRIPTION
                      "The total number of MIB objects which have been
                      retrieved successfully by the SNMP protocol entity
                      as the result of receiving valid SNMP Get-Request
                      and Get-Next PDUs."
              ::= { snmp 13 }

          snmpInTotalSetVars OBJECT-TYPE
              SYNTAX  Counter
              ACCESS  read-only
              STATUS  mandatory
              DESCRIPTION
                      "The total number of MIB objects which have been
                      altered successfully by the SNMP protocol entity
                      as the result of receiving valid SNMP Set-Request
                      PDUs."
              ::= { snmp 14 }

          snmpInGetRequests OBJECT-TYPE
              SYNTAX  Counter
              ACCESS  read-only
              STATUS  mandatory
              DESCRIPTION
                      "The total number of SNMP Get-Request PDUs which
                      have been accepted and processed by the SNMP
                      protocol entity."
              ::= { snmp 15 }

          snmpInGetNexts OBJECT-TYPE
              SYNTAX  Counter
              ACCESS  read-only
              STATUS  mandatory
              DESCRIPTION
                      "The total number of SNMP Get-Next PDUs which have
                      been accepted and processed by the SNMP protocol
                      entity."
              ::= { snmp 16 }

          snmpInSetRequests OBJECT-TYPE
              SYNTAX  Counter
              ACCESS  read-only
              STATUS  mandatory
              DESCRIPTION
                      "The total number of SNMP Set-Request PDUs which
                      have been accepted and processed by the SNMP
                      protocol entity."
              ::= { snmp 17 }

          snmpInGetResponses OBJECT-TYPE
              SYNTAX  Counter
              ACCESS  read-only
              STATUS  mandatory
              DESCRIPTION
                      "The total number of SNMP Get-Response PDUs which
                      have been accepted and processed by the SNMP
                      protocol entity."
              ::= { snmp 18 }

          snmpInTraps OBJECT-TYPE
              SYNTAX  Counter
              ACCESS  read-only
              STATUS  mandatory
              DESCRIPTION
                      "The total number of SNMP Trap PDUs which have
                      been accepted and processed by the SNMP protocol
                      entity."
              ::= { snmp 19 }

          snmpOutTooBigs OBJECT-TYPE
              SYNTAX  Counter
              ACCESS  read-only
              STATUS  mandatory
              DESCRIPTION
                      "The total number of SNMP PDUs which were
                      generated by the SNMP protocol entity and for
                      which the value of the error-status field is
                      `tooBig.'"
              ::= { snmp 20 }

          snmpOutNoSuchNames OBJECT-TYPE
              SYNTAX  Counter
              ACCESS  read-only
              STATUS  mandatory
              DESCRIPTION
                      "The total number of SNMP PDUs which were
                      generated by the SNMP protocol entity and for
                      which the value of the error-status is
                      `noSuchName'."
              ::= { snmp 21 }

          snmpOutBadValues OBJECT-TYPE
              SYNTAX  Counter
              ACCESS  read-only
              STATUS  mandatory
              DESCRIPTION
                      "The total number of SNMP PDUs which were
                      generated by the SNMP protocol entity and for
                      which the value of the error-status field is
                      `badValue'."
              ::= { snmp 22 }

          -- { snmp 23 } is not used

          snmpOutGenErrs OBJECT-TYPE
              SYNTAX  Counter
              ACCESS  read-only
              STATUS  mandatory
              DESCRIPTION
                      "The total number of SNMP PDUs which were
                      generated by the SNMP protocol entity and for
                      which the value of the error-status field is
                      `genErr'."
              ::= { snmp 24 }

          snmpOutGetRequests OBJECT-TYPE
              SYNTAX  Counter
              ACCESS  read-only
              STATUS  mandatory
              DESCRIPTION
                      "The total number of SNMP Get-Request PDUs which
                      have been generated by the SNMP protocol entity."
              ::= { snmp 25 }

          snmpOutGetNexts OBJECT-TYPE
              SYNTAX  Counter
              ACCESS  read-only
              STATUS  mandatory
              DESCRIPTION
                      "The total number of SNMP Get-Next PDUs which have
                      been generated by the SNMP protocol entity."
              ::= { snmp 26 }

          snmpOutSetRequests OBJECT-TYPE
              SYNTAX  Counter
              ACCESS  read-only
              STATUS  mandatory
              DESCRIPTION
                      "The total number of SNMP Set-Request PDUs which
                      have been generated by the SNMP protocol entity."
              ::= { snmp 27 }

          snmpOutGetResponses OBJECT-TYPE
              SYNTAX  Counter
              ACCESS  read-only
              STATUS  mandatory
              DESCRIPTION
                      "The total number of SNMP Get-Response PDUs which
                      have been generated by the SNMP protocol entity."
              ::= { snmp 28 }

          snmpOutTraps OBJECT-TYPE
              SYNTAX  Counter
              ACCESS  read-only
              STATUS  mandatory
              DESCRIPTION
                      "The total number of SNMP Trap PDUs which have
                      been generated by the SNMP protocol entity."
              ::= { snmp 29 }

          snmpEnableAuthenTraps OBJECT-TYPE
              SYNTAX  INTEGER { enabled(1), disabled(2) }
              ACCESS  read-write
              STATUS  mandatory
              DESCRIPTION
                      "Indicates whether the SNMP agent process is
                      permitted to generate authentication-failure
                      traps.  The value of this object overrides any
                      configuration information; as such, it provides a
                      means whereby all authentication-failure traps may
                      be disabled.

                      Note that it is strongly recommended that this
                      object be stored in non-volatile memory so that it
                      remains constant between re-initializations of the
                      network management system."
              ::= { snmp 30 }


--
-- FILE: /users/sse/mibs/src/rfc/rfc1316.mib
--

-- Changes for RFC1316 (Character MIB)
--      Added IMPORT for mib-2.




            -- this is the MIB module for character stream devices

            char    OBJECT IDENTIFIER ::= { mib-2 19 }

            -- Textual Conventions

                AutonomousType    ::= OBJECT IDENTIFIER

            -- The object identifier is an independently extensible type
            -- identification value.  It may, for example indicate a
            -- particular sub-tree with further MIB definitions, or
            -- define something like a protocol type or type of
            -- hardware.

                InstancePointer   ::= OBJECT IDENTIFIER

            -- The object identifier is a pointer to a specific instance
            -- of a MIB object in this agent's implemented MIB.  By
            -- convention, it is the first object in the conceptual row
            -- for the instance.


            -- the generic Character group

            -- Implementation of this group is mandatory for all
            -- systems that offer character ports

            charNumber OBJECT-TYPE
                SYNTAX INTEGER
                ACCESS read-only
                STATUS mandatory
                DESCRIPTION
                    "The number of entries in charPortTable, regardless
                    of their current state."
                ::= { char 1 }


            -- the Character Port table

            charPortTable OBJECT-TYPE
                SYNTAX SEQUENCE OF CharPortEntry
                ACCESS not-accessible
                STATUS mandatory
                DESCRIPTION
                    "A list of port entries.  The number of entries is
                    given by the value of charNumber."
                ::= { char 2 }

            charPortEntry OBJECT-TYPE
                SYNTAX CharPortEntry
                ACCESS not-accessible
                STATUS mandatory
                DESCRIPTION
                    "Status and parameter values for a character port."
                INDEX { charPortIndex }
                ::= { charPortTable 1 }

            CharPortEntry ::=
                SEQUENCE {
                    charPortIndex
                        INTEGER,
                    charPortName
                        DisplayString,
                    charPortType
                        INTEGER,
                    charPortHardware
                        AutonomousType,
                    charPortReset
                        INTEGER,
                    charPortAdminStatus
                        INTEGER,
                    charPortOperStatus
                        INTEGER,
                    charPortLastChange
                        TimeTicks,
                    charPortInFlowType
                        INTEGER,
                    charPortOutFlowType
                        INTEGER,
                    charPortInFlowState
                        INTEGER,
                    charPortOutFlowState
                        INTEGER,
                    charPortInCharacters
                        Counter,
                    charPortOutCharacters
                        Counter,
                    charPortAdminOrigin
                        INTEGER,
                    charPortSessionMaximum
                        INTEGER,
                    charPortSessionNumber
                        Gauge,
                    charPortSessionIndex
                        INTEGER
                }

            charPortIndex OBJECT-TYPE
                SYNTAX INTEGER
                ACCESS read-only
                STATUS mandatory
                DESCRIPTION
                    "A unique value for each character port.  Its value
                    ranges between 1 and the value of charNumber.  By
                    convention and if possible, hardware port numbers
                    come first, with a simple, direct mapping.  The
                    value for each port must remain constant at least
                    from one re-initialization of the network management
                    agent to the next."
                ::= { charPortEntry 1 }

            charPortName OBJECT-TYPE
                SYNTAX DisplayString (SIZE (0..32))
                ACCESS read-write
                STATUS mandatory
                DESCRIPTION
                    "An administratively assigned name for the port,
                    typically with some local significance."
                ::= { charPortEntry 2 }

            charPortType OBJECT-TYPE
                SYNTAX INTEGER { physical(1), virtual(2) }
                ACCESS read-only
                STATUS mandatory
                DESCRIPTION
                    "The port's type, 'physical' if the port represents
                    an external hardware connector, 'virtual' if it does
                    not."
                ::= { charPortEntry 3 }

            charPortHardware OBJECT-TYPE
                SYNTAX AutonomousType
                ACCESS read-only
                STATUS mandatory
                DESCRIPTION
                    "A reference to hardware MIB definitions specific to
                    a physical port's external connector.  For example,
                    if the connector is RS-232, then the value of this
                    object refers to a MIB sub-tree defining objects
                    specific to RS-232.  If an agent is not configured
                    to have such values, the agent returns the object
                    identifier:

                        nullHardware OBJECT IDENTIFIER ::= { 0 0 }
                    "
                ::= { charPortEntry 4 }

            charPortReset OBJECT-TYPE
                SYNTAX INTEGER { ready(1), execute(2) }
                ACCESS read-write
                STATUS mandatory
                DESCRIPTION
                    "A control to force the port into a clean, initial
                    state, both hardware and software, disconnecting all
                    the port's existing sessions.  In response to a
                    get-request or get-next-request, the agent always
                    returns 'ready' as the value.  Setting the value to
                    'execute' causes a reset."
                ::= { charPortEntry 5 }

            charPortAdminStatus OBJECT-TYPE
                SYNTAX INTEGER { enabled(1), disabled(2), off(3),
                                 maintenance(4) }
                ACCESS read-write
                STATUS mandatory
                DESCRIPTION
                    "The port's desired state, independent of flow
                    control.  'enabled' indicates that the port is
                    allowed to pass characters and form new sessions.
                    'disabled' indicates that the port is allowed to
                    pass characters but not form new sessions.  'off'
                    indicates that the port is not allowed to pass
                    characters or have any sessions. 'maintenance'
                    indicates a maintenance mode, exclusive of normal
                    operation, such as running a test."
                ::= { charPortEntry 6 }

            charPortOperStatus OBJECT-TYPE
                SYNTAX INTEGER { up(1), down(2),
                                 maintenance(3), absent(4), active(5) }
                ACCESS read-only
                STATUS mandatory
                DESCRIPTION
                    "The port's actual, operational state, independent
                    of flow control.  'up' indicates able to function
                    normally.  'down' indicates inability to function
                    for administrative or operational reasons.
                    'maintenance' indicates a maintenance mode,
                    exclusive of normal operation, such as running a
                    test.  'absent' indicates that port hardware is not
                    present.  'active' indicates up with a user present
                    (e.g. logged in)."
                ::= { charPortEntry 7 }

            charPortLastChange OBJECT-TYPE
                SYNTAX TimeTicks
                ACCESS read-only
                STATUS mandatory
                DESCRIPTION
                    "The value of sysUpTime at the time the port entered
                    its current operational state.  If the current state
                    was entered prior to the last reinitialization of
                    the local network management subsystem, then this
                    object contains a zero value."
                ::= { charPortEntry 8 }

            charPortInFlowType OBJECT-TYPE
                SYNTAX INTEGER { none(1), xonXoff(2), hardware(3),
                                 ctsRts(4), dsrDtr(5) }
                ACCESS read-write
                STATUS mandatory
                DESCRIPTION
                    "The port's type of input flow control.  'none'
                    indicates no flow control at this level or below.
                    'xonXoff' indicates software flow control by
                    recognizing XON and XOFF characters.  'hardware'
                    indicates flow control delegated to the lower level,
                    for example a parallel port.

                    'ctsRts' and 'dsrDtr' are specific to RS-232-like
                    ports.  Although not architecturally pure, they are
                    included here for simplicity's sake."
                ::= { charPortEntry 9 }

            charPortOutFlowType OBJECT-TYPE
                SYNTAX INTEGER { none(1), xonXoff(2), hardware(3),
                                 ctsRts(4), dsrDtr(5) }
                ACCESS read-write
                STATUS mandatory
                DESCRIPTION
                    "The port's type of output flow control.  'none'
                    indicates no flow control at this level or below.
                    'xonXoff' indicates software flow control by
                    recognizing XON and XOFF characters.  'hardware'
                    indicates flow control delegated to the lower level,
                    for example a parallel port.

                    'ctsRts' and 'dsrDtr' are specific to RS-232-like
                    ports.  Although not architecturally pure, they are
                    included here for simplicy's sake."
                ::= { charPortEntry 10 }

            charPortInFlowState OBJECT-TYPE
                SYNTAX INTEGER { none(1), unknown(2), stop(3), go(4) }
                ACCESS read-only
                STATUS mandatory
                DESCRIPTION
                    "The current operational state of input flow control
                    on the port.  'none' indicates not applicable.
                    'unknown' indicates this level does not know.
                    'stop' indicates flow not allowed.  'go' indicates
                    flow allowed."
                ::= { charPortEntry 11 }

            charPortOutFlowState OBJECT-TYPE
                SYNTAX INTEGER { none(1), unknown(2), stop(3), go(4) }
                ACCESS read-only
                STATUS mandatory
                DESCRIPTION
                    "The current operational state of output flow
                    control on the port.  'none' indicates not
                    applicable.  'unknown' indicates this level does not
                    know.  'stop' indicates flow not allowed.  'go'
                    indicates flow allowed."
                ::= { charPortEntry 12 }

            charPortInCharacters OBJECT-TYPE
                SYNTAX Counter
                ACCESS read-only
                STATUS mandatory
                DESCRIPTION
                    "Total number of characters detected as input from
                    the port since system re-initialization and while
                    the port operational state was 'up', 'active', or
                    'maintenance', including, for example, framing, flow
                    control (i.e. XON and XOFF), each occurrence of a
                    BREAK condition, locally-processed input, and input
                    sent to all sessions."
                ::= { charPortEntry 13 }

            charPortOutCharacters OBJECT-TYPE
                SYNTAX Counter
                ACCESS read-only
                STATUS mandatory
                DESCRIPTION
                    "Total number of characters detected as output to
                    the port since system re-initialization and while
                    the port operational state was 'up', 'active', or
                    'maintenance', including, for example, framing, flow
                    control (i.e. XON and XOFF), each occurrence of a
                    BREAK condition, locally-created output, and output
                    received from all sessions."
                ::= { charPortEntry 14 }

            charPortAdminOrigin OBJECT-TYPE
                SYNTAX INTEGER { dynamic(1), network(2), local(3),
                                 none(4) }
                ACCESS read-write
                STATUS mandatory
                DESCRIPTION
                    "The administratively allowed origin for
                    establishing session on the port.  'dynamic' allows
                    'network' or 'local' session establishment. 'none'
                    disallows session establishment."
                ::= { charPortEntry 15 }

            charPortSessionMaximum OBJECT-TYPE
                SYNTAX INTEGER
                ACCESS read-write
                STATUS mandatory
                DESCRIPTION
                    "The maximum number of concurrent sessions allowed
                    on the port.  A value of -1 indicates no maximum.
                    Setting the maximum to less than the current number
                    of sessions has unspecified results."
                ::= { charPortEntry 16 }

            charPortSessionNumber OBJECT-TYPE
                SYNTAX Gauge
                ACCESS read-only
                STATUS mandatory
                DESCRIPTION
                    "The number of open sessions on the port that are in
                    the connecting, connected, or disconnecting state."
                ::= { charPortEntry 17 }

            charPortSessionIndex OBJECT-TYPE
                SYNTAX INTEGER
                ACCESS read-only
                STATUS mandatory
                DESCRIPTION
                    "The value of charSessIndex for the port's first or
                    only active session.  If the port has no active
                    session, the agent returns the value zero."
                ::= { charPortEntry 18 }


            -- the Character Session table

            charSessTable OBJECT-TYPE
                SYNTAX SEQUENCE OF CharSessEntry
                ACCESS not-accessible
                STATUS mandatory
                DESCRIPTION
                    "A list of port session entries."
                ::= { char 3 }

            charSessEntry OBJECT-TYPE
                SYNTAX CharSessEntry
                ACCESS not-accessible
                STATUS mandatory
                DESCRIPTION
                    "Status and parameter values for a character port
                    session."
                INDEX { charSessPortIndex, charSessIndex }
                ::= { charSessTable 1 }

            CharSessEntry ::=
                SEQUENCE {
                    charSessPortIndex
                        INTEGER,
                    charSessIndex
                        INTEGER,
                    charSessKill
                        INTEGER,
                    charSessState
                        INTEGER,
                    charSessProtocol
                        AutonomousType,
                    charSessOperOrigin
                        INTEGER,
                    charSessInCharacters
                        Counter,
                    charSessOutCharacters
                        Counter,
                    charSessConnectionId
                        InstancePointer,
                    charSessStartTime
                        TimeTicks
                }

            charSessPortIndex OBJECT-TYPE
                SYNTAX INTEGER
                ACCESS read-only
                STATUS mandatory
                DESCRIPTION
                    "The value of charPortIndex for the port to which
                    this session belongs."
                ::= { charSessEntry 1 }

            charSessIndex OBJECT-TYPE
                SYNTAX INTEGER
                ACCESS read-only
                STATUS mandatory
                DESCRIPTION
                    "The session index in the context of the port, a
                    non-zero positive integer.  Session indexes within a
                    port need not be sequential.  Session indexes may be
                    reused for different ports.  For example, port 1 and
                    port 3 may both have a session 2 at the same time.
                    Session indexes may have any valid integer value,
                    with any meaning convenient to the agent
                    implementation."
                ::= { charSessEntry 2 }

            charSessKill OBJECT-TYPE
                SYNTAX INTEGER { ready(1), execute(2) }
                ACCESS read-write
                STATUS mandatory
                DESCRIPTION
                    "A control to terminate the session.  In response to
                    a get-request or get-next-request, the agent always
                    returns 'ready' as the value.  Setting the value to
                    'execute' causes termination."
                ::= { charSessEntry 3 }

            charSessState OBJECT-TYPE
                SYNTAX INTEGER { connecting(1), connected(2),
                                 disconnecting(3) }
                ACCESS read-only
                STATUS mandatory
                DESCRIPTION
                    "The current operational state of the session,
                    disregarding flow control.  'connected' indicates
                    that character data could flow on the network side
                    of session.  'connecting' indicates moving from
                    nonexistent toward 'connected'.  'disconnecting'
                    indicates moving from 'connected' or 'connecting' to
                    nonexistent."
                ::= { charSessEntry 4 }

            charSessProtocol OBJECT-TYPE
                SYNTAX AutonomousType
                ACCESS read-only
                STATUS mandatory
                DESCRIPTION
                    "The network protocol over which the session is
                    running.  Other OBJECT IDENTIFIER values may be
                    defined elsewhere, in association with specific
                    protocols.  However, this document assigns those of
                    known interest as of this writing."
                ::= { charSessEntry 5 }

            wellKnownProtocols OBJECT IDENTIFIER ::= { char 4 }

            protocolOther  OBJECT IDENTIFIER ::= {wellKnownProtocols 1}
            protocolTelnet OBJECT IDENTIFIER ::= {wellKnownProtocols 2}
            protocolRlogin OBJECT IDENTIFIER ::= {wellKnownProtocols 3}
            protocolLat    OBJECT IDENTIFIER ::= {wellKnownProtocols 4}
            protocolX29    OBJECT IDENTIFIER ::= {wellKnownProtocols 5}
            protocolVtp    OBJECT IDENTIFIER ::= {wellKnownProtocols 6}

            charSessOperOrigin OBJECT-TYPE
                SYNTAX INTEGER { unknown(1), network(2), local(3) }
                ACCESS read-only
                STATUS mandatory
                DESCRIPTION
                    "The session's source of establishment."
                ::= { charSessEntry 6 }

            charSessInCharacters OBJECT-TYPE
                SYNTAX Counter
                ACCESS read-only
                STATUS mandatory
                DESCRIPTION
                    "This session's subset of charPortInCharacters."
                ::= { charSessEntry 7 }

            charSessOutCharacters OBJECT-TYPE
                SYNTAX Counter
                ACCESS read-only
                STATUS mandatory
                DESCRIPTION
                    "This session's subset of charPortOutCharacters."
                ::= { charSessEntry 8 }

            charSessConnectionId OBJECT-TYPE
                SYNTAX InstancePointer
                ACCESS read-only
                STATUS mandatory
                DESCRIPTION
                    "A reference to additional local MIB information.
                    This should be the highest available related MIB,
                    corresponding to charSessProtocol, such as Telnet.
                    For example, the value for a TCP connection (in the
                    absence of a Telnet MIB) is the object identifier of
                    tcpConnState.  If an agent is not configured to have
                    such values, the agent returns the object
                    identifier:

                        nullConnectionId OBJECT IDENTIFIER ::= { 0 0 }
                    "
                ::= { charSessEntry 9 }

            charSessStartTime OBJECT-TYPE
                SYNTAX TimeTicks
                ACCESS read-only
                STATUS mandatory
                DESCRIPTION
                    "The value of sysUpTime in MIB-2 when the session
                    entered connecting state."
                ::= { charSessEntry 10 }


--
-- FILE: /users/sse/mibs/src/rfc/rfc1317.mib
--

-- Changes for RFC1317 (RS-232 MIB)
--      No changes needed.




       -- this is the MIB module for RS-232-like hardware devices

       rs232    OBJECT IDENTIFIER ::= { transmission 33 }


       -- the generic RS-232-like group

       -- Implementation of this group is mandatory for all
       -- systems that have RS-232-like hardware ports
       -- supporting higher level services such as character
       -- streams or network interfaces

       rs232Number OBJECT-TYPE
           SYNTAX INTEGER
           ACCESS read-only
           STATUS mandatory
           DESCRIPTION
               "The number of ports (regardless of their current
               state) in the RS-232-like general port table."
           ::= { rs232 1 }


       -- the RS-232-like general Port table

       rs232PortTable OBJECT-TYPE
           SYNTAX SEQUENCE OF Rs232PortEntry
           ACCESS not-accessible
           STATUS mandatory
           DESCRIPTION
               "A list of port entries.  The number of entries is
               given by the value of rs232Number."
           ::= { rs232 2 }

       rs232PortEntry OBJECT-TYPE
           SYNTAX Rs232PortEntry
           ACCESS not-accessible
           STATUS mandatory
           DESCRIPTION
               "Status and parameter values for a port."
           INDEX { rs232PortIndex }
           ::= { rs232PortTable 1 }

       Rs232PortEntry ::=
           SEQUENCE {
               rs232PortIndex
                   INTEGER,
               rs232PortType
                   INTEGER,
               rs232PortInSigNumber
                   INTEGER,
               rs232PortOutSigNumber
                   INTEGER,
               rs232PortInSpeed
                   INTEGER,
               rs232PortOutSpeed
                   INTEGER    }

       rs232PortIndex OBJECT-TYPE
           SYNTAX INTEGER
           ACCESS read-only
           STATUS mandatory
           DESCRIPTION
               "A unique value for each port.  Its value ranges
               between 1 and the value of rs232Number.  By
               convention and if possible, hardware port numbers
               map directly to external connectors.  The value for
               each port must remain constant at least from one
               re-initialization of the network management agent to
               the next."
           ::= { rs232PortEntry 1 }

       rs232PortType OBJECT-TYPE
           SYNTAX INTEGER { other(1), rs232(2), rs422(3),
                            rs423(4), v35(5) }
           ACCESS read-only
           STATUS mandatory
           DESCRIPTION
               "The port's hardware type."
           ::= { rs232PortEntry 2 }

       rs232PortInSigNumber OBJECT-TYPE
           SYNTAX INTEGER
           ACCESS read-only
           STATUS mandatory
           DESCRIPTION
               "The number of input signals for the port in the
               input signal table (rs232PortInSigTable).  The table
               contains entries only for those signals the software
               can detect."
           ::= { rs232PortEntry 3 }

       rs232PortOutSigNumber OBJECT-TYPE
           SYNTAX INTEGER
           ACCESS read-only
           STATUS mandatory
           DESCRIPTION
               "The number of output signals for the port in the
               output signal table (rs232PortOutSigTable).  The
               table contains entries only for those signals the
               software can assert."
           ::= { rs232PortEntry 4 }

       rs232PortInSpeed OBJECT-TYPE
           SYNTAX INTEGER
           ACCESS read-write
           STATUS mandatory
           DESCRIPTION
               "The port's input speed in bits per second."
           ::= { rs232PortEntry 5 }

       rs232PortOutSpeed OBJECT-TYPE
           SYNTAX INTEGER
           ACCESS read-write
           STATUS mandatory
           DESCRIPTION
               "The port's output speed in bits per second."
           ::= { rs232PortEntry 6 }


       -- the RS-232-like Asynchronous Port group

       -- Implementation of this group is mandatory if the system
       -- has any asynchronous ports.  Otherwise it is not
       -- present.

       rs232AsyncPortTable OBJECT-TYPE
           SYNTAX SEQUENCE OF Rs232AsyncPortEntry
           ACCESS not-accessible
           STATUS mandatory
           DESCRIPTION
               "A list of asynchronous port entries.  The maximum
               entry number is given by the value of rs232Number.
               Entries need not exist for synchronous ports."
           ::= { rs232 3 }

       rs232AsyncPortEntry OBJECT-TYPE
           SYNTAX Rs232AsyncPortEntry
           ACCESS not-accessible
           STATUS mandatory
           DESCRIPTION
               "Status and parameter values for an asynchronous
               port."
           INDEX { rs232AsyncPortIndex }
           ::= { rs232AsyncPortTable 1 }

       Rs232AsyncPortEntry ::=
           SEQUENCE {
               rs232AsyncPortIndex
                   INTEGER,
               rs232AsyncPortBits
                   INTEGER,
               rs232AsyncPortStopBits
                   INTEGER,
               rs232AsyncPortParity
                   INTEGER,
               rs232AsyncPortAutobaud
                   INTEGER,
               rs232AsyncPortParityErrs
                   Counter,
               rs232AsyncPortFramingErrs
                   Counter,
               rs232AsyncPortOverrunErrs
                   Counter

           }

       rs232AsyncPortIndex OBJECT-TYPE
           SYNTAX INTEGER
           ACCESS read-only
           STATUS mandatory
           DESCRIPTION
               "A unique value for each port.  Its value is the
               same as rs232PortIndex for the port."
           ::= { rs232AsyncPortEntry 1 }

       rs232AsyncPortBits OBJECT-TYPE
           SYNTAX INTEGER (5..8)
           ACCESS read-write
           STATUS mandatory
           DESCRIPTION
               "The port's number of bits in a character."
           ::= { rs232AsyncPortEntry 2 }

       rs232AsyncPortStopBits OBJECT-TYPE
           SYNTAX INTEGER { one(1), two(2),
                            one-and-half(3), dynamic(4) }
           ACCESS read-write
           STATUS mandatory
           DESCRIPTION
               "The port's number of stop bits."
           ::= { rs232AsyncPortEntry 3 }

       rs232AsyncPortParity OBJECT-TYPE
           SYNTAX INTEGER { none(1), odd(2), even(3),
                            mark(4), space(5) }
           ACCESS read-write
           STATUS mandatory
           DESCRIPTION
               "The port's sense of a character parity bit."
           ::= { rs232AsyncPortEntry 4 }

       rs232AsyncPortAutobaud OBJECT-TYPE
           SYNTAX INTEGER { enabled(1), disabled(2) }
           ACCESS read-write
           STATUS mandatory
           DESCRIPTION
               "A control for the port's ability to automatically
               sense input speed.

               When rs232PortAutoBaud is 'enabled', a port may
               autobaud to values different from the set values for
               speed, parity, and character size.  As a result a
               network management system may temporarily observe
               values different from what was previously set."
           ::= { rs232AsyncPortEntry 5 }

       rs232AsyncPortParityErrs OBJECT-TYPE
           SYNTAX Counter
           ACCESS read-only
           STATUS mandatory
           DESCRIPTION
               "Total number of characters with a parity error,
               input from the port since system re-initialization
               and while the port state was 'up' or 'test'."
           ::= { rs232AsyncPortEntry 6 }

       rs232AsyncPortFramingErrs OBJECT-TYPE
           SYNTAX Counter
           ACCESS read-only
           STATUS mandatory
           DESCRIPTION
               "Total number of characters with a framing error,
               input from the port since system re-initialization
               and while the port state was 'up' or 'test'."
           ::= { rs232AsyncPortEntry 7 }

       rs232AsyncPortOverrunErrs OBJECT-TYPE
           SYNTAX Counter
           ACCESS read-only
           STATUS mandatory
           DESCRIPTION
               "Total number of characters with an overrun error,
               input from the port since system re-initialization
               and while the port state was 'up' or 'test'."
           ::= { rs232AsyncPortEntry 8 }


       -- the RS-232-like Synchronous Port group

       -- Implementation of this group is mandatory if the system
       -- has any synchronous ports.  Otherwise it is not
       -- present.

       rs232SyncPortTable OBJECT-TYPE
           SYNTAX SEQUENCE OF Rs232SyncPortEntry
           ACCESS not-accessible
           STATUS mandatory
           DESCRIPTION
               "A list of synchronous port entries.  The maximum
               entry number is given by the value of rs232Number.
               Entries need not exist for asynchronous ports."
           ::= { rs232 4 }

       rs232SyncPortEntry OBJECT-TYPE
           SYNTAX Rs232SyncPortEntry
           ACCESS not-accessible
           STATUS mandatory
           DESCRIPTION
               "Status and parameter values for a synchronous
               port."
           INDEX { rs232SyncPortIndex }
           ::= { rs232SyncPortTable 1 }

       Rs232SyncPortEntry ::=
           SEQUENCE {
               rs232SyncPortIndex
                   INTEGER,
               rs232SyncPortClockSource
                   INTEGER,
               rs232SyncPortFrameCheckErrs
                   Counter,
               rs232SyncPortTransmitUnderrunErrs
                   Counter,
               rs232SyncPortReceiveOverrunErrs
                   Counter,
               rs232SyncPortInterruptedFrames
                   Counter,
               rs232SyncPortAbortedFrames
                   Counter
           }

       rs232SyncPortIndex OBJECT-TYPE
           SYNTAX INTEGER
           ACCESS read-only
           STATUS mandatory
           DESCRIPTION
               "A unique value for each port.  Its value is the
               same as rs232PortIndex for the port."
           ::= { rs232SyncPortEntry 1 }

       rs232SyncPortClockSource OBJECT-TYPE
           SYNTAX INTEGER  { internal(1), external(2), split(3) }
           ACCESS read-write
           STATUS mandatory
           DESCRIPTION
               "Source of the port's bit rate clock. 'split' means
               the tranmit clock is internal and the receive clock
               is external."
           ::= { rs232SyncPortEntry 2 }

       rs232SyncPortFrameCheckErrs OBJECT-TYPE
           SYNTAX Counter
           ACCESS read-only
           STATUS mandatory
           DESCRIPTION
               "Total number of frames with an invalid frame check
               sequence, input from the port since system
               re-initialization and while the port state was 'up'
               or 'test'."
           ::= { rs232SyncPortEntry 3 }

       rs232SyncPortTransmitUnderrunErrs OBJECT-TYPE
           SYNTAX Counter
           ACCESS read-only
           STATUS mandatory
           DESCRIPTION
               "Total number of frames that failed to be
               transmitted on the port since system
               re-initialization and while the port state was 'up'
               or 'test' because data was not available to the
               transmitter in time."
           ::= { rs232SyncPortEntry 4 }

       rs232SyncPortReceiveOverrunErrs OBJECT-TYPE
           SYNTAX Counter
           ACCESS read-only
           STATUS mandatory
           DESCRIPTION
               "Total number of frames that failed to be received
               on the port since system re-initialization and while
               the port state was 'up' or 'test' because the
               receiver did not accept the data in time."
           ::= { rs232SyncPortEntry 5 }

       rs232SyncPortInterruptedFrames OBJECT-TYPE
           SYNTAX Counter
           ACCESS read-only
           STATUS mandatory
           DESCRIPTION
               "Total number of frames that failed to be received
               or transmitted on the port due to loss of modem
               signals since system re-initialization and while the
               port state was 'up' or 'test'."
           ::= { rs232SyncPortEntry 6 }

       rs232SyncPortAbortedFrames OBJECT-TYPE
           SYNTAX Counter
           ACCESS read-only
           STATUS mandatory
           DESCRIPTION
               "Number of frames aborted on the port due to
               receiving an abort sequence since system
               re-initialization and while the port state was 'up'
               or 'test'."
           ::= { rs232SyncPortEntry 7 }


       -- the Input Signal table

       rs232InSigTable OBJECT-TYPE
           SYNTAX SEQUENCE OF Rs232InSigEntry
           ACCESS not-accessible
           STATUS mandatory
           DESCRIPTION
               "A list of port input control signal entries."
           ::= { rs232 5 }

       rs232InSigEntry OBJECT-TYPE
           SYNTAX Rs232InSigEntry
           ACCESS not-accessible
           STATUS mandatory
           DESCRIPTION
               "Input control signal status for a hardware port."
           INDEX { rs232InSigPortIndex, rs232InSigName }
           ::= { rs232InSigTable 1 }

       Rs232InSigEntry ::=
           SEQUENCE {
               rs232InSigPortIndex
                   INTEGER,
               rs232InSigName
                   INTEGER,
               rs232InSigState
                   INTEGER,
               rs232InSigChanges
                   Counter
           }

       rs232InSigPortIndex OBJECT-TYPE
           SYNTAX INTEGER
           ACCESS read-only
           STATUS mandatory
           DESCRIPTION
               "The value of rs232PortIndex for the port to which
               this entry belongs."
           ::= { rs232InSigEntry 1 }

       rs232InSigName OBJECT-TYPE
           SYNTAX INTEGER { rts(1), cts(2), dsr(3), dtr(4), ri(5),
                            dcd(6), sq(7), srs(8), srts(9),
                            scts(10), sdcd(11) }
           ACCESS read-only
           STATUS mandatory
           DESCRIPTION
               "Identification of a hardware signal, as follows:

                   rts    Request to Send
                   cts    Clear to Send
                   dsr    Data Set Ready
                   dtr    Data Terminal Ready
                   ri     Ring Indicator
                   dcd    Received Line Signal Detector
                   sq     Signal Quality Detector
                   srs    Data Signaling Rate Selector
                   srts   Secondary Request to Send
                   scts   Secondary Clear to Send
                   sdcd   Secondary Received Line Signal Detector
               "
           REFERENCE
               "EIA Standard RS-232-C, August 1969."
           ::= { rs232InSigEntry 2 }

       rs232InSigState OBJECT-TYPE
           SYNTAX INTEGER { none(1), on(2), off(3) }
           ACCESS read-only
           STATUS mandatory
           DESCRIPTION
               "The current signal state."
           ::= { rs232InSigEntry 3 }

       rs232InSigChanges OBJECT-TYPE
           SYNTAX Counter
           ACCESS read-only
           STATUS mandatory
           DESCRIPTION
               "The number of times the signal has changed from
               'on' to 'off' or from 'off' to 'on'."
           ::= { rs232InSigEntry 4 }


       -- the Output Signal table

       rs232OutSigTable OBJECT-TYPE
           SYNTAX SEQUENCE OF Rs232OutSigEntry
           ACCESS not-accessible
           STATUS mandatory
           DESCRIPTION
               "A list of port output control signal entries."
           ::= { rs232 6 }

       rs232OutSigEntry OBJECT-TYPE
           SYNTAX Rs232OutSigEntry
           ACCESS not-accessible
           STATUS mandatory
           DESCRIPTION
               "Output control signal status for a hardware port."
           INDEX { rs232OutSigPortIndex, rs232OutSigName }
           ::= { rs232OutSigTable 1 }

       Rs232OutSigEntry ::=
           SEQUENCE {
               rs232OutSigPortIndex
                   INTEGER,
               rs232OutSigName
                   INTEGER,
               rs232OutSigState
                   INTEGER,
               rs232OutSigChanges
                   Counter
           }

       rs232OutSigPortIndex OBJECT-TYPE
           SYNTAX INTEGER
           ACCESS read-only
           STATUS mandatory
           DESCRIPTION
               "The value of rs232PortIndex for the port to which
               this entry belongs."
           ::= { rs232OutSigEntry 1 }

       rs232OutSigName OBJECT-TYPE
           SYNTAX INTEGER { rts(1), cts(2), dsr(3), dtr(4), ri(5),
                            dcd(6), sq(7), srs(8), srts(9),
                            scts(10), sdcd(11) }
           ACCESS read-only
           STATUS mandatory
           DESCRIPTION
               "Identification of a hardware signal, as follows:

                   rts    Request to Send
                   cts    Clear to Send
                   dsr    Data Set Ready
                   dtr    Data Terminal Ready
                   ri     Ring Indicator
                   dcd    Received Line Signal Detector
                   sq     Signal Quality Detector
                   srs    Data Signaling Rate Selector
                   srts   Secondary Request to Send
                   scts   Secondary Clear to Send
                   sdcd   Secondary Received Line Signal Detector
               "
           REFERENCE
               "EIA Standard RS-232-C, August 1969."
           ::= { rs232OutSigEntry 2 }

       rs232OutSigState OBJECT-TYPE
           SYNTAX INTEGER { none(1), on(2), off(3) }
           ACCESS read-only
           STATUS mandatory
           DESCRIPTION
               "The current signal state."
           ::= { rs232OutSigEntry 3 }

       rs232OutSigChanges OBJECT-TYPE
           SYNTAX Counter
           ACCESS read-only
           STATUS mandatory
           DESCRIPTION
               "The number of times the signal has changed from
               'on' to 'off' or from 'off' to 'on'."
           ::= { rs232OutSigEntry 4 }


--
-- FILE: /users/sse/mibs/src/rfc/rfc1289.mib
--

-- Changes for RFC1289 (DECnet Phase IV):
--      Inserted space between SYNTAX and INTEGER for
--              phivRouteType.
--      Added phivCircuitIndex to definition of sequences
--          PhivCiruitCountEntry and PhivDDCMPCircuitCountEntry.
--      Added range to phivCircuitCountDataBlocksRecd.
--   Note: these corrections are guesses...
--      Corrected syntax for phivDDCMPCircuitAdjNodeAddr in
--          sequence PhivDDCMPCircuitParametersEntry from
--          INTEGER to PhivAddr.
--      Corrected syntax for phivDDCMPCircuitSelectTimeouts
--          from INTEGER to PhivCounter.
--      Corrected syntax for phivCountersCountSendFailure
--          from INTEGER to PhivCounter.
--      Corrected syntax for phivCountersCountCollDetectFailure
--          from INTEGER to PhivCounter.
--      Corrected syntax for phivCountersCountReceiveFailure
--          from INTEGER to PhivCounter.
--      Corrected syntax for phivCountersCountUnrecFrameDest
--          from INTEGER to PhivCounter.
--      Corrected syntax for phivCountersCountDataOver
--          from INTEGER to PhivCounter.
--      Corrected syntax for phivCountersCountSysBuffUnav
--          from INTEGER to PhivCounter.
--      Corrected syntax for phivCountersCountUsrBuffUnav
--          from INTEGER to PhivCounter.
--      Corrected syntax for phivCircuitCountTermCongLoss
--          by adding range of (0..65535).
--      Question: It seems like all objects that use
--          syntax PhivCounter should have a range specified.



            -- RFC1289
            -- December 91


       -- DECNet Phase-IV MIB

            phiv             OBJECT IDENTIFIER ::= { mib-2 18 }

       -- textual conventions

       PhivAddr ::= OCTET STRING (SIZE (2))
       -- This data type is intended as a short word representation of
       -- standard DECnet Phase IV addresses. DECnet addresses are
       -- hierarchically structured numbers assigned to a particular
       -- DECnet node. The address is structured so that the area
       -- number is contained in the most significant 6 bits of the
       -- first octet.  The next 2 bits of the first octet contain
       -- the first two bits of the host address.  The remainder of
       -- the host address is contained in the second octet.

       PhivCounter ::= INTEGER
       -- This data type has been created for DECnet  counters.  These
       -- counters latch at their maximum specified value until either
       -- the system is restared, or they are reset to zero by the user
       -- or management software.

       -- groups in the decnetiv mib

             phivSystem             OBJECT IDENTIFIER ::= { phiv 1 }
             phivManagement         OBJECT IDENTIFIER ::= { phiv 2 }
             session                OBJECT IDENTIFIER ::= { phiv 3 }
             end                    OBJECT IDENTIFIER ::= { phiv 4 }
             routing                OBJECT IDENTIFIER ::= { phiv 5 }
             circuit                OBJECT IDENTIFIER ::= { phiv 6 }
             ddcmp                  OBJECT IDENTIFIER ::= { phiv 7 }
             control                OBJECT IDENTIFIER ::= { phiv 8 }
             ethernet               OBJECT IDENTIFIER ::= { phiv 9 }
             counters               OBJECT IDENTIFIER ::= { phiv 10 }
             adjacency              OBJECT IDENTIFIER ::= { phiv 11 }
             line                   OBJECT IDENTIFIER ::= { phiv 12 }
             nonBroadcastLine       OBJECT IDENTIFIER ::= { phiv 14 }
             area                   OBJECT IDENTIFIER ::= { phiv 15 }

       -- System Group

       -- The implementation of the System Group is mandatory for
       -- all systems.



       -- Network Management Group

       -- The implementation of the Network Management Group is
       -- mandatory for all systems which contain a DECnet style
       -- management version.



       -- Session Layer Group

       -- The implementation of the Session Layer Group is mandatory for
       -- all systems that implement session layer communications.




       -- End Communication Layer Group

       -- The implementation of the End Communication Layer Group is
       -- mandatory for all systems that implement end layer
       -- communications.

       -- Remote State Table







       -- End System Counter Table


















       -- additional End System objects









       -- Routing Layer Group

       -- The implementation of the Routing Layer Group is mandatory for
       -- all systems that implement level 1 routing layer
       -- communications.






















        -- Level 1 Routing Table








       -- Additional routing parameters



       -- Circuit Group

       -- The implementation of the Circuit Group is mandatory for
       -- all systems.

       -- Circuit Parameters Table


       phivCircuitParametersTable OBJECT-TYPE
           SYNTAX SEQUENCE OF PhivCircuitParametersEntry
           ACCESS not-accessible
           STATUS mandatory
           DESCRIPTION
               "Information about the parameters associated with all
               circuits currently known."
           ::= {circuit 1 }

       phivCircuitParametersEntry OBJECT-TYPE
           SYNTAX PhivCircuitParametersEntry
           ACCESS not-accessible
           STATUS mandatory
           DESCRIPTION
               "Parameters information about all circuits currently
               known."
            INDEX  { phivCircuitIndex }
            ::= { phivCircuitParametersTable 1 }

       PhivCircuitParametersEntry ::=
           SEQUENCE {
               phivCircuitIndex
                   INTEGER,
               phivCircuitLineIndex
                   INTEGER,
               phivCircuitCommonState
                   INTEGER,
               phivCircuitCommonSubState
                   INTEGER,
               phivCircuitCommonName
                   DisplayString,
               phivCircuitExecRecallTimer
                   INTEGER,
               phivCircuitCommonType
                   INTEGER,
               phivCircuitService
                   INTEGER,
               phivCircuitExecCost
                   INTEGER,
               phivCircuitExecHelloTimer
                   INTEGER
           }
        phivCircuitIndex OBJECT-TYPE
           SYNTAX INTEGER
           ACCESS read-only
           STATUS mandatory
           DESCRIPTION
               "A unique index value for each known circuit."
           ::= { phivCircuitParametersEntry 1 }

       phivCircuitLineIndex OBJECT-TYPE
           SYNTAX INTEGER
           ACCESS read-only
           STATUS mandatory
           DESCRIPTION
               "The line on which this circuit is active.  This is
               the same as the IfIndex."
           ::= { phivCircuitParametersEntry 2 }

       phivCircuitCommonState OBJECT-TYPE
           SYNTAX INTEGER {
               on (1),
               off (2),
               service (3),
               cleared (4)
           }
           ACCESS read-write
           STATUS mandatory
           DESCRIPTION
               "This value represents the circuit's Network Management
               operational state. NOTE: These values are incremented
               by one compared to the standard DECnet values in order
               to maintain compliance with RFC 1155."
           ::= { phivCircuitParametersEntry 3 }

       phivCircuitCommonSubState OBJECT-TYPE
           SYNTAX INTEGER {
               starting (1),
               reflecting (2),
               looping (3),
               loading (4),
               dumping (5),
               triggering (6),
               autoservice (7),
               autoloading (8),
               autodumping (9),
               autotriggering (10),
               synchronizing (11),
               failed (12),
               running (13)
           }
           ACCESS read-only
           STATUS mandatory
           DESCRIPTION
               "This value represents the circuit's Network Management
               operational and service substate. NOTE: These values are
               incremented by one compared to the standard DECnet values
               in order to maintain compliance with RFC 1155."
           ::= { phivCircuitParametersEntry 4 }

       phivCircuitCommonName OBJECT-TYPE
           SYNTAX DisplayString ( SIZE (0..16) )
           ACCESS read-only
           STATUS mandatory
           DESCRIPTION
               "The name of the circuit entry in the table, for example,
               SVA-0 or in a level 2 router ASYNC-8 or ETHER-1)."
           ::= { phivCircuitParametersEntry 5 }

       phivCircuitExecRecallTimer OBJECT-TYPE
           SYNTAX INTEGER (0..65535)
           ACCESS read-write
           STATUS mandatory
           DESCRIPTION
               "This parameter represents the minimum number of
               seconds to wait before restarting the circuit.  A
               value of 0 indicates not timer is running."
           ::= { phivCircuitParametersEntry 6 }

       phivCircuitCommonType OBJECT-TYPE
           SYNTAX INTEGER {
               ddcmp-point (1),
               ddcmp-control (2),
               ddcmp-tributary (3),
               x25 (4),
               ddcmp-dmc (5),
               ethernet (6),
               ci (7),
               qp2-dte20 (8),
               bisync (9),
               other (14),
               fddi (15)
           }
           ACCESS read-only
           STATUS mandatory
           DESCRIPTION
               "Represents the type of the circuit. For X.25 circuits,
               the value must be set to X25. For DDCMP and Ethernet
               circuits it is read only and is the same value as the
               protocol of the associated line.
               NOTE: Values 1 - 5 are incremented by one compared to the
               standard DECnet values in order to maintain compliance
               with RFC 1155."
           ::= { phivCircuitParametersEntry 7 }

       phivCircuitService  OBJECT-TYPE
           SYNTAX INTEGER {
               enabled (1),
               disabled (2)
           }
           ACCESS read-write
           STATUS mandatory
           DESCRIPTION
               "This value indicates whether or not Network Management
               allows service operations on a circuit. The values for
               service-control are as follows:

               ENABLED     SERVICE state and/or service functions are
                           allowed.

               DISABLED    SERVICE state and/or service functions are not
                           allowed.

               NOTE: These values are incremented by one compared to the
               standard DECnet values in order to maintain compliance
               with RFC 1155."
           ::= { phivCircuitParametersEntry 8 }

       phivCircuitExecCost OBJECT-TYPE
           SYNTAX INTEGER (1..25)
           ACCESS read-write
           STATUS mandatory
           DESCRIPTION
               "This value represents the routing cost of the circuit.
               Routing sends messages along the path between two nodes
               having the smallest cost."
           ::= { phivCircuitParametersEntry 9 }

       phivCircuitExecHelloTimer OBJECT-TYPE
           SYNTAX INTEGER (1..8191)
           ACCESS read-write
           STATUS mandatory
           DESCRIPTION
               "This value determines the frequency of Routing Hello
               messages sent to the adjacent node on the circuit."
           ::= { phivCircuitParametersEntry 10 }

       -- Circuit Counters Table


       phivCircuitCountTable OBJECT-TYPE
           SYNTAX SEQUENCE OF PhivCircuitCountEntry
           ACCESS not-accessible
           STATUS mandatory
           DESCRIPTION
               "Information about the counters associated with all
               circuits currently known."
           ::= { circuit 2 }

       phivCircuitCountEntry OBJECT-TYPE
           SYNTAX PhivCircuitCountEntry
           ACCESS not-accessible
           STATUS mandatory
           DESCRIPTION
               "Counter information about all circuits currently known"
           INDEX     { phivCircuitIndex }
           ::= { phivCircuitCountTable 1 }

       PhivCircuitCountEntry ::=
           SEQUENCE {
               phivCircuitCountSecLastZeroed
                   PhivCounter (0..65535),
               phivCircuitCountTermPacketsRecd
                   PhivCounter,
               phivCircuitCountOriginPackSent
                   PhivCounter,
               phivCircuitCountTermCongLoss
                   PhivCounter (0..65535),
               phivCircuitCountCorruptLoss
                   PhivCounter (0..255),
               phivCircuitCountTransitPksRecd
                   PhivCounter,
               phivCircuitCountTransitPkSent
                   PhivCounter,
               phivCircuitCountTransitCongestLoss
                   PhivCounter (0..65535),
               phivCircuitCountCircuitDown
                   PhivCounter (0..255),
               phivCircuitCountInitFailure
                   PhivCounter (0..255),
               phivCircuitCountAdjDown
                   PhivCounter,
               phivCircuitCountPeakAdj
                   PhivCounter,
               phivCircuitCountBytesRecd
                   PhivCounter,
               phivCircuitCountBytesSent
                   PhivCounter,
               phivCircuitCountDataBlocksRecd
                   PhivCounter (0..65535),
               phivCircuitCountDataBlocksSent
                   PhivCounter,
               phivCircuitCountUsrBuffUnav
                   PhivCounter (0..65535)
           }
       phivCircuitCountSecLastZeroed  OBJECT-TYPE
           SYNTAX PhivCounter (0..65535)
           ACCESS read-only
           STATUS mandatory
           DESCRIPTION
               "Number of seconds since the circuit counters for this
               circuit were last zeroed."
           ::= { phivCircuitCountEntry 1 }

       phivCircuitCountTermPacketsRecd OBJECT-TYPE
           SYNTAX PhivCounter
           ACCESS read-only
           STATUS mandatory
           DESCRIPTION
               "Number of terminating packets received on this circuit."
           ::= { phivCircuitCountEntry 2 }

       phivCircuitCountOriginPackSent OBJECT-TYPE
           SYNTAX PhivCounter
           ACCESS read-only
           STATUS mandatory
           DESCRIPTION
               "Number of originating packets sent on this circuit."
           ::= { phivCircuitCountEntry 3 }

       phivCircuitCountTermCongLoss OBJECT-TYPE
           SYNTAX PhivCounter (0..65535)
           ACCESS read-only
           STATUS mandatory
           DESCRIPTION
               "Number of terminating congestion losses on this
               circuit."
           ::= { phivCircuitCountEntry 4 }

       phivCircuitCountCorruptLoss OBJECT-TYPE
           SYNTAX PhivCounter (0..255)
           ACCESS read-only
           STATUS mandatory
           DESCRIPTION
               "Number of corruption losses on this circuit."
           ::= { phivCircuitCountEntry 5 }

       phivCircuitCountTransitPksRecd OBJECT-TYPE
           SYNTAX PhivCounter
           ACCESS read-only
           STATUS mandatory
           DESCRIPTION
               "Number of Transit packets received on this circuit."
           ::= { phivCircuitCountEntry 6 }

       phivCircuitCountTransitPkSent OBJECT-TYPE
           SYNTAX PhivCounter
           ACCESS read-only
           STATUS mandatory
           DESCRIPTION
               "Number of transit packets sent on this circuit."
           ::= { phivCircuitCountEntry 7 }

       phivCircuitCountTransitCongestLoss OBJECT-TYPE
           SYNTAX PhivCounter (0..65535)
           ACCESS read-only
           STATUS mandatory
           DESCRIPTION
               "Number of transit congestion losses on this circuit."
           ::= { phivCircuitCountEntry 8 }

       phivCircuitCountCircuitDown OBJECT-TYPE
           SYNTAX PhivCounter (0..255)
           ACCESS read-only
           STATUS mandatory
           DESCRIPTION
               "Number of circuit downs on this circuit."
           ::= { phivCircuitCountEntry 9 }

       phivCircuitCountInitFailure OBJECT-TYPE
           SYNTAX PhivCounter (0..255)
           ACCESS read-only
           STATUS mandatory
           DESCRIPTION
               "Number of Initialization failures on this circuit."
           ::= { phivCircuitCountEntry 10 }

       phivCircuitCountAdjDown OBJECT-TYPE
           SYNTAX PhivCounter
           ACCESS read-only
           STATUS mandatory
           DESCRIPTION
               "This counter indicates the number of adjacency losses
               that result from any of the following:
                    Node listener timeout
                    Invalid data received at node listener
                    Unexpected control (initialization or verification)
                        message received
                    Routing message received with a checksum error
                    Node identification from a routing message or a
                    Hello message that is not the one expected Hello
                    message received indicating that connectivity
                    became one-way
                    Adjacency idled."
           ::= { phivCircuitCountEntry 11 }

       phivCircuitCountPeakAdj OBJECT-TYPE
           SYNTAX PhivCounter
           ACCESS read-only
           STATUS mandatory
           DESCRIPTION
               "This counter indicates the maximum number of nodes
               that are up on the circuit."
           ::= { phivCircuitCountEntry 12 }

       phivCircuitCountBytesRecd OBJECT-TYPE
           SYNTAX PhivCounter
           ACCESS read-only
           STATUS mandatory
           DESCRIPTION
               "Number of bytes received on this circuit."
           ::= { phivCircuitCountEntry 13 }

       phivCircuitCountBytesSent OBJECT-TYPE
           SYNTAX PhivCounter
           ACCESS read-only
           STATUS mandatory
           DESCRIPTION
               "Number of bytes sent on this circuit."
           ::= { phivCircuitCountEntry 14 }

       phivCircuitCountDataBlocksRecd OBJECT-TYPE
           SYNTAX PhivCounter (0..65535)
           ACCESS read-only
           STATUS mandatory
           DESCRIPTION
               "Number of data blocks received on this circuit."
           ::= { phivCircuitCountEntry 15 }

       phivCircuitCountDataBlocksSent OBJECT-TYPE
           SYNTAX PhivCounter
           ACCESS read-only
           STATUS mandatory
           DESCRIPTION
               "Number of data blocks sent on this circuit."
           ::= { phivCircuitCountEntry 16 }

       phivCircuitCountUsrBuffUnav OBJECT-TYPE
           SYNTAX PhivCounter (0..65535)
           ACCESS read-only
           STATUS mandatory
           DESCRIPTION
               "Number of user buffer unavailable errors."
           ::= { phivCircuitCountEntry 17 }

       -- Additional Circuit Parameters

       phivCircuitOrigQueueLimit OBJECT-TYPE
           SYNTAX INTEGER
           ACCESS read-write
           STATUS mandatory
           DESCRIPTION
               "This parameter indicates the maximum number of
               originating packets that may be outstanding on this
               circuit. This does not include route-thru traffic."
           ::= { circuit 3 }

       phivCircuitCountZeroCount OBJECT-TYPE
           SYNTAX INTEGER {
             other (1),
             reset (2)
           }
           ACCESS read-write
           STATUS mandatory
           DESCRIPTION
               "When this value is set to 2, all of the counters in the
               Circuit Counter Table are set to zero."
           ::= { circuit 4 }

       -- DDCMP Circuit Group

       -- The implementation of the DDCMP Circuit Group is mandatory for
       -- all systems which support DDCMP circuits.

       -- DDCMP Parameters Table






       -- DDCMP Circuit Counter Table












       -- DDCMP Line Count Table








       -- DDCMP Multipoint Circuit Control Group

       -- The implementation of the DDCMP Multipoint Circuit Control
       -- Group is mandatory for all systems which support DDCMP
       -- multipoint control circuits.





       -- DDCMP Multipoint Circuit Control Parameters Table















       -- Ethernet Group

       -- The implementation of the Ethernet Group is mandatory
       -- for all systems which support ethernet links.

       -- Ethernet Parameters Table








       -- Counters Group

       -- The implementation of the Counters Group is mandatory for
       -- systems which only support DECnet style locking counters.

       -- Counters Table























       -- Adjacency Group

       -- The implementation of the Adjacency Group is mandatory for all
       -- conformant implementations of this memo.













       -- Line Group

       -- The implementation of the Line Group is mandatory for all
       -- conformant implementations of this memo.














       -- Non Broadcast Line Group

       -- The implementation of the Non Broadcast Line Group is
       -- mandatory for all systems which implement non broadcast
       -- lines.








       -- Area Parameters Group

       -- The implementation of the Area Parameters Group is mandatory
       -- for all systems which implement level 2 routing.









       -- Additional Area Parameters





--
-- FILE: /users/sse/mibs/src/rfc/rfc1215.smi
--

-- Changes for rfc1215 (Concise TRAP):
--      Added MODULE definition.
--      Commented out TRAP-TYPE macro definition and replaced
--        with SMIC directive to enable it.




    -- Make builtin items known

--    SMI TRAP-TYPE

        --  TRAP-TYPE MACRO ::=
        --  BEGIN
        --      TYPE NOTATION ::= "ENTERPRISE" value
        --                            (enterprise OBJECT IDENTIFIER)
        --                        VarPart
        --                        DescrPart
        --                        ReferPart
        --      VALUE NOTATION ::= value (VALUE INTEGER)
        --
        --      VarPart ::=
        --                 "VARIABLES" "{" VarTypes "}"
        --                      | empty
        --      VarTypes ::=
        --                 VarType | VarTypes "," VarType
        --      VarType ::=
        --                 value (vartype ObjectName)
        --
        --      DescrPart ::=
        --                 "DESCRIPTION" value (description DisplayString)
        --                      | empty
        --
        --      ReferPart ::=
        --                 "REFERENCE" value (reference DisplayString)
        --                      | empty
        --
        --  END


--
-- FILE: /users/sse/mibs/src/rfc/rfc1493.mib
--



          -- All representations of MAC addresses in this MIB Module
          -- use, as a textual convention (i.e. this convention does
          -- not affect their encoding), the data type:

          MacAddress ::= OCTET STRING (SIZE (6))    -- a 6 octet address
                                                    -- in the
                                                    -- "canonical"
                                                    -- order
          -- defined by IEEE 802.1a, i.e., as if it were transmitted
          -- least significant bit first, even though 802.5 (in
          -- contrast to other n802.x protocols) requires MAC
          -- addresses to be transmitted most significant bit first.
          --
          -- 16-bit addresses, if needed, are represented by setting
          -- their upper 4 octets to all 0's, i.e., AAFF would be
          -- represented as 00000000AAFF.


          -- Similarly, all representations of Bridge-Id in this MIB
          -- Module use, as a textual convention (i.e. this
          -- convention does not affect their encoding), the data
          -- type:

          BridgeId ::= OCTET STRING (SIZE (8))   -- the
                                                 -- Bridge-Identifier
                                                 -- as used in the
                                                 -- Spanning Tree
          -- Protocol to uniquely identify a bridge.  Its first two
          -- octets (in network byte order) contain a priority
          -- value and its last 6 octets contain the MAC address
          -- used to refer to a bridge in a unique fashion
          -- (typically, the numerically smallest MAC address
          -- of all ports on the bridge).
          -- Several objects in this MIB module represent values of
          -- timers used by the Spanning Tree Protocol.  In this
          -- MIB, these timers have values in units of hundreths of
          -- a second (i.e. 1/100 secs).
          -- These timers, when stored in a Spanning Tree Protocol's
          -- BPDU, are in units of 1/256 seconds.  Note, however,
          -- that 802.1D-1990 specifies a settable granularity of
          -- no more than 1 second for these timers.  To avoid
          -- ambiguity, a data type is defined here as a textual
          -- convention and all representation of these timers
          -- in this MIB module are defined using this data type.  An
          -- algorithm is also defined for converting between the
          -- different units, to ensure a timer's value is not
          -- distorted by multiple conversions.
          -- The data type is:

          Timeout ::= INTEGER -- a STP timer in units of 1/100 seconds

          -- To convert a Timeout value into a value in units of
          -- 1/256 seconds, the following algorithm should be used:
          --
          --      b  = floor( (n * 256) / 100)
          --
          -- where:
          --      floor   =  quotient [ignore remainder]
          --      n is the value in 1/100 second units
          --      b is the value in 1/256 second units
          --
          -- To convert the value from 1/256 second units back to
          -- 1/100 seconds, the following algorithm should be used:
          --
          --      n = ceiling( (b * 100) / 256)
          --
          -- where:
          --      ceiling =  quotient [if remainder is 0], or
          --                 quotient + 1 [if remainder is non-zero]
          --      n is the value in 1/100 second units
          --      b is the value in 1/256 second units
          --
          -- Note: it is important that the arithmetic operations are
          -- done in the order specified (i.e., multiply first, divide
          -- second).


             dot1dBridge   OBJECT IDENTIFIER ::= { mib-2 17 }

          -- groups in the Bridge MIB

          dot1dBase     OBJECT IDENTIFIER ::= { dot1dBridge 1 }

          dot1dStp      OBJECT IDENTIFIER ::= { dot1dBridge 2 }

          dot1dSr       OBJECT IDENTIFIER ::= { dot1dBridge 3 }
          -- separately documented

          dot1dTp       OBJECT IDENTIFIER ::= { dot1dBridge 4 }

          dot1dStatic   OBJECT IDENTIFIER ::= { dot1dBridge 5 }


          -- the dot1dBase group

          -- Implementation of the dot1dBase group is mandatory for all
          -- bridges.

          dot1dBaseBridgeAddress OBJECT-TYPE
              SYNTAX  MacAddress
              ACCESS  read-only
              STATUS  mandatory
              DESCRIPTION
                      "The MAC address used by this bridge when it must
                      be referred to in a unique fashion.   It is
                      recommended that this be the numerically smallest
                      MAC address of all ports that belong to this
                      bridge.  However it is only required to be unique.
                      When concatenated with dot1dStpPriority a unique
                      BridgeIdentifier is formed which is used in the
                      Spanning Tree Protocol."
              REFERENCE
                      "IEEE 802.1D-1990: Sections 6.4.1.1.3 and 3.12.5"
              ::= { dot1dBase 1 }

          dot1dBaseNumPorts OBJECT-TYPE
              SYNTAX  INTEGER
              ACCESS  read-only
              STATUS  mandatory
              DESCRIPTION
                      "The number of ports controlled by this bridging
                      entity."
              REFERENCE
                      "IEEE 802.1D-1990: Section 6.4.1.1.3"
              ::= { dot1dBase 2 }

          dot1dBaseType OBJECT-TYPE
              SYNTAX  INTEGER {
                          unknown(1),
                          transparent-only(2),
                          sourceroute-only(3),
                          srt(4)
                      }
              ACCESS  read-only
              STATUS  mandatory
              DESCRIPTION
                      "Indicates what type of bridging this bridge can
                      perform.  If a bridge is actually performing a
                      certain type of bridging this will be indicated by
                      entries in the port table for the given type."
              ::= { dot1dBase 3 }

          -- The Generic Bridge Port Table

          dot1dBasePortTable OBJECT-TYPE
              SYNTAX  SEQUENCE OF Dot1dBasePortEntry
              ACCESS  not-accessible
              STATUS  mandatory
              DESCRIPTION
                      "A table that contains generic information about
                      every port that is associated with this bridge.
                      Transparent, source-route, and srt ports are
                      included."
              ::= { dot1dBase 4 }

          dot1dBasePortEntry OBJECT-TYPE
              SYNTAX  Dot1dBasePortEntry
              ACCESS  not-accessible
              STATUS  mandatory
              DESCRIPTION
                      "A list of information for each port of the
                      bridge."
              REFERENCE
                      "IEEE 802.1D-1990: Section 6.4.2, 6.6.1"
              INDEX  { dot1dBasePort }
              ::= { dot1dBasePortTable 1 }


          Dot1dBasePortEntry ::=
              SEQUENCE {
                  dot1dBasePort
                      INTEGER,
                  dot1dBasePortIfIndex
                      INTEGER,
                  dot1dBasePortCircuit
                      OBJECT IDENTIFIER,
                  dot1dBasePortDelayExceededDiscards
                      Counter,
                  dot1dBasePortMtuExceededDiscards
                      Counter
              }

          dot1dBasePort OBJECT-TYPE
              SYNTAX  INTEGER (1..65535)
              ACCESS  read-only
              STATUS  mandatory
              DESCRIPTION
                      "The port number of the port for which this entry
                      contains bridge management information."
              ::= { dot1dBasePortEntry 1 }

          dot1dBasePortIfIndex OBJECT-TYPE
              SYNTAX  INTEGER
              ACCESS  read-only
              STATUS  mandatory
              DESCRIPTION
                      "The value of the instance of the ifIndex object,
                      defined in MIB-II, for the interface corresponding
                      to this port."
              ::= { dot1dBasePortEntry 2 }

          dot1dBasePortCircuit OBJECT-TYPE
              SYNTAX  OBJECT IDENTIFIER
              ACCESS  read-only
              STATUS  mandatory
              DESCRIPTION
                      "For a port which (potentially) has the same value
                      of dot1dBasePortIfIndex as another port on the
                      same bridge, this object contains the name of an
                      object instance unique to this port.  For example,
                      in the case where multiple ports correspond one-
                      to-one with multiple X.25 virtual circuits, this
                      value might identify an (e.g., the first) object
                      instance associated with the X.25 virtual circuit
                      corresponding to this port.

                      For a port which has a unique value of
                      dot1dBasePortIfIndex, this object can have the
                      value { 0 0 }."
              ::= { dot1dBasePortEntry 3 }

          dot1dBasePortDelayExceededDiscards OBJECT-TYPE
              SYNTAX  Counter
              ACCESS  read-only
              STATUS  mandatory
              DESCRIPTION
                      "The number of frames discarded by this port due
                      to excessive transit delay through the bridge.  It
                      is incremented by both transparent and source
                      route bridges."
              REFERENCE
                       "IEEE 802.1D-1990: Section 6.6.1.1.3"
              ::= { dot1dBasePortEntry 4 }

          dot1dBasePortMtuExceededDiscards OBJECT-TYPE
              SYNTAX  Counter
              ACCESS  read-only
              STATUS  mandatory
              DESCRIPTION
                      "The number of frames discarded by this port due
                      to an excessive size.  It is incremented by both
                      transparent and source route bridges."
              REFERENCE
                      "IEEE 802.1D-1990: Section 6.6.1.1.3"
              ::= { dot1dBasePortEntry 5 }


          -- the dot1dStp group

          -- Implementation of the dot1dStp group is optional.  It is
          -- implemented by those bridges that support the Spanning Tree
          -- Protocol.


          dot1dStpProtocolSpecification OBJECT-TYPE
              SYNTAX  INTEGER {
                          unknown(1),
                          decLb100(2),
                          ieee8021d(3)
                      }
              ACCESS  read-only
              STATUS  mandatory
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { dot1dStp 1 }

          dot1dStpPriority OBJECT-TYPE
              SYNTAX  INTEGER (0..65535)
              ACCESS  read-write
              STATUS  mandatory
              DESCRIPTION
                      "The value of the write-able portion of the Bridge
                      ID, i.e., the first two octets of the (8 octet
                      long) Bridge ID.  The other (last) 6 octets of the
                      Bridge ID are given by the value of
                      dot1dBaseBridgeAddress."
              REFERENCE
                      "IEEE 802.1D-1990: Section 4.5.3.7"
              ::= { dot1dStp 2 }

          dot1dStpTimeSinceTopologyChange OBJECT-TYPE
              SYNTAX  TimeTicks
              ACCESS  read-only
              STATUS  mandatory
              DESCRIPTION
                      "The time (in hundredths of a second) since the
                      last time a topology change was detected by the
                      bridge entity."
              REFERENCE
                      "IEEE 802.1D-1990: Section 6.8.1.1.3"
              ::= { dot1dStp 3 }

          dot1dStpTopChanges OBJECT-TYPE
              SYNTAX  Counter
              ACCESS  read-only
              STATUS  mandatory
              DESCRIPTION
                      "The total number of topology changes detected by
                      this bridge since the management entity was last
                      reset or initialized."
              REFERENCE
                      "IEEE 802.1D-1990: Section 6.8.1.1.3"
              ::= { dot1dStp 4 }

          dot1dStpDesignatedRoot OBJECT-TYPE
              SYNTAX  BridgeId
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { dot1dStp 5 }

          dot1dStpRootCost OBJECT-TYPE
              SYNTAX  INTEGER
              ACCESS  read-only
              STATUS  mandatory
              DESCRIPTION
                      "The cost of the path to the root as seen from
                      this bridge."
              REFERENCE
                      "IEEE 802.1D-1990: Section 4.5.3.2"
              ::= { dot1dStp 6 }

          dot1dStpRootPort OBJECT-TYPE
              SYNTAX  INTEGER
              ACCESS  read-only
              STATUS  mandatory
              DESCRIPTION
                      "The port number of the port which offers the
                      lowest cost path from this bridge to the root
                      bridge."
              REFERENCE
                      "IEEE 802.1D-1990: Section 4.5.3.3"
              ::= { dot1dStp 7 }

          dot1dStpMaxAge OBJECT-TYPE
              SYNTAX  Timeout
              ACCESS  read-only
              STATUS  mandatory
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { dot1dStp 8 }

          dot1dStpHelloTime OBJECT-TYPE
              SYNTAX  Timeout
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { dot1dStp 9 }

          dot1dStpHoldTime OBJECT-TYPE
              SYNTAX  INTEGER
              ACCESS  read-only
              STATUS  mandatory
              DESCRIPTION
                      "This time value determines the interval length
                      during which no more than two Configuration bridge
                      PDUs shall be transmitted by this node, in units
                      of hundredths of a second."
              REFERENCE
                      "IEEE 802.1D-1990: Section 4.5.3.14"
              ::= { dot1dStp 10 }

          dot1dStpForwardDelay OBJECT-TYPE
              SYNTAX  Timeout
              ACCESS  read-only
              STATUS  mandatory
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      dot1dStpBridgeForwardDelay which is the value that
                      this bridge and all others would start using
                      if/when this bridge were to become the root.]"
              REFERENCE
                      "IEEE 802.1D-1990: Section 4.5.3.6"
              ::= { dot1dStp 11 }

          dot1dStpBridgeMaxAge OBJECT-TYPE
              SYNTAX  Timeout (600..4000)
              ACCESS  read-write
              STATUS  mandatory
              DESCRIPTION
                      "The value that all bridges use for MaxAge when
                      this bridge is acting as the root.  Note that
                      802.1D-1990 specifies that the range for this
                      parameter is related to the value of
                      dot1dStpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { dot1dStp 12 }

          dot1dStpBridgeHelloTime OBJECT-TYPE
              SYNTAX  Timeout (100..1000)
              ACCESS  read-write
              STATUS  mandatory
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { dot1dStp 13 }

          dot1dStpBridgeForwardDelay OBJECT-TYPE
              SYNTAX  Timeout (400..3000)
              ACCESS  read-write
              STATUS  mandatory
              DESCRIPTION
                      "The value that all bridges use for ForwardDelay
                      when this bridge is acting as the root.  Note that
                      802.1D-1990 specifies that the range for this
                      parameter is related to the value of
                      dot1dStpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { dot1dStp 14 }

          -- The Spanning Tree Port Table

          dot1dStpPortTable OBJECT-TYPE
              SYNTAX  SEQUENCE OF Dot1dStpPortEntry
              ACCESS  not-accessible
              STATUS  mandatory
              DESCRIPTION
                      "A table that contains port-specific information
                      for the Spanning Tree Protocol."
              ::= { dot1dStp 15 }

          dot1dStpPortEntry OBJECT-TYPE
              SYNTAX  Dot1dStpPortEntry
              ACCESS  not-accessible
              STATUS  mandatory
              DESCRIPTION
                      "A list of information maintained by every port
                      about the Spanning Tree Protocol state for that
                      port."
              INDEX   { dot1dStpPort }
              ::= { dot1dStpPortTable 1 }

          Dot1dStpPortEntry ::=
              SEQUENCE {
                  dot1dStpPort
                      INTEGER,
                  dot1dStpPortPriority
                      INTEGER,
                  dot1dStpPortState
                      INTEGER,
                  dot1dStpPortEnable
                      INTEGER,
                  dot1dStpPortPathCost
                      INTEGER,
                  dot1dStpPortDesignatedRoot
                      BridgeId,
                  dot1dStpPortDesignatedCost
                      INTEGER,
                  dot1dStpPortDesignatedBridge
                      BridgeId,
                  dot1dStpPortDesignatedPort
                      OCTET STRING,
                  dot1dStpPortForwardTransitions
                      Counter
              }

          dot1dStpPort OBJECT-TYPE
              SYNTAX  INTEGER (1..65535)
              ACCESS  read-only
              STATUS  mandatory
              DESCRIPTION
                      "The port number of the port for which this entry
                      contains Spanning Tree Protocol management
                      information."
              REFERENCE
                      "IEEE 802.1D-1990: Section 6.8.2.1.2"
              ::= { dot1dStpPortEntry 1 }

          dot1dStpPortPriority OBJECT-TYPE
              SYNTAX  INTEGER (0..255)
              ACCESS  read-write
              STATUS  mandatory
              DESCRIPTION
                      "The value of the priority field which is
                      contained in the first (in network byte order)
                      octet of the (2 octet long) Port ID.  The other
                      octet of the Port ID is given by the value of
                      dot1dStpPort."
              REFERENCE
                      "IEEE 802.1D-1990: Section 4.5.5.1"
              ::= { dot1dStpPortEntry 2 }

          dot1dStpPortState OBJECT-TYPE
              SYNTAX  INTEGER {
                          disabled(1),
                          blocking(2),
                          listening(3),
                          learning(4),
                          forwarding(5),
                          broken(6)
                      }
              ACCESS  read-only
              STATUS  mandatory
              DESCRIPTION
                      "The port's current state as defined by
                      application of the Spanning Tree Protocol.  This
                      state controls what action a port takes on
                      reception of a frame.  If the bridge has detected
                      a port that is malfunctioning it will place that
                      port into the broken(6) state.  For ports which
                      are disabled (see dot1dStpPortEnable), this object
                      will have a value of disabled(1)."
              REFERENCE
                      "IEEE 802.1D-1990: Section 4.5.5.2"
              ::= { dot1dStpPortEntry 3 }

          dot1dStpPortEnable OBJECT-TYPE
              SYNTAX  INTEGER {
                          enabled(1),
                          disabled(2)
                      }
              ACCESS  read-write
              STATUS  mandatory
              DESCRIPTION
                      "The enabled/disabled status of the port."
              REFERENCE
                      "IEEE 802.1D-1990: Section 4.5.5.2"
              ::= { dot1dStpPortEntry 4 }

          dot1dStpPortPathCost OBJECT-TYPE
              SYNTAX  INTEGER (1..65535)
              ACCESS  read-write
              STATUS  mandatory
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { dot1dStpPortEntry 5 }

          dot1dStpPortDesignatedRoot OBJECT-TYPE
              SYNTAX  BridgeId
              ACCESS  read-only
              STATUS  mandatory
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { dot1dStpPortEntry 6 }

          dot1dStpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "IEEE 802.1D-1990: Section 4.5.5.5"
              ::= { dot1dStpPortEntry 7 }

          dot1dStpPortDesignatedBridge OBJECT-TYPE
              SYNTAX  BridgeId
              ACCESS  read-only
              STATUS  mandatory
              DESCRIPTION
                      "The Bridge Identifier of the bridge which this
                      port considers to be the Designated Bridge for
                      this port's segment."
              REFERENCE
                      "IEEE 802.1D-1990: Section 4.5.5.6"
              ::= { dot1dStpPortEntry 8 }

          dot1dStpPortDesignatedPort OBJECT-TYPE
              SYNTAX  OCTET STRING (SIZE (2))
              ACCESS  read-only
              STATUS  mandatory
              DESCRIPTION
                      "The Port Identifier of the port on the Designated
                      Bridge for this port's segment."
              REFERENCE
                      "IEEE 802.1D-1990: Section 4.5.5.7"
              ::= { dot1dStpPortEntry 9 }

          dot1dStpPortForwardTransitions OBJECT-TYPE
              SYNTAX  Counter
              ACCESS  read-only
              STATUS  mandatory
              DESCRIPTION
                      "The number of times this port has transitioned
                      from the Learning state to the Forwarding state."
              ::= { dot1dStpPortEntry 10 }


          -- the dot1dTp group

          -- Implementation of the dot1dTp group is optional.  It is
          -- implemented by those bridges that support the transparent
          -- bridging mode.  A transparent or SRT bridge will implement
          -- this group.


          dot1dTpLearnedEntryDiscards OBJECT-TYPE
              SYNTAX  Counter
              ACCESS  read-only
              STATUS  mandatory
              DESCRIPTION
                      "The total number of Forwarding Database entries,
                      which have been or would have been learnt, but
                      have been discarded due to a lack of space to
                      store them in the Forwarding Database.  If this
                      counter is increasing, it indicates that the
                      Forwarding Database is regularly becoming full (a
                      condition which has unpleasant performance effects
                      on the subnetwork).  If this counter has a
                      significant value but is not presently increasing,
                      it indicates that the problem has been occurring
                      but is not persistent."
              REFERENCE
                      "IEEE 802.1D-1990: Section 6.7.1.1.3"
              ::= { dot1dTp 1 }

          dot1dTpAgingTime OBJECT-TYPE
              SYNTAX   INTEGER (10..1000000)
              ACCESS   read-write
              STATUS   mandatory
              DESCRIPTION
                      "The timeout period in seconds for aging out
                      dynamically learned forwarding information.
                      802.1D-1990 recommends a default of 300 seconds."
              REFERENCE
                      "IEEE 802.1D-1990: Section 6.7.1.1.3"
              ::= { dot1dTp 2 }


          --  The Forwarding Database for Transparent Bridges

          dot1dTpFdbTable OBJECT-TYPE
              SYNTAX  SEQUENCE OF Dot1dTpFdbEntry
              ACCESS  not-accessible
              STATUS  mandatory
              DESCRIPTION
                      "A table that contains information about unicast
                      entries for which the bridge has forwarding and/or
                      filtering information.  This information is used
                      by the transparent bridging function in
                      determining how to propagate a received frame."
              ::= { dot1dTp 3 }

          dot1dTpFdbEntry OBJECT-TYPE
              SYNTAX  Dot1dTpFdbEntry
              ACCESS  not-accessible
              STATUS  mandatory
              DESCRIPTION
                      "Information about a specific unicast MAC address
                      for which the bridge has some forwarding and/or
                      filtering information."
              INDEX   { dot1dTpFdbAddress }
              ::= { dot1dTpFdbTable 1 }

          Dot1dTpFdbEntry ::=
              SEQUENCE {
                  dot1dTpFdbAddress
                      MacAddress,
                  dot1dTpFdbPort
                      INTEGER,
                  dot1dTpFdbStatus
                      INTEGER
              }

          dot1dTpFdbAddress OBJECT-TYPE
              SYNTAX  MacAddress
              ACCESS  read-only
              STATUS  mandatory
              DESCRIPTION
                      "A unicast MAC address for which the bridge has
                      forwarding and/or filtering information."
              REFERENCE
                      "IEEE 802.1D-1990: Section 3.9.1, 3.9.2"
              ::= { dot1dTpFdbEntry 1 }

          dot1dTpFdbPort OBJECT-TYPE
              SYNTAX  INTEGER
              ACCESS  read-only
              STATUS  mandatory
              DESCRIPTION
                      "Either the value '0', or the port number of the
                      port on which a frame having a source address
                      equal to the value of the corresponding instance
                      of dot1dTpFdbAddress has been seen.  A value of
                      '0' indicates that the port number has not been
                      learned but that the bridge does have some
                      forwarding/filtering information about this
                      address (e.g. in the dot1dStaticTable).
                      Implementors are encouraged to assign the port
                      value to this object whenever it is learned even
                      for addresses for which the corresponding value of
                      dot1dTpFdbStatus is not learned(3)."
              ::= { dot1dTpFdbEntry 2 }

          dot1dTpFdbStatus OBJECT-TYPE
              SYNTAX  INTEGER {
                          other(1),
                          invalid(2),
                          learned(3),
                          self(4),
                          mgmt(5)
                      }
              ACCESS  read-only
              STATUS  mandatory
              DESCRIPTION
                      "The status of this entry.  The meanings of the
                      values are:

                        other(1)   : none of the following.  This would
                                     include the case where some other
                                     MIB object (not the corresponding
                                     instance of dot1dTpFdbPort, nor an
                                     entry in the dot1dStaticTable) is
                                     being used to determine if and how
                                     frames addressed to the value of
                                     the corresponding instance of
                                     dot1dTpFdbAddress are being
                                     forwarded.

                        invalid(2) : this entry is not longer valid
                                     (e.g., it was learned but has since
                                     aged-out), but has not yet been
                                     flushed from the table.

                        learned(3) : the value of the corresponding
                                     instance of dot1dTpFdbPort was
                                     learned, and is being used.

                        self(4)    : the value of the corresponding
                                     instance of dot1dTpFdbAddress
                                     represents one of the bridge's
                                     addresses.  The corresponding
                                     instance of dot1dTpFdbPort
                                     indicates which of the bridge's
                                     ports has this address.

                        mgmt(5)    : the value of the corresponding
                                     instance of dot1dTpFdbAddress is
                                     also the value of an existing
                                     instance of dot1dStaticAddress."
              ::= { dot1dTpFdbEntry 3 }

          --  Port Table for Transparent Bridges

          dot1dTpPortTable OBJECT-TYPE
              SYNTAX  SEQUENCE OF Dot1dTpPortEntry
              ACCESS  not-accessible
              STATUS  mandatory
              DESCRIPTION
                      "A table that contains information about every
                      port that is associated with this transparent
                      bridge."
              ::= { dot1dTp 4 }

          dot1dTpPortEntry OBJECT-TYPE
              SYNTAX  Dot1dTpPortEntry
              ACCESS  not-accessible
              STATUS  mandatory
              DESCRIPTION
                      "A list of information for each port of a
                      transparent bridge."
              INDEX   { dot1dTpPort }
              ::= { dot1dTpPortTable 1 }

          Dot1dTpPortEntry ::=
              SEQUENCE {
                  dot1dTpPort
                      INTEGER,
                  dot1dTpPortMaxInfo
                      INTEGER,
                  dot1dTpPortInFrames
                      Counter,
                  dot1dTpPortOutFrames
                      Counter,
                  dot1dTpPortInDiscards
                      Counter
              }

          dot1dTpPort OBJECT-TYPE
              SYNTAX  INTEGER (1..65535)
              ACCESS  read-only
              STATUS  mandatory
              DESCRIPTION
                      "The port number of the port for which this entry
                      contains Transparent bridging management
                      information."
              ::= { dot1dTpPortEntry 1 }

          -- It would be nice if we could use ifMtu as the size of the
          -- largest INFO field, but we can't because ifMtu is defined
          -- to be the size that the (inter-)network layer can use which
          -- can differ from the MAC layer (especially if several layers
          -- of encapsulation are used).

          dot1dTpPortMaxInfo OBJECT-TYPE
              SYNTAX  INTEGER
              ACCESS  read-only
              STATUS  mandatory
              DESCRIPTION
                      "The maximum size of the INFO (non-MAC) field that
                      this port will receive or transmit."
              ::= { dot1dTpPortEntry 2 }

          dot1dTpPortInFrames OBJECT-TYPE
              SYNTAX  Counter
              ACCESS  read-only
              STATUS  mandatory
              DESCRIPTION
                      "The number of frames that have been received by
                      this port from its segment. Note that a frame
                      received on the interface corresponding to this
                      port is only counted by this object if and only if
                      it is for a protocol being processed by the local
                      bridging function, including bridge management
                      frames."
              REFERENCE
                      "IEEE 802.1D-1990: Section 6.6.1.1.3"
              ::= { dot1dTpPortEntry 3 }

          dot1dTpPortOutFrames OBJECT-TYPE
              SYNTAX  Counter
              ACCESS  read-only
              STATUS  mandatory
              DESCRIPTION
                      "The number of frames that have been transmitted
                      by this port to its segment.  Note that a frame
                      transmitted on the interface corresponding to this
                      port is only counted by this object if and only if
                      it is for a protocol being processed by the local
                      bridging function, including bridge management
                      frames."
              REFERENCE
                      "IEEE 802.1D-1990: Section 6.6.1.1.3"
              ::= { dot1dTpPortEntry 4 }

          dot1dTpPortInDiscards OBJECT-TYPE
              SYNTAX   Counter
              ACCESS   read-only
              STATUS   mandatory
              DESCRIPTION
                      "Count of valid frames received which were
                      discarded (i.e., filtered) by the Forwarding
                      Process."
              REFERENCE
                      "IEEE 802.1D-1990: Section 6.6.1.1.3"
              ::= { dot1dTpPortEntry 5 }


          -- The Static (Destination-Address Filtering) Database

          -- Implementation of this group is optional.


          dot1dStaticTable OBJECT-TYPE
              SYNTAX  SEQUENCE OF Dot1dStaticEntry
              ACCESS  not-accessible
              STATUS  mandatory
              DESCRIPTION
                      "A table containing filtering information
                      configured into the bridge by (local or network)
                      management specifying the set of ports to which
                      frames received from specific ports and containing
                      specific destination addresses are allowed to be
                      forwarded.  The value of zero in this table as the
                      port number from which frames with a specific
                      destination address are received, is used to
                      specify all ports for which there is no specific
                      entry in this table for that particular
                      destination address.  Entries are valid for
                      unicast and for group/broadcast addresses."
              REFERENCE
                      "IEEE 802.1D-1990: Section 6.7.2"
              ::= { dot1dStatic 1 }

          dot1dStaticEntry OBJECT-TYPE
              SYNTAX  Dot1dStaticEntry
              ACCESS  not-accessible
              STATUS  mandatory
              DESCRIPTION
                      "Filtering information configured into the bridge
                      by (local or network) management specifying the
                      set of ports to which frames received from a
                      specific port and containing a specific
                      destination address are allowed to be forwarded."
              REFERENCE
                      "IEEE 802.1D-1990: Section 6.7.2"
              INDEX   { dot1dStaticAddress, dot1dStaticReceivePort }
              ::= { dot1dStaticTable 1 }

          Dot1dStaticEntry ::=
              SEQUENCE {
                  dot1dStaticAddress
                      MacAddress,
                  dot1dStaticReceivePort
                      INTEGER,
                  dot1dStaticAllowedToGoTo
                      OCTET STRING,
                  dot1dStaticStatus
                      INTEGER
              }

          dot1dStaticAddress OBJECT-TYPE
              SYNTAX  MacAddress
              ACCESS  read-write
              STATUS  mandatory
              DESCRIPTION
                      "The destination MAC address in a frame to which
                      this entry's filtering information applies.  This
                      object can take the value of a unicast address, a
                      group address or the broadcast address."
              REFERENCE
                      "IEEE 802.1D-1990: Section 3.9.1, 3.9.2"
              ::= { dot1dStaticEntry 1 }

          dot1dStaticReceivePort OBJECT-TYPE
              SYNTAX  INTEGER
              ACCESS  read-write
              STATUS  mandatory
              DESCRIPTION
                      "Either the value '0', or the port number of the
                      port from which a frame must be received in order
                      for this entry's filtering information to apply.
                      A value of zero indicates that this entry applies
                      on all ports of the bridge for which there is no
                      other applicable entry."
              ::= { dot1dStaticEntry 2 }

          dot1dStaticAllowedToGoTo OBJECT-TYPE
              SYNTAX  OCTET STRING
              ACCESS  read-write
              STATUS  mandatory
              DESCRIPTION
                      "The set of ports to which frames received from a
                      specific port and destined for a specific MAC
                      address, are allowed to be forwarded.  Each octet
                      within the value of this object specifies a set of
                      eight ports, with the first octet specifying ports
                      1 through 8, the second octet specifying ports 9
                      through 16, etc.  Within each octet, the most
                      significant bit represents the lowest numbered
                      port, and the least significant bit represents the
                      highest numbered port.  Thus, each port of the
                      bridge is represented by a single bit within the
                      value of this object.  If that bit has a value of
                      '1' then that port is included in the set of
                      ports; the port is not included if its bit has a
                      value of '0'.  (Note that the setting of the bit
                      corresponding to the port from which a frame is
                      received is irrelevant.)  The default value of
                      this object is a string of ones of appropriate
                      length."
              ::= { dot1dStaticEntry 3 }

          dot1dStaticStatus OBJECT-TYPE
              SYNTAX  INTEGER {
                          other(1),
                          invalid(2),
                          permanent(3),
                          deleteOnReset(4),
                          deleteOnTimeout(5)
                      }
              ACCESS  read-write
              STATUS  mandatory
              DESCRIPTION
                      "This object indicates the status of this entry.
                      The default value is permanent(3).

                           other(1) - this entry is currently in use but
                                the conditions under which it will
                                remain so are different from each of the
                                following values.
                           invalid(2) - writing this value to the object
                                removes the corresponding entry.
                           permanent(3) - this entry is currently in use
                                and will remain so after the next reset
                                of the bridge.
                           deleteOnReset(4) - this entry is currently in
                                use and will remain so until the next
                                reset of the bridge.
                           deleteOnTimeout(5) - this entry is currently
                                in use and will remain so until it is
                                aged out."
              ::= { dot1dStaticEntry 4 }


          -- Traps for use by Bridges

          -- Traps for the Spanning Tree Protocol

          newRoot TRAP-TYPE
              ENTERPRISE  dot1dBridge
              DESCRIPTION
                      "The newRoot trap indicates that the sending agent
                      has become the new root of the Spanning Tree; the
                      trap is sent by a bridge soon after its election
                      as the new root, e.g., upon expiration of the
                      Topology Change Timer immediately subsequent to
                      its election.  Implementation of this trap is
                      optional."
              ::= 1

          topologyChange TRAP-TYPE
              ENTERPRISE  dot1dBridge
              DESCRIPTION
                      "A topologyChange trap is sent by a bridge when
                      any of its configured ports transitions from the
                      Learning state to the Forwarding state, or from
                      the Forwarding state to the Blocking state.  The
                      trap is not sent if a newRoot trap is sent for the
                      same transition.  Implementation of this trap is
                      optional."
              ::= 2


--
-- FILE: /users/sse/mibs/src/rfc/rfc1253.mib
--

-- Changes to rfc1253 (OSPF MIB):
--      Changed ospfAreaID in index clause for ospfAreaEntry to
--              ospfAreaId.
--      Changed ospfLSACount in definition for sequence OspfAreaEntry
--              to ospfAreaLSACount.
--      Suggestion: the DEFVAL clauses should be removed from
--              the objects that are counters. Some objects that
--              are gauges should probably not have DEFVAL clauses.


     -- RFC1253
     -- August 91


     --  This MIB module uses the extended OBJECT-TYPE macro as
     --  defined in [9].

             ospf OBJECT IDENTIFIER ::= { mib-2 14 }

     --  The Area ID, in OSPF, has the same format as an IP Address,
     --  but has the function of defining a summarization point for
     --  Link State Advertisements

             AreaID ::= IpAddress

     --  The Router ID, in OSPF, has the same format as an IP Address,
     --  but identifies the router independent of its IP Address.

             RouterID ::= IpAddress

     --  The OSPF Metric is defined as an unsigned value in the range

             Metric    ::= INTEGER (1..'FFFF'h)
             BigMetric ::= INTEGER (1..'FFFFFF'h)

     --  Boolean Values

             TruthValue ::= INTEGER { true (1), false (2) }

     --  Status Values

             Status ::= INTEGER { enabled (1), disabled (2) }

     --  Row Creation/Deletion Values

             Validation ::= INTEGER { valid (1), invalid (2) }

     --  Time Durations measured in seconds

             PositiveInteger ::= INTEGER (1..'FFFFFFFF'h)
             HelloRange      ::= INTEGER (1..'FFFF'h)
             UpToMaxAge      ::= INTEGER (1..3600)

     --  The range of ifIndex, i.e. (1..ifNumber)

             InterfaceIndex ::= INTEGER

     --  Potential Priorities for the Designated Router Election

             DesignatedRouterPriority ::= INTEGER (0..'FF'h)

     --  Type of Service is defined as a mapping to the IP Type of
     --  Service Flags as defined in the Router Requirements
     --  Document:
     --
     --      D => Low Delay          R => Reliable Route
     --      T => High Bandwidth

     --  D T R   TOS      D T R   TOS
     --  0 0 0 =>  0      0 0 1 =>  4
     --  0 1 0 =>  8      0 1 1 => 12
     --  1 0 0 => 16      1 0 1 => 20
     --  1 1 0 => 24      1 1 1 => 28

     --  The remaining values are left for future definition.

             TOSType ::= INTEGER (0..31)

     --  OSPF General Variables

     --      These parameters apply globally to the Router's
     --      OSPF Process.

     ospfGeneralGroup OBJECT IDENTIFIER ::= { ospf 1 }












     --      The OSPF Area Data Structure contains information
     --      regarding the various areas. The interfaces and
     --      virtual links are configured as part of these areas.
     --      Area 0.0.0.0, by definition, is the Backbone Area





                     -- none (0),
                     -- simplePassword (1)
                     -- reserved for specification by IANA (> 1)








     --  OSPF Area Default Metric Table

     --      The OSPF Area Default Metric Table describes the metrics
     --      that a default Area Border Router will advertise into a
     --      Stub area.









     --  OSPF Link State Database

     --      The Link State Database contains the Link State
     --      Advertisements from throughout the areas that the
     --      device is attached to.








     --  Note that the OSPF Sequence Number is a 32 bit signed
     --  integer.  It starts with the value '80000001'h,
     --  or -'7FFFFFFF'h, and increments until '7FFFFFFF'h
     --  Thus, a typical sequence number will be very negative.






     --  Address Range Table

     --      The Address Range Table acts as an adjunct to the Area
     --      Table; It describes those Address Range Summaries that
     --      are configured to be propagated from an Area to reduce
     --      the amount of information about it which is known beyond
     --      its borders.









     --  OSPF Host Table

     --      The Host/Metric Table indicates what hosts are directly
     --      attached to the Router, and what metrics and types of
     --      service should be advertised for them.








     --  OSPF Interface Table

     --      The OSPF Interface Table augments the ifTable with OSPF
     --      specific information.





















     --  OSPF Interface Metric Table

     --      The Metric Table describes the metrics to be advertised
     --      for a specified interface at the various types of service.
     --      As such, this table is an adjunct of the OSPF Interface
     --      Table.

     -- Types of service, as defined by RFC 791, have the ability
     -- to request low delay, high bandwidth, or reliable linkage.

     -- For the purposes of this specification, the measure of
     -- bandwidth

     --      Metric = 10^8 / ifSpeed

     -- is the default value.  For multiple link interfaces, note
     -- that ifSpeed is the sum of the individual link speeds.
     -- This yields a number having the following typical values:

     --      Network Type/bit rate   Metric

     --      >= 100 MBPS                 1
     --      Ethernet/802.3             10
     --      E1                         48
     --      T1 (ESF)                   65
     --       64 KBPS                 1562
     --       56 KBPS                 1785
     --       19.2 KBPS               5208
     --        9.6 KBPS              10416

     -- Routes that are not specified use the default (TOS 0) metric










     --  OSPF Virtual Interface Table

     --      The Virtual Interface Table describes the virtual
     --      links that the OSPF Process is configured to
     --      carry on.















     --  OSPF Neighbor Table

     --      The OSPF Neighbor Table describes all neighbors in
     --      the locality of the subject router.














     --  OSPF Virtual Neighbor Table

     --      This table describes all virtual neighbors.
     --      Since Virtual Links are configured in the
     --      virtual interface table, this table is read-only.












--
-- FILE: /users/sse/mibs/src/rfc/rfc1471.mib
--



               --  PPP MIB

               ppp  OBJECT IDENTIFIER ::= { transmission 23 }

               pppLcp OBJECT IDENTIFIER ::= { ppp 1 }


               -- The individual groups within the PPP-LCP-MIB

               pppLink      OBJECT IDENTIFIER ::= { pppLcp 1 }
               pppLqr       OBJECT IDENTIFIER ::= { pppLcp 2 }
               pppTests     OBJECT IDENTIFIER ::= { pppLcp 3 }

          -- 4.1.  PPP Link Group

          --
          -- The PPP Link Group. Implementation of this
          -- group is mandatory for all PPP entities.
          --

          -- The following object reflect the values of the option
          -- parameters used in the PPP Link Control Protocol
          --   pppLinkStatusLocalMRU
          --   pppLinkStatusRemoteMRU
          --   pppLinkStatusLocalToPeerACCMap
          --   pppLinkStatusPeerToLocalACCMap
          --   pppLinkStatusLocalToRemoteProtocolCompression
          --   pppLinkStatusRemoteToLocalProtocolCompression
          --   pppLinkStatusLocalToRemoteACCompression
          --   pppLinkStatusRemoteToLocalACCompression
          --   pppLinkStatusTransmitFcsSize
          --   pppLinkStatusReceiveFcsSize
          --
          -- These values are not available until after the PPP Option
          -- negotiation has completed, which is indicated by the link
          -- reaching the open state (i.e., ifOperStatus is set to
          -- up).
          --
          -- Therefore, when ifOperStatus is not up
          -- the contents of these objects is undefined. The value
          -- returned when accessing the objects is an implementation
          -- dependent issue.

          pppLinkStatusTable   OBJECT-TYPE
               SYNTAX    SEQUENCE OF PppLinkStatusEntry
               ACCESS    not-accessible
               STATUS    mandatory
               DESCRIPTION
                         "A table containing PPP-link specific variables
                         for this PPP implementation."
               ::= { pppLink 1 }


          pppLinkStatusEntry   OBJECT-TYPE
               SYNTAX    PppLinkStatusEntry
               ACCESS    not-accessible
               STATUS    mandatory
               DESCRIPTION
                         "Management information about a particular PPP
                         Link."
               INDEX     { ifIndex }
               ::= { pppLinkStatusTable 1 }

          PppLinkStatusEntry ::= SEQUENCE {
               pppLinkStatusPhysicalIndex
                    INTEGER,
               pppLinkStatusBadAddresses
                    Counter,
               pppLinkStatusBadControls
                    Counter,
               pppLinkStatusPacketTooLongs
                    Counter,
               pppLinkStatusBadFCSs
                    Counter,
               pppLinkStatusLocalMRU
                    INTEGER,
               pppLinkStatusRemoteMRU
                    INTEGER,
               pppLinkStatusLocalToPeerACCMap
                    OCTET STRING,
               pppLinkStatusPeerToLocalACCMap
                    OCTET STRING,
               pppLinkStatusLocalToRemoteProtocolCompression
                    INTEGER,
               pppLinkStatusRemoteToLocalProtocolCompression
                    INTEGER,
               pppLinkStatusLocalToRemoteACCompression
                    INTEGER,
               pppLinkStatusRemoteToLocalACCompression
                    INTEGER,
               pppLinkStatusTransmitFcsSize
                    INTEGER,
               pppLinkStatusReceiveFcsSize
                    INTEGER
               }
          pppLinkStatusPhysicalIndex   OBJECT-TYPE
               SYNTAX    INTEGER (0..2147483647)
               ACCESS    read-only
               STATUS    mandatory
               DESCRIPTION


                         "The value of ifIndex that identifies the
                         lower-level interface over which this PPP Link
                         is operating. This interface would usually be
                         an HDLC or RS-232 type of interface. If there
                         is no lower-layer interface element, or there
                         is no ifEntry for the element, or the element
                         can not be identified, then the value of this
                         object is 0.  For example, suppose that PPP is
                         operating over a serial port. This would use
                         two entries in the ifTable. The PPP could be
                         running over `interface' number 123 and the
                         serial port could be running over `interface'
                         number 987.  Therefore, ifSpecific.123 would
                         contain the OBJECT IDENTIFIER ppp
                         pppLinkStatusPhysicalIndex.123 would contain
                         987, and ifSpecific.987 would contain the
                         OBJECT IDENTIFIER for the serial-port's media-
                         specific MIB."
               ::= { pppLinkStatusEntry 1 }

          pppLinkStatusBadAddresses   OBJECT-TYPE
               SYNTAX    Counter
               ACCESS    read-only
               STATUS    mandatory
               DESCRIPTION
                         "The number of packets received with an
                         incorrect Address Field. This counter is a
                         component of the ifInErrors variable that is
                         associated with the interface that represents
                         this PPP Link."
               REFERENCE
                         "Section 3.1, Address Field, of RFC1331."
               ::= { pppLinkStatusEntry 2 }

          pppLinkStatusBadControls   OBJECT-TYPE
               SYNTAX    Counter
               ACCESS    read-only
               STATUS    mandatory
               DESCRIPTION
                         "The number of packets received on this link
                         with an incorrect Control Field. This counter
                         is a component of the ifInErrors variable that
                         is associated with the interface that
                         represents this PPP Link."
               REFERENCE
                         "Section 3.1, Control Field, of RFC1331."


               ::= { pppLinkStatusEntry 3 }

          pppLinkStatusPacketTooLongs   OBJECT-TYPE
               SYNTAX    Counter
               ACCESS    read-only
               STATUS    mandatory
               DESCRIPTION
                         "The number of received packets that have been
                         discarded because their length exceeded the
                         MRU. This counter is a component of the
                         ifInErrors variable that is associated with the
                         interface that represents this PPP Link. NOTE,
                         packets which are longer than the MRU but which
                         are successfully received and processed are NOT
                         included in this count."
               ::= { pppLinkStatusEntry 4 }

          pppLinkStatusBadFCSs   OBJECT-TYPE
               SYNTAX    Counter
               ACCESS    read-only
               STATUS    mandatory
               DESCRIPTION
                         "The number of received packets that have been
                         discarded due to having an incorrect FCS. This
                         counter is a component of the ifInErrors
                         variable that is associated with the interface
                         that represents this PPP Link."
               ::= { pppLinkStatusEntry 5 }

          pppLinkStatusLocalMRU   OBJECT-TYPE
               SYNTAX    INTEGER (1..2147483648)
               ACCESS    read-only
               STATUS    mandatory
               DESCRIPTION
                         "The current value of the MRU for the local PPP
                         Entity. This value is the MRU that the remote
                         entity is using when sending packets to the
                         local PPP entity. The value of this object is
                         meaningful only when the link has reached the
                         open state (ifOperStatus is up)."
               ::= { pppLinkStatusEntry 6 }

          pppLinkStatusRemoteMRU   OBJECT-TYPE
               SYNTAX    INTEGER (1..2147483648)


               ACCESS    read-only
               STATUS    mandatory
               DESCRIPTION
                         "The current value of the MRU for the remote
                         PPP Entity. This value is the MRU that the
                         local entity is using when sending packets to
                         the remote PPP entity. The value of this object
                         is meaningful only when the link has reached
                         the open state (ifOperStatus is up)."
               ::= { pppLinkStatusEntry 7 }

          pppLinkStatusLocalToPeerACCMap   OBJECT-TYPE
               SYNTAX    OCTET STRING (SIZE (4))
               ACCESS    read-only
               STATUS    mandatory
               DESCRIPTION
                         "The current value of the ACC Map used for
                         sending packets from the local PPP entity to
                         the remote PPP entity. The value of this object
                         is meaningful only when the link has reached
                         the open state (ifOperStatus is up)."
               ::= { pppLinkStatusEntry 8 }

          pppLinkStatusPeerToLocalACCMap   OBJECT-TYPE
               SYNTAX    OCTET STRING (SIZE (4))
               ACCESS    read-only
               STATUS    mandatory
               DESCRIPTION
                         "The ACC Map used by the remote PPP entity when
                         transmitting packets to the local PPP entity.
                         The value of this object is meaningful only
                         when the link has reached the open state
                         (ifOperStatus is up)."
               ::= { pppLinkStatusEntry 9 }

          pppLinkStatusLocalToRemoteProtocolCompression
               OBJECT-TYPE
               SYNTAX    INTEGER {
                         enabled(1),
                         disabled(2)
                    }
               ACCESS    read-only
               STATUS    mandatory
               DESCRIPTION
                         "Indicates whether the local PPP entity will


                         use Protocol Compression when transmitting
                         packets to the remote PPP entity. The value of
                         this object is meaningful only when the link
                         has reached the open state (ifOperStatus is
                         up)."
               ::= { pppLinkStatusEntry 10 }

          pppLinkStatusRemoteToLocalProtocolCompression
               OBJECT-TYPE
               SYNTAX    INTEGER {
                         enabled(1),
                         disabled(2)
                    }
               ACCESS    read-only
               STATUS    mandatory
               DESCRIPTION
                         "Indicates whether the remote PPP entity will
                         use Protocol Compression when transmitting
                         packets to the local PPP entity. The value of
                         this object is meaningful only when the link
                         has reached the open state (ifOperStatus is
                         up)."
               ::= { pppLinkStatusEntry 11 }

          pppLinkStatusLocalToRemoteACCompression   OBJECT-TYPE
               SYNTAX    INTEGER {
                         enabled(1),
                         disabled(2)
                    }
               ACCESS    read-only
               STATUS    mandatory
               DESCRIPTION
                         "Indicates whether the local PPP entity will
                         use Address and Control Compression when
                         transmitting packets to the remote PPP entity.
                         The value of this object is meaningful only
                         when the link has reached the open state
                         (ifOperStatus is up)."
               ::= { pppLinkStatusEntry 12 }

          pppLinkStatusRemoteToLocalACCompression   OBJECT-TYPE
               SYNTAX    INTEGER {
                         enabled(1),
                         disabled(2)
                    }


               ACCESS    read-only
               STATUS    mandatory
               DESCRIPTION
                         "Indicates whether the remote PPP entity will
                         use Address and Control Compression when
                         transmitting packets to the local PPP entity.
                         The value of this object is meaningful only
                         when the link has reached the open state
                         (ifOperStatus is up)."
               ::= { pppLinkStatusEntry 13 }

          pppLinkStatusTransmitFcsSize   OBJECT-TYPE
               SYNTAX    INTEGER (0..128)
               ACCESS    read-only
               STATUS    mandatory
               DESCRIPTION
                         "The size of the Frame Check Sequence (FCS) in
                         bits that the local node will generate when
                         sending packets to the remote node. The value
                         of this object is meaningful only when the link
                         has reached the open state (ifOperStatus is
                         up)."
               ::= { pppLinkStatusEntry 14 }

          pppLinkStatusReceiveFcsSize   OBJECT-TYPE
               SYNTAX    INTEGER (0..128)
               ACCESS    read-only
               STATUS    mandatory
               DESCRIPTION
                         "The size of the Frame Check Sequence (FCS) in
                         bits that the remote node will generate when
                         sending packets to the local node. The value of
                         this object is meaningful only when the link
                         has reached the open state (ifOperStatus is
                         up)."
               ::= { pppLinkStatusEntry 15 }

          pppLinkConfigTable   OBJECT-TYPE
               SYNTAX    SEQUENCE OF PppLinkConfigEntry
               ACCESS    not-accessible
               STATUS    mandatory
               DESCRIPTION
                         "A table containing the LCP configuration
                         parameters for this PPP Link. These variables
                         represent the initial configuration of the PPP


                         Link. The actual values of the parameters may
                         be changed when the link is brought up via the
                         LCP options negotiation mechanism."
               ::= { pppLink 2 }

          pppLinkConfigEntry   OBJECT-TYPE
               SYNTAX    PppLinkConfigEntry
               ACCESS    not-accessible
               STATUS    mandatory
               DESCRIPTION
                         "Configuration information about a particular
                         PPP Link."
               INDEX     { ifIndex }
               ::= { pppLinkConfigTable 1 }

          PppLinkConfigEntry ::= SEQUENCE {
               pppLinkConfigInitialMRU
                    INTEGER,
               pppLinkConfigReceiveACCMap
                    OCTET STRING,
               pppLinkConfigTransmitACCMap
                    OCTET STRING,
               pppLinkConfigMagicNumber
                    INTEGER,
               pppLinkConfigFcsSize
                    INTEGER
               }

          pppLinkConfigInitialMRU   OBJECT-TYPE
               SYNTAX    INTEGER (0..2147483647)
               ACCESS       read-only
--               ACCESS    read-write
               STATUS    mandatory
               DESCRIPTION
                         "The initial Maximum Receive Unit (MRU) that
                         the local PPP entity will advertise to the
                         remote entity. If the value of this variable is
                         0 then the local PPP entity will not advertise
                         any MRU to the remote entity and the default
                         MRU will be assumed. Changing this object will
                         have effect when the link is next restarted.

                         Agent variations:
                         	DESCRIPTION
                         		writing not supported"
               REFERENCE
                         "Section 7.2, Maximum Receive Unit of RFC1331."
               DEFVAL    { 1500 }
               ::= { pppLinkConfigEntry 1 }


          pppLinkConfigReceiveACCMap   OBJECT-TYPE
               SYNTAX    OCTET STRING (SIZE (4))
               ACCESS    read-write
               STATUS    mandatory
               DESCRIPTION
                         "The Asynchronous-Control-Character-Map (ACC)
                         that the local PPP entity requires for use on
                         its receive side. In effect, this is the ACC
                         Map that is required in order to ensure that
                         the local modem will successfully receive all
                         characters. The actual ACC map used on the
                         receive side of the link will be a combination
                         of the local node's pppLinkConfigReceiveACCMap
                         and the remote node's
                         pppLinkConfigTransmitACCMap. Changing this
                         object will have effect when the link is next
                         restarted."
               REFERENCE
                         "Section 7.3, page 4, Async-Control-Character-
                         Map of RFC1331."
               DEFVAL    { 'ffffffff'h }
               ::= { pppLinkConfigEntry 2 }

          pppLinkConfigTransmitACCMap   OBJECT-TYPE
               SYNTAX    OCTET STRING (SIZE (4))
               ACCESS       read-only
--               ACCESS    read-write
               STATUS    mandatory
               DESCRIPTION
                         "The Asynchronous-Control-Character-Map (ACC)
                         that the local PPP entity requires for use on
                         its transmit side. In effect, this is the ACC
                         Map that is required in order to ensure that
                         all characters can be successfully transmitted
                         through the local modem.  The actual ACC map
                         used on the transmit side of the link will be a
                         combination of the local node's
                         pppLinkConfigTransmitACCMap and the remote
                         node's pppLinkConfigReceiveACCMap. Changing
                         this object will have effect when the link is
                         next restarted.

                         Agent variations:
                         	DESCRIPTION
                         		writing not supported"
               REFERENCE
                         "Section 7.3, page 4, Async-Control-Character-
                         Map of RFC1331."
               DEFVAL    { 'ffffffff'h }
               ::= { pppLinkConfigEntry 3 }


          pppLinkConfigMagicNumber   OBJECT-TYPE
               SYNTAX    INTEGER {false (1), true (2)}
               ACCESS       read-only
--               ACCESS    read-write
               STATUS    mandatory
               DESCRIPTION
                         "If true(2) then the local node will attempt to
                         perform Magic Number negotiation with the
                         remote node. If false(1) then this negotiation
                         is not performed. In any event, the local node
                         will comply with any magic number negotiations
                         attempted by the remote node, per the PPP
                         specification. Changing this object will have
                         effect when the link is next restarted.

                         Agent variations:
                         	DESCRIPTION
                         		writing not supported"
               REFERENCE
                         "Section 7.6, Magic Number, of RFC1331."
               DEFVAL    { false }
               ::= { pppLinkConfigEntry 4 }

          pppLinkConfigFcsSize   OBJECT-TYPE
               SYNTAX    INTEGER (0..128)
               ACCESS       read-only
--               ACCESS    read-write
               STATUS    mandatory
               DESCRIPTION
                         "The size of the FCS, in bits, the local node
                         will attempt to negotiate for use with the
                         remote node. Regardless of the value of this
                         object, the local node will comply with any FCS
                         size negotiations initiated by the remote node,
                         per the PPP specification. Changing this object
                         will have effect when the link is next
                         restarted.

                         Agent variations:
                         	DESCRIPTION
                         		writing not supported"
               DEFVAL    { 16 }
               ::= { pppLinkConfigEntry 5 }

          -- 4.2.  PPP LQR Group

               --
               -- The PPP LQR Group.
               -- Implementation of this group is mandatory for all
               -- PPP implementations that implement LQR.
               --











          --
          -- The PPP LQR Configuration table.
          --







          -- 4.3.  PPP LQR Extensions Group

          --
          -- The PPP LQR Extensions Group.
          -- Implementation of this group is optional.
          --
          -- The intent of this group is to allow external
          -- implementation of the policy mechanisms that
          -- are used to declare a link to be "bad" or not.
          --
          -- It is not practical to examine the MIB objects
          -- which are used to generate LQR packets since
          -- LQR policies tend to require synchronization of
          -- the values of all data used to determine Link
          -- Quality; i.e. the values of the relevant counters
          -- must all be taken at the same instant in time.
          --





          -- 4.4.  PPP Tests

          -- The extensions to the interface table in RFC1229 define a
          -- table through which the network manager can instruct the
          -- managed object to perform various tests of the interface. This
          -- is the ifExtnsTestTable.

          -- The PPP MIB defines two such tests.

          -- 4.4.1.  PPP Echo Test

          -- The PPP Echo Test is defined as

               pppEchoTest    OBJECT IDENTIFIER ::= { pppTests 1 }

          -- Invoking this test causes a PPP Echo Packet to be sent on the
          -- line. ifExtnsTestResult returns success(2) if the echo
          -- response came back properly. It returns failed(7) if the
          -- response did not properly return. The definition of "proper"


          -- in this context is left to the discretion of the implementor.

          -- 4.4.2.  PPP Discard Test

          -- The PPP Discard Test is defined as

               pppDiscardTest OBJECT IDENTIFIER ::= { pppTests 2 }

          -- Invoking this test causes a PPP Discard Packet to be sent on
          -- the line. ifExtnsTestResult returns success(2) if the discard
          -- packet was successfully transmitted and failed(7) if an error
          -- was detected on transmission. The definition of "transmission
          -- error" in this context is left to the discretion of the
          -- implementor.


--
-- FILE: /users/sse/mibs/src/rfc/rfc1473.mib
--



               -- The PPP IP Group.
               -- Implementation of this group is mandatory for all
               -- PPP implementations that support operating IP over PPP.

               pppIp OBJECT IDENTIFIER ::= { ppp 3 }

          pppIpTable   OBJECT-TYPE
               SYNTAX    SEQUENCE OF PppIpEntry
               ACCESS    not-accessible
               STATUS    mandatory
               DESCRIPTION
                         "Table containing the IP parameters and
                         statistics for the local PPP entity."
               ::= { pppIp 1 }

          pppIpEntry   OBJECT-TYPE


               SYNTAX    PppIpEntry
               ACCESS    not-accessible
               STATUS    mandatory
               DESCRIPTION
                         "IPCP status information for a particular PPP
                         link."
               INDEX     { ifIndex }
               ::= { pppIpTable 1 }

          PppIpEntry ::= SEQUENCE {
               pppIpOperStatus
                    INTEGER,
               pppIpLocalToRemoteCompressionProtocol
                    INTEGER,
               pppIpRemoteToLocalCompressionProtocol
                    INTEGER,
               pppIpRemoteMaxSlotId
                    INTEGER,
               pppIpLocalMaxSlotId
                    INTEGER
          }

          -- The following object reflect the values of the option
          -- parameters used in the PPP IP Control Protocol
          --   pppIpLocalToRemoteCompressionProtocol
          --   pppIpRemoteToLocalCompressionProtocol
          --   pppIpRemoteMaxSlotId
          --   pppIpLocalMaxSlotId
          -- These values are not available until after the PPP Option
          -- negotiation has completed, which is indicated by the link
          -- reaching the open state (i.e., pppIpOperStatus is set to
          -- opened).
          --
          -- Therefore, when pppIpOperStatus is not opened
          -- the contents of these objects is undefined. The value
          -- returned when accessing the objects is an implementation
          -- dependent issue.

          pppIpOperStatus   OBJECT-TYPE
               SYNTAX    INTEGER {opened(1), not-opened(2)}
               ACCESS    read-only
               STATUS    mandatory
               DESCRIPTION
                         "The operational status of the IP network
                         protocol. If the value of this object is up
                         then the finite state machine for the IP


                         network protocol has reached the Opened state."
               ::= { pppIpEntry 1 }

          pppIpLocalToRemoteCompressionProtocol   OBJECT-TYPE
               SYNTAX    INTEGER {
                         none(1),
                         vj-tcp(2)
                    }
               ACCESS    read-only
               STATUS    mandatory
               DESCRIPTION
                         "The IP compression protocol that the local
                         PPP-IP entity uses when sending packets to the
                         remote PPP-IP entity. The value of this object
                         is meaningful only when the link has reached
                         the open state (pppIpOperStatus is opened)."
               ::= { pppIpEntry 2 }

          pppIpRemoteToLocalCompressionProtocol   OBJECT-TYPE
               SYNTAX    INTEGER {
                         none(1),
                         vj-tcp(2)
                    }
               ACCESS    read-only
               STATUS    mandatory
               DESCRIPTION
                         "The IP compression protocol that the remote
                         PPP-IP entity uses when sending packets to the
                         local PPP-IP entity. The value of this object
                         is meaningful only when the link has reached
                         the open state (pppIpOperStatus is opened)."
               ::= { pppIpEntry 3 }

          pppIpRemoteMaxSlotId   OBJECT-TYPE
               SYNTAX    INTEGER(0..255)
               ACCESS    read-only
               STATUS    mandatory
               DESCRIPTION
                         "The Max-Slot-Id parameter that the remote node
                         has advertised and that is in use on the link.
                         If vj-tcp header compression is not in use on
                         the link then the value of this object shall be
                         0. The value of this object is meaningful only
                         when the link has reached the open state
                         (pppIpOperStatus is opened)."


               ::= { pppIpEntry 4 }

          pppIpLocalMaxSlotId   OBJECT-TYPE
               SYNTAX    INTEGER(0..255)
               ACCESS    read-only
               STATUS    mandatory
               DESCRIPTION
                         "The Max-Slot-Id parameter that the local node
                         has advertised and that is in use on the link.
                         If vj-tcp header compression is not in use on
                         the link then the value of this object shall be
                         0. The value of this object is meaningful only
                         when the link has reached the open state
                         (pppIpOperStatus is opened)."
               ::= { pppIpEntry 5 }

          --
          -- The PPP IP Configuration table.
          -- This is a separate table in order to facilitate
          -- placing these variables in a separate MIB view.
          --

          pppIpConfigTable   OBJECT-TYPE
               SYNTAX    SEQUENCE OF PppIpConfigEntry
               ACCESS    not-accessible
               STATUS    mandatory
               DESCRIPTION
                         "Table containing configuration variables for
                         the IPCP for the local PPP entity."
               ::= { pppIp 2 }

          pppIpConfigEntry   OBJECT-TYPE
               SYNTAX    PppIpConfigEntry
               ACCESS    not-accessible
               STATUS    mandatory
               DESCRIPTION
                         "IPCP information for a particular PPP link."
               INDEX     { ifIndex }
               ::= { pppIpConfigTable 1 }

          PppIpConfigEntry ::= SEQUENCE {
               pppIpConfigAdminStatus
                    INTEGER,
               pppIpConfigCompression


                    INTEGER
          }

          pppIpConfigAdminStatus   OBJECT-TYPE
               SYNTAX    INTEGER {open(1), close(2)}
               ACCESS       read-only
--               ACCESS    read-write
               STATUS    mandatory
               DESCRIPTION
                         "The immediate desired status of the IP network
                         protocol. Setting this object to open will
                         inject an administrative open event into the IP
                         network protocol's finite state machine.
                         Setting this object to close will inject an
                         administrative close event into the IP network
                         protocol's finite state machine.

                         Agent variations:
                         	DESCRIPTION
                         		writing not supported"
               ::= { pppIpConfigEntry 1 }

          pppIpConfigCompression   OBJECT-TYPE
               SYNTAX    INTEGER {
                         none(1),
                         vj-tcp(2)
                    }
               ACCESS    read-write
               STATUS    mandatory
               DESCRIPTION
                         "If none(1) then the local node will not
                         attempt to negotiate any IP Compression option.
                         Otherwise, the local node will attempt to
                         negotiate compression mode indicated by the
                         enumerated value. Changing this object will
                         have effect when the link is next restarted."
               REFERENCE
                         "Section 4.0, Van Jacobson TCP/IP Header
                         Compression of RFC1332."
               DEFVAL    { none }
               ::= { pppIpConfigEntry 2 }


--
-- FILE: /users/sse/mibs/src/inReach/ir-mib.mib
--

-- $Id: ir-mib.mib,v 1.1 2002/06/27 15:38:10 sse Exp $




            mrvInReachProductDivision     OBJECT IDENTIFIER ::= { enterprises 33 }
            agent           OBJECT IDENTIFIER ::= { mrvInReachProductDivision 8 }

            -- This is a MIB module for all MRV Communications In-Reach 
            -- Products Division systems.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- Textual Conventions

            -- This data type is used throughout the mrvInReachProductDivision private MIB
            -- to model an absolute date and time.
            -- In order, the octets contain the following information:
            -- century, year within century (0..99), month (1..12),
            -- day (1..31), hour (0..23), minute (0..59),
            -- second (0..59), hundredth (0..99).  If the century
            -- value is zero, the date and time are unknown, and the
            -- other values are meaningless.

            DateTime ::=
                OCTET STRING (SIZE (8))

            -- This data type is used throughout the mrvInReachProductDivision private MIB
            -- to indicate the type of an address stored in a related
            -- octet string.

            AddressType ::=
                INTEGER  { 
                           unknown(1), 
                           other(2), 
                           local(3),
                           ip(4), 
                           ethernet(5) 
                         }

            -- This data type is used throughout the mrvInReachProductDivision private MIB
            -- to indicate an address with a type attached.  The type is
            -- the first byte.  The address immediately follows the
            -- type, occupying the appropriate number of bytes, (0..31).
            -- The type values are:
            --     1   unknown
            --     2   other
            --     3   local
            --     4   ip
            --     5   ethernet

            TypedAddress ::=
                OCTET STRING (SIZE (1..32))

            -- This data type is used throughout the mrvInReachProductDivision private MIB
            -- to indicate the type of software running on a system. 

            SoftwareType ::=
                INTEGER  { 
                           terminalServer(1), 
                           bridge(3), 
                           repeater(4),
                           bridgeRouter(5), 
                           router(6),
                           bridgeRouterRepeater(7), 
                           switch(8), 
                           oem(9) 
                         }

            -- This data type is used throughout the mrvInReachProductDivision private MIB
            -- to indicate the type of a system's main function 
            -- hardware.  


            HardwareType ::=
                INTEGER  { 
                           unknown(1),
                           em1608(29), 
                           ir7520(30), 
                           ir9020(31), 
                           ir7020(32),
                           mxTServJ8(33), 
                           mxTservJ16(34), 
                           mxManF2(35),
                           mx1500(36), 
                           mx1100(37), 
                           mx1800(38),
                           mxNpcP1(39), 
                           mxTsrLJ16(40), 
                           mxTsrvLJ8(41), 
                           mxTsrvMj8(42), 
                           mxTsrvNJ8(43), 
                           mxTsrvOJ8(44),
                           mx1400(45), 
                           mx6510(46),
                           mxRb2(47),  
                           mx1500x8(49), 
                           mx1710(50), 
                           mx2710(51),
                           ts3395(52), 
                           mx1120(53), 
                           mx1520(54),
                           mx1820(55), 
                           mx2220(56), 
                           mx3510(57),
                           mx6625(58), 
                           mx2120(59), 
                           mx6020(60),
                           mx3610(61), 
                           etsmim(62), 
                           mx3010(63),
                           mx6025(64), 
                           lannetTs(65), 
                           fn1500(66),
                           dpXp1(67), 
                           mx3710(68), 
                           mx3210(69),
                           mx6710(70), 
                           mx6220(71),
                           mx1600a(74), 
                           mx1450(75),
                           ts720(76), 
                           so3395aTs(77), 
                           mx1608(78),
                           mx2210a(79), 
                           br401(80), 
                           mx6800a(81),
                           notApplicable(83), 
                           rp210(84),
                           mx6800b(85), 
                           mx1620(86), 
                           mx2240(87),
                           ps3m(88), 
                           lb2Wan(89), 
                           nio1600(90),
                           asy160(91), 
                           mx1640(92), 
                           br220(93),
                           rp211(94), 
                           br221(95), 
                           mx2210b(96),
                           mx1600b(97), 
                           mx1600c(98), 
                           mx800a(99),
                           mx1600d(100), 
                           tokenRing(101), 
                           mx800b(102),
                           br501(103), 
                           br350(105), 
                           br350ExpansionSlot(107),
                           n3000(108), 
                           br402(109), 
                           sw610(110), 
                           sw610S(111), 
                           br501s(112),
                           br501c(113), 
                           br501sc(114),
                           routeRunnerIsdnSt(115), 
                           routeRunner(116),
                           mx1608a(117),  
                           routerRunnerIsdnU(118),
                           mx1608b(119),  
                           mx1604(120),  
                           n3000Ias(123),
                           irMgr0Rdc(124), 
                           ir9040(125),
                           ir7040(126),
                           irMgr0(127),
                           irM800(128),
                           irM700(129),
                           ir8020(130),
                           ir8040(131),
                           ir7004(132),
                           ir7008(133),
                           ir8004(134),
                           ir8008(135),
                           irM900(136),
                           irMGR0AC(137),                       
                           irMGR0AC-IN(138),                       
                           ir9004(139),                       
                           ir9008(140),                       
                           ir9504(141),                       
                           n3000SP(230) 
                         }

            -- This data type is used throughout the mrvInReachProductDivision private MIB
            -- to indicate the type of chassis hardware.

            ChassisType ::= 
                 INTEGER { other(1), mx45xx(2), net9000(3), net9000SWITCH(4) }

            -- This data type is used throughout the mrvInReachProductDivision private MIB
            -- to indicate the type of I/O hardware.

            IOType ::=
                 INTEGER { 
                           io616(16),
                           dualE175(32), 
                           dualT1(33), 
                           bri8(34), 
                           io351d(35),
                           io352d(36),
                           dualE1120(37), 
                           singleT1(38), 
                           singleE175(39),
                           singleE1120(40),
                           io625(128),
                           io626(129),
                           io601(144), 
                           io602(145), 
                           io603(146),
                           io601A(147), 
                           io602A(148), 
                           io603A(149),
                           io604(150), 
                           io621(155),  
                           io622(156),
                           io623(157),
                           io624(158), 
                           io301x12(160), 
                           io521(174),
                           io522(175), 
                           io512x3(176), 
                           io511x3(177),
                           io520(178),
                           io514(179), 
                           io513(180), 
                           io470x4(182), 
                           io469x2(183),
                           io467x4(184), 
                           io467x2(185), 
                           io468x4(186),
                           io468x2(187), 
                           io466x4(188), 
                           io465x2(189),
                           io464x4(190), 
                           io463x2(191), 
                           io201(192), 
                           io202(193), 
                           io204(194), 
                           io203(195), 
                           io251(196), 
                           io231(197), 
                           io254(198),
                           io206(199), 
                           io253(200), 
                           io256(201), 
                           io201a(202), 
                           io202a(203), 
                           io203a(204), 
                           ioRepeater(207),
                           io205x12(209),
                           io205(210), 
                           io255(214), 
                           io722(224),
                           io721(225), 
                           io411(226), 
                           io724(227),
                           io725(231),
                           io723(232), 
                           io462(233), 
                           io412(234),
                           ioTS16a(235),  
                           ioTS16b(236),  
                           io461(237), 
                           io101(238), 
                           io119(239) 
                         }


            -- Agent Object Identifiers

            -- A mrvInReachProductDivision agent identifer has the following fields:
            --
            --     mrvInReachProductDivision.agent.software.variant.version
            --
            -- Where:
            --
            --     mrvInReachProductDivision.agent  is an ordinary OID prefix. Note that
            --                         mrvInReachProductDivision's original form for
            --                         such OID's used the value 1 for agent
            --                         and had no variant or version.  Later
            --                         forms included variant and version in
            --                         an inconsistent manner.
            --
            --     software       a value of the mrvInReachProductDivision SoftwareType
            --                    textual convention.
            --
            --     variant        a variant within a software type,
            --                    typically hardware dependent.  If the
            --                    software has no variants, it uses the
            --                    value 1.
            --
            --     version        a version number within the variant,
            --                    increased by one each time that
            --                    variant's agent changes in a way that
            --                    is significant to its MIB
            --                    capabilities description

            -- Terminal Servers

            terminalServer   OBJECT IDENTIFIER ::= { agent 1 }

            --     MAXserver variants, 1M memory
            tsMxCard1M       OBJECT IDENTIFIER ::= { terminalServer 1 }
            tsMxBox1M        OBJECT IDENTIFIER ::= { terminalServer 2 }

            --     MAXserver variants, 1M memory
            tsMxCard         OBJECT IDENTIFIER ::= { terminalServer 3 }
            tsMxBox          OBJECT IDENTIFIER ::= { terminalServer 4 }

            --     Network 9000 variant
            tsN9             OBJECT IDENTIFIER ::= { terminalServer 5 }

            --     Printer controller variant
            tsPrint          OBJECT IDENTIFIER ::= { terminalServer 6 }

            --     X.25 Gateway variant
            tsX25            OBJECT IDENTIFIER ::= { terminalServer 7 }

            --  InReach-Product-Division and Environmental Manager variants. These models
            --  use their hardwareType as the agent variant.
            em1608           OBJECT IDENTIFIER ::= { terminalServer 29 }
            ir7520           OBJECT IDENTIFIER ::= { terminalServer 30 }
            ir9020           OBJECT IDENTIFIER ::= { terminalServer 31 }
            ir7020           OBJECT IDENTIFIER ::= { terminalServer 32 }
            irMgr0Rdc        OBJECT IDENTIFIER ::= { terminalServer 124 }
            ir9040           OBJECT IDENTIFIER ::= { terminalServer 125 }
            ir7040           OBJECT IDENTIFIER ::= { terminalServer 126 }
            irMgr0           OBJECT IDENTIFIER ::= { terminalServer 127 }
            irM800           OBJECT IDENTIFIER ::= { terminalServer 128 }
            irM700           OBJECT IDENTIFIER ::= { terminalServer 129 }
            ir8020           OBJECT IDENTIFIER ::= { terminalServer 130 }
            ir8040           OBJECT IDENTIFIER ::= { terminalServer 131 }
            ir7004           OBJECT IDENTIFIER ::= { terminalServer 132 }
            ir7008           OBJECT IDENTIFIER ::= { terminalServer 133 }
            ir8004           OBJECT IDENTIFIER ::= { terminalServer 134 }
            ir8008           OBJECT IDENTIFIER ::= { terminalServer 135 }
            irM900           OBJECT IDENTIFIER ::= { terminalServer 136 }
            irMGR0AC         OBJECT IDENTIFIER ::= { terminalServer 137 }
            irMGR0AC-IN      OBJECT IDENTIFIER ::= { terminalServer 138 }
            ir9004           OBJECT IDENTIFIER ::= { terminalServer 139 }
            ir9008           OBJECT IDENTIFIER ::= { terminalServer 140 }
            ir9504           OBJECT IDENTIFIER ::= { terminalServer 141 }

            -- Bridges

            bridge                 OBJECT IDENTIFIER ::= { agent 3 }

            -- Repeaters

            repeater               OBJECT IDENTIFIER ::= { agent 4 }

            --     MAXserver variant
            rpMx                   OBJECT IDENTIFIER ::= { repeater 1 }

            --     Network 9000 variant
            rpN9                   OBJECT IDENTIFIER ::= { repeater 2 }

            -- Bridge/Routers

            bridgeRouter           OBJECT IDENTIFIER ::= { agent 5 }

            --     MAXserver variant
            bridgeRouterMx         OBJECT IDENTIFIER ::= { bridgeRouter 1 }

            --     Network 9000 variant
            bridgeRouterN9         OBJECT IDENTIFIER ::= { bridgeRouter 2 }

            -- Network 3000 variant
            bridgeRouterN3         OBJECT IDENTIFIER ::=  { bridgeRouter 3 }

            -- Network 3000 RouteRunner variant
            bridgeRouterN2         OBJECT IDENTIFIER ::=  { bridgeRouter 4 }

            -- EdgeBlaster variant
            bridgeRouterEB         OBJECT IDENTIFIER ::=  { bridgeRouter 5 }

            -- Bridge/Router/Repeaters

            bridgeRouterRepeater   OBJECT IDENTIFIER ::= { agent 7 }

            -- Switches

            switch                 OBJECT IDENTIFIER ::= { agent 8 }

            -- OEM Devices

            oem                    OBJECT IDENTIFIER ::= { agent 9 }

            --     NetVantage variant
            netVantage             OBJECT IDENTIFIER ::= { oem 1 }
            --     NetVantage product variants
            nv8516TT               OBJECT IDENTIFIER ::= { netVantage 1 }
            nv8516FF               OBJECT IDENTIFIER ::= { netVantage 2 }

            -- NBase Devices

            nbase                    OBJECT IDENTIFIER ::= { agent 10 }
            nbaseSwitch              OBJECT IDENTIFIER ::= { nbase 1 }
            nbaseSwitchN9            OBJECT IDENTIFIER ::= { nbaseSwitch 1 }









--
-- FILE: /users/sse/mibs/src/rfc/rfc1243.mib
--

-- Changes to rfc1243 (AppleTalk MIB):
--      Changed llapInBads in definition of sequence LlapEntry
--              to llapInErros.



          -- RFC1243
          -- July '91


          --  This MIB module uses the extended OBJECT-TYPE macro as
          --  defined in [9]


          --  AppleTalk MIB

                  appletalk    OBJECT IDENTIFIER ::= { mib-2 13 }


                  DdpAddress ::=  -- 2 octets of net number
                                  -- 1 octet of node number
                          OCTET STRING (SIZE (3))
                  -- This data type is used for encoding a DDP protocol
                  -- address.  The format of this address is a serial
                  -- encoding of the two octets of network number in
                  -- network byte order, followed by the 1 octet node
                  -- number.

                  llap     OBJECT IDENTIFIER ::= { appletalk 1 }
                  aarp     OBJECT IDENTIFIER ::= { appletalk 2 }
                  atport   OBJECT IDENTIFIER ::= { appletalk 3 }
                  ddp      OBJECT IDENTIFIER ::= { appletalk 4 }
                  rtmp     OBJECT IDENTIFIER ::= { appletalk 5 }
                  kip      OBJECT IDENTIFIER ::= { appletalk 6 }
                  zip      OBJECT IDENTIFIER ::= { appletalk 7 }
                  nbp      OBJECT IDENTIFIER ::= { appletalk 8 }
                  atecho   OBJECT IDENTIFIER ::= { appletalk 9 }


          -- The LLAP Group















          -- The AARP Group







          -- The ATPort Group
















          -- The DDP Group

















          -- The RTMP Group












          -- The KIP Group













          -- The ZIP Group










          -- The NBP Group









          -- The ATEcho Group



--
-- FILE: /users/sse/mibs/src/inReach/ir-appletalk-mib.mib
--

-- $Id: ir-appletalk-mib.mib,v 1.1 2002/06/27 15:47:22 sse Exp $


            xApple          OBJECT IDENTIFIER ::= { mrvInReachProductDivision 21 }

            -- MRV In-Reach AppleTalk subgroups

            xAppleSystem        OBJECT IDENTIFIER ::= { xApple 1 }
            xApplePort          OBJECT IDENTIFIER ::= { xApple 2 }
            xApplePolicy        OBJECT IDENTIFIER ::= { xApple 3 }
            xAppleNbp           OBJECT IDENTIFIER ::= { xApple 4 }
            xAppleTraffic       OBJECT IDENTIFIER ::= { xApple 5 }
            xAppleRemoteAccess  OBJECT IDENTIFIER ::= { xApple 6 }

            -- This is a MIB module for all MRV In-Reach systems that
            -- implement Appletalk.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the AppleTalk System group

            appleState OBJECT-TYPE
                SYNTAX INTEGER { disabled(1), enabled(2) }
                ACCESS read-write
                STATUS mandatory
                DESCRIPTION
                    "Controls whether the router will perform AppleTalk 
                    routing."
                ::= { xAppleSystem 1 }

            appleStatus OBJECT-TYPE
                SYNTAX INTEGER { disabled(1), active(2), noInterface(3),
                                 badConfig(4), noInterfaceActive (5) }
                ACCESS read-only
                STATUS mandatory
                DESCRIPTION
                    "Indicates whether the router is performing 
                    AppleTalk routing."
                ::= { xAppleSystem 2 }

            appleStatusIf OBJECT-TYPE
                SYNTAX INTEGER
                ACCESS read-only
                STATUS mandatory
                DESCRIPTION
                    "The ifIndex of the bad interface if appleStatus is 
                    'badConfig'."
                ::= { xAppleSystem 3 }


            -- the AppleTalk Port group

            applePortTable OBJECT-TYPE
                SYNTAX SEQUENCE OF ApplePortEntry
                ACCESS not-accessible
                STATUS mandatory
                DESCRIPTION
                    "Table of fields indexed by interface."
                ::= { xApplePort 1 }

            applePortEntry OBJECT-TYPE
                SYNTAX ApplePortEntry
                ACCESS not-accessible
                STATUS mandatory
                DESCRIPTION
                    "A particular entry."
                INDEX { applePortIndex }
                ::= { applePortTable 1 }

            ApplePortEntry ::=
                SEQUENCE {
                    applePortIndex
                        INTEGER,
                    applePortProtocolPriority
                        INTEGER,
                    applePortArpInterval
                        INTEGER,
                    applePortArpRetransmitCount
                        INTEGER,
                    applePortChecksum
                        INTEGER,
                    applePortPacketsIn
                        Counter,
                    applePortPacketsOut
                        Counter,
                    applePortForwardsIn
                        Counter,
                    applePortForwardsOut
                        Counter,
                    applePortNetAddress
                        DdpAddress,
                    applePortNetStart
                        OCTET STRING,
                    applePortNetEnd
                        OCTET STRING,
                    applePortErrors
                        Counter,
                    applePortLastError
                        INTEGER,
                    applePortLastErrorTime
                        TimeTicks,
                    applePortLastErrorData
                        OCTET STRING,
                    applePortBringBackTime
                        INTEGER,
                    applePortUseNeighborNotify
                        INTEGER,
                    applePortRouterType
                        INTEGER
                }

            applePortIndex OBJECT-TYPE
                SYNTAX INTEGER
                ACCESS read-only
                STATUS mandatory
                DESCRIPTION
                    "The index of the interface; same as IfIndex."
                ::= { applePortEntry 1 }

            applePortProtocolPriority OBJECT-TYPE
                SYNTAX INTEGER { low(1), medium(3), high(5) }
                ACCESS read-write
                STATUS mandatory
                DESCRIPTION
                    "This value defines the priority at which all Apple 
                    routed packets will be placed on the WAN output 
                    queue."
                DEFVAL { medium }
                ::= { applePortEntry 2 }

            applePortArpInterval OBJECT-TYPE
                SYNTAX INTEGER (33..65535)
                ACCESS read-write
                STATUS mandatory
                DESCRIPTION
                    "The interval at which ARP messages should be sent 
                    during the process of selecting a network address."
                DEFVAL { 33 }
                ::= { applePortEntry 3 }

            applePortArpRetransmitCount OBJECT-TYPE
                SYNTAX INTEGER (1..65535)
                ACCESS read-write
                STATUS mandatory
                DESCRIPTION
                    "The number of ARP messages that should be sent 
                    during the process of selecting a network address."
                DEFVAL { 20 }
                ::= { applePortEntry 4 }

            applePortChecksum OBJECT-TYPE
                SYNTAX INTEGER { disabled(1), enabled(2) }
                ACCESS read-write
                STATUS mandatory
                DESCRIPTION
                    "Controls whether checksums are generated on all DDP 
                    packets sent out the interface."
                DEFVAL { disabled }
                ::= { applePortEntry 5 }

            applePortPacketsIn OBJECT-TYPE
                SYNTAX Counter
                ACCESS read-only
                STATUS mandatory
                DESCRIPTION
                    "The number of AppleTalk packets received on this 
                    interface."
                ::= { applePortEntry 6 }

            applePortPacketsOut OBJECT-TYPE
                SYNTAX Counter
                ACCESS read-only
                STATUS mandatory
                DESCRIPTION
                    "The number of AppleTalk packets transmitted on this 
                    interface."
                ::= { applePortEntry 7 }

            applePortForwardsIn OBJECT-TYPE
                SYNTAX Counter
                ACCESS read-only
                STATUS mandatory
                DESCRIPTION
                    "The number of AppleTalk packets received on this 
                    interface which were not addressed to this router."
                ::= { applePortEntry 8 }

            applePortForwardsOut OBJECT-TYPE
                SYNTAX Counter
                ACCESS read-only
                STATUS mandatory
                DESCRIPTION
                    "The number of AppleTalk packets transmitted on this 
                    interface which were not originated by this 
                    router."
                ::= { applePortEntry 9 }

            applePortNetAddress OBJECT-TYPE
                SYNTAX DdpAddress
                ACCESS read-only
                STATUS mandatory
                DESCRIPTION
                    "The actual address used by this port."
                ::= { applePortEntry 10 }

            applePortNetStart OBJECT-TYPE
                SYNTAX OCTET STRING ( SIZE(2) )
                ACCESS read-only
                STATUS mandatory
                DESCRIPTION
                    "The start of the actual network range used by this 
                    port."
                ::= { applePortEntry 11 }

            applePortNetEnd OBJECT-TYPE
                SYNTAX OCTET STRING ( SIZE(2) )
                ACCESS read-only
                STATUS mandatory
                DESCRIPTION
                    "The end of the actual network range used by this 
                    port."
                ::= { applePortEntry 12 }

            applePortErrors OBJECT-TYPE
                SYNTAX Counter
                ACCESS read-only
                STATUS mandatory
                DESCRIPTION
                    "The number of AppleTalk packets received in 
                    error."
                ::= { applePortEntry 13 }

            applePortLastError OBJECT-TYPE
                SYNTAX INTEGER { broadcast(1), checksum(2), hopCount(3),
                                 noProtocol(4), noRoute(5), shortDDP(6),
                                 tooLong(7), tooShort(8) }
                ACCESS read-only
                STATUS mandatory
                DESCRIPTION
                    "The type of the most recent error counted in 
                    applePortErrors.  A value of zero means no error."
                ::= { applePortEntry 14 }

            applePortLastErrorTime OBJECT-TYPE
                SYNTAX TimeTicks
                ACCESS read-only
                STATUS mandatory
                DESCRIPTION
                    "The value of sysUptime when applePortLastError last 
                    occured."
                ::= { applePortEntry 15 }

            applePortLastErrorData OBJECT-TYPE
                SYNTAX OCTET STRING ( SIZE(22) )
                ACCESS read-only
                STATUS mandatory
                DESCRIPTION
                    "The first 22 bytes of the packet from 
                    applePortLastError."
                ::= { applePortEntry 16 }

            applePortBringBackTime OBJECT-TYPE
                SYNTAX INTEGER (0..65535)
                ACCESS read-write
                STATUS mandatory
                DESCRIPTION
                    "The number of seconds to shut down an interface 
                    while waiting for a manager-initiated configuration 
                    change to propagate."
                ::= { applePortEntry 17 }

            applePortUseNeighborNotify OBJECT-TYPE
                SYNTAX INTEGER { disabled(1), enabled(2) }
                ACCESS read-write
                STATUS mandatory
                DESCRIPTION
                    "Controls generation of neighbor notify messages 
                    when an interface is disabled or system is shut 
                    down."
                ::= { applePortEntry 18 }

            applePortRouterType OBJECT-TYPE
                SYNTAX INTEGER { full(1), half(2) }
                ACCESS read-write
                STATUS mandatory
                DESCRIPTION
                    "Type of router operation over this port."
                ::= { applePortEntry 19 }


            -- the Port Zone table

            applePortZoneTable OBJECT-TYPE
                SYNTAX SEQUENCE OF ApplePortZoneEntry
                ACCESS not-accessible
                STATUS mandatory
                DESCRIPTION
                    "Table of fields indexed by interface and zone."
                ::= { xApplePort 2 }

            applePortZoneEntry OBJECT-TYPE
                SYNTAX ApplePortZoneEntry
                ACCESS not-accessible
                STATUS mandatory
                DESCRIPTION
                    "A particular entry."
                INDEX { applePortZoneIndex, applePortZoneName }
                ::= { applePortZoneTable 1 }

            ApplePortZoneEntry ::=
                SEQUENCE {
                    applePortZoneIndex
                        INTEGER,
                    applePortZoneName
                        OCTET STRING,
                    applePortZoneStatus
                        INTEGER
                }

            applePortZoneIndex OBJECT-TYPE
                SYNTAX INTEGER
                ACCESS read-only
                STATUS mandatory
                DESCRIPTION
                    "The index of the interface; same as IfIndex."
                ::= { applePortZoneEntry 1 }

            applePortZoneName OBJECT-TYPE
                SYNTAX OCTET STRING ( SIZE(32) )
                ACCESS read-only
                STATUS mandatory
                DESCRIPTION
                    "The name of the zone."
                ::= { applePortZoneEntry 2 }

            applePortZoneStatus OBJECT-TYPE
                SYNTAX INTEGER { invalid(1), valid(2) }
                ACCESS read-write
                STATUS mandatory
                DESCRIPTION
                    "The status of the entry.  Set to 'invalid' to 
                    remove the entry."
                DEFVAL { valid }
                ::= { applePortZoneEntry 3 }


            -- the AppleTalk Port Policy group

            applePortExportTable OBJECT-TYPE
                SYNTAX SEQUENCE OF ApplePortExportEntry
                ACCESS not-accessible
                STATUS mandatory
                DESCRIPTION
                    "Table of fields indexed by interface and zone."
                ::= { xApplePolicy 1 }

            applePortExportEntry OBJECT-TYPE
                SYNTAX ApplePortExportEntry
                ACCESS not-accessible
                STATUS mandatory
                DESCRIPTION
                    "A particular entry."
                INDEX { applePortExportIndex, applePortExportZone,
                        applePortExportName, applePortExportType }
                ::= { applePortExportTable 1 }

            ApplePortExportEntry ::=
                SEQUENCE {
                    applePortExportIndex
                        INTEGER,
                    applePortExportZone
                        OCTET STRING,
                    applePortExportName
                        OCTET STRING,
                    applePortExportType
                        OCTET STRING,
                    applePortExportAction
                        INTEGER,
                    applePortExportStatus
                        INTEGER
                }

            applePortExportIndex OBJECT-TYPE
                SYNTAX INTEGER
                ACCESS read-only
                STATUS mandatory
                DESCRIPTION
                    "The index of the interface; same as IfIndex."
                ::= { applePortExportEntry 1 }

            applePortExportZone OBJECT-TYPE
                SYNTAX OCTET STRING ( SIZE(0..32) )
                ACCESS read-only
                STATUS mandatory
                DESCRIPTION
                    "The name of the zone."
                ::= { applePortExportEntry 2 }

            applePortExportName OBJECT-TYPE
                SYNTAX OCTET STRING ( SIZE(0..32) )
                ACCESS read-only
                STATUS mandatory
                DESCRIPTION
                    "The name of the name."
                ::= { applePortExportEntry 3 }

            applePortExportType OBJECT-TYPE
                SYNTAX OCTET STRING ( SIZE(0..32) )
                ACCESS read-only
                STATUS mandatory
                DESCRIPTION
                    "The name of the type."
                ::= { applePortExportEntry 4 }

            applePortExportAction OBJECT-TYPE
                SYNTAX INTEGER { hide(1), advertise(2) }
                ACCESS read-write
                STATUS mandatory
                DESCRIPTION
                    "Control whether the data will be hidden or 
                    advertised."
                DEFVAL { advertise }
                ::= { applePortExportEntry 5 }

            applePortExportStatus OBJECT-TYPE
                SYNTAX INTEGER { invalid(1), valid(2) }
                ACCESS read-write
                STATUS mandatory
                DESCRIPTION
                    "The status of the entry.  Set to 'invalid' to 
                    remove the entry."
                DEFVAL { valid }
                ::= { applePortExportEntry 6 }

            applePortImportTable OBJECT-TYPE
                SYNTAX SEQUENCE OF ApplePortImportEntry
                ACCESS not-accessible
                STATUS mandatory
                DESCRIPTION
                    "Table of fields indexed by interface and zone."
                ::= { xApplePolicy 2 }

            applePortImportEntry OBJECT-TYPE
                SYNTAX ApplePortImportEntry
                ACCESS not-accessible
                STATUS mandatory
                DESCRIPTION
                    "A particular entry."
                INDEX { applePortImportIndex, applePortImportZone,
                        applePortImportName, applePortImportType }
                ::= { applePortImportTable 1 }

            ApplePortImportEntry ::=
                SEQUENCE {
                    applePortImportIndex
                        INTEGER,
                    applePortImportZone
                        OCTET STRING,
                    applePortImportName
                        OCTET STRING,
                    applePortImportType
                        OCTET STRING,
                    applePortImportAction
                        INTEGER,
                    applePortImportStatus
                        INTEGER
                }

            applePortImportIndex OBJECT-TYPE
                SYNTAX INTEGER
                ACCESS read-only
                STATUS mandatory
                DESCRIPTION
                    "The index of the interface; same as IfIndex."
                ::= { applePortImportEntry 1 }

            applePortImportZone OBJECT-TYPE
                SYNTAX OCTET STRING ( SIZE(0..32) )
                ACCESS read-only
                STATUS mandatory
                DESCRIPTION
                    "The name of the zone."
                ::= { applePortImportEntry 2 }

            applePortImportName OBJECT-TYPE
                SYNTAX OCTET STRING ( SIZE(0..32) )
                ACCESS read-only
                STATUS mandatory
                DESCRIPTION
                    "The name of the name."
                ::= { applePortImportEntry 3 }

            applePortImportType OBJECT-TYPE
                SYNTAX OCTET STRING ( SIZE(0..32) )
                ACCESS read-only
                STATUS mandatory
                DESCRIPTION
                    "The name of the type."
                ::= { applePortImportEntry 4 }

            applePortImportAction OBJECT-TYPE
                SYNTAX INTEGER { discard(1), accept(2) }
                ACCESS read-write
                STATUS mandatory
                DESCRIPTION
                    "Control whether the data will be discarded or 
                    accepted."
                DEFVAL { accept }
                ::= { applePortImportEntry 5 }

            applePortImportStatus OBJECT-TYPE
                SYNTAX INTEGER { invalid(1), valid(2) }
                ACCESS read-write
                STATUS mandatory
                DESCRIPTION
                    "The status of the entry.  Set to 'invalid' to 
                    remove the entry."
                DEFVAL { valid }
                ::= { applePortImportEntry 6 }


            -- the AppleTalk Name group

            appleNbpTable OBJECT-TYPE
                SYNTAX SEQUENCE OF AppleNbpEntry
                ACCESS not-accessible
                STATUS mandatory
                DESCRIPTION
                    "Table of fields indexed by interface and zone."
                ::= { xAppleNbp 1 }

            appleNbpEntry OBJECT-TYPE
                SYNTAX AppleNbpEntry
                ACCESS not-accessible
                STATUS mandatory
                DESCRIPTION
                    "A particular entry."
                INDEX { appleNbpZone, appleNbpName, appleNbpType }
                ::= { appleNbpTable 1 }

            AppleNbpEntry ::=
                SEQUENCE {
                    appleNbpZone
                        OCTET STRING,
                    appleNbpName
                        OCTET STRING,
                    appleNbpType
                        OCTET STRING,
                    appleNbpNode
                        DdpAddress,
                    appleNbpSocket
                        INTEGER
                }

            appleNbpZone OBJECT-TYPE
                SYNTAX OCTET STRING ( SIZE(0..32) )
                ACCESS read-only
                STATUS mandatory
                DESCRIPTION
                    "The name of the zone."
                ::= { appleNbpEntry 1 }

            appleNbpName OBJECT-TYPE
                SYNTAX OCTET STRING ( SIZE(0..32) )
                ACCESS read-only
                STATUS mandatory
                DESCRIPTION
                    "The name of the name."
                ::= { appleNbpEntry 2 }

            appleNbpType OBJECT-TYPE
                SYNTAX OCTET STRING ( SIZE(0..32) )
                ACCESS read-only
                STATUS mandatory
                DESCRIPTION
                    "The name of the type."
                ::= { appleNbpEntry 3 }

            appleNbpNode OBJECT-TYPE
                SYNTAX DdpAddress
                ACCESS read-only
                STATUS mandatory
                DESCRIPTION
                    "The address of the node who offers the service 
                    associated with this entry."
                ::= { appleNbpEntry 4 }

            appleNbpSocket OBJECT-TYPE
                SYNTAX INTEGER
                ACCESS read-only
                STATUS mandatory
                DESCRIPTION
                    "The socket of the service associated with this 
                    entry.  The value 0 means no socket."
                ::= { appleNbpEntry 5 }


            -- the AppleTalk Traffic group

            appleTrafficSort OBJECT-TYPE
                SYNTAX INTEGER { ready(1), execute(2) }
                ACCESS read-write
                STATUS mandatory
                DESCRIPTION
                    "Setting to EXECUTE causes the most recent traffic 
                    information to be sorted into the appleTrafficTable.  
                    The sorting precedence is: decreasing percentage, 
                    increasing destination address, increasing source 
                    address, and increasing interface number.  Setting 
                    to READY has no effect."
                ::= { xAppleTraffic 1 }

            -- Additional single objects follow the Traffic table

            -- the Traffic table

            appleTrafficTable OBJECT-TYPE
                SYNTAX SEQUENCE OF AppleTrafficEntry
                ACCESS not-accessible
                STATUS mandatory
                DESCRIPTION
                    "A list of traffic entries, sorted in the order 
                    specified by appleTrafficSort."
                ::= { xAppleTraffic 2 }

            appleTrafficEntry OBJECT-TYPE
                SYNTAX AppleTrafficEntry
                ACCESS not-accessible
                STATUS mandatory
                DESCRIPTION
                    "Parameter values for an Filter filter."
                INDEX { appleTrafficIndex }
                ::= { appleTrafficTable 1 }

            AppleTrafficEntry ::=
                SEQUENCE {
                    appleTrafficIndex
                        INTEGER,
                    appleTrafficPercent
                        INTEGER,
                    appleTrafficDst
                        DdpAddress,
                    appleTrafficSrc
                        DdpAddress,
                    appleTrafficIntf
                        INTEGER
                }

            appleTrafficIndex OBJECT-TYPE
                SYNTAX INTEGER
                ACCESS read-only
                STATUS mandatory
                DESCRIPTION
                    "Identification of a traffic entry."
                ::= { appleTrafficEntry 1 }

            appleTrafficPercent OBJECT-TYPE
                SYNTAX INTEGER ( 0..1000 )
                ACCESS read-only
                STATUS mandatory
                DESCRIPTION
                    "The percent of total traffic that this traffic 
                    entryrepresents, in tenths of a percent."
                ::= { appleTrafficEntry 2 }

            appleTrafficDst OBJECT-TYPE
                SYNTAX DdpAddress
                ACCESS read-only
                STATUS mandatory
                DESCRIPTION
                    "The destination to which the traffic entry 
                    applies."
                ::= { appleTrafficEntry 3 }

            appleTrafficSrc OBJECT-TYPE
                SYNTAX DdpAddress
                ACCESS read-only
                STATUS mandatory
                DESCRIPTION
                    "The source to which the traffic entry applies."
                ::= { appleTrafficEntry 4 }

            appleTrafficIntf OBJECT-TYPE
                SYNTAX INTEGER
                ACCESS read-only
                STATUS mandatory
                DESCRIPTION
                    "The inbound interface to which the traffic entry 
                    applies."
                ::= { appleTrafficEntry 5 }

            -- Additional individual objects

            appleTrafficMonitoring OBJECT-TYPE
                SYNTAX INTEGER { disable(1), enable(2) }
                ACCESS read-write
                STATUS mandatory
                DESCRIPTION
                    "Controls whether internet traffic information will 
                    be recorded."
                ::= { xAppleTraffic 3 }

            -- The MRV In-Reach ARAP MIB branch

            arapPassword OBJECT-TYPE
                SYNTAX DisplayString (SIZE (0..8))
                ACCESS read-write
                STATUS mandatory
                DESCRIPTION
                    "The server's ARAP password.  To increase security, Gets
                    of this object return the NULL string."
                ::= { xAppleRemoteAccess 1 }

            arapDefaultZoneName OBJECT-TYPE
                SYNTAX DisplayString (SIZE (0..32))
                ACCESS read-write
                STATUS mandatory
                DESCRIPTION
                    "The name of the AppleTalk zone that the server should
                    try to choose at boot time."
                ::= { xAppleRemoteAccess 2 }

            -- the ARAP Port table

            arapPortTable OBJECT-TYPE
                SYNTAX SEQUENCE OF ArapPortEntry
                ACCESS not-accessible
                STATUS mandatory
                DESCRIPTION
                    "A list of ARAP port entries."
                ::= { xAppleRemoteAccess 3 }

            arapPortEntry OBJECT-TYPE
                SYNTAX ArapPortEntry
                ACCESS not-accessible
                STATUS mandatory
                DESCRIPTION
                    "ARAP parameter values for a port."
                INDEX { charPortIndex }
                ::= { arapPortTable 1 }

            ArapPortEntry ::=
                SEQUENCE {
                    arapPortEnabled
                        INTEGER,
                    arapPortZoneAccess
                        INTEGER,
                    arapPortZoneName
                        DisplayString,
                    arapPortMaxConnectTime
                        INTEGER,
                    arapPortGuestLoginsOk
                        INTEGER,
                    arapPortTimeConnected
                        INTEGER,
                    arapPortTimeRemaining
                        INTEGER
                }

            arapPortEnabled OBJECT-TYPE
                SYNTAX INTEGER { disabled(1), enabled(2) }
                ACCESS read-write
                STATUS mandatory
                DESCRIPTION
                    "Indicates if ARAP connections are allowed on this port."
                ::= { arapPortEntry 1 }

            arapPortZoneAccess OBJECT-TYPE
                SYNTAX INTEGER { all(1), local(2), none(3), namedzone(4) }
                ACCESS read-write
                STATUS mandatory
                DESCRIPTION
                    "Indicates the AppleTalk zones that ARAP connections on
                    this port may access: none, local, all, or named zone."
                ::= { arapPortEntry 2 }

            arapPortZoneName OBJECT-TYPE
                SYNTAX DisplayString (SIZE (0..32))
                ACCESS read-write
                STATUS mandatory
                DESCRIPTION
                    "If this port's arapPortZoneAccess field indicates a
                    named zone, this field contains the zone name."
                ::= { arapPortEntry 3 }

            arapPortMaxConnectTime OBJECT-TYPE
                SYNTAX INTEGER
                ACCESS read-write
                STATUS mandatory
                DESCRIPTION
                    "Maximum number of minutes a single ARAP connection may
                    exist on the port before a server initiated disconnect.
                    To set no limit on the amount of time that an ARAP user
                    may be connected, set this object to -1."
                ::= { arapPortEntry 4 }

            arapPortGuestLoginsOk OBJECT-TYPE
                SYNTAX INTEGER { disabled(1), enabled(2) }
                ACCESS read-write
                STATUS mandatory
                DESCRIPTION
                    "Indicates if 'Guest' logins (with no password) are
                    allowed on the port."
                ::= { arapPortEntry 5 }

            arapPortTimeConnected OBJECT-TYPE
                SYNTAX INTEGER
                ACCESS read-only
                STATUS mandatory
                DESCRIPTION
                    "Indicates the number of minutes the current ARAP
                    connection has been established on the port, rounded
                    up to the nearest minute.  Gets return -1 if no ARAP
                    user is currently connected on the port or if ARAP is
                    not enabled on the port."
                ::= { arapPortEntry 6 }

            arapPortTimeRemaining OBJECT-TYPE
                SYNTAX INTEGER
                ACCESS read-write
                STATUS mandatory
                DESCRIPTION
                    "Indicates the number of minutes the current ARAP
                    connection may remain on the port before a server
                    initiated disconnect will occur, rounded up to the
                    nearest minute.  To set no limit on the amount of
                    time that the current ARAP user may continue to be
                    connected, set this object to the maximum value
                    in the range.  Gets return -1 if no ARAP user is
                    currently connected on the port or if ARAP is not
                    enabled on the port.  Gets also return -1 if there
                    is a user connected and there is no limit on the
                    amount of time that the current user may be connected."
                ::= { arapPortEntry 7 }


--
-- FILE: /users/sse/mibs/src/inReach/ir-boot-client-mib.mib
--

-- $Id: ir-boot-client-mib.mib,v 1.1 2002/06/27 15:40:14 sse Exp $


            xBootClient     OBJECT IDENTIFIER ::= { mrvInReachProductDivision 12 }

            --  This is the MIB module for clients of MRV In-Reach bootstrap
            --  service.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the Bootstrap Client group

            -- Implementation of this group is mandatory for all MRV In-Reach
            -- systems that use the MRV In-Reach bootstrap service

            bootClientStatus OBJECT-TYPE
                SYNTAX DisplayString (SIZE (0..1400))
                ACCESS read-only
                STATUS mandatory
                DESCRIPTION
                    "The overall status of the bootstrapping operation, 
                    including, for example, what is presently happening 
                    and error information."
                ::= { xBootClient 1 }


--
-- FILE: /users/sse/mibs/src/inReach/ir-boot-server-mib.mib
--

-- $Id: ir-boot-server-mib.mib,v 1.1 2002/06/27 15:39:58 sse Exp $


            xBootServer     OBJECT IDENTIFIER ::= { mrvInReachProductDivision 6 }

            -- MRV In-Reach Boot Server subgroups

            xBsBasic        OBJECT IDENTIFIER ::= { xBootServer 1 }
            xDump           OBJECT IDENTIFIER ::= { xBootServer 2 }
            xLoad           OBJECT IDENTIFIER ::= { xBootServer 3 }
            xParam          OBJECT IDENTIFIER ::= { xBootServer 4 }

            --  This is the MIB module for providers of MRV In-Reach
            --  bootstrap service.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- Textual Conventions

            DialogStatus ::=
                INTEGER { none(1),
                          fileTooLarge(2),
                          notImageFile(3),
                          notExecutableFile(4),
                          badFileData(5),
                          deviceWriteProtected(6),
                          operationTimeout(7),
                          remoteFileNotFound(8),
                          remoteFileAccessViolation(9),
                          protocolError(10),
                          fileSystemError(11),
                          temporaryResourceConflict(12),
                          success(13) }
            -- Final status of a boot dialog.


            -- the Bootstrap Server Basic group

            -- Implementation of this group is mandatory for all MRV In-Reach
            -- systems that provide the MRV In-Reach bootstrap service

            basicLogLimit OBJECT-TYPE
                SYNTAX INTEGER (1..100)
                ACCESS read-write
                STATUS mandatory
                DESCRIPTION
                    "Maximum allowed number of kilobytes for recording 
                    events.  Corresponds directly to MANAGER LOG FILE 
                    SIZE and the value labeled 'Log File Size:' in the 
                    MANAGER CHARACTERISTICS display."
                ::= { xBsBasic 1 }

            basicActiveLimit OBJECT-TYPE
                SYNTAX INTEGER (0..32)
                ACCESS read-write
                STATUS mandatory
                DESCRIPTION
                    "Maximum allowed number of simultaneous service 
                    dialogs.  Corresponds directly to MANAGER 
                    SIMULTANEOUS and the value labeled 'Maximum 
                    simultaneous requests:' in the MANAGER 
                    CHARACTERISTICS display."
                ::= { xBsBasic 2 }

            basicActiveNumber OBJECT-TYPE
                SYNTAX Gauge
                ACCESS read-only
                STATUS mandatory
                DESCRIPTION
                    "Number of active service dialogs.  Corresponds 
                    indirectly to the list of active clients in the 
                    MANAGER STATUS display."
                ::= { xBsBasic 3 }

            basicClientNumber OBJECT-TYPE
                SYNTAX Gauge
                ACCESS read-only
                STATUS mandatory
                DESCRIPTION
                    "Number of defined clients.  Corresponds indirectly 
                    to the list of defined clients in the MANAGER LOCAL, 
                    MANAGER GLOBAL, and MANAGER NODE displays."


                ::= { xBsBasic 4 }

            basicOffersSent OBJECT-TYPE
                SYNTAX Counter
                ACCESS read-only
                STATUS mandatory
                DESCRIPTION
                    "Total number of service offers sent in response to 
                    client requests.  Corresponds directly to the value 
                    labeled 'Total service offers sent:' in the MANAGER 
                    STATUS display."
                ::= { xBsBasic 5 }

            basicEventTotal OBJECT-TYPE
                SYNTAX Gauge
                ACCESS read-only
                STATUS mandatory
                DESCRIPTION
                    "Total number of events that have been written to 
                    the event log since it was last purged.  This may be 
                    less than the number currently in the log.  
                    Corresponds directly to the value labeled 'Total 
                    Messages Logged:' in the MANAGER EVENTS display."
                ::= { xBsBasic 6 }

            basicEventPurge OBJECT-TYPE
                SYNTAX INTEGER { ready(1), execute(2) }
                ACCESS read-write
                STATUS mandatory
                DESCRIPTION
                    "Control to cause emptying the event log.  In 
                    response to a get-request or get-next-request, the 
                    agent always returns 'ready' for this value.  
                    Setting the value to 'ready' has no effect.  Setting 
                    it to 'execute' causes the event log to immediately 
                    become empty.  Corresponds directly to the PURGE 
                    MANAGER LOG FILE command."
                ::= { xBsBasic 7 }


            -- The Active table

            activeTable OBJECT-TYPE
                SYNTAX SEQUENCE OF ActiveEntry
                ACCESS not-accessible
                STATUS mandatory
                DESCRIPTION
                    "A list of active client dialog entries.  The number 
                    of entries is given by basicActiveNumber."
                ::= { xBsBasic 8 }

            activeEntry OBJECT-TYPE
                SYNTAX ActiveEntry
                ACCESS not-accessible
                STATUS mandatory
                DESCRIPTION
                    "Parameter values for an active client dialog 
                    entry."
                INDEX { activeIdentificationType, activeIdentification }
                ::= { activeTable 1 }

            ActiveEntry ::=
                SEQUENCE {
                    activeIdentificationType
                        AddressType,
                    activeIdentification
                        OCTET STRING,
                    activeFunction
                        INTEGER,
                    activeSoftwareVersionType
                        INTEGER,
                    activeSoftwareVersion
                        OCTET STRING,
                    activeParameterVersion
                        INTEGER,
                    activeCurrentSequence
                        INTEGER,
                    activeBytesRemaining
                        INTEGER,
                    activeFile
                        DisplayString,
                    activeStatus
                        DialogStatus,
                    activeState
                        INTEGER
                }


            activeIdentificationType OBJECT-TYPE
                SYNTAX AddressType
                ACCESS read-only
                STATUS mandatory
                DESCRIPTION
                    "The type of identification value in 
                    activeIdentification.  Corresponds indirectly to the 
                    value labeled 'EthernetAddress' in the MANAGER 
                    STATUS display."
                ::= { activeEntry 1 }

            activeIdentification OBJECT-TYPE
                SYNTAX OCTET STRING (SIZE (1..6))
                ACCESS read-only
                STATUS mandatory
                DESCRIPTION
                    "Identification of the active partner.  Corresponds 
                    directly to the value labeled 'EthernetAddress' in 
                    the MANAGER STATUS display."
                ::= { activeEntry 2 }

            activeFunction OBJECT-TYPE
                SYNTAX INTEGER { parameterStore(1), load(2), dump(3),
                                 imageUpdate(4) }
                ACCESS read-only
                STATUS mandatory
                DESCRIPTION
                    "The function the server is performing with the 
                    partner.  Corresponds directly to the value labeled 
                    'Function' in the MANAGER STATUS display."
                ::= { activeEntry 3 }

            activeSoftwareVersionType OBJECT-TYPE
                SYNTAX INTEGER { alpha(1), beta(2),
                                 production(3), special(4),
                                 diagnostic(5),notApplicable(6) }
                ACCESS read-only
                STATUS mandatory
                DESCRIPTION
                    "If activeFunction is 'load', the software version 
                    being sent to the client, otherwise 'notApplicable'.  
                    Corresponds to the letter in the software version 
                    labeled 'Version' in the MANAGER STATUS display.

                    alpha         'A':   alpha test


                    beta          'B':   beta test
                    production    null:  normal, production software
                    special       'S':   special, custom software
                    diagnostic    'D':   diagnostic, debug software
                    "
                ::= { activeEntry 4 }

            activeSoftwareVersion OBJECT-TYPE
                SYNTAX OCTET STRING (SIZE (0..4))
                ACCESS read-only
                STATUS mandatory
                DESCRIPTION
                    "If activeFunction is 'load', the 4-byte software 
                    version being sent to the client, otherwise zero 
                    length.  In order, the octets contain major version, 
                    minor version, ECO, and pre-release number.  
                    Corresponds to the numbers in the software version 
                    labeled 'Version' in the MANAGER STATUS display.

                    For example, the version display for 
                    activeSoftwareVersionType 'production' and 
                    activeSoftwareVersion '2.2.0.0' is 'V2.2'.

                    The version display for activeSoftwareVersionType 
                    'beta' and activeSoftwareVersion '3.1.0.4' is 
                    'V3.1B4'."
                ::= { activeEntry 5 }

            activeParameterVersion OBJECT-TYPE
                SYNTAX INTEGER
                ACCESS read-only
                STATUS mandatory
                DESCRIPTION
                    "If activeFunction is 'parameterStore', the 
                    parameter version being stored by the client, 
                    otherwise zero.  Corresponds directly to the value 
                    labeled 'Version' in the MANAGER STATUS display."
                ::= { activeEntry 6 }

            activeCurrentSequence OBJECT-TYPE
                SYNTAX INTEGER
                ACCESS read-only
                STATUS mandatory
                DESCRIPTION
                    "The current dialog sequence number.  Corresponds 
                    directly to the value labeled 'Seq' in the MANAGER 
                    STATUS display."


                ::= { activeEntry 7 }

            activeBytesRemaining OBJECT-TYPE
                SYNTAX INTEGER
                ACCESS read-only
                STATUS mandatory
                DESCRIPTION
                    "The number of bytes remaining to be transferred in 
                    the dialog.  Corresponds directly to the value 
                    labeled 'Left' in the MANAGER STATUS display."
                ::= { activeEntry 8 }

            activeFile OBJECT-TYPE
                SYNTAX DisplayString (SIZE (1..64))
                ACCESS read-only
                STATUS mandatory
                DESCRIPTION
                    "The name of the file being used in the dialog.  
                    Corresponds directly to the value labeled 'File' in 
                    the MANAGER STATUS display."
                ::= { activeEntry 9 }

            activeStatus OBJECT-TYPE
                SYNTAX DialogStatus
                ACCESS read-only
                STATUS mandatory
                DESCRIPTION
                    "The final status of the most recent attempt to get 
                    an image.  Corresponds directly to the value labeled 
                    'Get Status:' in the DEVICE STATUS display."
                ::= { activeEntry 10 }

            activeState OBJECT-TYPE
                SYNTAX INTEGER { idle(1),
                                 internal1(2),
                                 internal2(3),
                                 openPartner(4),
                                 openFile(5),
                                 receivePartner(6),
                                 writeFile(7),
                                 closePartner(8),
                                 closeFile(9),
                                 cleanup(10),
                                 done(11),
                                 error(12) }
                ACCESS read-only


                STATUS mandatory
                DESCRIPTION
                    "The dynamic state of an active attempt to get an 
                    image.  Corresponds directly to the value labeled 
                    'Get State:' in the DEVICE STATUS display."
                ::= { activeEntry 11 }


            -- The Client table

            clientTable OBJECT-TYPE
                SYNTAX SEQUENCE OF ClientEntry
                ACCESS not-accessible
                STATUS mandatory
                DESCRIPTION
                    "A list of client data base entries.  The number of 
                    entries is given by basicClientNumber."
                ::= { xBsBasic 9 }

            clientEntry OBJECT-TYPE
                SYNTAX ClientEntry
                ACCESS not-accessible
                STATUS mandatory
                DESCRIPTION
                    "Parameter values for a client data base entry."
                INDEX { clientIdentificationType, clientIdentification }
                ::= { clientTable 1 }

            ClientEntry ::=
                SEQUENCE {
                    clientIdentificationType
                        AddressType,
                    clientIdentification
                        OCTET STRING,
                    clientEntryStatus
                        INTEGER,
                    clientName
                        DisplayString,
                    clientLoadFile
                        DisplayString,
                    clientDiagnosticFile
                        DisplayString,
                    clientLoadService
                        INTEGER,
                    clientDumpService
                        INTEGER
                }

            clientIdentificationType OBJECT-TYPE
                SYNTAX AddressType
                ACCESS read-only
                STATUS mandatory
                DESCRIPTION
                    "The type of identification value in 


                            clientIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 1 }

            clientIdentification OBJECT-TYPE
                SYNTAX OCTET STRING (SIZE (1..6))
                ACCESS read-only
                STATUS mandatory
                DESCRIPTION
                    "Identification of the client, either a hardware 
                    type or an Ethernet address, depending on 
                    clientIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 2 }

            clientEntryStatus OBJECT-TYPE
                SYNTAX INTEGER { invalid(1), valid(2) }
                ACCESS read-write
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { clientEntry 3 }

            clientName OBJECT-TYPE
                SYNTAX DisplayString (SIZE (0..16))
                ACCESS read-write
                STATUS mandatory
                DESCRIPTION
                    "A name that may be used to identify the client.  
                    Corresponds directly to the value labeled 'Name' in 
                    the MANAGER NODE display."
                DEFVAL { "" }
                ::= { clientEntry 4 }


            clientLoadFile OBJECT-TYPE
                SYNTAX DisplayString (SIZE (0..16))
                ACCESS read-write
                STATUS mandatory
                DESCRIPTION
                    "The file with the client's load image.  Corresponds 
                    directly to the value labeled 'Load File' in the 
                    MANAGER LOCAL, MANAGER GLOBAL, and MANAGER NODE 
                    displays."
                DEFVAL { "" }
                ::= { clientEntry 5 }

            clientDiagnosticFile OBJECT-TYPE
                SYNTAX DisplayString (SIZE (0..16))
                ACCESS read-write
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { clientEntry 6 }

            clientLoadService OBJECT-TYPE
                SYNTAX INTEGER { disabled(1), enabled(2) }
                ACCESS read-write
                STATUS mandatory
                DESCRIPTION
                    "Control for allowing load service for the client.  
                    Corresponds directly to the value labeled 'Load' in 
                    the MANAGER LOCAL, MANAGER GLOBAL, and MANAGER NODE 
                    displays."
                DEFVAL { enabled }
                ::= { clientEntry 7 }

            clientDumpService OBJECT-TYPE
                SYNTAX INTEGER { disabled(1), enabled(2) }
                ACCESS read-write
                STATUS mandatory
                DESCRIPTION
                    "Control for allowing dump service for the client.  
                    Corresponds directly to the value labeled 'Dump' in 
                    the MANAGER LOCAL, MANAGER GLOBAL, and MANAGER NODE 
                    displays."


                DEFVAL { disabled }
                ::= { clientEntry 8 }


            -- The Named Client table

            -- This table is strict subset of the Client table, being
            -- the same information in the same form with client name
            -- as the table index instead of client identification.
            -- It does not contain clients that have no name.

            namedTable OBJECT-TYPE
                SYNTAX SEQUENCE OF NamedEntry
                ACCESS not-accessible
                STATUS mandatory
                DESCRIPTION
                    "A list of named client data base entries.  The 
                    number of entries is given by basicClientNumber."
                ::= { xBsBasic 10 }

            namedEntry OBJECT-TYPE
                SYNTAX NamedEntry
                ACCESS not-accessible
                STATUS mandatory
                DESCRIPTION
                    "Parameter values for a named client data base 
                    entry."
                INDEX { namedName }
                ::= { namedTable 1 }

            NamedEntry ::=
                SEQUENCE {
                    namedIdentificationType
                        AddressType,
                    namedIdentification
                        OCTET STRING,
                    namedEntryStatus
                        INTEGER,
                    namedName
                        DisplayString,
                    namedLoadFile
                        DisplayString,
                    namedDiagnosticFile
                        DisplayString,
                    namedLoadService
                        INTEGER,
                    namedDumpService
                        INTEGER
                }


            namedIdentificationType OBJECT-TYPE
                SYNTAX AddressType
                ACCESS read-only
                STATUS mandatory
                DESCRIPTION
                    "The type of identification value in 
                    namedIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 1 }

            namedIdentification OBJECT-TYPE
                SYNTAX OCTET STRING (SIZE (1..6))
                ACCESS read-only
                STATUS mandatory
                DESCRIPTION
                    "Identification of the client, either a hardware 
                    type or an Ethernet address, depending on 
                    namedIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 2 }

            namedEntryStatus OBJECT-TYPE
                SYNTAX INTEGER { invalid(1), valid(2) }
                ACCESS read-only
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { namedEntry 3 }

            namedName OBJECT-TYPE
                SYNTAX DisplayString (SIZE (0..16))
                ACCESS read-only
                STATUS mandatory


                DESCRIPTION
                    "A name that may be used to identify the client.  
                    Corresponds directly to the value labeled 'Name' in 
                    the MANAGER NODE display."
                ::= { namedEntry 4 }

            namedLoadFile OBJECT-TYPE
                SYNTAX DisplayString (SIZE (0..16))
                ACCESS read-only
                STATUS mandatory
                DESCRIPTION
                    "The file with the client's load image.  Corresponds 
                    directly to the value labeled 'Load File' in the 
                    MANAGER LOCAL, MANAGER GLOBAL, and MANAGER NODE 
                    displays."
                DEFVAL { "" }
                ::= { namedEntry 5 }

            namedDiagnosticFile OBJECT-TYPE
                SYNTAX DisplayString (SIZE (0..16))
                ACCESS read-only
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { namedEntry 6 }

            namedLoadService OBJECT-TYPE
                SYNTAX INTEGER { disabled(1), enabled(2) }
                ACCESS read-only
                STATUS mandatory
                DESCRIPTION
                    "Control for allowing load service for the client.  
                    Corresponds directly to the value labeled 'Load' in 
                    the MANAGER LOCAL, MANAGER GLOBAL, and MANAGER NODE 
                    displays."
                DEFVAL { enabled }
                ::= { namedEntry 7 }

            namedDumpService OBJECT-TYPE
                SYNTAX INTEGER { disabled(1), enabled(2) }
                ACCESS read-only
                STATUS mandatory


                DESCRIPTION
                    "Control for allowing dump service for the client.  
                    Corresponds directly to the value labeled 'Dump' in 
                    the MANAGER LOCAL, MANAGER GLOBAL, and MANAGER NODE 
                    displays."
                DEFVAL { disabled }
                ::= { namedEntry 8 }


            -- The Event table

            xEventTable OBJECT-TYPE
                SYNTAX SEQUENCE OF XEventEntry
                ACCESS not-accessible
                STATUS mandatory
                DESCRIPTION
                    "A list of event entries.  The number of entries is 
                    given by basicEventNumber."
                ::= { xBsBasic 11 }

            xEventEntry OBJECT-TYPE
                SYNTAX XEventEntry
                ACCESS not-accessible
                STATUS mandatory
                DESCRIPTION
                    "Parameter values for a event entry."
                INDEX { xEventIndex }
                ::= { xEventTable 1 }

            XEventEntry ::=
                SEQUENCE {
                    xEventIndex
                        INTEGER,
                    xEventText
                        DisplayString
                }

            xEventIndex OBJECT-TYPE
                SYNTAX INTEGER
                ACCESS read-only
                STATUS mandatory
                DESCRIPTION
                    "In identification number for an event.  The value 1 
                    indicates the oldest event in the file, with 
                    subsequent numbers indicating sequential events.  
                    The event text for a given number may change as a 
                    circular event log wraps over its beginning.  
                    Corresponds directly to the relative position of an 
                    event in the MANAGER EVENTS display."
                ::= { xEventEntry 1 }

            xEventText OBJECT-TYPE
                SYNTAX DisplayString (SIZE (1..255))
                ACCESS read-only
                STATUS mandatory


                DESCRIPTION
                    "The text of the event, including date, time and 
                    other information.  Corresponds directly to the 
                    individual event text in the MANAGER EVENTS 
                    display."
                ::= { xEventEntry 2 }


            -- The Device table

            basicDeviceNumber OBJECT-TYPE
                SYNTAX INTEGER
                ACCESS read-only
                STATUS mandatory
                DESCRIPTION
                    "The system's number of mass-storage devices."
                ::= { xBsBasic 12 }

            deviceTable OBJECT-TYPE
                SYNTAX SEQUENCE OF DeviceEntry
                ACCESS not-accessible
                STATUS mandatory
                DESCRIPTION
                    "A list of device entries.  The number of entries is 
                    given by basicDeviceNumber."
                ::= { xBsBasic 13 }

            deviceEntry OBJECT-TYPE
                SYNTAX DeviceEntry
                ACCESS not-accessible
                STATUS mandatory
                DESCRIPTION
                    "Parameter values for a device entry."
                INDEX { deviceIndex }
                ::= { deviceTable 1 }

            DeviceEntry ::=
                SEQUENCE {
                    deviceIndex
                        INTEGER,
                    deviceName
                        DisplayString,
                    deviceDescr
                        DisplayString,
                    deviceOperation
                        INTEGER,
                    deviceFormat
                        INTEGER,
                    deviceProtection
                        INTEGER,
                    deviceFormatMedium
                        INTEGER,
                    deviceGetFile
                        INTEGER,


                    deviceGetFileHostIdentificationType
                        AddressType,
                    deviceGetFileHostIdentification
                        OCTET STRING,
                    deviceGetFileName
                        DisplayString,
                    deviceGetFileArea
                        INTEGER,
                    deviceFormatOption
                        INTEGER,
                    deviceFormatRedundantParams
                        INTEGER,
                    devicePreviousStatus
                        DialogStatus
                }

            deviceIndex OBJECT-TYPE
                SYNTAX INTEGER
                ACCESS read-only
                STATUS mandatory
                DESCRIPTION
                    "In identification number for a device, in the range 
                    1 to basicDeviceNumber"
                ::= { deviceEntry 1 }

            deviceName OBJECT-TYPE
                SYNTAX DisplayString (SIZE (0..16))
                ACCESS read-only
                STATUS mandatory
                DESCRIPTION
                    "A name by which the device is known in other 
                    displays, such as 'C1' or 'D2'."
                ::= { deviceEntry 2 }

            deviceDescr OBJECT-TYPE
                SYNTAX DisplayString (SIZE (0..80))
                ACCESS read-only
                STATUS mandatory
                DESCRIPTION
                    "Details of the device type, including, for example, 
                    size, manufacturer, Flash versus RAM, and such.  
                    Corresponds directly to the value labeled 'Device 
                    Type: in the MANAGER DEVICE STATUS display."
                ::= { deviceEntry 3 }

            deviceOperation OBJECT-TYPE


                SYNTAX INTEGER { read(1), write(2), format(3), idle(4),
                                 erase(5), paramStore(6), unpack(7),
                                 loadingClient(8) }
                ACCESS read-only
                STATUS mandatory
                DESCRIPTION
                    "Current operational state of the device.  
                    Corresponds directly the value labeled 'Device 
                    Operation:' in the MANAGER DEVICE STATUS display."
                ::= { deviceEntry 4 }

            deviceFormat OBJECT-TYPE
                SYNTAX INTEGER { unformatted(1), formatted(2),
                                 unknown(3) }
                ACCESS read-only
                STATUS mandatory
                DESCRIPTION
                    "Formatting status of the device.  Corresponds 
                    directly the presence of one of the value labels 
                    under the label 'Device Status:' in the MANAGER 
                    DEVICE STATUS display."
                ::= { deviceEntry 5 }

            deviceProtection OBJECT-TYPE
                SYNTAX INTEGER { write-enabled(1), write-protected(2),
                                 unknown(3) }
                ACCESS read-only
                STATUS mandatory
                DESCRIPTION
                    "Write-protect status of the device.  Corresponds 
                    directly the presence of one of the value labels 
                    under the label 'Device Status:' in the MANAGER 
                    DEVICE STATUS display."
                ::= { deviceEntry 6 }

            deviceFormatMedium OBJECT-TYPE
                SYNTAX INTEGER { ready(1), execute(2) }
                ACCESS read-write
                STATUS mandatory
                DESCRIPTION
                    "Control to cause formatting of the medium in the 
                    device.  In response to a get-request or 
                    get-next-request, the agent always returns 'ready' 
                    for this value.  Setting the value to 'ready' has no 
                    effect.  Setting it to 'execute' causes the device 
                    to be formatted.  Corresponds directly to the FORMAT 


                            DEVICE command."
                ::= { deviceEntry 7 }

            deviceGetFile OBJECT-TYPE
                SYNTAX INTEGER { ready(1), execute(2), abort(3) }
                ACCESS read-write
                STATUS mandatory
                DESCRIPTION
                    "Control to cause getting a file to the device from 
                    a remote host system.  In response to a get-request 
                    or get-next-request, the agent always returns 
                    'ready' for this value.  Setting the value to 
                    'ready' has no effect.  Setting it to 'execute' 
                    causes the get to be attempted.  Corresponds 
                    directly to the GET DEVICE command.

                    When set to 'execute', the objects 
                    deviceGetFileHostIdentificationType, 
                    deviceGetFileHostIdentification,
                    deviceGetFileName and deviceGetFileArea
                    must be somewhere in the same set 
                    request message."
                ::= { deviceEntry 8 }

            deviceGetFileHostIdentificationType OBJECT-TYPE
                SYNTAX AddressType
                ACCESS read-write
                STATUS mandatory
                DESCRIPTION
                    "The type of identification value in 
                    deviceIdentification.  Corresponds indirectly to 
                    ADDRESS in the GET DEVICE command.

                    This object may not be set outside the context of 
                    setting deviceGetFile to 'execute'.  In response to 
                    a get-request or get-next-request, the value of this 
                    object is 'undefined'."
                ::= { deviceEntry 9 }

            deviceGetFileHostIdentification OBJECT-TYPE
                SYNTAX OCTET STRING (SIZE (1..6))
                ACCESS read-write
                STATUS mandatory
                DESCRIPTION
                    "Identification of the host to get the file from, 
                    with type depending on deviceIdentificationType.  
                    Corresponds directly to ADDRESS in the GET DEVICE 
                    command.

                    This object may not be set outside the context of 
                    setting deviceGetFile to 'execute'.  In response to 
                    a get-request or get-next-request, the value of this 
                    object is zero length."
                ::= { deviceEntry 10 }

            deviceGetFileName OBJECT-TYPE
                SYNTAX DisplayString (SIZE (1..64))
                ACCESS read-write
                STATUS mandatory
                DESCRIPTION
                    "The name of the file to get.  Corresponds directly 
                    to LOAD FILE in the GET DEVICE command.

                    This object may not be set outside the context of 
                    setting deviceGetFile to 'execute'.  In response to 
                    a get-request or get-next-request, the value of this 
                    object is zero length."
                ::= { deviceEntry 11 }

            deviceGetFileArea OBJECT-TYPE
                SYNTAX INTEGER (1..16)
                ACCESS read-write
                STATUS mandatory
                DESCRIPTION
                    "The area number in which to put the file.  
                    Corresponds directly to AREA in the GET DEVICE 
                    command. If it is not relevant to the particular 
                    device, it is ignored.

                    This object may not be set outside the context of 
                    setting deviceGetFile to 'execute'.  In response to 
                    a get-request or get-next-request, the value of this 
                    object is zero."
                ::= { deviceEntry 12 }

            deviceFormatOption OBJECT-TYPE
                SYNTAX INTEGER (1..3)
                ACCESS read-write
                STATUS mandatory
                DESCRIPTION
                    "Formatting option to apply.  Corresponds directly 
                    to the OPTION in the FORMAT DEVICE command.

                    This object may not be set outside the context of 
                    setting deviceFormatMedium to 'execute'.  In 
                    response to a get-request or get-next-request, the 
                    value of this object is zero."
                DEFVAL { 1 }
                ::= { deviceEntry 13 }

            deviceFormatRedundantParams OBJECT-TYPE
                SYNTAX INTEGER { nonredundant(1), redundant(2) }
                ACCESS read-write
                STATUS mandatory
                DESCRIPTION
                    "Control for creating redundant parameter storage 
                    areas when formatting.    Corresponds directly to 
                    NONREDUNDANT in the FORMAT DEVICE command.

                    This object may not be set outside the context of 
                    setting deviceFormatMedium to 'execute'.  In 
                    response to a get-request or get-next-request, the 
                    value of this object is zero."
                DEFVAL { redundant }
                ::= { deviceEntry 14 }

            devicePreviousStatus OBJECT-TYPE
                SYNTAX DialogStatus
                ACCESS read-only
                STATUS mandatory
                DESCRIPTION
                    "Result of the immediately previous concluded boot 
                    dialog.  Corresponds directly to the value labeled 
                    'Get File Previous Status:' in the SHOW CARD STATUS 
                    display."
                ::= { deviceEntry 15 }


            -- the Bootstrap Server Dump group

            -- Implementation of this group is mandatory for all MRV In-Reach
            -- systems that provide the MRV In-Reach bootstrap dump service

            dumpService OBJECT-TYPE
                SYNTAX INTEGER { disabled(1), enabled(2) }
                ACCESS read-write
                STATUS mandatory
                DESCRIPTION
                    "Control for allowing dump service for any client.  
                    Corresponds directly to DUMP and the value labeled 
                    'Dump:' in the MANAGER CHARACTERISTICS display."
                ::= { xDump 1 }

            dumpDrive OBJECT-TYPE
                SYNTAX INTEGER (1..2)
                ACCESS read-write
                STATUS mandatory
                DESCRIPTION
                    "Identification number of the disk drive where dumps 
                    are stored.  Corresponds directly to DUMP DRIVE and 
                    the value labeled 'Dump Drive:' in the MANAGER 
                    CHARACTERISTICS display."
                ::= { xDump 2 }

            dumpMerit OBJECT-TYPE
                SYNTAX INTEGER (0..15)
                ACCESS read-write
                STATUS mandatory
                DESCRIPTION
                    "Relative preference for this dump server over 
                    others.  Corresponds directly to DUMP MERIT and the 
                    value labeled 'Dump Merit:' in the MANAGER 
                    CHARACTERISTICS display."
                ::= { xDump 3 }

            dumpSize OBJECT-TYPE
                SYNTAX INTEGER { small(1), full(2) }
                ACCESS read-write
                STATUS mandatory
                DESCRIPTION
                    "Type of dump file to keep.  Corresponds directly to 
                    DUMP SIZE and the value labeled 'Dump Size:' in the 
                    MANAGER CHARACTERISTICS display."
                ::= { xDump 4 }


            dumpCompleted OBJECT-TYPE
                SYNTAX Counter
                ACCESS read-only
                STATUS mandatory
                DESCRIPTION
                    "The number of dumps completed since system 
                    initialization.  Corresponds directly to the value 
                    labeled 'Dump Operations Completed:' in the MANAGER 
                    STATUS display."
                ::= { xDump 5 }

            dumpActive OBJECT-TYPE
                SYNTAX Gauge
                ACCESS read-only
                STATUS mandatory
                DESCRIPTION
                    "The number of dumps in progress.  Corresponds 
                    directly to the value labeled 'Currently Dumping:' 
                    in the MANAGER STATUS display."
                ::= { xDump 6 }

            dumpFileNumber OBJECT-TYPE
                SYNTAX Gauge
                ACCESS read-only
                STATUS mandatory
                DESCRIPTION
                    "The number of dump files currently stored.  
                    Corresponds directly to the value labeled 'Network 
                    dump files' and 'files' in the MANAGER FILES 
                    display."
                ::= { xDump 7 }


            -- The Dump File table

            dumpFileTable OBJECT-TYPE
                SYNTAX SEQUENCE OF DumpFileEntry
                ACCESS not-accessible
                STATUS mandatory
                DESCRIPTION
                    "A list of dump file entries.  The number of entries 
                    is given by dumpFileNumber."
                ::= { xDump 8 }

            dumpFileEntry OBJECT-TYPE
                SYNTAX DumpFileEntry
                ACCESS not-accessible
                STATUS mandatory
                DESCRIPTION
                    "Parameter values for a dump file entry."
                INDEX { dumpFileIdentificationType,
                        dumpFileIdentification }
                ::= { dumpFileTable 1 }

            DumpFileEntry ::=
                SEQUENCE {
                    dumpFileIdentificationType
                        AddressType,
                    dumpFileIdentification
                        OCTET STRING,
                    dumpFileEntryStatus
                        INTEGER,
                    dumpFileCreation
                        DateTime,
                    dumpFileSize
                        INTEGER
                }

            dumpFileIdentificationType OBJECT-TYPE
                SYNTAX AddressType
                ACCESS read-only
                STATUS mandatory
                DESCRIPTION
                    "The type of identification value in 
                    dumpFileIdentification.  Corresponds indirectly to a 
                    file name part in the section labeled 'Network dump 
                    files' in the MANAGER FILES display."
                ::= { dumpFileEntry 1 }


            dumpFileIdentification OBJECT-TYPE
                SYNTAX OCTET STRING (SIZE (1..6))
                ACCESS read-only
                STATUS mandatory
                DESCRIPTION
                    "Identification of the dump file, an Ethernet 
                    address, as indicated by dumpFileIdentificationType.  
                    Corresponds indirectly to a file name part in the 
                    section labeled 'Network dump files' in the MANAGER 
                    FILES display."
                ::= { dumpFileEntry 2 }

            dumpFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER DUMP FILES command.  Actual 
                    removal of the entry is implementation specific."
                ::= { dumpFileEntry 3 }

            dumpFileCreation OBJECT-TYPE
                SYNTAX DateTime
                ACCESS read-only
                STATUS mandatory
                DESCRIPTION
                    "The time the dump file was created.  Corresponds 
                    directly to a date and time in the section labeled 
                    'Network dump files' in the MANAGER FILES display."
                ::= { dumpFileEntry 4 }

            dumpFileSize OBJECT-TYPE
                SYNTAX INTEGER
                ACCESS read-only
                STATUS mandatory
                DESCRIPTION
                    "The number of bytes stored in the dump file.  
                    Corresponds directly to the value labeled 'bytes' in 
                    the section labeled 'Network dump files' in the 
                    MANAGER FILES display."
                ::= { dumpFileEntry 5 }


            -- the Bootstrap Server Load group

            -- Implementation of this group is mandatory for all MRV In-Reach
            -- systems that provide the MRV In-Reach bootstrap load service

            loadService OBJECT-TYPE
                SYNTAX INTEGER { disabled(1), enabled(2) }
                ACCESS read-write
                STATUS mandatory
                DESCRIPTION
                    "Control for allowing load service for any client.  
                    Corresponds directly to LOAD and the value labeled 
                    'Load:' in the MANAGER CHARACTERISTICS display."
                ::= { xLoad 1 }

            loadMerit OBJECT-TYPE
                SYNTAX INTEGER (0..15)
                ACCESS read-write
                STATUS mandatory
                DESCRIPTION
                    "Relative preference for this load server over 
                    others.  Corresponds directly to LOAD MERIT and the 
                    value labeled 'Load Merit:' in the MANAGER 
                    CHARACTERISTICS display."
                ::= { xLoad 2 }

            loadCompleted OBJECT-TYPE
                SYNTAX Counter
                ACCESS read-only
                STATUS mandatory
                DESCRIPTION
                    "The number of loads completed since system 
                    initialization.  Corresponds directly to the value 
                    labeled 'Load Operations Completed:' in the MANAGER 
                    STATUS display."
                ::= { xLoad 3 }

            loadActive OBJECT-TYPE
                SYNTAX Gauge
                ACCESS read-only
                STATUS mandatory
                DESCRIPTION
                    "The number of loads in progress.  Corresponds 
                    directly to the value labeled 'Currently Loading:' 
                    in the MANAGER STATUS display."
                ::= { xLoad 4 }


            loadFileNumber OBJECT-TYPE
                SYNTAX Gauge
                ACCESS read-only
                STATUS mandatory
                DESCRIPTION
                    "The number of load files currently stored.  
                    Corresponds directly to the value labeled 'Load 
                    image files' and 'files' in the MANAGER FILES 
                    display."
                ::= { xLoad 5 }


            -- The Load File table

            loadFileTable OBJECT-TYPE
                SYNTAX SEQUENCE OF LoadFileEntry
                ACCESS not-accessible
                STATUS mandatory
                DESCRIPTION
                    "A list of load file entries.  The number of entries 
                    is given by loadFileNumber."
                ::= { xLoad 6 }

            loadFileEntry OBJECT-TYPE
                SYNTAX LoadFileEntry
                ACCESS not-accessible
                STATUS mandatory
                DESCRIPTION
                    "Parameter values for a load file entry."
                INDEX { loadFileName }
                ::= { loadFileTable 1 }

            LoadFileEntry ::=
                SEQUENCE {
                    loadFileName
                        DisplayString,
                    loadFileCreation
                        DateTime,
                    loadFileSize
                        INTEGER,
                    loadFileSoftwareVersionType
                        INTEGER,
                    loadFileSoftwareVersion
                        OCTET STRING
                }

            loadFileName OBJECT-TYPE
                SYNTAX DisplayString (SIZE (1..16))
                ACCESS read-only
                STATUS mandatory
                DESCRIPTION
                    "The name of a load file.  Corresponds directly to a 
                    file name part in the section labeled 'Load image 
                    files' in the MANAGER FILES display."
                ::= { loadFileEntry 1 }

            loadFileCreation OBJECT-TYPE
                SYNTAX DateTime


                ACCESS read-only
                STATUS mandatory
                DESCRIPTION
                    "The time the load file was created.  Corresponds 
                    directly to a date and time in the section labeled 
                    'Load image files' in the MANAGER FILES display."
                ::= { loadFileEntry 2 }

            loadFileSize OBJECT-TYPE
                SYNTAX INTEGER
                ACCESS read-only
                STATUS mandatory
                DESCRIPTION
                    "The number of bytes stored in the load file.  
                    Corresponds directly to the value labeled 'bytes' in 
                    the section labeled 'Load image files' in the 
                    MANAGER FILES display."
                ::= { loadFileEntry 3 }

            loadFileSoftwareVersionType OBJECT-TYPE
                SYNTAX INTEGER { alpha(1), beta(2),
                                 production(3), special(4) }
                ACCESS read-only
                STATUS mandatory
                DESCRIPTION
                    "The software version type of the image in the load 
                    file.  Corresponds directly to a software version in 
                    the section labeled 'Load image files' in the 
                    MANAGER FILES display.

                    alpha         'A':   alpha test
                    beta          'B':   beta test
                    production    null:  normal, production software
                    special       'S':   special, custom software
                    "
                ::= { loadFileEntry 4 }

            loadFileSoftwareVersion OBJECT-TYPE
                SYNTAX OCTET STRING (SIZE (0..4))
                ACCESS read-only
                STATUS mandatory
                DESCRIPTION
                    "The software version of the image in the load file.  
                    Corresponds directly to a software version in the 
                    section labeled 'Load image files' in the MANAGER 
                    FILES display.


                    For example, the version display for 
                    loadFileSoftwareVersionType 'production' and 
                    loadFileSoftwareVersion '2.2.0.0' is 'V2.2'.

                    The version display for loadFileSoftwareVersionType 
                    'beta' and loadFileSoftwareVersion '3.1.0.4' is 
                    'V3.1B4'."
                ::= { loadFileEntry 5 }


            -- the Bootstrap Server Parameter Storage group

            -- Implementation of this group is mandatory for all MRV In-Reach
            -- systems that provide the MRV In-Reach bootstrap parameter
            -- storage service

            paramService OBJECT-TYPE
                SYNTAX INTEGER { disabled(1), enabled(2) }
                ACCESS read-write
                STATUS mandatory
                DESCRIPTION
                    "Control for allowing parameter storage service for 
                    any client.  Corresponds directly to PARAMETER 
                    SERVICE and the value labeled 'Parameter Service:' 
                    in the MANAGER CHARACTERISTICS display."
                ::= { xParam 1 }

            paramDefaultService OBJECT-TYPE
                SYNTAX INTEGER { disabled(1), enabled(2) }
                ACCESS read-write
                STATUS mandatory
                DESCRIPTION
                    "Control for allowing default parameter loading 
                    service for any client.  Corresponds directly to 
                    PARAMETER DEFAULT SERVICE and the value labeled 
                    'Parameter Default Service:' in the MANAGER 
                    CHARACTERISTICS display."
                ::= { xParam 2 }

            paramDrive OBJECT-TYPE
                SYNTAX INTEGER (1..2)
                ACCESS read-write
                STATUS mandatory
                DESCRIPTION
                    "Identification number of the disk drive where 
                    parameters are stored.  Corresponds directly to 
                    PARAMETER DRIVE and the value labeled 'Parameter 
                    Drive:' in the MANAGER CHARACTERISTICS display."
                ::= { xParam 3 }

            paramActive OBJECT-TYPE
                SYNTAX Gauge
                ACCESS read-only
                STATUS mandatory
                DESCRIPTION
                    "The number of params in progress.  Corresponds 


                            directly to the value labeled 'Currently Paraming:' 
                    in the MANAGER STATUS display."
                ::= { xParam 4 }

            paramStorageActive OBJECT-TYPE
                SYNTAX Gauge
                ACCESS read-only
                STATUS mandatory
                DESCRIPTION
                    "The number of parameter storage operations in 
                    progress.  Corresponds directly to the value labeled 
                    'Currently saving parameters:' in the MANAGER STATUS 
                    display."
                ::= { xParam 5 }

            paramFileNumber OBJECT-TYPE
                SYNTAX Gauge
                ACCESS read-only
                STATUS mandatory
                DESCRIPTION
                    "The number of parameter files currently stored.  
                    Corresponds directly to the value labeled 'Parameter 
                    files' and 'files' in the MANAGER FILES display."
                ::= { xParam 6 }


            -- The Param File table

            paramFileTable OBJECT-TYPE
                SYNTAX SEQUENCE OF ParamFileEntry
                ACCESS not-accessible
                STATUS mandatory
                DESCRIPTION
                    "A list of param file entries.  The number of 
                    entries is given by paramFileNumber."
                ::= { xParam 7 }

            paramFileEntry OBJECT-TYPE
                SYNTAX ParamFileEntry
                ACCESS not-accessible
                STATUS mandatory
                DESCRIPTION
                    "Parameter values for a param file entry."
                INDEX { paramFileIdentificationType,
                        paramFileIdentification }
                ::= { paramFileTable 1 }

            ParamFileEntry ::=
                SEQUENCE {
                    paramFileIdentificationType
                        AddressType,
                    paramFileIdentification
                        OCTET STRING,
                    paramFileEntryStatus
                        INTEGER,
                    paramFileWrite
                        DateTime,
                    paramFileSize
                        INTEGER,
                    paramFileParameterVersion
                        INTEGER
                }

            paramFileIdentificationType OBJECT-TYPE
                SYNTAX AddressType
                ACCESS read-only
                STATUS mandatory
                DESCRIPTION
                    "The type of identification value in 
                    paramFileIdentification.  Corresponds indirectly to 
                    a file name part in the section labeled 'Parameter 
                    files' in the MANAGER FILES display."


                ::= { paramFileEntry 1 }

            paramFileIdentification OBJECT-TYPE
                SYNTAX OCTET STRING (SIZE (1..6))
                ACCESS read-only
                STATUS mandatory
                DESCRIPTION
                    "Identification of the param file, an Ethernet 
                    address, as indicated by 
                    paramFileIdentificationType.  Corresponds indirectly 
                    to a file name part in the section labeled 
                    'Parameter files' in the MANAGER FILES display."
                ::= { paramFileEntry 2 }

            paramFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER PARAMETER FILES command.  Actual 
                    removal of the entry is implementation specific."
                ::= { paramFileEntry 3 }

            paramFileWrite OBJECT-TYPE
                SYNTAX DateTime
                ACCESS read-only
                STATUS mandatory
                DESCRIPTION
                    "The time the parameter file was last written.  
                    Corresponds directly to a date and time in the 
                    section labeled 'Parameter files' in the MANAGER 
                    FILES display."
                ::= { paramFileEntry 4 }

            paramFileSize OBJECT-TYPE
                SYNTAX INTEGER
                ACCESS read-only
                STATUS mandatory
                DESCRIPTION
                    "The number of bytes stored in the param file.  
                    Corresponds directly to the value labeled 'bytes' in 
                    the section labeled 'Parameter files' in the MANAGER 
                    FILES display."
                ::= { paramFileEntry 5 }


            paramFileParameterVersion OBJECT-TYPE
                SYNTAX INTEGER
                ACCESS read-only
                STATUS mandatory
                DESCRIPTION
                    "The version number of the parameter data in the 
                    file.  Corresponds directly to the value labeled 
                    'ver' in the section labeled 'Parameter files' in 
                    the MANAGER FILES display."
                ::= { paramFileEntry 6 }


--
-- FILE: /users/sse/mibs/src/inReach/ir-chassis-mib.mib
--

-- $Id: ir-chassis-mib.mib,v 1.1 2002/06/27 15:42:02 sse Exp $


       xChassis         OBJECT IDENTIFIER ::= { mrvInReachProductDivision 16 }

       -- MRV In-Reach Character subgroups

       xChassisBasic    OBJECT IDENTIFIER ::= { xChassis 1 }
       xSegment         OBJECT IDENTIFIER ::= { xChassis 2 }
       xPort            OBJECT IDENTIFIER ::= { xChassis 3 }
       xController      OBJECT IDENTIFIER ::= { xChassis 4 }
       xInterface       OBJECT IDENTIFIER ::= { xChassis 5 }
       xSlotBootControl OBJECT IDENTIFIER ::= { xChassis 6 }
       xSlot            OBJECT IDENTIFIER ::= { xChassis 7 }
       xPowerSupply     OBJECT IDENTIFIER ::= { xChassis 8 }
       xFirmwareUpdate  OBJECT IDENTIFIER ::= { xChassis 9 }


            -- This is a MIB module for all MRV Communications systems that
            -- are on the management bus of a Network 9000 chassis.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


       -- Textual Conventions

       NetworkType ::=
           INTEGER { unknown(1), other(2), ethernet(3),
                            tokenRing(4), fddi(5), wan(6),
                            ethernetRepeater(7),
                            tokenRingConcentrator(8),
                            fddiConcentrator(9),
							atm(10), isdn(11),
							switchplane(12), switchedEthernet(13) }
       -- This data type is used in the MRV In-Reach Chassis MIB
       -- to indicate the type of segment or port.

       SerialNumber ::=
           OCTET STRING (SIZE (0..6))
       -- This data type is used in the MRV In-Reach Chassis MIB
       -- to indicate a 6-byte serial number, stored high-
       -- order byte first.  A zero-length value indicates
       -- unknown.

       Letter ::=
           INTEGER { a(1), b(2), c(3), d(4), e(5), f(6), g(7),
                     h(8), i(9), j(10), k(11), l(12), m(13),
                     n(14), o(15), p(16), q(17), r(18), s(19),
                     t(20), u(21), v(22), w(23), x(24), y(25),
                     z(26) }
       -- This data type is used in the MRV In-Reach Chassis MIB
       -- to identify an object with a letter.


       -- the Chassis Basic group

       -- Implementation of this group is mandatory for all MRV In-Reach
       -- Network 9000 management bus systems

       -- Chassis type, revision, and status are found in the
       -- MRV In-Reach System MIB objects sysChassisType,
       -- sysChassisVersion, and sysChassisState

       basicBase802Address OBJECT-TYPE
           SYNTAX MacAddress
           ACCESS read-only
           STATUS mandatory
           DESCRIPTION
               "Base IEEE 802 global address for the chassis."
           ::= { xChassisBasic 1 }

       basicSlot OBJECT-TYPE
           SYNTAX INTEGER
           ACCESS read-only
           STATUS mandatory
           DESCRIPTION
               "Chassis slot number (slotIndex) of the system whose 
               agent is supplying this MIB."
           ::= { xChassisBasic 2 }

       basicSlotNumber OBJECT-TYPE
           SYNTAX INTEGER
           ACCESS read-only
           STATUS mandatory
           DESCRIPTION
               "Number of slots in the chassis."
           ::= { xChassisBasic 3 }

       basicNewBase802Address OBJECT-TYPE
           SYNTAX MacAddress
           ACCESS read-write
           STATUS mandatory
           DESCRIPTION
               "New base IEEE 802 global address for the chassis.  
               Must be set in conjunction with featType 
               'changeEthernetAddress' and featKey from the MRV In-Reach 
               System MIB."
           ::= { xChassisBasic 4 }


       -- the Chassis Segment group

       -- Implementation of this group is mandatory for all MRV In-Reach
       -- Network 9000 management bus systems

       -- the Segment table

       segmentTable OBJECT-TYPE
           SYNTAX SEQUENCE OF SegmentEntry
           ACCESS not-accessible
           STATUS mandatory
           DESCRIPTION
               "A list of segment entries, one for each segment of 
               each type on the chassis."
           ::= { xSegment 1 }

       segmentEntry OBJECT-TYPE
           SYNTAX SegmentEntry
           ACCESS not-accessible
           STATUS mandatory
           DESCRIPTION
               "Values for a chassis segment."
           INDEX { segmentType, segmentIndex }
           ::= { segmentTable 1 }

       SegmentEntry ::=
           SEQUENCE {
               segmentType
                   NetworkType,
               segmentIndex
                   Letter
           }

       segmentType OBJECT-TYPE
           SYNTAX NetworkType
           ACCESS read-only
           STATUS mandatory
           DESCRIPTION
               "The segment type."
           ::= { segmentEntry 1 }

       segmentIndex OBJECT-TYPE
           SYNTAX Letter
           ACCESS read-only
           STATUS mandatory
           DESCRIPTION
               "An index value that uniquely identifies a 
               segment."
           ::= { segmentEntry 2 }


       -- the Chassis Port group

       -- Implementation of this group is mandatory for all MRV In-Reach
       -- Network 9000 management bus systems.  It describes only
       -- the local system's own ports and is intended for network
       -- ports as opposed to terminal or printer ports.

       portIOCardType OBJECT-TYPE
           SYNTAX IOType
           ACCESS read-only
           STATUS mandatory
           DESCRIPTION
               "The hardware type of the I/O card in this slot."
           ::= { xPort 1 }

       portIOCardSerialNumber OBJECT-TYPE
           SYNTAX SerialNumber
           ACCESS read-only
           STATUS mandatory
           DESCRIPTION
               "The MRV In-Reach serial number of the I/O card in this 
               slot."
           ::= { xPort 2 }

       portIOCardOperStatus OBJECT-TYPE
           SYNTAX INTEGER { unknown(1), mismatch(2), good(3) }
           ACCESS read-only
           STATUS mandatory
           DESCRIPTION
               "Status of the I/O card relative to the function 
               card in this slot."
           ::= { xPort 3 }

       -- the Port table

       portTable OBJECT-TYPE
           SYNTAX SEQUENCE OF PortEntry
           ACCESS not-accessible
           STATUS mandatory
           DESCRIPTION
               "A list of port entries, one for each port of each 
               type on the slots I/O card."
           ::= { xPort 4 }

       portEntry OBJECT-TYPE
           SYNTAX PortEntry
           ACCESS not-accessible
           STATUS mandatory
           DESCRIPTION
               "Values for an I/O card port."
           INDEX { portType, portIndex }
           ::= { portTable 1 }

       PortEntry ::=
           SEQUENCE {
               portType
                   NetworkType,
               portIndex
                   INTEGER
           }

       portType OBJECT-TYPE
           SYNTAX NetworkType
           ACCESS read-only
           STATUS mandatory
           DESCRIPTION
               "The port type."
           ::= { portEntry 1 }

       portIndex OBJECT-TYPE
           SYNTAX INTEGER
           ACCESS read-only
           STATUS mandatory
           DESCRIPTION
               "An index value that uniquely identifies a port."
           ::= { portEntry 2 }


       -- the Chassis Controller group

       -- Implementation of this group is mandatory for all MRV In-Reach
       -- Network 9000 management bus systems.  It describes only
       -- the local system's own controllers.

       -- the Controller table

       controllerTable OBJECT-TYPE
           SYNTAX SEQUENCE OF ControllerEntry
           ACCESS not-accessible
           STATUS mandatory
           DESCRIPTION
               "A list of controller entries, one for each 
               controller of each type on the local system."
           ::= { xController 1 }

       controllerEntry OBJECT-TYPE
           SYNTAX ControllerEntry
           ACCESS not-accessible
           STATUS mandatory
           DESCRIPTION
               "Values for a controller."
           INDEX { controllerType, controllerIndex }
           ::= { controllerTable 1 }

       ControllerEntry ::=
           SEQUENCE {
               controllerType
                   NetworkType,
               controllerIndex
                   INTEGER,
               controllerNetwork
                   OBJECT IDENTIFIER
           }

       controllerType OBJECT-TYPE
           SYNTAX NetworkType
           ACCESS read-only
           STATUS mandatory
           DESCRIPTION
               "The controller type."
           ::= { controllerEntry 1 }

       controllerIndex OBJECT-TYPE
           SYNTAX INTEGER
           ACCESS read-only
           STATUS mandatory
           DESCRIPTION
               "An index value that uniquely identifies a 
               controller."
           ::= { controllerEntry 2 }

       controllerNetwork OBJECT-TYPE
           SYNTAX OBJECT IDENTIFIER
           ACCESS read-write
           STATUS mandatory
           DESCRIPTION
               "The instance identifier of the first object in the 
               conceptual row entry for the segment, port, or 
               controller this controller is to use, that is, 
               segmentType, portType or controllerType."
           ::= { controllerEntry 3 }


       -- the Chassis Interface group

       -- Implementation of this group is mandatory for all MRV In-Reach
       -- Network 9000 management bus systems.  It describes only
       -- the local system's own interfaces.

       -- the Interface table

       interfaceTable OBJECT-TYPE
           SYNTAX SEQUENCE OF InterfaceEntry
           ACCESS not-accessible
           STATUS mandatory
           DESCRIPTION
               "A list of interface entries, corresponding to the 
               MIB II Interface group.  These are directly 
               equivalent to hardware network controllers, and must 
               be the lowest numbered interfaces on the system."
           ::= { xInterface 1 }

       interfaceEntry OBJECT-TYPE
           SYNTAX InterfaceEntry
           ACCESS not-accessible
           STATUS mandatory
           DESCRIPTION
               "Values for an interface."
           INDEX { interfaceIndex }
           ::= { interfaceTable 1 }

       InterfaceEntry ::=
           SEQUENCE {
               interfaceIndex
                   INTEGER,
               interfaceNetwork
                   OBJECT IDENTIFIER
           }

       interfaceIndex OBJECT-TYPE
           SYNTAX INTEGER
           ACCESS read-only
           STATUS mandatory
           DESCRIPTION
               "An index value that uniquely identifies an 
               interface.  The interface identified by a particular 
               value of this index is the same interface as 
               identified by the same value of ifIndex."
           ::= { interfaceEntry 1 }

       interfaceNetwork OBJECT-TYPE
           SYNTAX OBJECT IDENTIFIER
           ACCESS read-write
           STATUS mandatory
           DESCRIPTION
               "The instance identifier of the first object in the 
               conceptual row entry for the segment, port, or 
               controller this interface is to use, that is, 
               segmentType, portType, or controllerType."
           ::= { interfaceEntry 2 }


       -- the Chassis Boot Control group

       -- Full implementation of this group is optional for MRV In-Reach
       -- Network 9000 management bus systems.  It is fully
       -- implemented on such systems that supply cross chassis
       -- management.  All systems must implement the instance
       -- corresponding to their own slot number.

       -- the Slot Boot Control table

       slotBootControlTable OBJECT-TYPE
           SYNTAX SEQUENCE OF SlotBootControlEntry
           ACCESS not-accessible
           STATUS mandatory
           DESCRIPTION
               "A list of slot boot control entries."
           ::= { xSlotBootControl 1 }

       slotBootControlEntry OBJECT-TYPE
           SYNTAX SlotBootControlEntry
           ACCESS not-accessible
           STATUS mandatory
           DESCRIPTION
               "Values for a chassis slot."
           INDEX { slotBootControlSlot, slotBootControlIndex }
           ::= { slotBootControlTable 1 }

       SlotBootControlEntry ::=
           SEQUENCE {
               slotBootControlSlot
                   INTEGER,
               slotBootControlIndex
                   INTEGER,
               slotBootControlStatus
                   INTEGER,
               slotBootControlController
                   OBJECT IDENTIFIER,
               slotBootControlNetwork
                   OBJECT IDENTIFIER,
               slotBootControlMopFile
                   DisplayString,
               slotBootControlInternetFile
                   DisplayString,
               slotBootControlInternetAddress
                   IpAddress,
               slotBootControlInternetServer
                   IpAddress,
               slotBootControlInternetGateway
                   IpAddress,
               slotBootControlInternetDelimiter
                   DisplayString
      }

       slotBootControlSlot OBJECT-TYPE
           SYNTAX INTEGER
           ACCESS read-only
           STATUS mandatory
           DESCRIPTION
               "An index value that uniquely identifies a slot, 
               defined the same as slotIndex."
           ::= { slotBootControlEntry 1 }

       slotBootControlIndex OBJECT-TYPE
           SYNTAX INTEGER
           ACCESS read-only
           STATUS mandatory
           DESCRIPTION
               "An index value that uniquely identifies a boot 
               control entry, from 1 to the number of entries for 
               the slot."
           ::= { slotBootControlEntry 2 }

       slotBootControlStatus OBJECT-TYPE
           SYNTAX INTEGER { disabled(1), enabled(2) }
           ACCESS read-write
           STATUS mandatory
           DESCRIPTION
               "The status of the entry.  Set to 'disabled' to 
               disable the entry."
           DEFVAL { enabled }
           ::= { slotBootControlEntry 3 }

       slotBootControlController OBJECT-TYPE
           SYNTAX OBJECT IDENTIFIER
           ACCESS read-write
           STATUS mandatory
           DESCRIPTION
               "The instance identifier of the first object in the 
               conceptual row entry for the controller this entry 
               selects for bootstrap operation, that is, 
               controllerType.  This entry must be compatible with 
               slotBootControlNetwork, including being of the same 
               network type.  The value 0.0 indicates default 
               action."
           DEFVAL { { 0 0 } }  -- 0.0
           ::= { slotBootControlEntry 4 }

       slotBootControlNetwork OBJECT-TYPE
           SYNTAX OBJECT IDENTIFIER
           ACCESS read-write
           STATUS mandatory
           DESCRIPTION
               "The instance identifier of the first object in the 
               conceptual row entry for the segment or port this                entry selects for bootstrap operation, that is, 
               segmentType or portType.  This entry must be 
               compatible with slotBootControlController, including 
               being of the same network type.  The value 0.0 
               indicates default action."
           DEFVAL { { 0 0 } }  -- 0.0
           ::= { slotBootControlEntry 5 }

       slotBootControlMopFile OBJECT-TYPE
           SYNTAX DisplayString (SIZE (0..15))
           ACCESS read-write
           STATUS mandatory
           DESCRIPTION
               "The software file name to request for down-line 
               load of the server via MOP or XMOP."
           DEFVAL { '00'h }  -- the null string
           ::= { slotBootControlEntry 6 }

       slotBootControlInternetFile OBJECT-TYPE
           SYNTAX DisplayString (SIZE (0..64))
           ACCESS read-write
           STATUS mandatory
           DESCRIPTION
               "The filename to request when loading an image via 
               TFTP."
           DEFVAL { '00'h }  -- the null string
           ::= { slotBootControlEntry 7 }

       slotBootControlInternetAddress OBJECT-TYPE
           SYNTAX IpAddress
           ACCESS read-write
           STATUS mandatory
           DESCRIPTION
               "The internet address of the system is to use for 
               itself when loading via TFTP.  The value 0.0.0.0 
               indicates default action."
           DEFVAL { 0 }
           ::= { slotBootControlEntry 8 }

       slotBootControlInternetServer OBJECT-TYPE
           SYNTAX IpAddress
           ACCESS read-write
           STATUS mandatory
           DESCRIPTION
               "The internet address of the server to use when 
               loading an image via TFTP.  The value 0.0.0.0 
               indicates default action."
           DEFVAL { 0 }
           ::= { slotBootControlEntry 9 }

       slotBootControlInternetGateway OBJECT-TYPE
           SYNTAX IpAddress
           ACCESS read-write
           STATUS mandatory
           DESCRIPTION
               "The internet address of the gateway to use when 
               loading an image via TFTP.  The value 0.0.0.0 
               indicates default action."
           DEFVAL { 0 }
           ::= { slotBootControlEntry 10 }

       slotBootControlInternetDelimiter OBJECT-TYPE
           SYNTAX DisplayString (SIZE (0..1))
           ACCESS read-write
           STATUS mandatory
           DESCRIPTION
               "The character separating the load file directory name  
               from the file name."
           DEFVAL { '00'h }  -- the null string
           ::= { slotBootControlEntry 11 }

       -- the Slot Boot Control Flag table

       -- Entries in this table are directly connected to a 
       -- particular slotBootControlIndex, and are created and 
       -- deleted together with that entry.

       -- By convention, this table contains flags in recurring
       -- groups of three operations for each protocol.  Adding
       -- a new protocol will add three new objects in the same
       -- order of operations.

       slotBootControlFlagTable OBJECT-TYPE
           SYNTAX SEQUENCE OF SlotBootControlFlagEntry
           ACCESS not-accessible
           STATUS mandatory
           DESCRIPTION
               "A list of slot boot control source flag entries."
           ::= { xSlotBootControl 2 }

       slotBootControlFlagEntry OBJECT-TYPE
           SYNTAX SlotBootControlFlagEntry
           ACCESS not-accessible
           STATUS mandatory
           DESCRIPTION
               "Values for a boot control flag."
           INDEX { slotBootControlSlot, slotBootControlIndex }
           ::= { slotBootControlFlagTable 1 }

       SlotBootControlFlagEntry ::=
           SEQUENCE {
               slotBootControlFlagLoadBootpTftp
                   INTEGER,
               slotBootControlFlagParamBootpTftp
                   INTEGER,
               slotBootControlFlagDumpBootpTftp
                   INTEGER,
               slotBootControlFlagLoadTftpDirect
                   INTEGER,
               slotBootControlFlagParamTftpDirect
                   INTEGER,
               slotBootControlFlagDumpTftpDirect
                   INTEGER,
               slotBootControlFlagLoadLocal
                   INTEGER,
               slotBootControlFlagParamLocal
                   INTEGER,
               slotBootControlFlagDumpLocal
                   INTEGER,
               slotBootControlFlagLoadMop
                   INTEGER,
               slotBootControlFlagParamMop
                   INTEGER,
               slotBootControlFlagDumpMop
                   INTEGER,
               slotBootControlFlagLoadXmop
                   INTEGER,
               slotBootControlFlagParamXmop
                   INTEGER,
               slotBootControlFlagDumpXmop
                   INTEGER,
               slotBootControlFlagLoadRarpTftp
                   INTEGER,
               slotBootControlFlagParamRarpTftp
                   INTEGER,
               slotBootControlFlagDumpRarpTftp
                   INTEGER
           }

       slotBootControlFlagLoadBootpTftp OBJECT-TYPE
           SYNTAX INTEGER { disabled(1), enabled(2) }
           ACCESS read-write
           STATUS mandatory
           DESCRIPTION
               "Control for performing load over BOOTP/TFTP."
           ::= { slotBootControlFlagEntry 1 }

       slotBootControlFlagParamBootpTftp OBJECT-TYPE
           SYNTAX INTEGER { disabled(1), enabled(2) }
           ACCESS read-write
           STATUS mandatory
           DESCRIPTION
               "Control for performing parameter load over 
               BOOTP/TFTP."
           ::= { slotBootControlFlagEntry 2 }

       slotBootControlFlagDumpBootpTftp OBJECT-TYPE
           SYNTAX INTEGER { disabled(1), enabled(2) }
           ACCESS read-write
           STATUS mandatory
           DESCRIPTION
               "Control for performing dump over BOOTP/TFTP."
           ::= { slotBootControlFlagEntry 3 }

       slotBootControlFlagLoadTftpDirect OBJECT-TYPE
           SYNTAX INTEGER { disabled(1), enabled(2) }
           ACCESS read-write
           STATUS mandatory
           DESCRIPTION
               "Control for performing load over direct TFTP."
           ::= { slotBootControlFlagEntry 4 }

       slotBootControlFlagParamTftpDirect OBJECT-TYPE
           SYNTAX INTEGER { disabled(1), enabled(2) }
           ACCESS read-write
           STATUS mandatory
           DESCRIPTION
               "Control for performing parameter load over direct 
               TFTP."
           ::= { slotBootControlFlagEntry 5 }

       slotBootControlFlagDumpTftpDirect OBJECT-TYPE
           SYNTAX INTEGER { disabled(1), enabled(2) }
           ACCESS read-write
           STATUS mandatory
           DESCRIPTION
               "Control for performing dump over direct TFTP."
           ::= { slotBootControlFlagEntry 6 }

       slotBootControlFlagLoadLocal OBJECT-TYPE
           SYNTAX INTEGER { disabled(1), enabled(2) }
           ACCESS read-write
           STATUS mandatory
           DESCRIPTION
               "Control for performing load from a local device."
           ::= { slotBootControlFlagEntry 7 }

       slotBootControlFlagParamLocal OBJECT-TYPE
           SYNTAX INTEGER { disabled(1), enabled(2) }
           ACCESS read-write
           STATUS mandatory
           DESCRIPTION
               "Control for performing parameter load from a local 
               device."
           ::= { slotBootControlFlagEntry 8 }

       slotBootControlFlagDumpLocal OBJECT-TYPE
           SYNTAX INTEGER { disabled(1), enabled(2) }
           ACCESS read-write
           STATUS mandatory
           DESCRIPTION
               "Control for performing dump from a local device."
           ::= { slotBootControlFlagEntry 9 }

       slotBootControlFlagLoadMop OBJECT-TYPE
           SYNTAX INTEGER { disabled(1), enabled(2) }
           ACCESS read-write
           STATUS mandatory
           DESCRIPTION
               "Control for performing load over Digital's MOP."
           ::= { slotBootControlFlagEntry 10 }

       slotBootControlFlagParamMop OBJECT-TYPE
           SYNTAX INTEGER { disabled(1), enabled(2) }
           ACCESS read-write
           STATUS mandatory
           DESCRIPTION
               "Control for performing parameter load over 
               Digital's MOP."
           ::= { slotBootControlFlagEntry 11 }

       slotBootControlFlagDumpMop OBJECT-TYPE
           SYNTAX INTEGER { disabled(1), enabled(2) }
           ACCESS read-write
           STATUS mandatory
           DESCRIPTION
               "Control for performing dump over Digital's MOP."
           ::= { slotBootControlFlagEntry 12 }

       slotBootControlFlagLoadXmop OBJECT-TYPE
           SYNTAX INTEGER { disabled(1), enabled(2) }
           ACCESS read-write
           STATUS mandatory
           DESCRIPTION
               "Control for performing load over MRV In-Reach extended 
               MOP."
           ::= { slotBootControlFlagEntry 13 }

       slotBootControlFlagParamXmop OBJECT-TYPE
           SYNTAX INTEGER { disabled(1), enabled(2) }
           ACCESS read-write
           STATUS mandatory
           DESCRIPTION
               "Control for performing parameter load over MRV In-Reach 
               extended MOP."
           ::= { slotBootControlFlagEntry 14 }

       slotBootControlFlagDumpXmop OBJECT-TYPE
           SYNTAX INTEGER { disabled(1), enabled(2) }
           ACCESS read-write
           STATUS mandatory
           DESCRIPTION
               "Control for performing dump over MRV In-Reach extended 
               MOP."
           ::= { slotBootControlFlagEntry 15 }

       slotBootControlFlagLoadRarpTftp OBJECT-TYPE
           SYNTAX INTEGER { disabled(1), enabled(2) }
           ACCESS read-write
           STATUS mandatory
           DESCRIPTION
               "Control for performing load over RARP/TFTP."
           ::= { slotBootControlFlagEntry 16 }

       slotBootControlFlagParamRarpTftp OBJECT-TYPE
           SYNTAX INTEGER { disabled(1), enabled(2) }
           ACCESS read-write
           STATUS mandatory
           DESCRIPTION
               "Control for performing parameter load over 
               RARP/TFTP."
           ::= { slotBootControlFlagEntry 17 }

       slotBootControlFlagDumpRarpTftp OBJECT-TYPE
           SYNTAX INTEGER { disabled(1), enabled(2) }
           ACCESS read-write
           STATUS mandatory
           DESCRIPTION
               "Control for performing dump over RARP/TFTP."
           ::= { slotBootControlFlagEntry 18 }


       slotBootControlStorageTable OBJECT-TYPE
           SYNTAX SEQUENCE OF SlotBootControlStorageEntry
           ACCESS not-accessible 
           STATUS mandatory 
           DESCRIPTION
               "A list of slot boot control Storage entries."
           ::= { xSlotBootControl 3 }
                
       slotBootControlStorageEntry OBJECT-TYPE
           SYNTAX SlotBootControlStorageEntry 
           ACCESS not-accessible
           STATUS mandatory 
           DESCRIPTION 
               "Values for a chassis slot."
           INDEX { slotBootControlStorageClientSlot,  slotBootControlStorageServerSlot}
           ::= { slotBootControlStorageTable 1 }
                
       SlotBootControlStorageEntry ::= 
           SEQUENCE {
               slotBootControlStorageClientSlot 
                   INTEGER, 
               slotBootControlStorageServerSlot
                   INTEGER, 
               slotBootControlStorageStatus
                   INTEGER,
               slotBootControlStorageFailures
                   Counter
              }

       slotBootControlStorageClientSlot OBJECT-TYPE
           SYNTAX INTEGER 
           ACCESS read-only 
           STATUS mandatory 
           DESCRIPTION 
               "An index value that uniquely identifies a slot,
               defined the same as slotIndex."
           ::= { slotBootControlStorageEntry 1 }
             
       slotBootControlStorageServerSlot OBJECT-TYPE
           SYNTAX INTEGER
           ACCESS read-only
           STATUS mandatory 
           DESCRIPTION    
               "An index value that uniquely identifies the slot in
               which the Storage record resides, with the same values
               as slotIndex."
           ::= { slotBootControlStorageEntry 2 } 
            
       slotBootControlStorageStatus OBJECT-TYPE
           SYNTAX INTEGER { present(1), failed(2), ok(3), notpresent(4) }
           ACCESS read-only
           STATUS mandatory
           DESCRIPTION 
               "The status of the entry."
           ::= { slotBootControlStorageEntry 3 } 

       slotBootControlStorageFailures OBJECT-TYPE
           SYNTAX Counter
           ACCESS read-only
           STATUS mandatory
           DESCRIPTION 
               "The number of times a read from or write to a given 
               Storage location failed"
           ::= { slotBootControlStorageEntry 4 } 


       -- the Chassis Slot group

       -- Implementation of this group is optional for MRV In-Reach
       -- Network 9000 management bus systems.  It is implemented
       -- on such systems that supply cross chassis management.

       -- the Slot table

       slotTable OBJECT-TYPE
           SYNTAX SEQUENCE OF SlotEntry
           ACCESS not-accessible
           STATUS mandatory
           DESCRIPTION
               "A list of slot entries."
           ::= { xSlot 1 }

       slotEntry OBJECT-TYPE
           SYNTAX SlotEntry
           ACCESS not-accessible
           STATUS mandatory
           DESCRIPTION
               "Values for a chassis slot."
           INDEX { slotIndex }
           ::= { slotTable 1 }

       SlotEntry ::=
           SEQUENCE {
               slotIndex
                   INTEGER,
               slotAdminAction
                   INTEGER,
               slotOperStatus
                   INTEGER,
               slotSecondsSinceReset
                   Gauge,
               slotHardwareType
                   HardwareType,
               slotHardwareSerialNumber
                   SerialNumber,
               slotHardwareRevision
                   INTEGER,
               slotIOCardType
                   IOType,
               slotIOCardSerialNumber
                   SerialNumber,
               slotIOCardOperStatus
                   INTEGER,
               slotBootstrapFirmwareRevision
                   INTEGER,
               slotElementalFirmwareRevision
                   INTEGER,
               slotMemorySize
                   INTEGER,
               slotLedNumber
                   Gauge,
               slotLedStatus
                   OCTET STRING,
               slotBase802Address
                   MacAddress,
               slotIpAddress
                   IpAddress,
               slotPlus5Status
                   INTEGER,
               slotPlus12Status
                   INTEGER,
               slotMinus12Status
                   INTEGER,
               slotPlus5Watts
                   Gauge,
               slotPlus12Watts
                   Gauge,
               slotMinus12Watts
                   Gauge,
               slotIOCardHardwareVersion
                   INTEGER,
               slotRestoreNVS
                   INTEGER,
               slotDefaultNVS
                   INTEGER
                   }

       slotIndex OBJECT-TYPE
           SYNTAX INTEGER
           ACCESS read-only
           STATUS mandatory
           DESCRIPTION
               "An index value that uniquely identifies a slot, in 
               the range 0 to basicSlotNumber, where the value 0 
               indicates the same slot as basicSlot.  As the 
               objects found at instance zero are duplicates, that 
               instance does not appear in responses a get-next, 
               that is, the lowest numbered slotIndex returned by 
               get-next is 1."
           ::= { slotEntry 1 }

       slotAdminAction OBJECT-TYPE
           SYNTAX INTEGER { ready(1), reset(2), resetHold(3) }
           ACCESS read-write
           STATUS mandatory
           DESCRIPTION
               "Control to cause reset of the system in a slot.  
               When read, the value is always 'ready'.  Setting to 
               'reset' or 'resetHold' causes a single attempt to 
               take that action, but does not ensure transition to 
               any particular value of slotOperStatus."
           ::= { slotEntry 2 }

       slotOperStatus OBJECT-TYPE
           SYNTAX INTEGER { loadRequested(1),
                            loading(2),
                            dumpRequested(3),
                            dumping(4),
                            paramRequested(5),
                            paramLoading(6),
                            running(7),
                            initializing(8),     -- ROM wait
                            attended(9),         -- in config menu
                            internal10(10),      -- read chas info
                            internal11(11),      -- read config
                            inhibited(12),       -- run inhibited
                            maxserverCard(13),
                            invalidConfigStorage(14), -- suspended
                            securityLockdown(15),

                            resetHold(64),       -- SCM, reset
                            selfTest(65),        -- SCM, diag.
                            notResponding(66),   -- SCM running
                            broken(67),          -- SCM, failed
                            unknown(68),         -- SCM
                            notApplicable(69)    -- SCM
                           }
           ACCESS read-only
           STATUS mandatory
           DESCRIPTION
               "Relative to the chassis, the current operating 
               status of the system in the slot."
           ::= { slotEntry 3 }

       slotSecondsSinceReset OBJECT-TYPE
           SYNTAX Gauge
           ACCESS read-only
           STATUS mandatory
           DESCRIPTION
               "The number of seconds since the system in the slot 
               was last reset by hardware or software."
           ::= { slotEntry 4 }

       slotHardwareType OBJECT-TYPE
           SYNTAX HardwareType
           ACCESS read-only
           STATUS mandatory
           DESCRIPTION
               "The type of hardware in the slot."
           ::= { slotEntry 5 }

       slotHardwareSerialNumber OBJECT-TYPE
           SYNTAX SerialNumber
           ACCESS read-only
           STATUS mandatory
           DESCRIPTION
               "The MRV In-Reach serial number of the function card 
               hardware in this slot."
           ::= { slotEntry 6 }

       slotHardwareRevision OBJECT-TYPE
           SYNTAX INTEGER
           ACCESS read-only
           STATUS mandatory
           DESCRIPTION
               "This revision level of the function card hardware 
               in the slot."
           ::= { slotEntry 7 }

       slotIOCardType OBJECT-TYPE
           SYNTAX IOType
           ACCESS read-only
           STATUS mandatory
           DESCRIPTION
               "The hardware type of the I/O card in this slot."
           ::= { slotEntry 8 }

       slotIOCardSerialNumber OBJECT-TYPE
           SYNTAX SerialNumber
           ACCESS read-only
           STATUS mandatory
           DESCRIPTION
               "The MRV In-Reach serial number of the I/O card in this 
               slot."
           ::= { slotEntry 9 }

       slotIOCardOperStatus OBJECT-TYPE
           SYNTAX INTEGER { unknown(1), mismatch(2), good(3),
                            notApplicable(4) }
           ACCESS read-only
           STATUS mandatory
           DESCRIPTION
               "Status of the I/O card relative to the function 
               card in this slot."
           ::= { slotEntry 10 }

       slotBootstrapFirmwareRevision OBJECT-TYPE
           SYNTAX INTEGER
           ACCESS read-only
           STATUS mandatory
           DESCRIPTION
               "The firmware revision level of the bootstrap ROM 
               installed in the system in the slot."
           ::= { slotEntry 11 }

       slotElementalFirmwareRevision OBJECT-TYPE
           SYNTAX INTEGER
           ACCESS read-only
           STATUS mandatory
           DESCRIPTION
               "The firmware revision level of the minimal function 
               ROM (management bus microprocessor) installed in the 
               system in the slot."
           ::= { slotEntry 12 }

       slotMemorySize OBJECT-TYPE
           SYNTAX INTEGER
           ACCESS read-only
           STATUS mandatory
           DESCRIPTION
               "The number of bytes of memory installed in the 
               system in the slot."
           ::= { slotEntry 13 }

       slotLedNumber OBJECT-TYPE
           SYNTAX Gauge
           ACCESS read-only
           STATUS mandatory
           DESCRIPTION
               "The number of LEDs on the system in the slot.  A 
               value of 0 indicates none, unknown, or status not 
               readable."
           ::= { slotEntry 14 }

       slotLedStatus OBJECT-TYPE
           SYNTAX OCTET STRING (SIZE (0..9))
           ACCESS read-only
           STATUS mandatory
           DESCRIPTION
               "The status of the LEDs displayed on the front and 
               back of the system in the slot.  The first bit is 
               the high-order bit of the first byte of the value, 
               proceeding to the low-order bit, then to then next 
               byte.  On the system hardware, the first LED is at 
               the top, left, front, proceeding left to right, top 
               to bottom, and front to back."
           ::= { slotEntry 15 }

       slotBase802Address OBJECT-TYPE
           SYNTAX MacAddress
           ACCESS read-only
           STATUS mandatory
           DESCRIPTION
               "Base IEEE 802 global address for the slot."
           ::= { slotEntry 16 }

       slotIpAddress OBJECT-TYPE
           SYNTAX IpAddress
           ACCESS read-only
           STATUS mandatory
           DESCRIPTION
               "An internet address to which the system in this 
               slot might respond.  May be one of many."
           ::= { slotEntry 17 }

       slotPlus5Status OBJECT-TYPE
           SYNTAX INTEGER { unknown(1), broken(2), good(3) }
           ACCESS read-only
           STATUS mandatory
           DESCRIPTION
               "Status of the +5 volt power to the slot."
           ::= { slotEntry 18 }

       slotPlus12Status OBJECT-TYPE
           SYNTAX INTEGER { unknown(1), broken(2), good(3) }
           ACCESS read-only
           STATUS mandatory
           DESCRIPTION
               "Status of the +12 volt power to the slot."
           ::= { slotEntry 19 }

       slotMinus12Status OBJECT-TYPE
           SYNTAX INTEGER { unknown(1), broken(2), good(3) }
           ACCESS read-only
           STATUS mandatory
           DESCRIPTION
               "Status of the -12 volt power to the slot."
           ::= { slotEntry 20 }

       slotPlus5Watts OBJECT-TYPE
           SYNTAX Gauge
           ACCESS read-only
           STATUS mandatory
           DESCRIPTION
               "Tenths of watts of +5 volt power currently drawn by 
               the slot."
           ::= { slotEntry 21 }

       slotPlus12Watts OBJECT-TYPE
           SYNTAX Gauge
           ACCESS read-only
           STATUS mandatory
           DESCRIPTION
               "Tenths of watts of +12 volt power currently drawn 
               by the slot."
           ::= { slotEntry 22 }

       slotMinus12Watts OBJECT-TYPE
           SYNTAX Gauge
           ACCESS read-only
           STATUS mandatory
           DESCRIPTION
               "Tenths of watts of -12 volt power currently drawn 
               by the slot."
           ::= { slotEntry 23 }

       slotIOCardHardwareVersion OBJECT-TYPE
           SYNTAX INTEGER
           ACCESS read-only
           STATUS mandatory
           DESCRIPTION
               "Version number of I/O card in the slot."
           ::= { slotEntry 24 }

       slotRestoreNVS OBJECT-TYPE
           SYNTAX INTEGER { ready(1), execute(2) }
           ACCESS read-write
           STATUS mandatory
           DESCRIPTION
               "Setting to 'execute' causes the non-volatile 
               parameter storage to be restored from an installed 
               memory card.  Setting to 'ready' has no effect."
           ::= { slotEntry 25 }

       slotDefaultNVS OBJECT-TYPE
           SYNTAX INTEGER { ready(1), execute(2) }
           ACCESS read-write
           STATUS mandatory
           DESCRIPTION
               "Setting to 'execute' causes non-volatile stored 
               parameters to be reset to factory defaults.  Setting 
               to 'ready' has no effect."
           ::= { slotEntry 26 }


       -- the Slot Bootstrap Status table

       slotBootTable OBJECT-TYPE
           SYNTAX SEQUENCE OF SlotBootEntry
           ACCESS not-accessible
           STATUS mandatory
           DESCRIPTION
               "A list of slot bootstrap status entries.  A given 
               slot has an entry in this table only when 
               slotOperStatus is one of:  loadRequested, loading, 
               dumpRequested, dumping, paramRequested, 
               paramLoading"
           ::= { xSlot 2 }

       slotBootEntry OBJECT-TYPE
           SYNTAX SlotBootEntry
           ACCESS not-accessible
           STATUS mandatory
           DESCRIPTION
               "Bootstrap status values for a chassis slot."
           INDEX { slotBootIndex }
           ::= { slotBootTable 1 }

       SlotBootEntry ::=
           SEQUENCE {
               slotBootIndex
                   INTEGER,
               slotBootIfIndex
                   INTEGER,
               slotBootNetwork
                   OBJECT IDENTIFIER,
               slotBootProtocol
                   INTEGER,
               slotBoot802Address
                   MacAddress,
               slotBootAddressType
                   AddressType,
               slotBootAddress
                   OCTET STRING,
               slotBootServerAddressType
                   AddressType,
               slotBootServerAddress
                   OCTET STRING,
               slotBootGatewayAddress
                   IpAddress,
               slotBootFileName
                   DisplayString,
               slotBootBlockNumber
                   Gauge,
               slotBootCrashCode
                   OCTET STRING
           }

       slotBootIndex OBJECT-TYPE
           SYNTAX INTEGER
           ACCESS read-only
           STATUS mandatory
           DESCRIPTION
               "An index value that uniquely identifies a slot, 
               defined the same as slotIndex."
           ::= { slotBootEntry 1 }

       slotBootIfIndex OBJECT-TYPE
           SYNTAX INTEGER
           ACCESS read-only
           STATUS mandatory
           DESCRIPTION
               "An index value that uniquely identifies the 
               interface in use for bootstrap functions.  The 
               interface identified by a particular value of this 
               index is the same interface as identified by the 
               same value of ifIndex."
           ::= { slotBootEntry 2 }

       slotBootNetwork OBJECT-TYPE
           SYNTAX OBJECT IDENTIFIER
           ACCESS read-only
           STATUS mandatory
           DESCRIPTION
               "The instance identifier of the first object in the 
               conceptual row entry for the segment or port this 
               interface is using, that is, segmentType or 
               portType."
           ::= { slotBootEntry 3 }

       slotBootProtocol OBJECT-TYPE
           SYNTAX INTEGER { other(1), unknown(2), mop(3), xmop(4),
                            rarpTftp(5), bootpTftp(6), tftp(7),
                            local(8), managementBus(9) }
           ACCESS read-only
           STATUS mandatory
           DESCRIPTION
               "The protocol in use for bootstrap operation."
           ::= { slotBootEntry 4 }

       slotBoot802Address OBJECT-TYPE
           SYNTAX MacAddress
           ACCESS read-only
           STATUS mandatory
           DESCRIPTION
               "IEEE 802 global address in use for bootstrap 
               operation."
           ::= { slotBootEntry 5 }

       slotBootAddressType OBJECT-TYPE
           SYNTAX AddressType
           ACCESS read-only
           STATUS mandatory
           DESCRIPTION
               "The type of network address contained in 
               slotBootAddress."
           ::= { slotBootEntry 6 }

       slotBootAddress OBJECT-TYPE
           SYNTAX OCTET STRING (SIZE (0..6))
           ACCESS read-only
           STATUS mandatory
           DESCRIPTION
               "The network address the system in the slot is using 
               to identify itself for bootstrap operation."
           ::= { slotBootEntry 7 }

       slotBootServerAddressType OBJECT-TYPE
           SYNTAX AddressType
           ACCESS read-only
           STATUS mandatory
           DESCRIPTION
               "The type of network address contained in 
               slotBootServerAddress."
           ::= { slotBootEntry 8 }

       slotBootServerAddress OBJECT-TYPE
           SYNTAX OCTET STRING (SIZE (0..6))
           ACCESS read-only
           STATUS mandatory
           DESCRIPTION
               "The network address of the system supplying 
               bootstrap services to the system in the slot."
           ::= { slotBootEntry 9 }

       slotBootGatewayAddress OBJECT-TYPE
           SYNTAX IpAddress
           ACCESS read-only
           STATUS mandatory
           DESCRIPTION
               "The internet address of the router in use for 
               bootstrap operation."
           ::= { slotBootEntry 10 }

       slotBootFileName OBJECT-TYPE
           SYNTAX DisplayString (SIZE (0..64))
           ACCESS read-only
           STATUS mandatory
           DESCRIPTION
               "The full name of the file in use for bootstrap 
               operation."
           ::= { slotBootEntry 11 }

       slotBootBlockNumber OBJECT-TYPE
           SYNTAX Gauge
           ACCESS read-only
           STATUS mandatory
           DESCRIPTION
               "The current block number being transferred for 
               bootstrap operation, zero if unknown or not 
               applicable."
           ::= { slotBootEntry 12 }

       slotBootCrashCode OBJECT-TYPE
           SYNTAX OCTET STRING (SIZE (0..4))
           ACCESS read-only
           STATUS mandatory
           DESCRIPTION
               "If slotOperStatus is dumpRequested or dumping, a 
               code number to identify the crash reason; otherwise 
               zero length."
           ::= { slotBootEntry 13 }


       -- the Slot Controller table

       slotControllerTable OBJECT-TYPE
           SYNTAX SEQUENCE OF SlotControllerEntry
           ACCESS not-accessible
           STATUS mandatory
           DESCRIPTION
               "A list of controller entries, one for each 
               controller of each type in each slot."
           ::= { xSlot 3 }

       slotControllerEntry OBJECT-TYPE
           SYNTAX SlotControllerEntry
           ACCESS not-accessible
           STATUS mandatory
           DESCRIPTION
               "Values for a controller."
           INDEX { slotControllerType,
                   slotControllerIndex }
           ::= { slotControllerTable 1 }

       SlotControllerEntry ::=
           SEQUENCE {
               slotControllerType
                   NetworkType,
               slotControllerIndex
                   INTEGER,
               slotControllerNetwork
                   OBJECT IDENTIFIER
           }

       slotControllerType OBJECT-TYPE
           SYNTAX NetworkType
           ACCESS read-only
           STATUS mandatory
           DESCRIPTION
               "The controller type."
           ::= { slotControllerEntry 1 }

       slotControllerIndex OBJECT-TYPE
           SYNTAX INTEGER
           ACCESS read-only
           STATUS mandatory
           DESCRIPTION
               "An index value that uniquely identifies a 
               controller."
           ::= { slotControllerEntry 2 }

       slotControllerNetwork OBJECT-TYPE
           SYNTAX OBJECT IDENTIFIER
           ACCESS read-only
           STATUS mandatory
           DESCRIPTION
               "The instance identifier of the first object in the 
               conceptual row entry for the segment or port this 
               controller is to use, that is, segmentType or 
               portType."
           ::= { slotControllerEntry 3 }


       -- the Chassis Power Supply group

       -- Implementation of this group is optional for MRV In-Reach
       -- Network 9000 management bus systems.  It is implemented
       -- on such systems that supply full chassis management.

       -- the Power Supply table

       powerSupplyTable OBJECT-TYPE
           SYNTAX SEQUENCE OF PowerSupplyEntry
           ACCESS not-accessible
           STATUS mandatory
           DESCRIPTION
               "A list of power supply entries."
           ::= { xPowerSupply 1 }

       powerSupplyEntry OBJECT-TYPE
           SYNTAX PowerSupplyEntry
           ACCESS not-accessible
           STATUS mandatory
           DESCRIPTION
               "Values for a chassis power supply."
           INDEX { powerSupplyIndex }
           ::= { powerSupplyTable 1 }

       PowerSupplyEntry ::=
           SEQUENCE {
               powerSupplyIndex
                   INTEGER,
               powerSupplyAdminAction
                   INTEGER,
               powerSupplyFirmwareVersion
                   INTEGER,
               powerSupplyRedundancyStatus
                   INTEGER,
               powerSupplyPlus5Status
                   INTEGER,
               powerSupplyPlus12Status
                   INTEGER,
               powerSupplyMinus12Status
                   INTEGER,
               powerSupplyThermalWarningStatus
                   INTEGER,
               powerSupplyThermalShutdownStatus
                   INTEGER,
               powerSupplyFanStatus
                   INTEGER,
               powerSupplyHardwareInhibitStatus
                   INTEGER,
               powerSupplyPlus5History
                   INTEGER,
               powerSupplyPlus12History
                   INTEGER,
               powerSupplyMinus12History
                   INTEGER,
               powerSupplyThermalWarningHistory
                   INTEGER,
               powerSupplyThermalShutdownHistory
                   INTEGER,
               powerSupplyFanHistory
                   INTEGER,
               powerSupplyHardwareInhibitHistory
                   INTEGER,
               powerSupplyPlus5Volts
                   Gauge,
               powerSupplyPlus12Volts
                   Gauge,
               powerSupplyMinus12Volts
                   Gauge,
               powerSupplyWatts
                   Gauge,
               powerSupplyWattsMax
                   Gauge,
               powerSupplyChassisWatts
                   Gauge,
               powerSupplyChassisWattsMax
                   Gauge,
               powerSupplyHardwareType
                   INTEGER
           }

       powerSupplyIndex OBJECT-TYPE
           SYNTAX INTEGER
           ACCESS read-only
           STATUS mandatory
           DESCRIPTION
               "An index value that uniquely identifies a power 
               supply, in the range 1 to the number of power supply 
               slots in the chassis."
           ::= { powerSupplyEntry 1 }

       powerSupplyAdminAction OBJECT-TYPE
           SYNTAX INTEGER { ready(1), reset(2), resetHold(3) }
           ACCESS read-write
           STATUS mandatory
           DESCRIPTION
               "Control to cause reset of the power supply.  When 
               read, the value is always 'ready'.  Setting to 
               'reset' or 'resetHold' causes a single attempt to 
               take that action, but does not ensure transition to 
               any particular value of 
               powerSupplyRedundancyStatus."
           ::= { powerSupplyEntry 2 }

       powerSupplyFirmwareVersion OBJECT-TYPE
           SYNTAX INTEGER
           ACCESS read-only
           STATUS mandatory
           DESCRIPTION
               "Version number of power supply firmware."
           ::= { powerSupplyEntry 3 }

       powerSupplyRedundancyStatus OBJECT-TYPE
           SYNTAX INTEGER { unknown(1), disabled(2),
                            redundant(3), engaged(4) }
           ACCESS read-only
           STATUS mandatory
           DESCRIPTION
               "The current redundancy status of the power 
               supply."
           ::= { powerSupplyEntry 4 }

       powerSupplyPlus5Status OBJECT-TYPE
           SYNTAX INTEGER { unknown(1), good(2), broken(3) }
           ACCESS read-only
           STATUS mandatory
           DESCRIPTION
               "Status of the +5 volt power from the power 
               supply."
           ::= { powerSupplyEntry 5 }

       powerSupplyPlus12Status OBJECT-TYPE
           SYNTAX INTEGER { unknown(1), good(2), broken(3) }
           ACCESS read-only
           STATUS mandatory
           DESCRIPTION
               "Status of the +12 volt power from the power 
               supply."
           ::= { powerSupplyEntry 6 }

       powerSupplyMinus12Status OBJECT-TYPE
           SYNTAX INTEGER { unknown(1), good(2), broken(3) }
           ACCESS read-only
           STATUS mandatory
           DESCRIPTION
               "Status of the -12 volt power from the power 
               supply."
           ::= { powerSupplyEntry 7 }

       powerSupplyThermalWarningStatus OBJECT-TYPE
           SYNTAX INTEGER { unknown(1), good(2), broken(3) }
           ACCESS read-only
           STATUS mandatory
           DESCRIPTION
               "The current thermal warning status of the power 
               supply."
           ::= { powerSupplyEntry 8 }

       powerSupplyThermalShutdownStatus OBJECT-TYPE
           SYNTAX INTEGER { unknown(1), good(2), broken(3) }
           ACCESS read-only
           STATUS mandatory
           DESCRIPTION
               "The current thermal shutdown status of the power 
               supply."
           ::= { powerSupplyEntry 9 }

       powerSupplyFanStatus OBJECT-TYPE
           SYNTAX INTEGER { unknown(1), good(2), broken(3) }
           ACCESS read-only
           STATUS mandatory
           DESCRIPTION
               "The current status of the power supply's fan."
           ::= { powerSupplyEntry 10 }

       powerSupplyHardwareInhibitStatus OBJECT-TYPE
           SYNTAX INTEGER { unknown(1), good(2), broken(3) }
           ACCESS read-only
           STATUS mandatory
           DESCRIPTION
               "The current status of the power supply's hardware 
               inhibit."
           ::= { powerSupplyEntry 11 }

       powerSupplyPlus5History OBJECT-TYPE
           SYNTAX INTEGER { unknown(1), good(2), broken(3) }
           ACCESS read-only
           STATUS mandatory
           DESCRIPTION
               "History of the +5 volt power from the power 
               supply."
           ::= { powerSupplyEntry 12 }

       powerSupplyPlus12History OBJECT-TYPE
           SYNTAX INTEGER { unknown(1), good(2), broken(3) }
           ACCESS read-only
           STATUS mandatory
           DESCRIPTION
               "History of the +12 volt power from the power 
               supply."
           ::= { powerSupplyEntry 13 }

       powerSupplyMinus12History OBJECT-TYPE
           SYNTAX INTEGER { unknown(1), good(2), broken(3) }
           ACCESS read-only
           STATUS mandatory
           DESCRIPTION
               "History of the -12 volt power from the power 
               supply."
           ::= { powerSupplyEntry 14 }

       powerSupplyThermalWarningHistory OBJECT-TYPE
           SYNTAX INTEGER { unknown(1), good(2), broken(3) }
           ACCESS read-only
           STATUS mandatory
           DESCRIPTION
               "The thermal warning history of the power supply."
           ::= { powerSupplyEntry 15 }

       powerSupplyThermalShutdownHistory OBJECT-TYPE
           SYNTAX INTEGER { unknown(1), good(2), broken(3) }
           ACCESS read-only
           STATUS mandatory
           DESCRIPTION
               "The thermal shutdown history of the power supply."
           ::= { powerSupplyEntry 16 }

       powerSupplyFanHistory OBJECT-TYPE
           SYNTAX INTEGER { unknown(1), good(2), broken(3) }
           ACCESS read-only
           STATUS mandatory
           DESCRIPTION
               "The status history of the power supply's fan."
           ::= { powerSupplyEntry 17 }

       powerSupplyHardwareInhibitHistory OBJECT-TYPE
           SYNTAX INTEGER { unknown(1), good(2), broken(3) }
           ACCESS read-only
           STATUS mandatory
           DESCRIPTION
               "The status history of the power supply's hardware 
               inhibit."
           ::= { powerSupplyEntry 18 }

       powerSupplyPlus5Volts OBJECT-TYPE
           SYNTAX Gauge
           ACCESS read-only
           STATUS mandatory
           DESCRIPTION
               "In hundredths, volts of +5 volt power currently 
               provided by the power supply.  A value of 0 
               indicates unknown."
           ::= { powerSupplyEntry 19 }

       powerSupplyPlus12Volts OBJECT-TYPE
           SYNTAX Gauge
           ACCESS read-only
           STATUS mandatory
           DESCRIPTION
               "In hundredths, volts of +12 volt power currently 
               provided by the power supply.  A value of 0 
               indicates unknown."
           ::= { powerSupplyEntry 20 }

       powerSupplyMinus12Volts OBJECT-TYPE
           SYNTAX Gauge
           ACCESS read-only
           STATUS mandatory
           DESCRIPTION
               "In hundredths, volts of -12 volt power currently 
               provided by the power supply.  A value of 0 
               indicates unknown."
           ::= { powerSupplyEntry 21 }

       powerSupplyWatts OBJECT-TYPE
           SYNTAX Gauge
           ACCESS read-only
           STATUS mandatory
           DESCRIPTION
               "Watts of power currently drawn from this power 
               supply.  A value of 0 indicates unknown."
           ::= { powerSupplyEntry 22 }

       powerSupplyWattsMax OBJECT-TYPE
           SYNTAX Gauge
           ACCESS read-only
           STATUS mandatory
           DESCRIPTION
               "Maximum watts of power available from this power 
               supply.  A value of 0 indicates unknown."
           ::= { powerSupplyEntry 23 }

       powerSupplyChassisWatts OBJECT-TYPE
           SYNTAX Gauge
           ACCESS read-only
           STATUS mandatory
           DESCRIPTION
               "Total watts of power currently drawn by the entire 
               chassis.  A value of 0 indicates unknown."
           ::= { powerSupplyEntry 24 }

       powerSupplyChassisWattsMax OBJECT-TYPE
           SYNTAX Gauge
           ACCESS read-only
           STATUS mandatory
           DESCRIPTION
               "Total maximum watts of power available from all the 
               power supplies in the chassis.  A value of 0 
               indicates unknown."
           ::= { powerSupplyEntry 25 }

       powerSupplyHardwareType OBJECT-TYPE
           SYNTAX INTEGER { other(1), ps130(2), bb190(3) }
           ACCESS read-only
           STATUS mandatory
           DESCRIPTION
               "The type of power supply."
           ::= { powerSupplyEntry 26 }

       -- The firmware update group

       -- A table which contains information and status
       -- concerning the writing of firmware to a target
       -- I/O card.

       -- The firmware update table

       firmwareUpdateTable OBJECT-TYPE
           SYNTAX SEQUENCE OF FirmwareUpdateEntry
           ACCESS not-accessible
           STATUS mandatory
           DESCRIPTION
               "Table of descriptive and status information concerning
               the writing of firmware to a target I/O card."
           ::= { xFirmwareUpdate 1 }

       firmwareUpdateEntry OBJECT-TYPE
           SYNTAX FirmwareUpdateEntry
           ACCESS not-accessible
           STATUS mandatory
           DESCRIPTION
               "An entry in the table concerning the writing of
               firmware to a target I/O card."
           INDEX { firmwareUpdateSlotIndex }
           ::= { firmwareUpdateTable 1 }

       FirmwareUpdateEntry  ::=
           SEQUENCE {
               firmwareUpdateSlotIndex
                   INTEGER,
               firmwareUpdateDefaultFileName
                   DisplayString,
               firmwareUpdateFileName
                   DisplayString,
               firmwareUpdateStatus
                   INTEGER,
               firmwareUpdateState
                   INTEGER,
               firmwareUpdateCompletionStatus
                   INTEGER,
			   firmwareUpdateMethod
                   INTEGER
           }

       firmwareUpdateSlotIndex  OBJECT-TYPE
           SYNTAX INTEGER
           ACCESS read-only
           STATUS mandatory
           DESCRIPTION
               "This variable identifies the slot to which is to
               be the target of the firmware update."
           ::= { firmwareUpdateEntry 1 }

       firmwareUpdateDefaultFileName  OBJECT-TYPE
           SYNTAX DisplayString
           ACCESS read-only
           STATUS mandatory
           DESCRIPTION
               "This variable when read will obtain the default
               file name from the target."
           ::= { firmwareUpdateEntry 2 }

       firmwareUpdateFileName  OBJECT-TYPE
           SYNTAX DisplayString
           ACCESS read-write
           STATUS mandatory
           DESCRIPTION
               "This variable contains the name of the file to be
               read from the flash memory card and written to the
               target."
           ::= { firmwareUpdateEntry 3 }

       firmwareUpdateStatus  OBJECT-TYPE
           SYNTAX INTEGER { ready(1), execute(2) }
           ACCESS read-write
           STATUS mandatory
           DESCRIPTION
               "This variable is used to start the update process.
               The agent always 'ready' for this value.  Setting this
               value to 'execute' causes the agent to write the file
               specified by firmwareUpdateFileName to be written to
               the taget.  Setting this value to 'execute' when
               firmwareUpdateFileName has not been written or when
               firmwareUpdateState is 'writing' causes bad value to be
               returned."
           ::= { firmwareUpdateEntry 4 }

       firmwareUpdateState  OBJECT-TYPE
           SYNTAX INTEGER { idle(1), writing(2) }
           ACCESS read-only
           STATUS mandatory
           DESCRIPTION
               "This variable indicates the current state of firmware
               update, 'idle' indicates that firmware update may be
               initiated, and 'writing' indicates that an update is in
               process."
           ::= { firmwareUpdateEntry 5 }

       firmwareUpdateCompletionStatus  OBJECT-TYPE
           SYNTAX INTEGER { none(1),
                            success(2),
                            noTarget(3),
                            busError(4),
                            badFileName(5),
                            targetError(6),
                            timeout(7)
                          }
           ACCESS read-only
           STATUS mandatory
           DESCRIPTION
               "This variable indicates the completion status of the
               the last firmware update attempt.  'none' indicates
               that no firmware update has yet been attempted."
           ::= { firmwareUpdateEntry 6 }

       firmwareUpdateMethod  OBJECT-TYPE
           SYNTAX INTEGER { card(1), local(2) }
           ACCESS read-write
           STATUS mandatory
           DESCRIPTION
               "This variable indicates the method of update of the
               firmware update attempt. "
           ::= { firmwareUpdateEntry 7 }


--
-- FILE: /users/sse/mibs/src/inReach/ir-character-mib.mib
--

-- $Id: ir-character-mib.mib,v 1.1 2002/06/27 15:35:08 sse Exp $
            
            
            characterDep    OBJECT IDENTIFIER ::= { mrvInReachProductDivision 2 }
            xCharacter      OBJECT IDENTIFIER ::= { mrvInReachProductDivision 13 }
            
            -- MRV In-Reach Character subgroups
            
            xBasic          OBJECT IDENTIFIER ::= { xCharacter 1 }
            xQueue          OBJECT IDENTIFIER ::= { xCharacter 2 }
            xMenu           OBJECT IDENTIFIER ::= { xCharacter 3 }
            xNetLogin       OBJECT IDENTIFIER ::= { xCharacter 4 }
            xDial           OBJECT IDENTIFIER ::= { xCharacter 5 }
            xSessionLog     OBJECT IDENTIFIER ::= { xCharacter 6 }
            xCcl            OBJECT IDENTIFIER ::= { xCharacter 7 }
            xBroadcastGroup OBJECT IDENTIFIER ::= { xCharacter 8 }
            xPingHosts      OBJECT IDENTIFIER ::= { xCharacter 9 }
            
            -- This is a MIB module for all MRV In-Reach systems that
            -- implement physical or logical character stream devices.
            -- It is also used by the In-Reach product line for alarm, sensor
            -- and power managment functions.
            
            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.

            
            -- the Character Basic group
            
            -- Implementation of this group is mandatory for all MRV In-Reach
            -- systems that implement physical or logical character
            -- stream devices
            
            basicBroadcast OBJECT-TYPE
                SYNTAX INTEGER { disabled(1), enabled(2) }
                ACCESS read-write
                STATUS mandatory
                DESCRIPTION
                    "Control for user ability to broadcast messages to 
                    other local ports.  Corresponds directly to SERVER 
                    BROADCAST and the presence of the label 'Broadcast' 
                    following the label 'Enabled Characteristics:' in 
                    the SERVER CHARACTERISTICS display."
                ::= { xBasic 1 }
            
            basicErrorReport OBJECT-TYPE
                SYNTAX INTEGER { disabled(1), enabled(2) }
                ACCESS read-write
                STATUS mandatory
                DESCRIPTION
                    "Control for server display of an error when the 
                    user gives an unsupported command.  Corresponds 
                    directly to SERVER REPORT ERRORS and the presence of 
                    the label 'Report Errors' following the label 
                    'Enabled Characteristics:' in the SERVER 
                    CHARACTERISTICS display."
                ::= { xBasic 2 }
            
            basicLock OBJECT-TYPE
                SYNTAX INTEGER { disabled(1), enabled(2) }
                ACCESS read-write
                STATUS mandatory
                DESCRIPTION
                    "Control for user ability to use a password to 
                    protect a logged in terminal from other users.  
                    Corresponds directly to SERVER LOCK and the presence 
                    of the label 'Lock' following the label 'Enabled 
                    Characteristics:' in the SERVER CHARACTERISTICS 
                    display."
                ::= { xBasic 3 }
            
            basicInactivityTimer OBJECT-TYPE
                SYNTAX INTEGER (1..480)
                ACCESS read-write
                STATUS mandatory
                DESCRIPTION
                    "Number of minutes a terminal may remain logged in 
                    with no sessions, no input or output, and no modem 
                    transitions.  Corresponds directly to SERVER 
                    INACTIVITY TIMER and the value labeled 'Inactivity 
                    Timer:' in the SERVER CHARACTERISTICS display."
                ::= { xBasic 4 }
            
            basicPasswordRetryLimit OBJECT-TYPE
                SYNTAX INTEGER (0..250)
                ACCESS read-write
                STATUS mandatory
                DESCRIPTION
                    "Number of times the server allows a user to retry 
                    an incorrect password.  Corresponds directly to 
                    SERVER PASSWORD LIMIT and the value labeled 
                    'Password Limit:' in the SERVER CHARACTERISTICS 
                    display."
                ::= { xBasic 5 }
            
            basicPrivilegedPassword OBJECT-TYPE
                SYNTAX DisplayString (SIZE (0..16))
                ACCESS read-write
                STATUS mandatory
                DESCRIPTION
                    "The password a user must enter to become 
                    privileged.
                    For security reasons, reading this object always 
                    returns a zero-length value.  Corresponds directly 
                    to SERVER PRIVILEGED PASSWORD."
                ::= { xBasic 6 }
            
            basicLoginPassword OBJECT-TYPE
                SYNTAX DisplayString (SIZE (0..16))
                ACCESS read-write
                STATUS mandatory
                DESCRIPTION
                    "The password a user must enter to be given the 
                    opportunity to log in.  For security reasons, 
                    reading this object always returns a zero-length 
                    value. Corresponds directly to SERVER LOGIN 
                    PASSWORD."
                ::= { xBasic 7 }
            
            basicLoginPrompt OBJECT-TYPE
                SYNTAX DisplayString (SIZE (0..8))
                ACCESS read-write
                STATUS mandatory
                DESCRIPTION
                    "The text string the server displays to prompt a 
                    user for the login password.  Corresponds directly 
                    to SERVER LOGIN PROMPT."
                ::= { xBasic 8 }
            
            basicWelcome OBJECT-TYPE
                SYNTAX DisplayString (SIZE (0..80))
                ACCESS read-write
                STATUS mandatory
                DESCRIPTION
                    "The text string the server displays before 
                    attempting to log in a user.  Corresponds directly 
                    to SERVER WELCOME and the value labeled 'Welcome:' 
                    in the SERVER CHARACTERISTICS display."
                ::= { xBasic 9 }
            
            basicActivePorts OBJECT-TYPE
                SYNTAX Gauge
                ACCESS read-only
                STATUS mandatory
                DESCRIPTION
                    "The number of ports with connected sessions or 
                    logged in users.  Corresponds directly to the value 
                    labeled 'Active Ports:' and 'Cur' in the SERVER 
                    STATUS display."
                ::= { xBasic 10 }
            
            basicActivePortsHigh OBJECT-TYPE
                SYNTAX Gauge
                ACCESS read-only
                STATUS mandatory
                DESCRIPTION
                    "The highest value of basicActivePorts since system 
                    initialization.  Corresponds directly to the value 
                    labeled 'Active Ports:' and 'High' in the SERVER 
                    STATUS display."
                ::= { xBasic 11 }
            
            basicActiveUsers OBJECT-TYPE
                SYNTAX Gauge
                ACCESS read-only
                STATUS mandatory
                DESCRIPTION
                    "The number of logged in users.  Corresponds 
                    directly to the value labeled 'Active Users:' and 
                    'Cur' in the SERVER STATUS display."
                ::= { xBasic 12 }
            
            basicActiveUsersHigh OBJECT-TYPE
                SYNTAX Gauge
                ACCESS read-only
                STATUS mandatory
                DESCRIPTION
                    "The highest value of basicActiveUsers since system 
                    initialization.  Corresponds directly to the value 
                    labeled 'Active Users:' and 'High' in the SERVER 
                    STATUS display."
                ::= { xBasic 13 }
            
            basicSessions OBJECT-TYPE
                SYNTAX Gauge
                ACCESS read-only
                STATUS mandatory
                DESCRIPTION
                    "The total number of connected sessions.  
                    Corresponds directly to the value labeled 'Connected 
                    Sessions:' and 'Cur' in the SERVER STATUS display."
                ::= { xBasic 14 }
            
            basicSessionsHigh OBJECT-TYPE
                SYNTAX Gauge
                ACCESS read-only
                STATUS mandatory
                DESCRIPTION
                    "The highest value of basicSessions since system 
                    initialization.  Corresponds directly to the value 
                    labeled 'Connected Sessions:' and 'High' in the 
                    SERVER STATUS display."
                ::= { xBasic 15 }
            
            basicSessionsLimit OBJECT-TYPE
                SYNTAX INTEGER (-1..255)
                ACCESS read-write
                STATUS mandatory
                DESCRIPTION
                    "The maximum total number of sessions that can 
                    simultaneously be connected to the system.  A value 
                    of -1 indicates no limit up to available dynamic 
                    system memory.  Corresponds directly to SERVER 
                    SESSION LIMIT and the value labeled 'Connected 
                    Sessions:' and 'Max' in the SERVER STATUS display."
                ::= { xBasic 16 }
            
            -- Additional Basic group parameters follow the port tables

            -- the Basic Port table
            
            basicPortTable OBJECT-TYPE
                SYNTAX SEQUENCE OF BasicPortEntry
                ACCESS not-accessible
                STATUS mandatory
                DESCRIPTION
                    "A list of basic character port entries."
                ::= { xBasic 17 }
            
            basicPortEntry OBJECT-TYPE
                SYNTAX BasicPortEntry
                ACCESS not-accessible
                STATUS mandatory
                DESCRIPTION
                    "Basic parameter values for a port."
                INDEX { basicPortIndex }
                ::= { basicPortTable 1 }
            
            BasicPortEntry ::=
                SEQUENCE {
                    basicPortIndex
                        INTEGER,
                    basicPortDefaultDestAction
                        INTEGER,
                    basicPortDefaultDestProtocol
                        INTEGER,
                    basicPortDefaultDestName
                        DisplayString,
                    basicPortDefaultDestLATNodeName
                        DisplayString,
                    basicPortDefaultDestLATPortName
                        DisplayString,
                    basicPortAutoConnect
                        INTEGER,
                    basicPortAutoLogin
                        INTEGER,
                    basicPortBroadcast
                        INTEGER,
                    basicPortConnectResume
                        INTEGER,
                    basicPortDialup
                        INTEGER,
                    basicPortIdleTimeout
                        INTEGER,
                    basicPortInactivityLogout
                        INTEGER,
                    basicPortLossNotification
                        INTEGER,
                    basicPortMessageCodes
                        INTEGER,
                    basicPortMultisessions
                        INTEGER,
                    basicPortDefaultUserName
                        DisplayString,
                    basicPortVerification
                        INTEGER,
                    basicPortDefaultProtocol
                        INTEGER,
                    basicPortLogins
                        Counter,
                    basicPortRemoteSessions
                        Counter,
                    basicPortIdleTimeouts
                        Counter,
                    basicPortStatus
                        INTEGER,
                    basicPortLastInCharacter
                        INTEGER,
                    basicPortLastOutCharacter
                        INTEGER,
                    basicPortActiveUserName
                        DisplayString,
                    basicPortDefaultSessionMode
                        INTEGER,
                    basicPortZero
                        INTEGER,
                    basicPortZeroTime
                        TimeTicks,
                    basicPortUnixCommands
                        INTEGER,
                    basicPortSessionMode
                        INTEGER,
                    basicPortRemoteDisconnectNotify
                        INTEGER,
                    basicPortDefaultDestControlled
                        INTEGER,
                    basicPortControlledPortLogin
                        OCTET STRING, 
                    basicPortControlledPortLogout
                        OCTET STRING,
                    basicPortControlledSessionInitialize
                        OCTET STRING,
                    basicPortControlledSessionTerminate
                        OCTET STRING,
                    basicPortRloginTransparentMode
                        INTEGER,
                    basicPortLoginDuration
                        INTEGER,
                    basicPortOutboundSecurity
                        INTEGER,
                    basicPortXonTimer
                        INTEGER,
                    basicPortDefaultDedicatedSessionType
                        INTEGER,
                    basicPortIdleTimeReceive
                        INTEGER,
                    basicPortIdleTimeTransmit
                        INTEGER,
                    basicPortZeroDisconnectSession
                        INTEGER,
                    basicPortConsolePort
                        INTEGER,
                    basicPortLoginPassword
                        DisplayString,
                    basicPortSensor
                        INTEGER,
                    basicPortAlarmControl
                        INTEGER,
                    basicPortCommandLogging
                        INTEGER,
                    basicPortBreakSequence
                        OCTET STRING,
                    basicPortTl1Mode
			INTEGER,
                    basicPortTl1Console
			INTEGER,
                    basicPortFallThrough
			INTEGER,
                    basicPortCommandLoggingSuppressControlCharacters 
			INTEGER,
                    basicPortDataLogging 
			INTEGER,
                    basicPortDataLoggingSuppressControlCharacters 
			INTEGER,
                    basicPortOnboardSecurity
			INTEGER,
                    basicPortFallBack
			INTEGER,
		    basicPortAlarmMaster
			INTEGER,
		    basicPortAlarmMasterAccounting
			INTEGER,
		    basicPortAlarmMasterAudibleAlarm
			INTEGER,
		    basicPortAlarmMasterFixTime
			INTEGER,
		    basicPortAlarmMasterLcdDisplayString
			DisplayString,
		    basicPortAlarmMasterReboot
			INTEGER,
		    basicPortAlarmMasterUpdateFirmwareHost
			IpAddress,
		    basicPortAlarmMasterUpdateFirmwareFileName
			DisplayString,
		    basicPortAlarmMasterUpdateFirmware
			INTEGER,
		    basicPortAlarmMasterStatus 
			INTEGER,
		    basicPortAlarmMasterFaultSeverity
			INTEGER,
		    basicPortPowerMaster
			INTEGER,
		    basicPortPowerMasterTimeDelay
			INTEGER,
		    basicPortPowerMasterSwitch
			INTEGER,
		    basicPortPowerMasterModel
			DisplayString,
		    basicPortPowerMasterSerialNumber
			DisplayString,
		    basicPortPowerMasterFirmware
			DisplayString,
		    basicPortLockout
			INTEGER,
		    basicPortAsciiToTrapTranslation
			INTEGER,
		    basicPortAsciiToTrapTranslationTrapSeverity
			INTEGER,
		    basicPortAsciiToTrapTranslationMessages
			Counter,
		    basicPortAsciiToTrapTranslationLastMessage
			DisplayString,
                    basicPortPowerMasterAlarmSeverity
			INTEGER,
                    basicPortPowerMasterDeviceStatus
			INTEGER,
                    basicPortBuffering
                        INTEGER,
                    basicPortLogFacilityLevel
                        INTEGER,
                    basicPortPppDialBackup
		        INTEGER,
                    basicPortPppDialBackupNumber
			DisplayString,
                    basicPortPppDialBackupRedialTimer
		        INTEGER,
                    basicPortPppDialBackupRedialRetries 
		        INTEGER,
                    basicPortPppDialBackupDisconnectTimer 
                        INTEGER,
                    basicPortPppDialBackupLocalAddress
                        IpAddress,
                    basicPortPppDialBackupDestinationAddress
		        IpAddress,
                    basicPortPppDialBackupAddresses
                        INTEGER
		 }

	     basicPortIndex OBJECT-TYPE
		 SYNTAX INTEGER
		 ACCESS read-only
		 STATUS mandatory
		 DESCRIPTION
		     "An index value that uniquely identifies a port.  
		     The port identified by a particular value of this 
		     index is the same port as identified by 
		     charPortIndex in the standard Character MIB."
		 ::= { basicPortEntry 1 }

	     basicPortDefaultDestAction OBJECT-TYPE
		 SYNTAX INTEGER { dedicated(1), preferred(2) }
		 ACCESS read-write
		 STATUS mandatory
		 DESCRIPTION
		     "The action to take relative to 
		     basicPortDefaultDestName.  Corresponds directly to 
		     PORT DEDICATED/PREFERRED SERVICE and the label 
		     'Dedicated/Preferred Service:' in the PORT 
		     CHARACTERISTICS display."
		 ::= { basicPortEntry 2 }

	     basicPortDefaultDestProtocol OBJECT-TYPE
		 SYNTAX INTEGER { lat(1), telnet(2), any(3) }
		 ACCESS read-write
		 STATUS mandatory
		 DESCRIPTION
		     "The session protocol to use with 
		     basicPortDefaultDestName.  Corresponds directly to 
		     LAT/TELNET PORT DEDICATED/PREFERRED SERVICE."
		 ::= { basicPortEntry 3 }

	     basicPortDefaultDestName OBJECT-TYPE
		 SYNTAX DisplayString (SIZE (0..50))
		 ACCESS read-write
		 STATUS mandatory
		 DESCRIPTION
		     "The default name to use in forming a connection 
		     when no other name is specified.  Corresponds 
		     directly to PORT DEDICATED/PREFERRED SERVICE and the 
		     value labeled 'Dedicated/Preferred Service:' in the 
		     PORT CHARACTERISTICS display.  If the value of 
		     basicPortDefaultDestProtocol is 'telnet', an 
		     Internet port number may be included on the end of 
		     the name, delimited with a colon (':').  If the 
		     value of basicPortDefaultDestProtocol is not 
		     'telnet', then the maximum length is 16."
		 ::= { basicPortEntry 4 }

	     basicPortDefaultDestLATNodeName OBJECT-TYPE
		 SYNTAX DisplayString (SIZE (0..16))
		 ACCESS read-write
		 STATUS mandatory
		 DESCRIPTION
		     "A LAT node name to use with 
		     basicPortDefaultDestName.  Corresponds directly to 
		     PORT DEDICATED/PREFERRED SERVICE NODE and the value 
		     labeled 'Node:' following the label 
		     'Dedicated/Preferred Service:' in the PORT 
		     CHARACTERISTICS display.  This object can have a 
		     non- zero-length value only if the value of 
		     basicPortDefaultDestProtocol is 'lat'."
		 ::= { basicPortEntry 5 }

	     basicPortDefaultDestLATPortName OBJECT-TYPE
		 SYNTAX DisplayString (SIZE (0..16))
		 ACCESS read-write
		 STATUS mandatory
		 DESCRIPTION
		     "A LAT port name to use with 
		     basicPortDefaultDestName.  Corresponds directly to 
		     PORT DEDICATED/PREFERRED SERVICE NODE and the value 
		     labeled 'Node:' following the label 
		     'Dedicated/Preferred Service:' in the PORT 
		     CHARACTERISTICS display.  this object can hav a 
		     non-zero-length value only if the value if 
		     basicPortDefaultDestProtocol is 'lat'"
		 ::= { basicPortEntry 6 }

	     basicPortAutoConnect OBJECT-TYPE
		 SYNTAX INTEGER { disabled(1), enabled(2) }
		 ACCESS read-write
		 STATUS mandatory
		 DESCRIPTION
		     "Control for automatic session connection.  
		     Corresponds directly to PORT AUTOCONNECT and the 
		     presence of the label 'Autoconnect' following the 
		     label 'Enabled Characteristics:' in the PORT 
		     CHARACTERISTICS display."
		 ::= { basicPortEntry 7 }

	     basicPortAutoLogin OBJECT-TYPE
		 SYNTAX INTEGER { disabled(1), enabled(2) }
		 ACCESS read-write
		 STATUS mandatory
		 DESCRIPTION
		     "Control for automatic port login.  Corresponds 
		     directly to PORT AUTODEDICATED and the presence of 
		     the label 'Autodedicated' following the label 
		     'Enabled Characteristics:' in the PORT 
		     CHARACTERISTICS display."
		 ::= { basicPortEntry 8 }

	     basicPortBroadcast OBJECT-TYPE
		 SYNTAX INTEGER { disabled(1), enabled(2) }
		 ACCESS read-write
		 STATUS mandatory
		 DESCRIPTION
		     "Control for display of messages sent by users on 
		     other ports.  Corresponds directly to PORT BROADCAST 
		     and the presence of the label 'Broadcast' following 
		     the label 'Enabled Characteristics:' in the PORT 
		     CHARACTERISTICS display."
		 ::= { basicPortEntry 9 }

	     basicPortConnectResume OBJECT-TYPE
		 SYNTAX INTEGER { disabled(1), enabled(2) }
		 ACCESS read-write
		 STATUS mandatory
		 DESCRIPTION
		     "Control for behavior of a connection attempt to a 
		     destination where the port already has a connection.  
		     'disabled' causes a new connection.  'enabled' 
		     causes the existing connection to become the active 
		     connection.  Corresponds directly to PORT 
		     CONNECTRESUME and the presence of the label 
		     'Connectresume' following the label 'Enabled 
		     Characteristics:' in the PORT CHARACTERISTICS 
		     display."
		 ::= { basicPortEntry 10 }

	     basicPortDialup OBJECT-TYPE
		 SYNTAX INTEGER { disabled(1), enabled(2) }
		 ACCESS read-write
		 STATUS mandatory
		 DESCRIPTION
		     "Defines whether the port should be considered as 
		     connected to a dialup line.  'enabled' means that it 
		     is.  Corresponds directly to PORT DIALUP and the 
		     presence of the label 'Dial Up' following the label 
		     'Enabled Characteristics:' in the PORT 
		     CHARACTERISTICS display. This object is not available
		     on units that do not support modem signals (ie 2220)."
		 ::= { basicPortEntry 11 }

	     basicPortIdleTimeout OBJECT-TYPE
		 SYNTAX INTEGER (-1..480)
		 ACCESS read-write
		 STATUS mandatory
		 DESCRIPTION
		     "The number of minutes the system will allow a 
		     session to have no activity before automatically 
		     disconnecting it.  A value of -1 indicates no 
		     timeout.  Zero is not a valid value.  Corresponds 
		     directly to PORT IDLE TIMEOUT and the value labeled 
		     'Idle Timeout:' in the PORT ALTERNATE 
		     CHARACTERISTICS display."
		 ::= { basicPortEntry 12 }

	     basicPortInactivityLogout OBJECT-TYPE
		 SYNTAX INTEGER { disabled(1), enabled(2) }
		 ACCESS read-write
		 STATUS mandatory
		 DESCRIPTION
		     "Control for the system automatically logging the 
		     port out when it has no sessions, no local activity, 
		     and no modem signal changes for the time period 
		     specified by basicInactivityTimer.  Corresponds 
		     directly to PORT INACTIVITY LOGOUT and the presence 
		     of the label 'Inactivity Logout' following the label 
		     'Enabled Characteristics:' in the PORT 
		     CHARACTERISTICS display."
		 ::= { basicPortEntry 13 }

	     basicPortLossNotification OBJECT-TYPE
		 SYNTAX INTEGER { disabled(1), enabled(2) }
		 ACCESS read-write
		 STATUS mandatory
		 DESCRIPTION
		     "Control for the system sending a Bell character to 
		     the port when it looses an input character due to an 
		     overrun or data error.  Corresponds directly to PORT 
		     LOSS NOTIFICATION and the presence of the label 
		     'Loss Notification' following the label 'Enabled 
		     Characteristics:' in the PORT CHARACTERISTICS 
		     display."
		 ::= { basicPortEntry 14 }

	     basicPortMessageCodes OBJECT-TYPE
		 SYNTAX INTEGER { disabled(1), enabled(2) }
		 ACCESS read-write
		 STATUS mandatory
		 DESCRIPTION
		     "Control for including error numbers in error 
		     messages displayed on the port.  Corresponds 
		     directly to PORT MESSAGE CODES and the presence of 
		     the label 'Message Codes' following the label 
		     'Enabled Characteristics:' in the PORT 
		     CHARACTERISTICS display."
		 ::= { basicPortEntry 15 }

	     basicPortMultisessions OBJECT-TYPE
		 SYNTAX INTEGER { disabled(1), enabled(2) }
		 ACCESS read-write
		 STATUS mandatory
		 DESCRIPTION
		     "Control for running the multisession line protocol 
		     between the port and the locally-connected terminal.  
		     Corresponds directly to PORT MULTISESSIONS and the 
		     presence of the label 'Multisessions' following the 
		     label 'Enabled Characteristics:' in the PORT 
		     CHARACTERISTICS display."
		 ::= { basicPortEntry 16 }

	     basicPortDefaultUserName OBJECT-TYPE
		 SYNTAX DisplayString (SIZE (0..16))
		 ACCESS read-write
		 STATUS mandatory
		 DESCRIPTION
		     "Default user name to use for automatically logging 
		     in the port.  Corresponds directly to PORT USERNAME 
		     and the value labeled 'Port n:' in the PORT 
		     CHARACTERISTICS display."
		 ::= { basicPortEntry 17 }

	     basicPortVerification OBJECT-TYPE
		 SYNTAX INTEGER { disabled(1), enabled(2) }
		 ACCESS read-write
		 STATUS mandatory
		 DESCRIPTION
		     "Control for display of informational messages on 
		     the port when the user connects, disconnects, or 
		     switches a session.  Corresponds directly to PORT 
		     VERIFICATION and the presence of the label 
		     'Verification' following the label 'Enabled 
		     Characteristics:' in the PORT CHARACTERISTICS 
		     display."
		 ::= { basicPortEntry 18 }

	     basicPortDefaultProtocol OBJECT-TYPE
		 SYNTAX INTEGER { lat(1), telnet(2), anylat(3), anytelnet(13) }
		 ACCESS read-write
		 STATUS mandatory
		 DESCRIPTION
		     "The session protocol to use when not otherwise 
		     specified.  Corresponds directly to PORT RESOLVE 
		     SERVICE and the value labeled 'Resolve Service:' in 
		     the PORT ALTERNATE CHARACTERISTICS display."
		 ::= { basicPortEntry 19 }

	     basicPortLogins OBJECT-TYPE
		 SYNTAX Counter
		 ACCESS read-only
		 STATUS mandatory
		 DESCRIPTION
		     "The number of logins on the port since system 
		     initialization.  Corresponds directly to the value 
		     labeled 'Local Accesses:' in the PORT COUNTERS 
		     display."
		 ::= { basicPortEntry 20 }

	     basicPortRemoteSessions OBJECT-TYPE
		 SYNTAX Counter
		 ACCESS read-only
		 STATUS mandatory
		 DESCRIPTION
		     "The number of remotely originating sessions to the 
		     port since system initialization.  Corresponds 
		     directly to the value labeled 'Remote Accesses:' in 
		     the PORT COUNTERS display."
		 ::= { basicPortEntry 21 }

	     basicPortIdleTimeouts OBJECT-TYPE
		 SYNTAX Counter
		 ACCESS read-only
		 STATUS mandatory
		 DESCRIPTION
		     "The number of session disconnects due to expiration 
		     of basicPortIdleTimeout.  Corresponds directly to 
		     the value labeled 'Idle Timeouts:' in the PORT 
		     COUNTERS display."
		 ::= { basicPortEntry 22 }

	     basicPortStatus OBJECT-TYPE
		 SYNTAX INTEGER { idle(1), local(2), waitInput(3),
				  executingCommand(4), connecting(5),
				  checkConnect(6), waitOutput(7),
				  connected(8), disconnecting(9),
				  disconnect(10), suspended(11),
				  locked(12), permanent(13),
				  loginWait(14), retryConnect(15),
				  connectWait(16), logout(17),
				  login(18), waitSession(19),
				  reset(20), testServiceWait(21),
				  testServiceOut(22), 
				  connectPassword(23),
				  waitLogout(24), waitQueue(25),
				  cancelQueue(26), autobaud(27),
				  available(28), checkModem(29),
				  slip(30), signalWait(31),
				  scriptSearch(32), scriptLoad(33),
				  scriptRun(34), dialback1(35),
				  dialback2(36), dialback3(37),
				  xremote(38), ppp(39), cslip(40),
				  arapInit(41), cclAnswer(42),
				  cclOriginate(43), cclHangup(44),
				  kerberos(45), securID(46), arapUser(47),
				  arapDialback(48), arapSearch(49),
				  arapLoad(50), arapRead(51), arapDialDone(52),
				  arapExit(53), arapEnabling(54),
				  arapConnecting(55), cclLoading(56),
				  cclLoadError(57), cclLoadWaiting(58),
				  cclExecute(59), cclDone(60), apd(61) }
		 ACCESS read-only
		 STATUS mandatory
		 DESCRIPTION
		     "The current operational status of the port.  
		     Corresponds directly to the value labeled 'Status:' 
		     in the PORT STATUS display."
		 ::= { basicPortEntry 23 }

	     basicPortLastInCharacter OBJECT-TYPE
		 SYNTAX INTEGER (0..255)
		 ACCESS read-only
		 STATUS mandatory
		 DESCRIPTION
		     "The character that most recently came into the 
		     port.  Corresponds directly to the value labeled 
		     'Last Char Input:' in the PORT STATUS display."
		 ::= { basicPortEntry 24 }

	     basicPortLastOutCharacter OBJECT-TYPE
		 SYNTAX INTEGER (0..255)
		 ACCESS read-only
		 STATUS mandatory
		 DESCRIPTION
		     "The character that most recently went out of the 
		     port.  Corresponds directly to the value labeled 
		     'Last Char Output:' in the PORT STATUS display."
		 ::= { basicPortEntry 25 }

	     basicPortActiveUserName OBJECT-TYPE
		 SYNTAX DisplayString (SIZE (0..16))
		 ACCESS read-only
		 STATUS mandatory
		 DESCRIPTION
		     "The user name currently logged into the port.  
		     Corresponds directly to the value by the port number 
		     and labeled 'Username' in the USERS display."
		 ::= { basicPortEntry 26 }

	     basicPortDefaultSessionMode OBJECT-TYPE
		 SYNTAX INTEGER { interactive(1), binary(2),
				  binaryWithFlow(3), transparent(4)  }
		 ACCESS read-write
		 STATUS mandatory
		 DESCRIPTION 
		     "Data recognition mode when starting a session,
		     with the following meanings:

		     interactive      locally recognize all controls
		     binary           recognize only session protocol
				      (corresponds to PASSALL)
		     binaryWithFlow   recognize only XON and XOFF
				      (corresponds to PASTHRU
		     transparent      recognize no data

		     Corresponds directly to PORT DEFAULT SESSION MODE
		     and the value labeled 'Default Session Mode:' in
		     the PORT ALTERNATE CHARACTERISTICS display."
		 ::= { basicPortEntry 27 }

	     basicPortZero OBJECT-TYPE
		 SYNTAX INTEGER  { ready(1), execute(2) }
		 ACCESS read-write
		 STATUS mandatory
		 DESCRIPTION
		     "Control to zero counters for the port.  In response 
		     to a get-request or get-next-request, the agent 
		     always returns 'ready' for this value.  Setting the 
		     value to 'ready' has no effect.  Setting it to 
		     'execute' causes the port's counters to be zeroed.  
		     Corresponds to the ZERO PORT command."
		 ::= { basicPortEntry 28 }

	     basicPortZeroTime OBJECT-TYPE
		 SYNTAX TimeTicks
		 ACCESS read-only
		 STATUS mandatory
		 DESCRIPTION
		     "The number of hundredths of a second since the most 
		     recent zeroing of the port's counters, such as 
		     through execution of basicPortZero.  Corresponds 
		     directly to the value labeled 'Seconds Since 
		     Zeroed:' in the PORT COUNTERS display."
		 ::= { basicPortEntry 29 }

	     basicPortUnixCommands OBJECT-TYPE
		 SYNTAX INTEGER { disabled(1), enabled(2),
				  primary(3), only(4) }
		 ACCESS read-write
		 STATUS mandatory
		 DESCRIPTION
		     "Control to allow the user to use Unix-style 
		     commands the port."
		 ::= { basicPortEntry 30 }

	     basicPortSessionMode OBJECT-TYPE
		 SYNTAX INTEGER { interactive(1), binary(2),
				  binaryWithFlow(3), transparent(4),
				  noActiveSessions(5)  }
		 ACCESS read-write
		 STATUS mandatory
		 DESCRIPTION
		     "Data recognition mode for an active session, with
		     the following meanings:

		     interactive      locally recognize all controls
		     binary           recognize only session protocol
				      (corresponds to PASSALL)
		     binaryWithFlow   recognize only XON and XOFF
				      (corresponds to PASTHRU
		     transparent      recognize no data
		     noActiveSessions no sessions on this port.

		     This object can be set to values of 1 to 4, but
		     only if there is an active session on the port."
		 ::= { basicPortEntry 31 }

	     basicPortRemoteDisconnectNotify OBJECT-TYPE
		 SYNTAX INTEGER { disabled(1), enabled(2) }
		 ACCESS read-write
		 STATUS mandatory
		 DESCRIPTION
		     "If enabled, a BELL (ctrl G) will be sent out the
		     serial port when a remote session is disconnected
		     and the port is logged out."
		 ::= { basicPortEntry 32 }

	 basicPortDefaultDestControlled  OBJECT-TYPE
		SYNTAX INTEGER { disabled(1), enabled(2) }
		ACCESS read-write
		STATUS mandatory
		DESCRIPTION
		    "A control to send preconfigured controlled port session
		     strings when entering or exiting a session established to
		     the basicPortDefaultDestName. Corresponds directly to the
		     value labeled '(Controlled)' following the label
		     'Dedicated/Preferred Service:' in the PORT CHARACTERISTICS
		     display."
		     ::= { basicPortEntry 33 }

	 basicPortControlledPortLogin  OBJECT-TYPE
		SYNTAX OCTET STRING (SIZE (0..32))
		ACCESS read-write
		STATUS mandatory
		DESCRIPTION
		    "A control string to send out the serial port upon
		     port login. Corresponds to the hexadecimal code which is
		     represented in ASCII following the label
		     'Controlled Port Login:' in the PORT CONTROLLED display."

		    ::= { basicPortEntry 34 }

	 basicPortControlledPortLogout  OBJECT-TYPE
		SYNTAX OCTET STRING (SIZE (0..32))
		ACCESS read-write
		STATUS mandatory
		DESCRIPTION
		    "A control string to send out the serial port upon
		     port logout. Corresponds to the hexadecimal code which is
		     represented in ASCII following the label
		     'Controlled Port Logout:' in the PORT CONTROLLED display."
		    ::= { basicPortEntry 35 }

	 basicPortControlledSessionInitialize  OBJECT-TYPE
		SYNTAX OCTET STRING (SIZE (0..32)) 
		ACCESS read-write
		STATUS mandatory
		DESCRIPTION
		    "A control string to send out the serial port upon
		     entering a session. Corresponds to the hexadecimal code 
		     which represented in ASCII following the label
		     'Controlled Session Initialize:' in the PORT CONTROLLED 
		     display."
		    ::= { basicPortEntry 36 }

	 basicPortControlledSessionTerminate  OBJECT-TYPE
		SYNTAX OCTET STRING (SIZE (0..32)) 
		ACCESS read-write
		STATUS mandatory
		DESCRIPTION
		    "A control string to send out the serial port upon
		     exiting a session. Corresponds to the hexadecimal code 
		     which is represented in ASCII following the label
		     'Controlled Session Terminate:' in the PORT CONTROLLED 
		     display."
		    ::= { basicPortEntry 37 }

	 basicPortRloginTransparentMode OBJECT-TYPE
		SYNTAX INTEGER { disabled(1), enabled(2) }
		ACCESS read-write
		STATUS mandatory 
		DESCRIPTION
		     "A control to pass x'ff' as binary data, not doubling x'ff'.
		Similar to basicPortSessionMode = transparent but for
		a rlogin session."
		 DEFVAL  { disabled }
			 ::= { basicPortEntry 38 }

	 basicPortLoginDuration OBJECT-TYPE
	     SYNTAX INTEGER  (0..64800)
	     ACCESS read-write
	     STATUS mandatory
	     DESCRIPTION
		 "The amount of time in minutes that a port may remain logged in
		  regardless of the activity on the port. The value 0 indicates
		  that the timer is disabled. Corresponds directly to the value
		  labeled 'Login Duration:' in the PORT ALTERNATE CHARACTERISTICS
		  display."
	     DEFVAL { 0 }
	     ::= { basicPortEntry 39 }

	 basicPortOutboundSecurity OBJECT-TYPE
	     SYNTAX INTEGER { disabled(1), enabled(2) }
	     ACCESS read-write
	     STATUS mandatory
	     DESCRIPTION
		 "Control to disable  outbound security, which can be either
		  Kerberos or SecureID, on a per port basis.  Corresponds
		  directly to the presence of the value 'OutboundSecurity'
		  following the label 'Enabled Characteristics' in the PORT
		  CHARACTERISTICS display."
	     DEFVAL { enabled }
	     ::= { basicPortEntry 40 }

	 basicPortXonTimer OBJECT-TYPE
	     SYNTAX INTEGER ( 0..2550 )
	     ACCESS read-write
	     STATUS mandatory
	     DESCRIPTION
		 "Indicates the number of seconds between successive 'XON's sent
		  out a port. A zero signifies that the timer is disabled.
		  Corresponds directly to the value labeled 'Xon Send Timer:' in
		  the PORT ALTERNATE CHARACTERISTICS display."
	     DEFVAL { 0 }
	     ::= { basicPortEntry 41 }

	 basicPortDefaultDedicatedSessionType OBJECT-TYPE
	     SYNTAX INTEGER ( 0..168 )
	     ACCESS read-write
	     STATUS mandatory
	     DESCRIPTION
		"This integer is interpreted as a bit mask that specifies the
                 default session type for a 
		 dedicated service for this port. The bit numbers are:
		 1;service name, 2;node name, 3;port name, 4, telnet
		 console; 5, rlogin; 6, bridge console; 7, chassis console."
	     DEFVAL { '0'h } 
	     ::= { basicPortEntry 42 }

	 basicPortIdleTimeReceive OBJECT-TYPE
	     SYNTAX INTEGER { disabled(1), enabled(2) }
	     ACCESS read-write
	     STATUS mandatory
	     DESCRIPTION
		 "Control to restrict the basicPortIdleTimeout to apply to data
		  received from the network and transmitted out the serial port.
		  Data received by the serial port will not be considered
		  activity. Corresponds directly to the value labeled 'Idle
		  Time Receive Mode:' in the PORT ALTERNATE CHARACTERISTICS
		  display."
	     DEFVAL { disabled }
	     ::= { basicPortEntry 43 }

	 basicPortIdleTimeTransmit OBJECT-TYPE
	     SYNTAX INTEGER { disabled(1), enabled(2) }
	     ACCESS read-write
	     STATUS mandatory
	     DESCRIPTION
		 "Control to restrict the basicPortIdleTimeout to apply to data
		  received from the serial port and transmitted out the LAN.
		  Data received from the network will not count as activity.
		  Corresponds directly to the value labeled 'Idle Time Transmit
		  Mode:' in the PORT ALTERNATE CHARACTERISTICS display."
	     DEFVAL { disabled }
	     ::= { basicPortEntry 44 }

	 basicPortZeroDisconnectSession OBJECT-TYPE
	     SYNTAX INTEGER { disabled(1), enabled(2) }
	     ACCESS read-write
	     STATUS mandatory 
	     DESCRIPTION
		 "A control to disconnect a session at Port 0 when the
		  password limit is reached."
	     DEFVAL  { disabled }
	     ::= { basicPortEntry 45 } 

	 basicPortConsolePort OBJECT-TYPE
	     SYNTAX  INTEGER { disabled(1), enabled(2) }
	     ACCESS  read-write
	     STATUS  mandatory
	     DESCRIPTION
		 "Control to configure this port as a console port. This
		  control is only valid on those models with variable 
		  configuration ports. This object can only be set enabled;
		  and doing so will disable basicPortSensor
		  and basicPortAlarmControl.
		  A set will only update the permanent database. Use a 
		  charPortReset for this change to take effect."
	 DEFVAL { enabled }
	 ::= { basicPortEntry 46 }

	 basicPortLoginPassword OBJECT-TYPE
	     SYNTAX DisplayString (SIZE (0..16))
	     ACCESS read-write
	     STATUS mandatory
	     DESCRIPTION
		 "The password a user must enter to be given the 
		 opportunity to log in to a given port. For security
		 reasons reading this object always returns a zero-length 
		 value. Corresponds directly to PORT LOGIN PASSWORD."
	     ::= { basicPortEntry 47 }

	 basicPortSensor OBJECT-TYPE
	     SYNTAX  INTEGER { disabled(1), enabled(2) }
	     ACCESS  read-write
	     STATUS  mandatory
	     DESCRIPTION
		 "Control to configure this port as a temperature and humidity
		  sensor. This control is only valid on those models with 
		  variable configuration ports. This object can only be set
		  enabled; and doing so will disable basicPortConsolePort
		  and basicPortAlarmControl.
		  A set will only update the permanent database. Use a 
		  charPortReset for this change to take effect."
	 DEFVAL { disabled }
	 ::= { basicPortEntry 48 }

	 basicPortAlarmControl OBJECT-TYPE 
	     SYNTAX  INTEGER { disabled(1), enabled(2) }
	     ACCESS  read-write
	     STATUS  mandatory
	     DESCRIPTION
		 "Control to configure this port for alarm input and control
                  output. This control is
		  only valid on those models with variable configuration ports.
		  This object can only be set enabled; and doing so will 
                  disable basicPortConsolePort and basicPortSensor.
		  A set will only update the permanent database. Use a 
		  charPortReset for this change to take effect."
	 DEFVAL { disabled }
	 ::= { basicPortEntry 49 }

	 basicPortCommandLogging OBJECT-TYPE
	     SYNTAX INTEGER { disabled(1), enabled(2) }
	     ACCESS read-write
	     STATUS mandatory
	     DESCRIPTION
		 "A control to toggle logging of commands at this port. 
		  Command input may be logged from direct terminal 
		  connections, session input from the LAN, or session output 
		  to the LAN. Corresponds directly to the presence of 'Command
		  Logging' under the label 'Enabled Characteristics:' in the 
		  PORT CHARACTERISTICS display. The desired change will not 
		  take effect until the port is logged off."
	     DEFVAL { disabled  }
	     ::= { basicPortEntry 50 }                

          basicPortBreakSequence OBJECT-TYPE
              SYNTAX OCTET STRING (SIZE (0..16)) 
              ACCESS read-write
              STATUS mandatory
              DESCRIPTION
                  "A sequence of characters to be sent out the serial port on
                   receipt of a Break from the network in lieu of a hardware
                   break. The sequence entered by the user is converted into
                   an octet string up to four bytes long to be sent out the
                   serial port. For example, the user's representation of 
                   octal 2, or '\002', takes four characters in
                   basicPortBreakSequence; but only one byte in the string
                   sent out the serial port."
              DEFVAL { '00'h }  -- the null string
              ::= { basicPortEntry 51 }                

 	basicPortTl1Mode OBJECT-TYPE
		SYNTAX INTEGER { disabled(1), hml(2), mml(3), mmlNoEcho(4) }
		ACCESS read-write
		STATUS mandatory
		DESCRIPTION
	           "Controls the TL1 mode of a port. Valid TL1 modes are human-
                    to-machine language (hml), machine-to-machine language 
		    (mml), and MML without echo. MML is for direct connection
                    to another TL1 device whereas HML provides human prompts.
                    A change takes effect after logging out the port."
		DEFVAL { disabled } 
		::= { basicPortEntry 53 }

 	basicPortTl1Console OBJECT-TYPE
		SYNTAX INTEGER { disabled(1), enabled(2) }
		ACCESS read-write
		STATUS mandatory
		DESCRIPTION
		    "Controls whether this port becomes the TL1 console
		    receiving and displaying autonomous reports of alarm
		    events. A change takes effect after logging out the port."
		DEFVAL {disabled }
		::= { basicPortEntry 54 }
 
 	basicPortFallThrough OBJECT-TYPE
		SYNTAX INTEGER { disabled(1), enabled(2) }
		ACCESS read-write
		STATUS mandatory
		DESCRIPTION
                    "Control to allow a user to login to a port after RADIUS
                     or SecurID authentication fails because the RADIUS servers
                     or SecurID servers are unavailable. When a user is logged
                     in via 'fallthrough', he is logged in to the port as a  
                     non-privileged user. The change takes effect after logging
                     out the port."
		DEFVAL {disabled }
		::= { basicPortEntry 55 }

 	basicPortCommandLoggingSuppressControlCharacters OBJECT-TYPE
		SYNTAX INTEGER { disabled(1), enabled(2) }
		ACCESS read-write
		STATUS mandatory
		DESCRIPTION
                    "Control to toggle suppression of control characters in the
                     command log. This object can only be set to enabled
                     when command logging is enabled on that port."
		DEFVAL {disabled }
		::= { basicPortEntry 56 }

 	basicPortDataLogging OBJECT-TYPE
		SYNTAX INTEGER { disabled(1), enabled(2) }
		ACCESS read-write
		STATUS mandatory
		DESCRIPTION
                    "Control to toggle data logging on the specified port."
		DEFVAL {disabled }
		::= { basicPortEntry 57 }

 	basicPortDataLoggingSuppressControlCharacters OBJECT-TYPE
		SYNTAX INTEGER { disabled(1), enabled(2) }
		ACCESS read-write
		STATUS mandatory
		DESCRIPTION
                    "Control to toggle suppression of control characters in the
                     data log. This object can only be set to enabled
                     when data logging is enabled on that port."
		DEFVAL {disabled }
		::= { basicPortEntry 58 }

        basicPortOnboardSecurity OBJECT-TYPE
	        SYNTAX INTEGER { disabled(1), enabled(2) }
	        ACCESS read-write
	        STATUS mandatory
	        DESCRIPTION
                    "A control to toggle onboard security for this port where
                     the username and password are authenticated against an
                     internal access list. The desired change will not take
                     effect until the port is logged off."
                DEFVAL { disabled }
	        ::= { basicPortEntry 59 }

 	basicPortFallBack OBJECT-TYPE
		SYNTAX INTEGER { disabled(1), enabled(2) }
		ACCESS read-write
		STATUS mandatory
		DESCRIPTION
                    "Control to allow a 'fallback' authentication mechanism
                     after RADIUS or SecurID authentication fails because the
                     RADIUS or SecurID servers are unavailable. Onboard 
                     security, an internal security database, is
                     used for fallback authentication. The user in fallback
                     mode must enter a valid username and password to be
                     successfully logged in. The change takes effect after
                     logging out the port."
		DEFVAL {disabled }
		::= { basicPortEntry 60 }


 	basicPortAlarmMaster OBJECT-TYPE
		SYNTAX INTEGER { disabled(1), enabled(2) }
		ACCESS read-write
		STATUS mandatory
		DESCRIPTION
		 "Control to configure this port for high densitiy alarm 
                  input and control output management. This control is
		  only valid on those models with variable configuration ports.
		  This object can only be set enabled; and doing so will 
                  disable basicPortConsolePort, basicPortSensor and 
                  basicPortAlarmControl. A set will only update the permanent 
                  database. Use a charPortReset for this change to take effect."
		DEFVAL {disabled }
		::= { basicPortEntry 61 }

 	basicPortAlarmMasterAccounting OBJECT-TYPE
		SYNTAX INTEGER { disabled(1), enabled(2) }
		ACCESS read-write
		STATUS mandatory
		DESCRIPTION
                    "Control to toggle logging of alarm events on this port.
		     Use a charPortReset for this change to take effect."
		DEFVAL {disabled }
		::= { basicPortEntry 62 }

 	basicPortAlarmMasterAudibleAlarm OBJECT-TYPE
		SYNTAX INTEGER { disabled(1), enabled(2) }
		ACCESS read-write
		STATUS mandatory
		DESCRIPTION
                    "Control whether the alarm will have an audible sound for
                     all alarm points attached to this port."
		DEFVAL {disabled }
		::= { basicPortEntry 63 }

 	basicPortAlarmMasterFixTime OBJECT-TYPE 
		SYNTAX INTEGER ( 1 .. 720 )
		ACCESS read-write
		STATUS mandatory
		DESCRIPTION
                    "Time in minutes between audible alarm soundings for an alarm 
                     master port. This occurs after someone hits the master alarm 
                     reset button. If there is at least one alarm condition on an 
                     alarm point within the fix time, then the alarm will sound 
                     again at the end of that fix time."
		DEFVAL { 30 }
		::= { basicPortEntry 64 }

 	basicPortAlarmMasterLcdDisplayString OBJECT-TYPE
		SYNTAX DisplayString (SIZE (32))
		ACCESS read-write
		STATUS mandatory
		DESCRIPTION
                    "Updates the LCD display message for the high density
                    alarm unit attached to the port. Corresponds directly 
                    to the DISPLAY AMST command."
		::= { basicPortEntry 65 }

 	basicPortAlarmMasterReboot OBJECT-TYPE
		SYNTAX INTEGER { ready(1), execute(2) }
		ACCESS read-write
		STATUS mandatory
		DESCRIPTION
                    "Control to reboot the high density alarm unit attached
                     to the port when set to 'execute'. In response to a 
                    get-request or get-next-request, the agent always 
                    returns 'ready' for this value.  Setting the value 
                    to 'ready' has no effect. Corresponds directly to the
                    REBOOT AMST command."
		::= { basicPortEntry 66 }


 	basicPortAlarmMasterUpdateFirmwareHost OBJECT-TYPE
		SYNTAX IpAddress
		ACCESS read-write
		STATUS mandatory
		DESCRIPTION
                    "The internet address of the server to use when 
                    downloading a new firmware image for the high density
                    alarm unit attached to this port via TFTP. 

                    Corresponds directly to the UPDATE AMST FIRMWARE
                    command's INTERNET ADDRESS parameter."
		::= { basicPortEntry 67 }

 	basicPortAlarmMasterUpdateFirmwareFileName OBJECT-TYPE
		SYNTAX DisplayString (SIZE (0..64))
		ACCESS read-write
		STATUS mandatory
		DESCRIPTION
                    "The filename to request when downloading a
                    new firmware image for the high density alarm
                    unit attached to this port via TFTP. 

                    Corresponds directly to the UPDATE AMST FIRMWARE
                    command's FILE parameter."
		::= { basicPortEntry 68 }

 	basicPortAlarmMasterUpdateFirmware OBJECT-TYPE
		SYNTAX INTEGER { ready(1), execute(2) }
		ACCESS read-write
		STATUS mandatory
		DESCRIPTION
                    "Control to update firmware for the high density alarm unit 
                    attached to the port when set to 'execute'. In response to a 
                    get-request or get-next-request, the agent always 
                    returns 'ready' for this value.  Setting the value 
                    to 'ready' has no effect. 

                    The basicPortAlarmMasterUpdateFirmwareHost
                    and basicPortAlarmMasterUpdateFirmwareFileName must be set
                    prior to setting this object.

                    Corresponds directly to the UPDATE AMST FIRMWARE command."
		::= { basicPortEntry 69 }

 	basicPortAlarmMasterStatus OBJECT-TYPE
	       SYNTAX  INTEGER { cleared (1), indeterminate (2), warning (3), 
        	                 minor (4), major (5), critical (6) }
		ACCESS read-only
		STATUS mandatory
		DESCRIPTION
                    "Indicates the current status of the high density
                     alarm unit attached to the port. If no response is
                     obtained from this unit, the status is set to
                     basicPortAlarmMasterFaultSeverity. Otherwise it is cleared."
		::= { basicPortEntry 70 }

 	basicPortAlarmMasterFaultSeverity OBJECT-TYPE
	       SYNTAX  INTEGER { indeterminate (2), warning (3), 
        	                 minor (4), major (5), critical (6) }
		ACCESS read-write
		STATUS mandatory
		DESCRIPTION
        	   "Control to determine the severity level associated with the
	            trap sent out when a fault occurs when no response is
		    obtained from the high density alarm unit attached to this
                    port."
                DEFVAL { major }
		::= { basicPortEntry 71 }


        basicPortPowerMaster OBJECT-TYPE
               SYNTAX  INTEGER { disabled (1), enabled (2) }
                ACCESS read-write
                STATUS mandatory
                DESCRIPTION
                   "Control to configure this port as a power master port.
                    This control is only valid on those models with variable 
                    configuration ports and which support the power master.
                    This object can only be set enabled, and doing so will 
                    disable the previous port type, such as basicPortConsolePort.
                    A set will only update the permanent database. Use a 
                    charPortReset for this change to take effect."
                DEFVAL { disabled }
                ::= { basicPortEntry 72 }

        basicPortPowerMasterTimeDelay OBJECT-TYPE
               SYNTAX  INTEGER { none (1), oneHundred (100), twoHundred (200),
                                 threeHundred (300), fourHundred (400),
                                 fiveHundred (500), sixHundred (600), 
                                 sevenHundred (700), eightHundred (800), 
                                 nineHundred (900) }
                ACCESS read-write
                STATUS mandatory
                DESCRIPTION
                   "Control to set the power up delay interval in milliseconds for
                    the power device attached to this port. A response of 'none'
                    to a get-request or get-next-request may indicate that the
                    power unit attached to this port is not responding with status."
                DEFVAL { none }
                ::= { basicPortEntry 73 }

        basicPortPowerMasterSwitch OBJECT-TYPE
               SYNTAX  INTEGER { ready (1), off (2), on (3) }
                ACCESS read-write
                STATUS mandatory
                DESCRIPTION
                   "Control to power on or off all of the outlets in the power
                    device attached to this port. A get-request or a get-next-
                    request always returns ready."
                ::= { basicPortEntry 74 }

        basicPortPowerMasterModel OBJECT-TYPE
               SYNTAX  DisplayString (SIZE (0..20))
                ACCESS read-only
                STATUS mandatory
                DESCRIPTION
                   "The model number of the power master device, which
                    is connected to this port. A response of a null string to
                    a get-request or get-next-request indicates that the power
                    unit attached to this port is not responding with status."
                ::= { basicPortEntry 75 }

        basicPortPowerMasterSerialNumber OBJECT-TYPE
               SYNTAX  DisplayString (SIZE (0..17))
                ACCESS read-only
                STATUS mandatory
                DESCRIPTION
                   "The serial number of the power master device, which
                    is connected to this port.  A response of a null string to
                    a get-request or get-next-request indicates that the power
                    unit attached to this port is not responding with status."
                ::= { basicPortEntry 76 }

       basicPortPowerMasterFirmware OBJECT-TYPE
               SYNTAX  DisplayString (SIZE (0..12))
                ACCESS read-only
                STATUS mandatory
                DESCRIPTION
                   "The firmware version of the power master device, which is
                    connected to this port.  A response of a null string to
                    a get-request or get-next-request indicates that the power
                    unit attached to this port is not responding with status."
                ::= { basicPortEntry 77 }

        basicPortLockout OBJECT-TYPE
               SYNTAX  INTEGER { disabled (1), enabled (2) }
                ACCESS read-write
                STATUS mandatory
                DESCRIPTION
                   "Control to prohibit access to this port and send a trap
                    when login authentication fails.
                    One must log out the port for this change to take effect."
                DEFVAL { disabled }
                ::= { basicPortEntry 78 }
 
        basicPortAsciiToTrapTranslation OBJECT-TYPE
               SYNTAX  INTEGER { disabled (1), enabled (2) }
                ACCESS read-write
                STATUS mandatory
                DESCRIPTION
                   "Control to configure the port as an ascii-to-trap translator.
                    One must log out the port for this change to take effect."
                DEFVAL { disabled }
                ::= { basicPortEntry 79 }
 
        basicPortAsciiToTrapTranslationTrapSeverity OBJECT-TYPE
               SYNTAX  INTEGER { cleared (1), indeterminate (2), warning (3),
                                 minor (4), major (5), critical (6) }
                ACCESS read-write
                STATUS mandatory
                DESCRIPTION
                   "Control to determine the severity level associated with the
                    trap sent out from this port. One must log out the port
                    for this change to take effect."
                DEFVAL { cleared }
                ::= { basicPortEntry 80 }
 
        basicPortAsciiToTrapTranslationMessages OBJECT-TYPE
               SYNTAX  Counter
                ACCESS read-only
                STATUS mandatory
                DESCRIPTION
                   "Count of number of trap messages sent from this port."
                ::= { basicPortEntry 81 }
 
        basicPortAsciiToTrapTranslationLastMessage OBJECT-TYPE
               SYNTAX  DisplayString  (SIZE(0..255))
                ACCESS read-only
                STATUS mandatory
                DESCRIPTION
                   "The last message or partial message sent out by this port."
                ::= { basicPortEntry 82 }
 
        basicPortPowerMasterAlarmSeverity OBJECT-TYPE
               SYNTAX  INTEGER { indeterminate (2), warning (3), minor (4), major (5), 
	                         critical (6) }
                ACCESS read-write
                STATUS mandatory
                DESCRIPTION
                   "Control to determine the severity level associated with the trap sent out when
                    the power device is not responding to this port."
                DEFVAL { major } 
                ::= { basicPortEntry 83 }

        basicPortPowerMasterDeviceStatus OBJECT-TYPE
               SYNTAX  INTEGER { cleared (1), indeterminate (2), warning (3), minor (4), major (5), 
	                         critical (6) }
                ACCESS read-only
                STATUS mandatory
                DESCRIPTION
                   "Indicates the current status of the power device controlled by this port. If 
                    the device is responding, the status is cleared. Otherwise the status matches
                    the basicPortPowerMasterAlarmSeverity."
                ::= { basicPortEntry 84 }

	basicPortBuffering OBJECT-TYPE
		SYNTAX  INTEGER { disabled (1), enabled (2) }
		 ACCESS read-write
		 STATUS mandatory
		 DESCRIPTION
		    "Control to allow data from an attached device to be 
                     retained across multiple sessions. When a session is 
                     established to a port with buffering, the contents of the
                     command buffer is sent to the remote device. 
		     One must log out the port for this change to take effect."
		 DEFVAL { disabled }
		 ::= { basicPortEntry 85 }

	basicPortLogFacilityLevel OBJECT-TYPE
                SYNTAX INTEGER { none (1), local0(2), local1(3), local2(4),
                                 local3(5), local4(6), local5(7),
                                 local6(8), local7(9), user(10) }
		 ACCESS read-write
		 STATUS mandatory
		 DESCRIPTION
		    "Indicates that server originated accounting messages 
                     pertaining to this port are logged to the syslog host at
                     this UNIX facility level. If 'none', the server's 
                     sessionLogFacility is used."
		 DEFVAL { none }
		 ::= { basicPortEntry 86 }


	basicPortPppDialBackup OBJECT-TYPE
		SYNTAX  INTEGER { disabled (1), enabled (2) }
		 ACCESS read-write
		 STATUS mandatory
		 DESCRIPTION
		    "Indicates whether this port is configured as a PPP dial 
                     backup port. This parameter will not take effect until
                     the port is logged out, and this function is restricted
                     to one port."
		 DEFVAL { disabled }
		 ::= { basicPortEntry 87 }

	basicPortPppDialBackupNumber OBJECT-TYPE
		SYNTAX  DisplayString (SIZE (0..32))
		 ACCESS read-write
		 STATUS mandatory
		 DESCRIPTION
		    "The number to dial when a PPP dial backup link is 
                     activated, which occurs when the network is down and
                     there are SNMP traps to forward. The port must be
                     a basicPortPppDialBackup port, and it must be logged 
                     out for the change to take effect."
		 ::= { basicPortEntry 88 }

	basicPortPppDialBackupRedialTimer OBJECT-TYPE
		SYNTAX  INTEGER ( 30..65535 )
		 ACCESS read-write
		 STATUS mandatory
		 DESCRIPTION
		    "Indicates the time in seconds to wait before redialing the
                     basicPortPppDialBackupNumber on a basicPortPppDialBackup
                     port."
		 DEFVAL { 30 }
		 ::= { basicPortEntry 89 }

	basicPortPppDialBackupRedialRetries OBJECT-TYPE
		SYNTAX  INTEGER (1..65535)
		 ACCESS read-write
		 STATUS mandatory
		 DESCRIPTION
		    "Indicates the number of time to try to dial the backup
                     number before recording an error, logging out the port,
                     and if there are new traps trying to dial again."
		 DEFVAL { 10 }
		 ::= { basicPortEntry 90 }

	basicPortPppDialBackupDisconnectTimer OBJECT-TYPE
		SYNTAX  INTEGER (1..65535)
		 ACCESS read-write
		 STATUS mandatory
		 DESCRIPTION
		    "Indicates the time in seconds that the dial backup link
                     will stay up when there is no more SNMP traffic flowing
                     prior to disconnecting it."
		 DEFVAL { 30 }
		 ::= { basicPortEntry 91 }

	basicPortPppDialBackupLocalAddress OBJECT-TYPE
		SYNTAX IpAddress
		 ACCESS read-write
		 STATUS mandatory
		 DESCRIPTION
		    "The local address to use in a PPP dial backup link when
                     the network connection is down and there are SNMP traps
                     to forward."
		 ::= { basicPortEntry 92 }

	basicPortPppDialBackupDestinationAddress OBJECT-TYPE
		SYNTAX IpAddress
		 ACCESS read-write
		 STATUS mandatory
		 DESCRIPTION
		    "The destination address to use in a PPP dial backup link
                     when the network connection is down and there are SNMP
                     traps to forward."
		 ::= { basicPortEntry 93 }

	basicPortPppDialBackupAddresses OBJECT-TYPE
                SYNTAX INTEGER  { ready(1), execute(2) }
                ACCESS read-write
                STATUS mandatory
                DESCRIPTION
                    "Control to initiate dialing from a dial backup port. In
                    response to get-request or get-next-request, the agent 
                    always returns 'ready' for this value.  Setting the value 
                    to 'ready' has no effect.  Setting it to 'execute' 
                    after a valid basicPortPppDialBackupLocalAddress and 
                    basicPortPppDialBackupDestinationAddress are configured
                    causes the basicPortPppDialBackup port to dial the
                    basicPortPppDialBackupNumbermber."
		 ::= { basicPortEntry 94 }



            -- the Basic Serial Port table
            
            basicSerialPortTable OBJECT-TYPE
                SYNTAX SEQUENCE OF BasicSerialPortEntry
                ACCESS not-accessible
                STATUS mandatory
                DESCRIPTION
                    "A list of basic character serial port entries."
                ::= { xBasic 18 }
            
            basicSerialPortEntry OBJECT-TYPE
                SYNTAX BasicSerialPortEntry
                ACCESS not-accessible
                STATUS mandatory
                DESCRIPTION
                    "Basic parameter values for a serial port."
                INDEX { basicSerialPortIndex }
                ::= { basicSerialPortTable 1 }
            
            BasicSerialPortEntry ::=
                SEQUENCE {
                    basicSerialPortIndex
                        INTEGER,
                    basicSerialPortBreak
                        INTEGER,
                    basicSerialPortInterrupts
                        INTEGER,
                    basicSerialPortNoLoss
                        INTEGER,
                    basicSerialPortPause
                        INTEGER,
                    basicSerialPortPrompt
                        DisplayString,
                    basicSerialPortTerminalType
                        INTEGER,
                    basicSerialPortTypeaheadLimit
                        INTEGER,
                    basicSerialPortBackwardSwitch
                        INTEGER,
                    basicSerialPortForwardSwitch
                        INTEGER,
                    basicSerialPortLocalSwitch
                        INTEGER,
                    basicSerialPortModemControl
                        INTEGER,
                    basicSerialPortSignalCheck
                        INTEGER,
                    basicSerialPortDSRLogout
                        INTEGER,
                    basicSerialPortDSRObserve
                        INTEGER,
                    basicSerialPortDCDTimeout
                        INTEGER,
                    basicSerialPortDTRAssert
                        INTEGER,
                    basicSerialPortLimitedCommands
                        INTEGER,
                    basicSerialPortLimitedView
                        INTEGER,
                    basicSerialPortPassword
                        INTEGER,
                    basicSerialPortLineEditor
                        INTEGER,
                    basicSerialPortLineEditorBackspace
                        INTEGER,
                    basicSerialPortLineEditorBeginning
                        INTEGER,
                    basicSerialPortLineEditorCancel
                        INTEGER,
                    basicSerialPortLineEditorDeleteBeginning
                        INTEGER,
                    basicSerialPortLineEditorDeleteLine
                        INTEGER,
                    basicSerialPortLineEditorEnd
                        INTEGER,
                    basicSerialPortLineEditorForward
                        INTEGER,
                    basicSerialPortLineEditorInsertToggle
                        INTEGER,
                    basicSerialPortLineEditorNextLine
                        INTEGER,
                    basicSerialPortLineEditorPreviousLine
                        INTEGER,
                    basicSerialPortLineEditorQuotingCharacter
                        INTEGER,
                    basicSerialPortLineEditorRedisplay
                        INTEGER,
                    basicSerialPortQuadartReceiveDiscard
                        INTEGER,
                    basicSerialPortAPDProtocols 
                        OCTET STRING,
                    basicSerialPortAPDTimeout 
                        INTEGER,
                    basicSerialPortAPDDefaultProtocol 
                        OCTET STRING,
                    basicSerialPortUsernameCharSet
                        INTEGER,
                    basicSerialPortAutoHangup
                        INTEGER,
                    basicSerialPortCommandSize
                        INTEGER,
                    basicSerialPortAutoProtocolDetectPrompt
                        INTEGER,
                    basicSerialPortUsernamePrompt
                        DisplayString,
                    basicSerialPortPasswordPrompt
                        DisplayString,
                    basicSerialPortAutoProtocolDetectSecurityInteractiveOnly
                        INTEGER,
                    basicSerialPortDedicatedUserData
                        DisplayString,
                    basicSerialPortIpAutoDiscovery 
                        INTEGER,
                    basicSerialPortDedicatedKickStartData
                        DisplayString,
                    basicSerialPortBreakLength
                        INTEGER,
                    basicSerialPortRotaryRoundRobin
                        INTEGER,
                    basicSerialPortWelcomeBeforeAuthentication
                        INTEGER,
                    basicSerialPortGatewayAutoDiscovery 
                        INTEGER,
                    basicSerialPortSubnetAutoDiscovery 
                        INTEGER,
                    basicSerialPortRaiseLowerDtr
                        INTEGER,
                    basicSerialPortRaiseControlDtr
                        INTEGER,
	            basicSerialPortIpConfigureBootp 
                        INTEGER
                     }
            
            basicSerialPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { basicSerialPortEntry 1 }
            
            basicSerialPortBreak OBJECT-TYPE
                SYNTAX INTEGER { ignore(1), localSwitch(2),
                                 sendRemote(3) }
                ACCESS read-write
                STATUS mandatory
                DESCRIPTION
                    "Action to take on a BREAK condition from the port.  
                    Corresponds directly to PORT BREAK and the value 
                    labeled 'Break:' in the PORT CHARACTERISTICS 
                    display."
                ::= { basicSerialPortEntry 2 }
            
            basicSerialPortInterrupts OBJECT-TYPE
                SYNTAX INTEGER { disabled(1), enabled(2) }
                ACCESS read-write
                STATUS mandatory
                DESCRIPTION
                    "Control for recognizing BREAK or local switch to 
                    interrupt a session.  Corresponds directly to PORT 
                    INTERRUPTS and the presence of the label 
                    'Interrupts' following the label 'Enabled 
                    Characteristics:' in the PORT CHARACTERISTICS 
                    display."
                ::= { basicSerialPortEntry 3 }
            
            basicSerialPortNoLoss OBJECT-TYPE
                SYNTAX INTEGER { disabled(1), enabled(2) }
                ACCESS read-write
                STATUS mandatory
                DESCRIPTION
                    "Control for storing port input locally in 
                    anticipation of session startup.  Corresponds 
                    directly to PORT NOLOSS and the presence of the 
                    label 'Noloss' following the label 'Enabled 
                    Characteristics:' in the PORT CHARACTERISTICS 
                    display."
                ::= { basicSerialPortEntry 4 }
            
            basicSerialPortPause OBJECT-TYPE
                SYNTAX INTEGER { disabled(1), enabled(2) }
                ACCESS read-write
                STATUS mandatory
                DESCRIPTION
                    "Control for pausing after each screenful of 
                    locally-originated output to the port.  Corresponds 
                    directly to PORT PAUSE and the presence of the label 
                    'Pause' following the label 'Enabled 
                    Characteristics:' in the PORT CHARACTERISTICS 
                    display."
                ::= { basicSerialPortEntry 5 }
            
            basicSerialPortPrompt OBJECT-TYPE
                SYNTAX DisplayString (SIZE (0..20))
                ACCESS read-write
                STATUS mandatory
                DESCRIPTION
                    "Prompt for the system to use on the port.  
                    Corresponds directly to PORT PROMPT and the value 
                    labeled 'Prompt:' in the PORT ALTERNATE 
                    CHARACTERISTICS display."
                ::= { basicSerialPortEntry 6 }
            
            basicSerialPortTerminalType OBJECT-TYPE
                SYNTAX INTEGER { ansi(1), hardcopy(2), softcopy(3) }
                ACCESS read-write
                STATUS mandatory
                DESCRIPTION
                    "Type of terminal attached to the port, for 
                    formatting local output.  Corresponds directly to 
                    PORT TYPE and the value labeled 'Type:' in the PORT 
                    CHARACTERISTICS display."
                ::= { basicSerialPortEntry 7 }
            
            basicSerialPortTypeaheadLimit OBJECT-TYPE
                SYNTAX INTEGER (80..16384)
                ACCESS read-write
                STATUS mandatory
                DESCRIPTION
                    "Maximum number of input characters to hold pending 
                    tranmission on a session.  Corresponds directly to 
                    PORT TYPEAHEAD SIZE and the value labeled 'Typeahead 
                    Size:' in the PORT ALTERNATE CHARACTERISTICS 
                    display."
                ::= { basicSerialPortEntry 8 }
            
            basicSerialPortBackwardSwitch OBJECT-TYPE
                SYNTAX INTEGER (0..255)
                ACCESS read-write
                STATUS mandatory
                DESCRIPTION
                    "Character input from the character port to cause a 
                    switch to the previous, lower numbered session.  The 
                    value 0 indicates no character has this effect.  
                    Corresponds directly to PORT BACKWARD SWITCH and the 
                    value labeled 'Backwards Switch:' in the PORT 
                    CHARACTERISTICS display."
                ::= { basicSerialPortEntry 9 }
            
            basicSerialPortForwardSwitch OBJECT-TYPE
                SYNTAX INTEGER (0..255)
                ACCESS read-write
                STATUS mandatory
                DESCRIPTION
                    "Character input from the character port to cause a 
                    switch to the next, higher numbered session.  The 
                    value 0 indicates no character has this effect.  
                    Corresponds directly to PORT FORWARD SWITCH and the 
                    value labeled 'Forwards Switch:' in the PORT 
                    CHARACTERISTICS display."
                ::= { basicSerialPortEntry 10 }
            
            basicSerialPortLocalSwitch OBJECT-TYPE
                SYNTAX INTEGER (0..255)
                ACCESS read-write
                STATUS mandatory
                DESCRIPTION
                    "Character input from the character port to cause a 
                    switch to local command mode.  The value 0 indicates 
                    no character has this effect.  Corresponds directly 
                    to PORT LOCAL SWITCH and the value labeled 'Local 
                    Switch:' in the PORT CHARACTERISTICS display."
                ::= { basicSerialPortEntry 11 }
            
            basicSerialPortModemControl OBJECT-TYPE
                SYNTAX INTEGER { disabled(1), enabled(2) }
                ACCESS read-write
                STATUS mandatory
                DESCRIPTION
                    "Control for observing hardware modem control 
                    signals.  Corresponds directly to PORT MODEM CONTROL 
                    and the value labeled 'Modem Control:' in the PORT 
                    CHARACTERISTICS display. This object is not available
                    on units that do not support modem signals (ie 2220)."
                ::= { basicSerialPortEntry 12 }
            
            basicSerialPortSignalCheck OBJECT-TYPE
                SYNTAX INTEGER { disabled(1), enabled(2) }
                ACCESS read-write
                STATUS mandatory
                DESCRIPTION
                    "Control for observing DSR and DCD to bound allowing 
                    sessions.  Corresponds directly to PORT SIGNAL CHECK 
                    and the presence of the label 'Signal Check' 
                    following the label 'Enabled Characteristics:' in 
                    the PORT CHARACTERISTICS display. This object is not 
                    available on units that do not support modem signals 
                    (ie 2220)."
                ::= { basicSerialPortEntry 13 }
            
            basicSerialPortDSRLogout OBJECT-TYPE
                SYNTAX INTEGER { disabled(1), enabled(2) }
                ACCESS read-write
                STATUS mandatory
                DESCRIPTION
                    "Control for logging out the port when DCD is 
                    deasserted.  Corresponds directly to PORT DSRLOGOUT 
                    and the presence of the label 'DSRlogout' following 
                    the label 'Enabled Characteristics:' in the PORT 
                    CHARACTERISTICS display. This object is not available
                    on units that do not support modem signals (ie 2220)."
                ::= { basicSerialPortEntry 14 }
            
            basicSerialPortDSRObserve OBJECT-TYPE
                SYNTAX INTEGER { disabled(1), enabled(2) }
                ACCESS read-write
                STATUS mandatory
                DESCRIPTION
                    "Control for beginning the login sequence on the 
                    port when DCD is asserted.  Corresponds directly to 
                    PORT DSRWAIT and the presence of the label 'DSRwait' 
                    following the label 'Enabled Characteristics:' in 
                    the PORT CHARACTERISTICS display. This object is not 
                    available on units that do not support modem signals
                    (ie 2220)."
                ::= { basicSerialPortEntry 15 }
            
            basicSerialPortDCDTimeout OBJECT-TYPE
                SYNTAX INTEGER (0..10000)
                ACCESS read-write
                STATUS mandatory
                DESCRIPTION
                    "The number of milleseconds that DCD may be asserted 
                    before disconnecting the port.  Corresponds directly 
                    to PORT DCD TIMEOUT and the value labeled 'DCD 
                    Timeout:' in the PORT ALTERNATE CHARACTERISTICS 
                    display. This object is not available
                    on units that do not support modem signals (ie 2220)."
                ::= { basicSerialPortEntry 16 }
            
            basicSerialPortDTRAssert OBJECT-TYPE
                SYNTAX INTEGER { always(1), onConnectionOrRing(2),
                                 onConnection(3), onRing(4) }
                ACCESS read-write
                STATUS mandatory
                DESCRIPTION
                    "Control when the system asserts DTR on the port.
            
                    always               unconditional(DISABLED)
                    onConnectionOrRing   connection formed or RING
                                         asserted(ENABLED)
                    onConnection         connection formed
                                         (FORCONNECTION)
                    onRing               RING asserted (FORRING)
            
                    Corresponds directly to PORT DTRWAIT and the value 
                    labeled 'DTR Wait:' in the PORT ALTERNATE 
                    CHARACTERISTICS display. This object is not available
                    on units that do not support modem signals (ie 2220)."
                ::= { basicSerialPortEntry 17 }
            
            basicSerialPortLimitedCommands OBJECT-TYPE
                SYNTAX INTEGER { disabled(1), enabled(2) }
                ACCESS read-write
                STATUS mandatory
                DESCRIPTION
                    "Control for limiting the commands available to the 
                    user on the port.  Corresponds directly to PORT 
                    SECURITY and the presence of the label 'Security' 
                    following the label 'Enabled Characteristics:' in 
                    the PORT CHARACTERISTICS display. This object is not
                    available on units that do not support modem signals 
                    (ie 2220)."
                ::= { basicSerialPortEntry 18 }
            
            basicSerialPortLimitedView OBJECT-TYPE
                SYNTAX INTEGER { disabled(1), enabled(2) }
                ACCESS read-write
                STATUS mandatory
                DESCRIPTION
                    "Control for restricting what a user may display.  
                    Corresponds directly to PORT LIMITED VIEW and the 
                    presence of the label 'Limited View' following the 
                    label 'Enabled Characteristics:' in the PORT 
                    CHARACTERISTICS display."
                ::= { basicSerialPortEntry 19 }
            
            basicSerialPortPassword OBJECT-TYPE
                SYNTAX INTEGER { disabled(1), enabled(2) }
                ACCESS read-write
                STATUS mandatory
                DESCRIPTION
                    "Control for requiring the user to supply the login 
                    password to log in on the port.  Corresponds 
                    directly to PORT PASSWORD and the presence of the 
                    label 'Password' following the label 'Enabled 
                    Characteristics:' in the PORT CHARACTERISTICS 
                    display."
                ::= { basicSerialPortEntry 20 }
            
            basicSerialPortLineEditor OBJECT-TYPE
                SYNTAX INTEGER { disabled(1), enabled(2) }
                ACCESS read-write
                STATUS mandatory
                DESCRIPTION
                    "Control for allowing the user to use local mode 
                    command line editing.  Corresponds directly to PORT 
                    LINE EDITOR and the presence of the label 'Line 
                    Editor' following the label 'Enabled 
                    Characteristics:' in the PORT CHARACTERISTICS 
                    display."
                ::= { basicSerialPortEntry 21 }
            
            -- Note that the values for the switching and 
            -- line editing characters are mutally exclusive
            
            basicSerialPortLineEditorBackspace OBJECT-TYPE
                SYNTAX INTEGER (0..255)
                ACCESS read-write
                STATUS mandatory
                DESCRIPTION
                    "Character input from the character port to move the 
                    cursor to the left.  The value 0 indicates no 
                    character has this effect.  Corresponds directly to 
                    PORT LINE EDITOR BACKSPACE and the value labeled 
                    'Backspace Character:' in the PORT ALTERNATE 
                    CHARACTERISTICS display."
                ::= { basicSerialPortEntry 22 }
            
            basicSerialPortLineEditorBeginning OBJECT-TYPE
                SYNTAX INTEGER (0..255)
                ACCESS read-write
                STATUS mandatory
                DESCRIPTION
                    "Character input from the character port to move the 
                    cursor to the beginning of the line.  The value 0 
                    indicates no character has this effect.  Corresponds 
                    directly to PORT LINE EDITOR BEGINNING and the value 
                    labeled 'Begin Line Character:' in the PORT 
                    ALTERNATE CHARACTERISTICS display."
                ::= { basicSerialPortEntry 23 }
            
            basicSerialPortLineEditorCancel OBJECT-TYPE
                SYNTAX INTEGER (0..255)
                ACCESS read-write
                STATUS mandatory
                DESCRIPTION
                    "Character input from the character port to cancel 
                    an interactive dialog or delete the current line.  
                    The value 0 indicates no character has this effect.  
                    Corresponds directly to PORT LINE EDITOR CANCEL and 
                    the value labeled 'Cancel Character:' in the PORT 
                    ALTERNATE CHARACTERISTICS display."
                ::= { basicSerialPortEntry 24 }
            
            basicSerialPortLineEditorDeleteBeginning OBJECT-TYPE
                SYNTAX INTEGER (0..255)
                ACCESS read-write
                STATUS mandatory
                DESCRIPTION
                    "Character input from the character port to delete 
                    the current line from the cursor to the beginning.  
                    The value 0 indicates no character has this effect.  
                    Corresponds directly to PORT LINE EDITOR DELETE 
                    BEGINNING and the value labeled 'Delete Begin 
                    Character:' in the PORT ALTERNATE CHARACTERISTICS 
                    display."
                ::= { basicSerialPortEntry 25 }
            
            basicSerialPortLineEditorDeleteLine OBJECT-TYPE
                SYNTAX INTEGER (0..255)
                ACCESS read-write
                STATUS mandatory
                DESCRIPTION
                    "Character input from the character port to delete 
                    the current line.  The value 0 indicates no 
                    character has this effect.  Corresponds directly to 
                    PORT LINE EDITOR DELETE LINE and the value labeled 
                    'Delete Line Character:' in the PORT ALTERNATE 
                    CHARACTERISTICS display."
                ::= { basicSerialPortEntry 26 }
            
            basicSerialPortLineEditorEnd OBJECT-TYPE
                SYNTAX INTEGER (0..255)
                ACCESS read-write
                STATUS mandatory
                DESCRIPTION
                    "Character input from the character port to move the 
                    cursor to the end of the line.  The value 0 
                    indicates no character has this effect.  Corresponds 
                    directly to PORT LINE EDITOR END and the value 
                    labeled 'End of Line Character:' in the PORT 
                    ALTERNATE CHARACTERISTICS display."
                ::= { basicSerialPortEntry 27 }
            
            basicSerialPortLineEditorForward OBJECT-TYPE
                SYNTAX INTEGER (0..255)
                ACCESS read-write
                STATUS mandatory
                DESCRIPTION
                    "Character input from the character port to move the 
                    cursor to the right.  The value 0 indicates no 
                    character has this effect.  Corresponds directly to 
                    PORT LINE EDITOR FORWARDS and the value labeled 
                    'Forwards Character:' in the PORT ALTERNATE 
                    CHARACTERISTICS display."
                ::= { basicSerialPortEntry 28 }
            
            basicSerialPortLineEditorInsertToggle OBJECT-TYPE
                SYNTAX INTEGER (0..255)
                ACCESS read-write
                STATUS mandatory
                DESCRIPTION
                    "Character input from the character port to toggle 
                    between insert and overwrite modes.  The value 0 
                    indicates no character has this effect.  Corresponds 
                    directly to PORT LINE EDITOR INSERT TOGGLE and the 
                    value labeled 'Insert Character:' in the PORT 
                    ALTERNATE CHARACTERISTICS display."
                ::= { basicSerialPortEntry 29 }
            
            basicSerialPortLineEditorNextLine OBJECT-TYPE
                SYNTAX INTEGER (0..255)
                ACCESS read-write
                STATUS mandatory
                DESCRIPTION
                    "Character input from the character port to recall 
                    the next, newer line in the command history.  The 
                    value -1 indicates no character has this effect.  
                    Corresponds directly to PORT LINE EDITOR NEXT LINE 
                    and the value labeled 'Next Line Character:' in the 
                    PORT ALTERNATE CHARACTERISTICS display."
                ::= { basicSerialPortEntry 30 }
            
            basicSerialPortLineEditorPreviousLine OBJECT-TYPE
                SYNTAX INTEGER (0..255)
                ACCESS read-write
                STATUS mandatory
                DESCRIPTION
                    "Character input from the character port to recall 
                    the previous, older line in the command history.  
                    The value 0 indicates no character has this effect.  
                    Corresponds directly to PORT LINE EDITOR PREVIOUS 
                    LINE and the value labeled 'Previous Line 
                    Character:' in the PORT ALTERNATE CHARACTERISTICS 
                    display."
                ::= { basicSerialPortEntry 31 }
            
            basicSerialPortLineEditorQuotingCharacter OBJECT-TYPE
                SYNTAX INTEGER (0..255)
                ACCESS read-write
                STATUS mandatory
                DESCRIPTION
                    "Character input from the character port to inhibit 
                    interpretation of the next input character.  The 
                    value 0 indicates no character has this effect.  
                    Corresponds directly to PORT LINE EDITOR QUOTING 
                    CHARACTER and the value labeled 'Quoting Character:' 
                    in the PORT ALTERNATE CHARACTERISTICS display."
                ::= { basicSerialPortEntry 32 }
            
            basicSerialPortLineEditorRedisplay OBJECT-TYPE
                SYNTAX INTEGER (0..255)
                ACCESS read-write
                STATUS mandatory
                DESCRIPTION
                    "Character input from the character port to 
                    redisplay the current command line.  The value 0 
                    indicates no character has this effect.  Corresponds 
                    directly to PORT LINE EDITOR REDISPLAY CHARACTER and 
                    the value labeled 'Redisplay Character:' in the PORT 
                    ALTERNATE CHARACTERISTICS display."
                ::= { basicSerialPortEntry 33 }
            
            basicSerialPortQuadartReceiveDiscard OBJECT-TYPE
                SYNTAX INTEGER { disabled(1), enabled(2) }
                ACCESS read-write
                STATUS mandatory
                DESCRIPTION
                    "Control for discard of received errors from quadart 
                    hardware."
                ::= { basicSerialPortEntry 34 }

            basicSerialPortAPDProtocols OBJECT-TYPE
                SYNTAX OCTET STRING (SIZE (2))
                ACCESS read-write
                STATUS mandatory
                DESCRIPTION
                    "A bit map that specifies the protocols
                      that this port will attempt to detect
                     using the Auto Protocol Detection
                     function. The bit numbers for the
                     protocols are: 1;ARAP, 3;Interactive, 4;SLIP, 5;PPP.
                     Bits 6-16 are reserved for future use.
                     More than one of these protocols may
                     be ORed together. The default is 0 (zero)
                     no protocols."
                DEFVAL { '00'h }  -- the null string
                ::= { basicSerialPortEntry 35 }
            
            basicSerialPortAPDTimeout OBJECT-TYPE
                SYNTAX INTEGER (0..255)
                ACCESS read-write
                STATUS mandatory
                DESCRIPTION
                    "A time value, in seconds, that 
                    specifies how long the port will
                    attempt to determine which
                    protocol is coming into the port.
                    When basicSerialPortAPDTimeout seconds
                    have expired, the port will assume the
                    protocol to use is that specified by
                    basicSerialPortAPDDefaultProtocol.
                    A value of 0 (zero provides an unlimited timeout."
                DEFVAL { 0 }
                ::= { basicSerialPortEntry 36 }
            
            basicSerialPortAPDDefaultProtocol OBJECT-TYPE
                SYNTAX OCTET STRING (SIZE (2))
                ACCESS read-write
                STATUS mandatory
                DESCRIPTION
                    "A bit map that specifies the protocol
                     that this port will use when the time
                     specified by basicSerialPortAPDTimeout
                     has expired without sucessfully
                     identifying the incoming porotocol.
                     The bit numbers for the protocols are:
                     None;Logout the port, 1;ARAP, 2;CSLIP,
                     3;Interactive, 4;SLIP, 5;PPP. Bits 6-16
                     are reserved for future use. Only
                     one protocol may be specified for this
                     object"
                DEFVAL { '00'h }  -- the null string
                ::= { basicSerialPortEntry 37 }
            
            basicSerialPortUsernameCharSet OBJECT-TYPE
                SYNTAX INTEGER {none(1), seven-bit(2)}
                ACCESS read-write
                STATUS mandatory
                DESCRIPTION
                    "A control, that if set to seven-bit, will
                    allow only the ASCII printable characters
                    in the range SP (X20) to ~ (X7E) in the username
                    field. A value of none allows any character"
                DEFVAL { none}
                ::= { basicSerialPortEntry 38 }
            
            basicSerialPortAutoHangup OBJECT-TYPE
                SYNTAX INTEGER { disabled(1), enabled(2) }
                ACCESS read-write
                STATUS mandatory
                DESCRIPTION 
                    "A control that, if enabled,  will cause the port to be
                    logged off when the last session on that port is destroyed"
                DEFVAL {disabled}
                ::= {basicSerialPortEntry 39}
            
            basicSerialPortCommandSize OBJECT-TYPE
                SYNTAX INTEGER (80..16384)
                ACCESS read-write
                STATUS mandatory 
                DESCRIPTION
                    "Maximum number of input characters to hold in the command
                    buffer. Corresponds directly to the PORT COMMAND SIZE
                    and the value labeled 'Command Size:' in the PORT 
                    ALTERNATE CHARACTERISTICS display." 	
                DEFVAL { 80 }
                ::= { basicSerialPortEntry 40 }

            basicSerialPortAutoProtocolDetectPrompt OBJECT-TYPE
                SYNTAX INTEGER { disabled(1), enabled(2) }
                ACCESS read-write
                STATUS mandatory
                DESCRIPTION
                    "Controls whether to send the basicAutoProtocolDetectMessage
                     out the serial port at the beginning of auto protocol
                     detection mode. Corresponds to the value labeled 'APD
                     Prompt' in the PORT ALTERNATE CHARACTERISTICS display."
                DEFVAL { enabled }
                ::= { basicSerialPortEntry 41 }

            basicSerialPortUsernamePrompt OBJECT-TYPE
                SYNTAX DisplayString (SIZE (0..25))
                ACCESS read-write
                STATUS mandatory
                DESCRIPTION
                    "The text string used to prompt for a user's name. 
                     Corresponds directly to the value labeled 'Username 
                     Prompt:' in the PORT ALTERNATE CHARACTERISTICS display."
                DEFVAL { "Enter username>"  }
                ::= { basicSerialPortEntry 42 }
 
            basicSerialPortPasswordPrompt OBJECT-TYPE
                SYNTAX DisplayString (SIZE (0..25))
                ACCESS read-write
                STATUS mandatory
                DESCRIPTION
                    "The text string used to prompt for a user's password.
                     Corresponds directly to the value labeled 'Password 
                     Prompt:' in the PORT ALTERNATE CHARACTERISTICS display."
                DEFVAL { "Enter user password>"  }
                ::= { basicSerialPortEntry 43 }
 
            basicSerialPortAutoProtocolDetectSecurityInteractiveOnly OBJECT-TYPE
                SYNTAX INTEGER { disabled(1), enabled(2) }
                ACCESS read-write
                STATUS mandatory
                DESCRIPTION
                    "Controls whether Auto Protocol Detect (APD) authentication 
                     applies only to interactive users, and not to other APD 
                     protocols such as PPP. Corresponds directly to the value 
                     labeled 'APD Authentication Interactive Only:' in the PORT
                     CHARACTERISTICS display."
                DEFVAL { disabled }
                ::= { basicSerialPortEntry 44 }
 
            basicSerialPortDedicatedUserData OBJECT-TYPE
                SYNTAX DisplayString (SIZE (0..16))
                ACCESS read-write
                STATUS mandatory
                DESCRIPTION
                    "The text string to send at the beginning of a connection
                     to a Telnet dedicated service. Corresponds to the value
                     labeled 'UserData:' in the PORT CHARACTERISTICS display."
                DEFVAL { "" }  -- the null string
                ::= { basicSerialPortEntry 45 }
 
           basicSerialPortIpAutoDiscovery OBJECT-TYPE
                SYNTAX INTEGER { disabled(1), enabled(2) }
                ACCESS read-write
                STATUS deprecated
                DESCRIPTION
                    "Control to enable a non-standard method of acquiring the
                     IP address after boot completes via the BOOTP protocol.
                     Corresponds to the value labeled 'IP Address
                     Auto Discovery' in the SERVER CHARACTERISTICS display."
                DEFVAL { disabled }
                ::= { basicSerialPortEntry 47 }
 
           basicSerialPortDedicatedKickStartData OBJECT-TYPE
                SYNTAX DisplayString (SIZE (0..16))
                ACCESS read-write
                STATUS mandatory
                DESCRIPTION
                    "A text string which is used to compare at login time to
                     incoming serial data. A match will initiate a telnet
                     session to a dedicated service. Corresponds to the value
                     labeled 'KickStart:' in the PORT CHARACTERISTICS display."
                DEFVAL { "" }  -- the null string
                ::= { basicSerialPortEntry 48 }
 
 
           basicSerialPortBreakLength OBJECT-TYPE
                SYNTAX INTEGER { ms250(1), ms500(2), ms750(3) }
                ACCESS read-write
                STATUS mandatory
                DESCRIPTION
                    "Specifies the duration in milliseconds of a remote serial
                     break which is sent via the Telnet Break command. 
                     Corresponds directly to the value labeled 'Break Length:'
                     in the PORT CHARACTERISTIC display."
                ::= { basicSerialPortEntry 50 }

           basicSerialPortRotaryRoundRobin OBJECT-TYPE
                SYNTAX INTEGER  { disabled(1), enabled(2) }
                ACCESS read-write
                STATUS mandatory
                DESCRIPTION
                    "Controls whether a port which participates in an internet
                     rotary is selected in round robin or fixed priority order.
                     Corresponds directly to the value labeled 'Round Robin
                     search:' in the SERVER INTERNET ROTARY display."
                DEFVAL { enabled }
                ::= { basicSerialPortEntry 51 }
 
           basicSerialPortWelcomeBeforeAuthentication OBJECT-TYPE
                SYNTAX INTEGER  { disabled(1), enabled(2) }
                ACCESS read-write
                STATUS mandatory
                DESCRIPTION
                    "Control to display the basicWelcome message prior to
                     authenticating the user. Corresponds to the presence of the
                     value 'Welcome-Banner-Pre-Authentication' following the 
                     label 'Enabled Characteristics' in the PORT CHARACTERISTICS
                     display."
                DEFVAL { disabled }
                ::= { basicSerialPortEntry 52 }

           basicSerialPortGatewayAutoDiscovery OBJECT-TYPE
                SYNTAX INTEGER { disabled(1), enabled(2) }
                ACCESS read-write
                STATUS deprecated
                DESCRIPTION
                    "Control to enable a non-standard method of acquiring the
                     gateway address after boot completes via the bootp
                     protocol."
                DEFVAL { disabled  }
                ::= { basicSerialPortEntry 53 }
           
           basicSerialPortSubnetAutoDiscovery OBJECT-TYPE
                SYNTAX INTEGER  { disabled(1), enabled(2) }  
                ACCESS read-write
                STATUS deprecated
                DESCRIPTION
                    "Control to enable a non-standard method of acquiring the 
                     subnet mask after boot completes via the bootp protocol."
                DEFVAL { disabled  }
                ::= { basicSerialPortEntry 54 }
          
           basicSerialPortRaiseLowerDtr OBJECT-TYPE
                SYNTAX INTEGER { low(1), high(2) } 
                ACCESS read-write
                STATUS mandatory
                DESCRIPTION
                    "A control to to raise or lower the DTR signal from this
                     port by setting it to high or low, respectively. This
                     request will have no effect unless 
                     basicSerialPortRaiseControlDtr is enabled. In response 
                     to a get-request or get-next-request the agent always 
                     returns low for this object."
                ::= { basicSerialPortEntry 55 }                

           basicSerialPortRaiseControlDtr  OBJECT-TYPE
                SYNTAX INTEGER { disabled(1), enabled(2) }
                ACCESS read-write
                STATUS mandatory
                DESCRIPTION
                    "Controls the ability to change the state of DTR using 
                     basicSerialPortRaiseLowerDTR. This characteristic is not
                     intended for use with modem ports. Corresponds directly
                     to the presence of 'Control DTR' under the label 
                     'Enabled Characteristics' in the PORT CHARACTERISTICS 
                     display. The desired change will not take effect until 
                     the port is logged off."
                DEFVAL { disabled }
                ::= { basicSerialPortEntry 56 }                
 
            basicSerialPortIpConfigureBootp OBJECT-TYPE
                SYNTAX INTEGER { disabled(1), enabled(2) }
                ACCESS read-write
                STATUS deprecated
                DESCRIPTION
		    "Control to use the BOOTP protocol upon startup to learn
                     the unit's own internet address, subnet mask, primary and 
                     secondary gateway servers, domain name servers, time 
                     server and domain name. This object was moved to the 
                     MRV-IN-REACH-INTERNET-MIB for InReach agent software version V2.4."
                DEFVAL { enabled }
                ::= { basicSerialPortEntry 57 }                

            -- the Basic group continued
            
            basicConsoleLogoutDisconnect OBJECT-TYPE
                SYNTAX INTEGER { disabled(1), enabled(2) }
                ACCESS read-write
                STATUS mandatory
                DESCRIPTION
                    "Control for automatic session disconnection when a 
                    console port user logs out.  Corresponds directly to 
                    SERVER CONSOLE LOGOUT and the presence of the label 
                    'Console Logout' following the label 'Enabled 
                    Characteristics:' in the SERVER CHARACTERISTICS 
                    display."
                ::= { xBasic 19 }
            
        basicControlledPorts OBJECT-TYPE
               SYNTAX INTEGER { disabled(1), enabled(2) }
               ACCESS read-write
               STATUS mandatory
               DESCRIPTION
		    "Status of Controlled Ports feature. Corresponds directly
		     to the 'Controlled Ports' following the label 'Enabled
		     Characteristics:' in the SERVER CHARACTERISTICS display.
             Enabling this feature causes strings of control characters
             to be sent out on a port upon starting and/or stopping a session"
                    ::= { xBasic 20 }
     
            -- the Basic Port Session table
 
            basicPortSessionTable OBJECT-TYPE
                SYNTAX SEQUENCE OF BasicPortSessEntry
                ACCESS not-accessible
                STATUS mandatory
                DESCRIPTION
                    "A list of port session entries."
                ::= { xBasic 21}

 

            basicPortSessEntry OBJECT-TYPE
                SYNTAX BasicPortSessEntry
                ACCESS not-accessible
                STATUS mandatory
                DESCRIPTION
                    "Status and parameter values for a basic port
                    session."
                INDEX { basicPortPortIndex, basicPortSessIndex }
                ::= { basicPortSessionTable 1 }
 
            BasicPortSessEntry ::=
                SEQUENCE {
                    basicPortPortIndex
                        INTEGER,
                    basicPortSessIndex
                        INTEGER,
		            basicSessControlled
			            INTEGER
		            }
       
 
            basicPortPortIndex OBJECT-TYPE
                SYNTAX INTEGER
                ACCESS read-only
                STATUS mandatory
                DESCRIPTION
                    "The value of basicPortIndex for the port to which
                    this session belongs.
                    The port identified by a particular value of this 
                    index is the same port as identified by 
                    charPortIndex in the standard Character MIB."
                ::= { basicPortSessEntry 1 }
 
            basicPortSessIndex OBJECT-TYPE
                SYNTAX INTEGER
                ACCESS read-only
                STATUS mandatory
                DESCRIPTION
                    "The session index in the context of the port, a
                    non-zero positive integer.  Session indexes within a
                    port need not be sequential.  Session indexes may be
                    reused for different ports.  For example, port 1 and
                    port 3 may both have a session 2 at the same time.
                    Session indexes may have any valid integer value,
                    with any meaning convenient to the agent
                    implementation.
                    The session identified by a particular value of this 
                    index is the same session as identified by 
                    charSessIndex in the standard Character MIB."
                ::= { basicPortSessEntry 2 }
	
            basicSessControlled OBJECT-TYPE
               SYNTAX INTEGER { disabled(1), enabled(2) }
               ACCESS read-only
               STATUS mandatory
               DESCRIPTION
		     "A control to send preconfigured controlled port session
		      strings out the serial port when entering or exiting
		      this session. Corresponds directly to the value labeled
		      'Controlled' under the Service Mode header in the 
		      SESSION display."
                    ::= { basicPortSessEntry 3 }

           basicPortSessEncryption OBJECT-TYPE
                SYNTAX INTEGER { disabled(1), enabled(2) }
                ACCESS read-write
                STATUS mandatory
                DESCRIPTION
                    "Status of the default encryption value to be set
                     for each session.  Corresponds directly to Console
					 Security on SHOW SERVER screen."
                ::= { xBasic 22}


basicTemperatureUnits OBJECT-TYPE
        SYNTAX  INTEGER { fahrenheit  (1), celcius (2) }
        ACCESS  read-write
        STATUS  mandatory
        DESCRIPTION
            "Indicates the units of measurement for the temperature sensors."
	DEFVAL {fahrenheit }
        ::= { xBasic 23 }

basicEnvironmentalManagerCircuitBreaker OBJECT-TYPE
        SYNTAX  INTEGER { disabled  (1), enabled (2) }
        ACCESS  read-only
        STATUS  mandatory
        DESCRIPTION
            "Indicates whether the circuit breaker is activated."
        ::= { xBasic 24 }

-- Contact Closure or Alarm Input Table

basicContactClosureOrAlarmInputTable OBJECT-TYPE
        SYNTAX  SEQUENCE OF BasicContactClosureOrAlarmInputEntry
        ACCESS  not-accessible
        STATUS  mandatory
        DESCRIPTION
            "Information about contact closures or alarm inputs."
        ::= { xBasic 25 }

basicContactClosureOrAlarmInputEntry OBJECT-TYPE
        SYNTAX  BasicContactClosureOrAlarmInputEntry
        ACCESS  not-accessible
        STATUS  mandatory
        DESCRIPTION
            "An entry in the basicContactClosureOrAlarmInputTable."
        INDEX { basicContactClosureOrAlarmInputIndex }
        ::= { basicContactClosureOrAlarmInputTable 1 }


BasicContactClosureOrAlarmInputEntry ::=
    SEQUENCE {
        basicContactClosureOrAlarmInputValue
       	    INTEGER,
        basicContactClosureOrAlarmInputName
            DisplayString,
        basicContactClosureOrAlarmInputTrapEnable
            INTEGER,
        basicContactClosureOrAlarmInputFaultSeverity 
            INTEGER,
        basicContactClosureOrAlarmInputFaultState
            INTEGER,
        basicContactClosureOrAlarmInputStatus 
            INTEGER,
        basicContactClosureOrAlarmInputZone 
            DisplayString,
        basicContactClosureOrAlarmInputRelatedEquipment 
            DisplayString,
        basicContactClosureOrAlarmInputSiteId 
            DisplayString,
        basicContactClosureOrAlarmInputIndex
            INTEGER,
        basicContactClosureOrAlarmInputManufacturer 
            DisplayString,
        basicContactClosureOrAlarmInputModel
            DisplayString
             }

 basicContactClosureOrAlarmInputValue  OBJECT-TYPE
        SYNTAX  INTEGER { open (1), closed (2) }
        ACCESS  read-only
        STATUS  mandatory
        DESCRIPTION
            "Indicates the state of the contact closure or alarm input."
        ::= { basicContactClosureOrAlarmInputEntry 1 }

 basicContactClosureOrAlarmInputName OBJECT-TYPE
        SYNTAX  DisplayString (SIZE (0..32 ))
        ACCESS  read-write
        STATUS  mandatory
        DESCRIPTION
            "The name used to identify this contact closure or alarm input."
       ::= { basicContactClosureOrAlarmInputEntry 2 }
 
 basicContactClosureOrAlarmInputTrapEnable OBJECT-TYPE
       SYNTAX  INTEGER { disabled (1), enabled (2) }
       ACCESS  read-write
       STATUS  mandatory
       DESCRIPTION
           "Control to send trap when contact closure or alarm input changes
            state."
       DEFVAL { enabled  }
       ::= { basicContactClosureOrAlarmInputEntry 3 }

 basicContactClosureOrAlarmInputFaultSeverity OBJECT-TYPE
       SYNTAX  INTEGER { indeterminate (2), warning (3), 
                         minor (4), major (5), critical (6) }
       ACCESS  read-write
       STATUS  mandatory
       DESCRIPTION
           "Control to determine the severity level associated with the
            trap sent out when a fault occurs for a given contact  
            closure or alarm input."
       DEFVAL { minor  }
       ::= { basicContactClosureOrAlarmInputEntry 4 }

 basicContactClosureOrAlarmInputFaultState OBJECT-TYPE
       SYNTAX  INTEGER { open (1), closed (2) }
       ACCESS  read-write
       STATUS  mandatory
       DESCRIPTION
           "Control to indicate which state, open or closed, represents the 
            fault condition. The other state is the cleared condition."
       DEFVAL { open  }
       ::= { basicContactClosureOrAlarmInputEntry 5 }

 basicContactClosureOrAlarmInputStatus OBJECT-TYPE
       SYNTAX  INTEGER { cleared (1), indeterminate (2), warning (3), 
                         minor (4), major (5), critical (6) }
       ACCESS  read-only
       STATUS  mandatory
       DESCRIPTION
           "Indicates the current status of the contact closure or alarm input.
            If the basicContactClosureOrAlarmInputValue matches the fault 
            state, then the status is equal to the fault severity. Otherwise
            the status is cleared."
       ::= { basicContactClosureOrAlarmInputEntry 6 }

        basicContactClosureOrAlarmInputZone OBJECT-TYPE
               SYNTAX  DisplayString (SIZE(0..32))
                ACCESS read-write
                STATUS mandatory
                DESCRIPTION
                   "The name used to identify the zone where the equipment
                    resides."
                ::= { basicContactClosureOrAlarmInputEntry 7 }
 
        basicContactClosureOrAlarmInputRelatedEquipment OBJECT-TYPE
               SYNTAX  DisplayString (SIZE(0..32))
                ACCESS read-write
                STATUS mandatory
                DESCRIPTION
                   "The name used to identify related equipment."
                ::= { basicContactClosureOrAlarmInputEntry 8 }
                   
        basicContactClosureOrAlarmInputSiteId OBJECT-TYPE
               SYNTAX  DisplayString (SIZE(0..32))
                ACCESS read-write
                STATUS mandatory
                DESCRIPTION
                   "The name used to identify the site where the unit resides."
                ::= { basicContactClosureOrAlarmInputEntry 9 }
           
 basicContactClosureOrAlarmInputIndex OBJECT-TYPE
        SYNTAX  INTEGER
        ACCESS  read-only
        STATUS  mandatory
        DESCRIPTION
            "An index which uniquely identifies the contact closure or alarm
             input."
        ::= { basicContactClosureOrAlarmInputEntry 10 }

        basicContactClosureOrAlarmInputManufacturer OBJECT-TYPE
               SYNTAX  DisplayString (SIZE(0..32))
                ACCESS read-write
                STATUS mandatory
                DESCRIPTION
                   "The name used to identify the manufacturer of this equipment."
                ::= { basicContactClosureOrAlarmInputEntry 11 }
 
        basicContactClosureOrAlarmInputModel OBJECT-TYPE
               SYNTAX  DisplayString (SIZE(0..32))
                ACCESS read-write
                STATUS mandatory
                DESCRIPTION
                   "The model name of this equipment."
                ::= { basicContactClosureOrAlarmInputEntry 12 }
 


-- Power Outlet Table

basicPowerOutletTable OBJECT-TYPE
        SYNTAX  SEQUENCE OF BasicPowerOutletEntry
        ACCESS  not-accessible
        STATUS  mandatory
        DESCRIPTION
                "Information about Environmental Manager Power Outlets."
        ::= { xBasic 26 }

basicPowerOutletEntry OBJECT-TYPE
        SYNTAX  BasicPowerOutletEntry
        ACCESS  not-accessible
        STATUS  mandatory
        DESCRIPTION
                "An entry in the basicPowerOutletTable."
        INDEX { basicPowerOutletIndex }
        ::= { basicPowerOutletTable 1 }

BasicPowerOutletEntry ::=
    SEQUENCE {
        basicPowerOutletOnOff
       	    INTEGER,
        basicPowerOutletReboot
            INTEGER,
        basicPowerOutletName
            DisplayString,
        basicPowerOutletRedundant
            INTEGER,
        basicPowerOutletConsoleName
            DisplayString,
        basicPowerOutletHighCurrent
            INTEGER,
        basicPowerOutletIndex
            INTEGER
	}


basicPowerOutletOnOff OBJECT-TYPE
        SYNTAX  INTEGER  { off(1), on(2) }
        ACCESS  read-write
        STATUS  mandatory
        DESCRIPTION
            "Controls turning on or off the power for the device connected to
             this power outlet."
        ::= { basicPowerOutletEntry 1 }

basicPowerOutletReboot OBJECT-TYPE
        SYNTAX  INTEGER  (1..1)
        ACCESS  read-write
        STATUS  mandatory
        DESCRIPTION
                "Controls rebooting of the device attached this power outlet."
        ::= { basicPowerOutletEntry 2 }

basicPowerOutletName OBJECT-TYPE 
        SYNTAX  DisplayString (SIZE (0..16 ))
        ACCESS  read-write
        STATUS  mandatory
        DESCRIPTION
            "A name used to identify this power outlet."
       ::= { basicPowerOutletEntry 3 }

basicPowerOutletRedundant OBJECT-TYPE
        SYNTAX INTEGER { disabled(1), enabled(2) }
        ACCESS  read-only
        STATUS  mandatory
        DESCRIPTION
            "Controls whether power outlets in bank A have redundant outlets
             in bank B. When enabled, powering on an outlet in bank A will
             simultaneously power on the corresponding outlet number in bank
             B."  
        DEFVAL { enabled }
        ::= { basicPowerOutletEntry 4 }

basicPowerOutletConsoleName OBJECT-TYPE
   SYNTAX DisplayString (SIZE (0..16))
   ACCESS read-write
   STATUS mandatory
   DESCRIPTION
      "A name used to identify a console port on a unit with power outlet 
       managment."
   ::= { basicPowerOutletEntry 5 }                

 basicPowerOutletHighCurrent OBJECT-TYPE
    SYNTAX INTEGER { disabled(1), enabled(2) }
    ACCESS read-write
    STATUS mandatory
    DESCRIPTION
       "A control to indicate a high current unit is attached to this 
        power outlet. When enabled the high current unit will provide current
        when it detects no power from the power outlet; and will stop the
        current when the outlet resumes power. This control only works on 
        those InReach devices which support the high current unit such as 
        the IRMGR0. Corresponds directly to the value labeled 'HCNC Setting'
        in the INREACH MANAGER OUTLET STATUS display."
    DEFVAL { disabled }
    ::= { basicPowerOutletEntry 6 }                

basicPowerOutletIndex OBJECT-TYPE
        SYNTAX  INTEGER
        ACCESS  read-only
        STATUS  mandatory
        DESCRIPTION
            "An index which uniquely identifies a power outlet."
        ::= { basicPowerOutletEntry 10 }

-- Temperature and Humidity Sensor Tables

basicTemperatureHumiditySensor OBJECT IDENTIFIER ::= { xBasic 27 }

-- Temperature Sensor Table

basicTemperatureSensorTable OBJECT-TYPE
        SYNTAX  SEQUENCE OF BasicTemperatureSensorEntry
        ACCESS  not-accessible
        STATUS  mandatory
        DESCRIPTION
            "Information about Environmental Manager Temperature Sensors."
        ::= { basicTemperatureHumiditySensor 1 }

basicTemperatureSensorEntry OBJECT-TYPE
        SYNTAX  BasicTemperatureSensorEntry
        ACCESS  not-accessible
        STATUS  mandatory
        DESCRIPTION
                "An entry in the basicTemperatureSensorTable."
        INDEX { basicTemperatureSensorIndex }
        ::= { basicTemperatureSensorTable 1 }

BasicTemperatureSensorEntry ::=
    SEQUENCE {
        basicTempTrapHighThreshold
            INTEGER,
        basicTempTrapLowThreshold
            INTEGER,
        basicTemperatureSensor
            INTEGER,
        basicTemperatureValue
            INTEGER,
        basicTemperatureAlarmSeverity
            INTEGER,
        basicTemperatureAlarmStatus
            INTEGER,
         basicTemperatureHumiditySensorName 
             DisplayString,
        basicTemperatureSensorIndex
	    INTEGER
	}

basicTempTrapHighThreshold OBJECT-TYPE
        SYNTAX  INTEGER
        ACCESS  read-write
        STATUS  mandatory
        DESCRIPTION
            "The temperature at or above which a sensorThresholdTrap is 
             generated."
        ::= { basicTemperatureSensorEntry 1 }

basicTempTrapLowThreshold OBJECT-TYPE
        SYNTAX  INTEGER
        ACCESS  read-write
        STATUS  mandatory
        DESCRIPTION
            "The temperature at or below which a sensorThresholdTrap is 
             generated."
        ::= { basicTemperatureSensorEntry 2 }

basicTemperatureSensor OBJECT-TYPE
        SYNTAX  INTEGER { disabled(1), enabled(2) }
        ACCESS  read-write
        STATUS  mandatory
        DESCRIPTION
                "Controls the enabling or disabling of a temperature sensor."
        ::= { basicTemperatureSensorEntry 3 }

basicTemperatureValue OBJECT-TYPE
        SYNTAX  INTEGER
        ACCESS  read-write
        STATUS  mandatory
        DESCRIPTION
				"The current temperature reading for this sensor."
        ::= { basicTemperatureSensorEntry 4 }

 basicTemperatureAlarmSeverity OBJECT-TYPE
       SYNTAX  INTEGER { indeterminate (2), warning (3), 
                         minor (4), major (5), critical (6) }
       ACCESS  read-write
       STATUS  mandatory
       DESCRIPTION
           "Control to determine the severity level associated with the
            trap sent out when the temperature reading is out-of-bounds."
       DEFVAL { minor  }
       ::= { basicTemperatureSensorEntry 5 }

 basicTemperatureAlarmStatus OBJECT-TYPE
       SYNTAX  INTEGER { cleared (1), indeterminate (2), warning (3), 
                         minor (4), major (5), critical (6) }
       ACCESS  read-only
       STATUS  mandatory
       DESCRIPTION
           "Indicates the current status of the temperature sensor.
            If the basicTemperatureValue falls within the normal range,
            the status is cleared. Otherwise the status matches the alarm
            severity level."
       ::= { basicTemperatureSensorEntry 6 }

 basicTemperatureHumiditySensorName OBJECT-TYPE
         SYNTAX DisplayString (SIZE (0..32))
	 ACCESS  read-write
	 STATUS  mandatory
	 DESCRIPTION
	    "The name used to identify this temperature sensor."
	 ::= { basicTemperatureSensorEntry 7 }

basicTemperatureSensorIndex OBJECT-TYPE
        SYNTAX  INTEGER
        ACCESS  read-only
        STATUS  mandatory
        DESCRIPTION
                "An index which uniquely identifies a temperature sensor."
        ::= { basicTemperatureSensorEntry 10 }


basicHumiditySensorTable OBJECT-TYPE
        SYNTAX  SEQUENCE OF BasicHumiditySensorEntry
        ACCESS  not-accessible
        STATUS  mandatory
        DESCRIPTION
            "Information about Environmental Manager Humidity Sensors."
        ::= { basicTemperatureHumiditySensor 2 }

basicHumiditySensorEntry OBJECT-TYPE
        SYNTAX  BasicHumiditySensorEntry
        ACCESS  not-accessible
        STATUS  mandatory
        DESCRIPTION
            "An entry in the basicHumiditySensorTable."
        INDEX { basicHumiditySensorIndex }
        ::= { basicHumiditySensorTable 1 }

BasicHumiditySensorEntry ::=
    SEQUENCE {
        basicHumidityTrapHighThreshold
            INTEGER,
        basicHumidityTrapLowThreshold
            INTEGER,
        basicHumiditySensor
            INTEGER,
        basicHumidityValue
	    INTEGER,
        basicHumidityAlarmSeverity
            INTEGER,
        basicHumidityAlarmStatus
            INTEGER,
        basicHumiditySensorIndex
            INTEGER
	}


basicHumidityTrapHighThreshold OBJECT-TYPE
        SYNTAX  INTEGER
        ACCESS  read-write
        STATUS  mandatory
        DESCRIPTION
            "The humidity at or above which a sensorThresholdTrap is generated."
        ::= { basicHumiditySensorEntry 1 }

basicHumidityTrapLowThreshold OBJECT-TYPE
        SYNTAX  INTEGER
        ACCESS  read-write
        STATUS  mandatory
        DESCRIPTION
            "The humidity at or below which a sensorThresholdTrap is generated."
        ::= { basicHumiditySensorEntry 2 }

basicHumiditySensor OBJECT-TYPE
        SYNTAX  INTEGER { disabled(1), enabled(2) }
        ACCESS  read-write
        STATUS  mandatory
        DESCRIPTION
            "Controls the enabling or disabling of a humidity sensor."
        ::= { basicHumiditySensorEntry 3 }

basicHumidityValue OBJECT-TYPE
        SYNTAX  INTEGER
        ACCESS  read-write
        STATUS  mandatory
        DESCRIPTION
            "The current humidity reading for this sensor."
        ::= { basicHumiditySensorEntry 4 }

 basicHumidityAlarmSeverity OBJECT-TYPE
       SYNTAX  INTEGER { indeterminate (2), warning (3), 
                         minor (4), major (5), critical (6) }
       ACCESS  read-write
       STATUS  mandatory
       DESCRIPTION
           "Control to indicate the severity level associated with the
            trap sent out when the humidity reading is out-of-bounds."
       DEFVAL { minor  }
       ::= { basicHumiditySensorEntry 5 }

 basicHumidityAlarmStatus OBJECT-TYPE
       SYNTAX  INTEGER { cleared (1), indeterminate (2), warning (3), 
                         minor (4), major (5), critical (6) }
       ACCESS  read-only
       STATUS  mandatory
       DESCRIPTION
           "Indicates the current status of the humidity sensor.
            If the basicHumidityValue falls within the normal range,
            the status is cleared. Otherwise the status matches the alarm
            severity level."
       ::= { basicHumiditySensorEntry 6 }

basicHumiditySensorIndex OBJECT-TYPE
        SYNTAX  INTEGER
        ACCESS  read-only
        STATUS  mandatory
        DESCRIPTION
                "An index which uniquely identifies a humidity sensor."
        ::= { basicHumiditySensorEntry 10 }

basicControlSignalTable OBJECT-TYPE
	SYNTAX  SEQUENCE OF BasicControlSignalEntry
        ACCESS  not-accessible
        STATUS  mandatory
        DESCRIPTION
                "Information about Environmental Manager Control Signal points."
        ::= { xBasic 28 }

basicControlSignalEntry OBJECT-TYPE
	SYNTAX  BasicControlSignalEntry
        ACCESS  not-accessible
        STATUS  mandatory
        DESCRIPTION
                "An entry in the basicControlSignalTable."
        INDEX { basicControlSignalIndex }
        ::= { basicControlSignalTable 1 }

BasicControlSignalEntry ::=
    SEQUENCE {
        basicControlSignalValue
		    INTEGER,
		basicControlSignalIndex
  		    INTEGER
	}

basicControlSignalValue  OBJECT-TYPE
        SYNTAX  INTEGER { high (1), low(2) } 
        ACCESS  read-write
        STATUS  mandatory
        DESCRIPTION
                "Sets and reads the state of the control signal point."
	    DEFVAL { high }
        ::= { basicControlSignalEntry 1 }

basicControlSignalIndex OBJECT-TYPE
        SYNTAX  INTEGER
        ACCESS  read-only
        STATUS  mandatory
        DESCRIPTION
                "An index which uniquely identifies a control signal point."
        ::= { basicControlSignalEntry 10 }

basicPowerAlarmTimer OBJECT-TYPE
        SYNTAX  INTEGER (1..60)
        ACCESS  read-write
        STATUS  mandatory
        DESCRIPTION
                "The polling interval in seconds for the fuse and power supply
                 status. An alarm trap is issued on power failure."
        DEFVAL { 10 }
        ::= { xBasic 29 }

 -- Control Output Table
 
 basicControlOutputTable OBJECT-TYPE
        SYNTAX  SEQUENCE OF BasicControlOutputEntry
        ACCESS  not-accessible
        STATUS  mandatory
        DESCRIPTION
                "Information about controlled output distribution points."
        ::= { xBasic 30 }
 
 basicControlOutputEntry OBJECT-TYPE
        SYNTAX  BasicControlOutputEntry
        ACCESS  not-accessible
        STATUS  mandatory
        DESCRIPTION
                "An entry in the basicControlOutputTable."
        INDEX { basicControlOutputIndex }
        ::= { basicControlOutputTable 1 }
 
 BasicControlOutputEntry ::=
        SEQUENCE {
            basicControlOutputSignalDtrRts
                INTEGER,
            basicControlOutputName
                DisplayString,
            basicControlOutputIndex
                INTEGER
        }
 
basicControlOutputSignalDtrRts OBJECT-TYPE
        SYNTAX  INTEGER { low(1), high(2) }
        ACCESS  read-write
        STATUS  mandatory
        DESCRIPTION
            "Controls the raising or lowering of a signal on a distribution
             control signal point. The signal is DTR when the
             basicControlOutputIndex is odd, or RTS when the
             basicControlOutputIndex is even."
        DEFVAL { high }
        ::= { basicControlOutputEntry 1 }
 
basicControlOutputName OBJECT-TYPE
        SYNTAX  DisplayString (SIZE (0..32 ))
        ACCESS  read-write
        STATUS  mandatory
        DESCRIPTION
           "The name used to identify this distribution control signal point."
       ::= { basicControlOutputEntry 2 }
 
basicControlOutputIndex OBJECT-TYPE
        SYNTAX  INTEGER
        ACCESS  read-only
        STATUS  mandatory
        DESCRIPTION
            "An index which uniquely identifies a distribution control
             signal point."
        ::= { basicControlOutputEntry 10 }

basicPowerStatusFuseA OBJECT-TYPE 
        SYNTAX  INTEGER { off (1), on (2) }
        ACCESS  read-only
        STATUS  mandatory
        DESCRIPTION
            "Indicates the status of fuse bank A."
        ::= { xBasic 31 }

basicPowerStatusFuseB OBJECT-TYPE 
        SYNTAX  INTEGER { off (1), on (2) }
        ACCESS  read-only
        STATUS  mandatory
        DESCRIPTION
            "Indicates the status of fuse bank B."
        ::= { xBasic 32 }

basicPowerSupplyStatusA OBJECT-TYPE 
        SYNTAX  INTEGER { off (1), on (2) }
        ACCESS  read-only
        STATUS  mandatory
        DESCRIPTION
            "Indicates the status of power supply A."
        ::= { xBasic 33 }

basicPowerSupplyStatusB OBJECT-TYPE 
        SYNTAX  INTEGER { off (1), on (2) }
        ACCESS  read-only
        STATUS  mandatory
        DESCRIPTION
            "Indicates the status of power supply B."
        ::= { xBasic 34 }

basicPortTrapTable OBJECT-TYPE
	SYNTAX SEQUENCE OF BasicPortTrapEntry
	ACCESS not-accessible
     	STATUS mandatory
	DESCRIPTION
	   "A list of traps associated with signal control changes on ports."
	::= { xBasic 35 }

basicPortTrapEntry OBJECT-TYPE
	SYNTAX BasicPortTrapEntry
	ACCESS not-accessible
     	STATUS mandatory
	DESCRIPTION
	    "Administrative status of signal change traps for a hardware port."
	INDEX { basicPortTrapIndex, basicPortSignalName }
	::= { basicPortTrapTable 1 }

BasicPortTrapEntry ::=
 	SEQUENCE {
	    basicPortTrapIndex
		INTEGER,
	    basicPortSignalName
		INTEGER,
	    basicPortTrapStatus
		INTEGER
	}

basicPortTrapIndex OBJECT-TYPE
	SYNTAX INTEGER
	ACCESS read-only
     	STATUS mandatory
	DESCRIPTION
	     "An index value that uniquely identifies a port.  
	     The port identified by a particular value of this 
	     index is the same port as identified by rs232PortIndex
	     in the standard rs232 MIB."
	::= { basicPortTrapEntry 1 }

basicPortSignalName OBJECT-TYPE
	SYNTAX INTEGER { rts(1), cts(2), dsr(3), dtr(4), ri(5), dcd(6) }
	ACCESS read-only
     	STATUS mandatory
	DESCRIPTION
	    "Identification of the hardware signal as specified in RFC1659
             as follows:
		rts 	Request to Send
		cts	Clear to Send
		dsr	Data Set Ready
		dts	Data Terminal Ready	
		ri	Ring Indicator
		dcd	Received Line Signal Detector  
	    Some agents do not support DSR since its pin is shared with DCD."
	::= { basicPortTrapEntry 2 }

basicPortTrapStatus OBJECT-TYPE	
        SYNTAX  INTEGER { disabled(1), enabled(2) }	
	ACCESS read-write
     	STATUS mandatory
	DESCRIPTION
	    "Control to toggle the sending of a trap on a specific signal 
             change on a physical port. One must logout the port prior to this
             taking effect."
	::= { basicPortTrapEntry 3 }


-- Alarm Master Input Table

basicAlarmMasterInputTable OBJECT-TYPE
        SYNTAX  SEQUENCE OF BasicAlarmMasterInputEntry
        ACCESS  not-accessible
        STATUS  mandatory
        DESCRIPTION
            "Information about the high density alarm manager's alarm inputs."
        ::= { xBasic 36 }

basicAlarmMasterInputEntry OBJECT-TYPE
        SYNTAX  BasicAlarmMasterInputEntry
        ACCESS  not-accessible
        STATUS  mandatory
        DESCRIPTION
            "An entry in the basicAlarmMasterInputTable."
        INDEX { basicAlarmMasterInputPort, basicAlarmMasterInputSlot, 
                basicAlarmMasterInputPoint }
        ::= { basicAlarmMasterInputTable 1 }

BasicAlarmMasterInputEntry ::=
    SEQUENCE {
        basicAlarmMasterInputPort
       	    INTEGER,
        basicAlarmMasterInputSlot
            INTEGER,
        basicAlarmMasterInputPoint
            INTEGER,
        basicAlarmMasterInputName      
            DisplayString,
        basicAlarmMasterInputTrapEnable
            INTEGER,
        basicAlarmMasterControlOutputSignal 
            INTEGER,
        basicAlarmMasterInputEnable 
            INTEGER,
        basicAlarmMasterInputDebounceInterval 
            INTEGER,
        basicAlarmMasterInputFaultSeverity 
            INTEGER,
        basicAlarmMasterInputFaultState
            INTEGER,
        basicAlarmMasterInputStatus
            INTEGER,
        basicAlarmMasterInputValue
            INTEGER,
        basicAlarmMasterDisplay
            INTEGER,
         basicAlarmMasterInputZone
             DisplayString,
         basicAlarmMasterInputRelatedEquipment
             DisplayString,
         basicAlarmMasterInputSiteId
             DisplayString,
         basicAlarmMasterInputManufacturer
             DisplayString,
         basicAlarmMasterInputModel
             DisplayString
             }

	basicAlarmMasterInputPort OBJECT-TYPE
                SYNTAX INTEGER
                ACCESS read-only
                STATUS mandatory
                DESCRIPTION
                    "An index value that uniquely identifies a port.
                    The port identified by a particular value of this 
                    index is the same port as identified by 
                    charPortIndex in the standard Character MIB."
                ::= { basicAlarmMasterInputEntry 1 }

	basicAlarmMasterInputSlot OBJECT-TYPE
                SYNTAX INTEGER
                ACCESS read-only
                STATUS mandatory
                DESCRIPTION
                    "An index value that uniquely identifies a slot of
                    alarm points on a given high density alarm port."
                ::= { basicAlarmMasterInputEntry 2 }

	basicAlarmMasterInputPoint OBJECT-TYPE
                SYNTAX INTEGER
                ACCESS read-only
                STATUS mandatory
                DESCRIPTION
                    "An index value that uniquely identifies an alarm
                     point within an alarm slot on a high density
                     alarm port."
                ::= { basicAlarmMasterInputEntry 3 }

 basicAlarmMasterInputName OBJECT-TYPE
        SYNTAX  DisplayString (SIZE (0..32 ))
        ACCESS  read-write
        STATUS  mandatory
        DESCRIPTION
            "The name used to identify this alarm point."
        ::= { basicAlarmMasterInputEntry 4 }

 basicAlarmMasterInputTrapEnable OBJECT-TYPE
       SYNTAX  INTEGER { disabled (1), enabled (2) }
       ACCESS  read-write
       STATUS  mandatory
       DESCRIPTION
           "Control to send a trap when the alarm input changes state."
      DEFVAL { disabled  }
        ::= { basicAlarmMasterInputEntry 5 }

 basicAlarmMasterControlOutputSignal OBJECT-TYPE
       SYNTAX  INTEGER { open (1), closed (2) }
       ACCESS  read-write
       STATUS  mandatory
       DESCRIPTION
           "Control to toggle the output signal for an alarm point." 
       DEFVAL { open }
        ::= { basicAlarmMasterInputEntry 6 }

 basicAlarmMasterInputEnable OBJECT-TYPE
       SYNTAX  INTEGER { disabled (1), enabled (2) }
       ACCESS  read-write
       STATUS  mandatory
       DESCRIPTION
           "Control to toggle whether this alarm point is active."
       DEFVAL { enabled  }
        ::= { basicAlarmMasterInputEntry 7 }

 basicAlarmMasterInputDebounceInterval OBJECT-TYPE
      SYNTAX  INTEGER ( 0..30 )
       ACCESS  read-write
       STATUS  mandatory
       DESCRIPTION
          "Amount of time in seconds to debounce a signal change before 
           triggering an alarm."
       DEFVAL { 0  }
        ::= { basicAlarmMasterInputEntry 8 }

 basicAlarmMasterInputFaultSeverity OBJECT-TYPE
       SYNTAX  INTEGER { indeterminate (2), warning (3), 
                         minor (4), major (5), critical (6) }
       ACCESS  read-write
       STATUS  mandatory
       DESCRIPTION
           "Control to determine the severity level associated with the
            trap sent out when a fault occurs for this alarm input point."
       DEFVAL { minor  }
  ::= { basicAlarmMasterInputEntry 9 }

 basicAlarmMasterInputFaultState OBJECT-TYPE
       SYNTAX  INTEGER { open (1), closed (2) }
       ACCESS  read-write
       STATUS  mandatory
       DESCRIPTION
           "Control to indicate which state, open or closed, represents the 
            fault condition for this alarm input point. The other state is 
            the cleared condition."
      DEFVAL { closed  }
  ::= { basicAlarmMasterInputEntry 10 }

 basicAlarmMasterInputStatus OBJECT-TYPE
       SYNTAX  INTEGER { cleared (1), indeterminate (2), warning (3), 
                         minor (4), major (5), critical (6) }
       ACCESS  read-only
       STATUS  mandatory
       DESCRIPTION
           "Indicates the current status of the alarm input point.
            If the basicAlarmMasterInputValue matches the fault 
            state, then the status is equal to the fault severity. Otherwise
            the status is cleared."
       ::= { basicAlarmMasterInputEntry 11 }

 basicAlarmMasterInputValue OBJECT-TYPE   
       SYNTAX  INTEGER { open (1), closed (2) }
       ACCESS  read-only
       STATUS  mandatory
       DESCRIPTION
           "Indicates the current state of the alarm input point."
       ::= { basicAlarmMasterInputEntry 12 }

 basicAlarmMasterDisplay OBJECT-TYPE
       SYNTAX  INTEGER { disabled (1), enabled (2) }
       ACCESS  read-write
       STATUS  mandatory
       DESCRIPTION
           "Control to toggle the display of the alarm status for this point
            in the display window of the high density alarm unit."
       DEFVAL { disabled  }
        ::= { basicAlarmMasterInputEntry 13 }

	 basicAlarmMasterInputZone OBJECT-TYPE
		SYNTAX  DisplayString (SIZE(0..32))
		 ACCESS read-write
		 STATUS mandatory
		 DESCRIPTION
		    "The name used to identify the zone where the equipment
		     resides."
	 ::= { basicAlarmMasterInputEntry 14 }

	 basicAlarmMasterInputRelatedEquipment OBJECT-TYPE
		SYNTAX  DisplayString (SIZE(0..32))
		 ACCESS read-write
		 STATUS mandatory
		 DESCRIPTION
		    "The name used to identify related equipment."
	 ::= { basicAlarmMasterInputEntry 15 }

	 basicAlarmMasterInputSiteId OBJECT-TYPE
		SYNTAX  DisplayString (SIZE(0..32))
		 ACCESS read-write
		 STATUS mandatory
		 DESCRIPTION
		    "The name used to identify the site where the unit resides."
	 ::= { basicAlarmMasterInputEntry 16 }

	 basicAlarmMasterInputManufacturer OBJECT-TYPE
		SYNTAX  DisplayString (SIZE(0..32))
		 ACCESS read-write
		 STATUS mandatory
		 DESCRIPTION
		    "The name used to identify the manufacturer of this equipment."
	 ::= { basicAlarmMasterInputEntry 17 }

	 basicAlarmMasterInputModel OBJECT-TYPE
		SYNTAX  DisplayString (SIZE(0..32))
		 ACCESS read-write
		 STATUS mandatory
		 DESCRIPTION
		    "The model name of this equipment."
	 ::= { basicAlarmMasterInputEntry 18 }


 -- Power Master Table
 
 basicPowerMasterOutletTable OBJECT-TYPE
        SYNTAX  SEQUENCE OF BasicPowerMasterOutletEntry
        ACCESS  not-accessible
        STATUS  mandatory
        DESCRIPTION
                "Information about power master outlets."
        ::= { xBasic 37 }

 basicPowerMasterOutletEntry OBJECT-TYPE
        SYNTAX  BasicPowerMasterOutletEntry
        ACCESS  not-accessible
        STATUS  mandatory
        DESCRIPTION
                "An entry in the basicPowerMasterOutletTable."
        INDEX { basicPowerMasterPortIndex, basicPowerMasterOutletIndex }
        ::= { basicPowerMasterOutletTable 1 }

 BasicPowerMasterOutletEntry ::=
        SEQUENCE {
            basicPowerMasterPortIndex
                INTEGER,
            basicPowerMasterOutletIndex
                INTEGER,
            basicPowerMasterOutletName
                DisplayString,
            basicPowerMasterOutletState
                INTEGER,
            basicPowerMasterOutletAmperageStatus
                DisplayString
        }

basicPowerMasterPortIndex OBJECT-TYPE
        SYNTAX  INTEGER
        ACCESS  read-only
        STATUS  mandatory
        DESCRIPTION
            "An index value that uniquely identifies a port.
             The port identified by a particular value of this 
             index is the same port as identified by the 
             charPortIndex in the standard Character MIB."
        ::= { basicPowerMasterOutletEntry 1 }

basicPowerMasterOutletIndex OBJECT-TYPE
        SYNTAX  INTEGER
        ACCESS  read-only
        STATUS  mandatory
        DESCRIPTION
            "An index which uniquely identifies a power master outlet."
        ::= { basicPowerMasterOutletEntry 2 }

basicPowerMasterOutletName OBJECT-TYPE
        SYNTAX  DisplayString (SIZE (0..32 ))
        ACCESS  read-write
        STATUS  mandatory
        DESCRIPTION
           "The name used to identify this power master outlet."
       ::= { basicPowerMasterOutletEntry 3 }

basicPowerMasterOutletState OBJECT-TYPE
        SYNTAX  INTEGER { off(1), on(2) }
        ACCESS  read-write
        STATUS  mandatory
        DESCRIPTION
            "Switches the power master outlet on or off. There may be a 
             noticeable time delay while processing a get-request for this
             object. A response of 'off' to a get-request may indicate that
             the state is temporarily unavailable."
        DEFVAL { on }
        ::= { basicPowerMasterOutletEntry 4 }

basicPowerMasterOutletAmperageStatus OBJECT-TYPE
        SYNTAX  DisplayString (SIZE (0..5))
        ACCESS  read-only
        STATUS  mandatory
        DESCRIPTION
            "Indicates the current amperage drawn at this outlet. There may
             be a noticeable time delay while processing a get-request for
             this object. A null string indicates that amperage status is
             temporarily unavailable."
        ::= { basicPowerMasterOutletEntry 5 }

 -- Control Output Relay Table
 
 basicControlOutputRelayTable OBJECT-TYPE
        SYNTAX  SEQUENCE OF BasicControlOutputRelayEntry
        ACCESS  not-accessible
        STATUS  mandatory
        DESCRIPTION
                "Information about controlled output relays."
        ::= { xBasic 38 }
 
 basicControlOutputRelayEntry OBJECT-TYPE
        SYNTAX  BasicControlOutputRelayEntry
        ACCESS  not-accessible
        STATUS  mandatory
        DESCRIPTION
                "An entry in the basicControlOutputRelayTable."
        INDEX { basicControlOutputRelayIndex }
        ::= { basicControlOutputRelayTable 1 }
 
 BasicControlOutputRelayEntry ::=
        SEQUENCE {
            basicControlOutputRelayIndex
                INTEGER,
            basicControlOutputRelayName
                DisplayString,
            basicControlOutputRelayState
                INTEGER,
            basicControlOutputRelayStatus
                INTEGER
        }

basicControlOutputRelayIndex OBJECT-TYPE
        SYNTAX  INTEGER
        ACCESS  read-only
        STATUS  mandatory
        DESCRIPTION
            "An index which uniquely identifies a control output relay."
        ::= { basicControlOutputRelayEntry 1 }

basicControlOutputRelayName OBJECT-TYPE
        SYNTAX  DisplayString (SIZE (0..32 ))
        ACCESS  read-write
        STATUS  mandatory
        DESCRIPTION
           "The name used to identify this control output relay."
       ::= { basicControlOutputRelayEntry 2 }

basicControlOutputRelayState OBJECT-TYPE
        SYNTAX  INTEGER { open(1), close(2) }
        ACCESS  read-write
        STATUS  mandatory
        DESCRIPTION
            "Controls the opening or closing of the control output relay."
        DEFVAL { open }
        ::= { basicControlOutputRelayEntry 3 }

basicControlOutputRelayStatus OBJECT-TYPE
        SYNTAX  INTEGER { open(1), close(2) }
        ACCESS  read-only
        STATUS  mandatory
        DESCRIPTION
            "Indicates the current status of the control output relay."
        ::= { basicControlOutputRelayEntry 4 }
 

           basicAutoProtocolDetectMessage OBJECT-TYPE
               SYNTAX DisplayString (SIZE (0..80))
               ACCESS read-write
               STATUS mandatory
               DESCRIPTION
                   "The text string sent as a prompt message out the
                    port at the beginning of auto protocol detection mode.
                    Corresponds to the value labeled 'APD Message' in the
                    SERVER UNIT display."
               DEFVAL {"AutoProtocolDetect - Begin protocol or enter 4 returns for interactive mode." }
               ::= { xBasic 100 } 

             
            -- the Queue group
            
            -- Implementation of this group is mandatory for all MRV In-Reach
            -- systems that implement port queueing
            
            queueLimit OBJECT-TYPE
                SYNTAX INTEGER (-1..100)
                ACCESS read-write
                STATUS mandatory
                DESCRIPTION
                    "The maximum number of entries that can be made in 
                    the Queue table.  The value -1 indicates the imit is 
                    available memory.  Corresponds directly to SERVER 
                    QUEUE LIMIT and the value labeled 'Queue Limit:' in 
                    the SERVER CHARACTERISTICS display."
                ::= { xQueue 1 }
            
            queueHigh OBJECT-TYPE
                SYNTAX Gauge
                ACCESS read-only
                STATUS mandatory
                DESCRIPTION
                    "The highest value of queueNumber since system 
                    initialization.  Corresponds directly to the value 
                    labeled 'Queue Entries' and 'High' in the SERVER 
                    STATUS display."
                ::= { xQueue 2 }
            
            queueNumber OBJECT-TYPE
                SYNTAX Gauge
                ACCESS read-only
                STATUS mandatory
                DESCRIPTION
                    "The number of entries in the Queue table.  
                    Corresponds directly to the value labeled 'Queue 
                    Entries' and 'Cur' in the SERVER STATUS display."
                ::= { xQueue 3 }
            
            -- The Queue table
            
            queueTable OBJECT-TYPE
                SYNTAX SEQUENCE OF QueueEntry
                ACCESS not-accessible
                STATUS mandatory
                DESCRIPTION
                    "A list of queue entries."
                ::= { xQueue 4 }
            
            queueEntry OBJECT-TYPE
                SYNTAX QueueEntry
                ACCESS not-accessible
                STATUS mandatory
                DESCRIPTION
                    "Parameter values for a queue entry."
                INDEX { queueJob }
                ::= { queueTable 1 }
            
            QueueEntry ::=
                SEQUENCE {
                    queueJob
                        INTEGER,
                    queueStatus
                        INTEGER,
                    queueSourceName
                        DisplayString,
                    queueServiceName
                        DisplayString,
                    queueServicePortIndex
                        INTEGER,
                    queueServicePortName
                        DisplayString
                }
            
            queueJob OBJECT-TYPE
                SYNTAX INTEGER
                ACCESS read-only
                STATUS mandatory
                DESCRIPTION
                    "The job number of a queued request.  Corresponds 
                    directly to the value labeled 'Entry' in the QUEUE 
                    display."
                ::= { queueEntry 1 }
            
            queueStatus OBJECT-TYPE
                SYNTAX INTEGER { invalid(1), valid(2) }
                ACCESS read-write
                STATUS mandatory
                DESCRIPTION
                    "The status of a queue entry.  Set to 'invalid' to 
                    remove the entry, which corresponds directly to the 
                    REMOVE QUEUE ENTRY command.  Actual removal of the 
                    entry is implementation specific."
                ::= { queueEntry 2 }
            
            queueSourceName OBJECT-TYPE
                SYNTAX DisplayString (SIZE (0..50))
                ACCESS read-only
                STATUS mandatory
                DESCRIPTION
                    "The name of the system that originated the queue 
                    entry.  Corresponds directly to the value labeled 
                    'Source Node' in the QUEUE display."
                ::= { queueEntry 3 }
            
            queueServiceName OBJECT-TYPE
                SYNTAX DisplayString (SIZE (0..16))
                ACCESS read-only
                STATUS mandatory
                DESCRIPTION
                    "The name of the service for which the originator is 
                    waiting.  Corresponds directly to the value labeled 
                    'Service' in the QUEUE display."
                ::= { queueEntry 4 }
            
            queueServicePortIndex OBJECT-TYPE
                SYNTAX INTEGER
                ACCESS read-only
                STATUS mandatory
                DESCRIPTION
                    "The charPortIndex of the port for which the 
                    originator is waiting, if supplied by the 
                    originator.  As defined in the standard Character 
                    MIB.  Corresponds indirectly to the port number part 
                    of the value labeled 'Port Name' in the QUEUE 
                    display."
                ::= { queueEntry 5 }
            
            queueServicePortName OBJECT-TYPE
                SYNTAX DisplayString (SIZE (0..16))
                ACCESS read-only
                STATUS mandatory
                DESCRIPTION
                    "The name of the port for which the originator is 
                    waiting, if supplied by the originator.  Corresponds 
                    directly to the port name part of the value labeled 
                    'Port Name' in the SERVER QUEUE display."
                ::= { queueEntry 6 }
            
            
            -- the Queue Port table
            
            queuePortTable OBJECT-TYPE
                SYNTAX SEQUENCE OF QueuePortEntry
                ACCESS not-accessible
                STATUS mandatory
                DESCRIPTION
                    "A list of queuing-related character port entries."
                ::= { xQueue 5 }
            
            queuePortEntry OBJECT-TYPE
                SYNTAX QueuePortEntry
                ACCESS not-accessible
                STATUS mandatory
                DESCRIPTION
                    "Queuing parameter values for a port."
                INDEX { queuePortIndex }
                ::= { queuePortTable 1 }
            
            QueuePortEntry ::=
                SEQUENCE {
                    queuePortIndex
                        INTEGER,
                    queuePortQueuing
                        INTEGER
                }
            
            queuePortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { queuePortEntry 1 }
            
            queuePortQueuing OBJECT-TYPE
                SYNTAX INTEGER { disabled(1), enabled(2) }
                ACCESS read-write
                STATUS mandatory
                DESCRIPTION
                    "Control for allowing queued requests for using the 
                    port.  Corresponds directly to PORT QUEUING and the 
                    presence of the label 'Queuing' following the label 
                    'Enabled Characteristics:' in the PORT 
                    CHARACTERISTICS display."
                ::= { queuePortEntry 2 }

            
            -- the Menu group
            
            -- Implementation of this group is mandatory for all MRV In-Reach
            -- systems that implement user menus
            
            menuNumber OBJECT-TYPE
                SYNTAX Gauge
                ACCESS read-only
                STATUS mandatory
                DESCRIPTION
                    "The number of entries in the Menu table.  
                    Corresponds indirectly to SERVER MENU display."
                ::= { xMenu 1 }
            
            menuContinuePrompt OBJECT-TYPE
                SYNTAX DisplayString (SIZE (0..50))
                ACCESS read-write
                STATUS mandatory
                DESCRIPTION
                    "The text to use when prompting a menu user to press 
                    RETURN to continue. Corresponds directly to SERVER 
                    MENU CONTINUE PROMPT and the value labeled 'Menu 
                    Continue Prompt:' in the SERVER MENU display."
                ::= { xMenu 2 }
            
            menuSelectionPrompt OBJECT-TYPE
                SYNTAX DisplayString (SIZE (0..50))
                ACCESS read-write
                STATUS mandatory
                DESCRIPTION
                    "The text to use when prompting a menu user for a 
                    menu selection. Corresponds directly to SERVER MENU 
                    PROMPT and the value labeled 'Menu Prompt:' in the 
                    SERVER MENU display."
                ::= { xMenu 3 }

            
            -- The Menu table
            
            menuTable OBJECT-TYPE
                SYNTAX SEQUENCE OF MenuEntry
                ACCESS not-accessible
                STATUS mandatory
                DESCRIPTION
                    "A list of menu entries."
                ::= { xMenu 4 }
            
            menuEntry OBJECT-TYPE
                SYNTAX MenuEntry
                ACCESS not-accessible
                STATUS mandatory
                DESCRIPTION
                    "Parameter values for a menu entry."
                INDEX { menuIndex }
                ::= { menuTable 1 }
            
            MenuEntry ::=
                SEQUENCE {
                    menuIndex
                        INTEGER,
                    menuStatus
                        INTEGER,
                    menuText
                        DisplayString,
                    menuCommand
                        DisplayString
                }
            
            menuIndex OBJECT-TYPE
                SYNTAX INTEGER
                ACCESS read-only
                STATUS mandatory
                DESCRIPTION
                    "The index number of a menu entry.  Corresponds 
                    directly to the numbers down the left of the SERVER 
                    MENU display."
                ::= { menuEntry 1 }
            
            menuStatus OBJECT-TYPE
                SYNTAX INTEGER { invalid(1), valid(2) }
                ACCESS read-write
                STATUS mandatory
                DESCRIPTION
                    "The status of a the entry.  Set to 'invalid' to
                    remove the entry, which corresponds directly to the 
                    CLEAR SERVER MENU command.  Actual removal of the 
                    entry is implementation specific."
                DEFVAL { valid }
                ::= { menuEntry 2 }
            
            menuText OBJECT-TYPE
                SYNTAX DisplayString (SIZE (0..30))
                ACCESS read-write
                STATUS mandatory
                DESCRIPTION
                    "The text to be displayed in the menu.  Corresponds 
                    directly to the line next to the entry number in the 
                    SERVER MENU display."
                ::= { menuEntry 3 }
            
            menuCommand OBJECT-TYPE
                SYNTAX DisplayString (SIZE (0..64))
                ACCESS read-write
                STATUS mandatory
                DESCRIPTION
                    "The commands to execute when the user chooses the 
                    menu entry.  Corresponds directly second line 
                    following the entry number in the SERVER MENU 
                    display."
                ::= { menuEntry 4 }

            
            -- the Menu Port table
            
            menuPortTable OBJECT-TYPE
                SYNTAX SEQUENCE OF MenuPortEntry
                ACCESS not-accessible
                STATUS mandatory
                DESCRIPTION
                    "A list of menu-related character port entries."
                ::= { xMenu 5 }
            
            menuPortEntry OBJECT-TYPE
                SYNTAX MenuPortEntry
                ACCESS not-accessible
                STATUS mandatory
                DESCRIPTION
                    "Menu parameter values for a port."
                INDEX { menuPortIndex }
                ::= { menuPortTable 1 }
            
            MenuPortEntry ::=
                SEQUENCE {
                    menuPortIndex
                        INTEGER,
                    menuPortMenuStatus
                        INTEGER,
                    menuPortNestedMenuStatus
                        INTEGER,
                    menuPortNestedMenuPrivilege
                        INTEGER,
                    menuPortNestedTopLevel
                        INTEGER
                }
            
            menuPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { menuPortEntry 1 }
            
            menuPortMenuStatus OBJECT-TYPE
                SYNTAX INTEGER { disabled(1), enabled(2), privileged(3) }
                ACCESS read-write
                STATUS mandatory
                DESCRIPTION
                    "Control for menu operation on the port.  
                    Corresponds indirectly to PORT MENU and PORT 
                    PRIVILEGED MENU and the presence of the labels 
                    'Menu' and 'Privileged Menu' following the label 
                    'Enabled Characteristics:' in the PORT 
                    CHARACTERISTICS display."
                ::= { menuPortEntry 2 }
            
            menuPortNestedMenuStatus OBJECT-TYPE
                SYNTAX INTEGER { disabled(1), enabled(2), required(3) }
                ACCESS read-write
                STATUS mandatory
                DESCRIPTION
                    "Control for nested menu operation on the port.  
                    Corresponds indirectly to PORT NESTED MENU and the 
                    presence of the label 'Nested Menu' following the 
                    label 'Enabled Characteristics:' in the PORT 
                    CHARACTERISTICS display."
                ::= { menuPortEntry 3 }
            
            menuPortNestedMenuPrivilege OBJECT-TYPE
                SYNTAX INTEGER { disabled(1), enabled(2) }
                ACCESS read-write
                STATUS mandatory
                DESCRIPTION
                    "Control for nested privileged menu operation on the 
                    port.  Corresponds indirectly to PORT NESTED 
                    PRIVILEGED MENU and the presence of the label 
                    'Nested Privileged Menu' following the label 
                    'Enabled Characteristics:' in the PORT 
                    CHARACTERISTICS display."
                ::= { menuPortEntry 4 }
            
            menuPortNestedTopLevel OBJECT-TYPE
                SYNTAX INTEGER (0..255)
                ACCESS read-write
                STATUS mandatory
                DESCRIPTION
                    "The top level nested menu to select from the menu 
                    definition file."
                ::= { menuPortEntry 5 }
            
            -- additional scalar objects
            
            menuNestedName OBJECT-TYPE
                SYNTAX DisplayString (SIZE (0..16))
                ACCESS read-write
                STATUS mandatory
                DESCRIPTION
                    "Name of the script file containing the nested 
                    menu."
                DEFVAL { "NESTMENU.TXT" }
                ::= { xMenu 6 }
            
            menuNestedScriptMaximum OBJECT-TYPE
                SYNTAX INTEGER (0..204800)
                ACCESS read-write
                STATUS mandatory
                DESCRIPTION
                    "Maximum number of temporary storage bytes for a 
                    nested menu script file.  If not zero, the nested 
                    menu function is enabled."
                DEFVAL { 16384 }
                ::= { xMenu 7 }

            menuNestedSystemName OBJECT-TYPE
                SYNTAX INTEGER { disabled(1), enabled(2) }
                ACCESS read-write
                STATUS mandatory
                DESCRIPTION
                    "Control to request to download a menu script which is 
                     unique for this unit by prepending the sysLocalName of 
                     this unit to the nestedMenuName."
                DEFVAL { disabled  }
                ::= { xMenu 8 }
        
            menuNestedEthernet OBJECT-TYPE
                SYNTAX INTEGER { disabled(1), enabled(2) }
                ACCESS read-write
                STATUS mandatory
                DESCRIPTION
                    "Control to request to download a menu script which is
                     unique for this unit by prepending the Ethernet address, 
                     or 802.3 MAC address, of this unit to the nestedMenuName."
                DEFVAL { disabled   }
                ::= { xMenu 9 }

            
            -- the Network Login group
            
            -- Implementation of this group is mandatory for all MRV In-Reach
            -- systems that implement network login
            
            netLoginNumber OBJECT-TYPE
                SYNTAX INTEGER
                ACCESS read-only
                STATUS mandatory
                DESCRIPTION
                    "The number of entries in the Network Login Server 
                    table."
                ::= { xNetLogin 1 }
            
            -- The Network Login Server table
            
            netLoginServerTable OBJECT-TYPE
                SYNTAX SEQUENCE OF NetLoginServerEntry
                ACCESS not-accessible
                STATUS mandatory
                DESCRIPTION
                    "A list of network login server entries."
                ::= { xNetLogin 2 }
            
            netLoginServerEntry OBJECT-TYPE
                SYNTAX NetLoginServerEntry
                ACCESS not-accessible
                STATUS mandatory
                DESCRIPTION
                    "Network login parameter values for a server 
                    entry."
                INDEX { netLoginServerName }
                ::= { netLoginServerTable 1 }
            
            NetLoginServerEntry ::=
                SEQUENCE {
                    netLoginServerName
                        DisplayString,
                    netLoginServerStatus
                        INTEGER,
                    netLoginServerPath
                        DisplayString,
                    netLoginServerSeparator
                        DisplayString
                }
            
            netLoginServerName OBJECT-TYPE
                SYNTAX DisplayString (SIZE (1..50))
                ACCESS read-only
                STATUS mandatory
                DESCRIPTION
                    "The name of a network login server, suitable for 
                    resolution to a network address.  Corresponds 
                    directly to host portion of SERVER SCRIPT SERVER and 
                    the value labeled 'Script Host' in the SERVER 
                    PARAMETER SERVER display."
                ::= { netLoginServerEntry 1 }
            
            netLoginServerStatus OBJECT-TYPE
                SYNTAX INTEGER { invalid(1), valid(2) }
                ACCESS read-write
                STATUS mandatory
                DESCRIPTION 
                 "Status of this entry.  Set to 'invalid' to remove
                 the entry, which corresponds directly to the CLEAR
                 SERVER SCRIPT SERVER command.  Actual removal of the
                 entry is implementation specific."
                DEFVAL { valid }
                ::= { netLoginServerEntry 2 }
            
            netLoginServerPath OBJECT-TYPE
                SYNTAX DisplayString (SIZE (0..40))
                ACCESS read-write
                STATUS mandatory
                DESCRIPTION
                    "The full path name to the script file that is 
                    identified by the user name.  Corresponds directly 
                    to path portion of SERVER SCRIPT SERVER and the 
                    value labeled 'Script Path' in the SERVER PARAMETER 
                    SERVER display.  Defaults to the NULL string when
                    a new entry is created."
                ::= { netLoginServerEntry 3 }
            
            netLoginServerSeparator OBJECT-TYPE
                SYNTAX DisplayString (SIZE (0..1))
                ACCESS read-write
                STATUS mandatory
                DESCRIPTION
                    "The single character string that will be inserted
                    between the components of a file's path on the
                    script server.  Defaults to the NULL string when
                    a new entry is created.  Corresponds directly to the
                    separator portion of  SERVER SCRIPT SERVER display."
                ::= { netLoginServerEntry 4 }
            
            -- the Network Login Port table
            
            netLoginPortTable OBJECT-TYPE
                SYNTAX SEQUENCE OF NetLoginPortEntry
                ACCESS not-accessible
                STATUS mandatory
                DESCRIPTION
                    "A list of network login character port entries."
                ::= { xNetLogin 3 }
            
            netLoginPortEntry OBJECT-TYPE
                SYNTAX NetLoginPortEntry
                ACCESS not-accessible
                STATUS mandatory
                DESCRIPTION
                    "Network login parameter values for a port."
                INDEX { netLoginPortIndex }
                ::= { netLoginPortTable 1 }
            
            NetLoginPortEntry ::=
                SEQUENCE {
                    netLoginPortIndex
                        INTEGER,
                    netLoginPortScriptUse
                        INTEGER,
                    netLoginPortScriptEcho
                        INTEGER,
                    netLoginPortLoaderAddressType
                        AddressType,
                    netLoginPortLoaderAddress
                        OCTET STRING,
                    netLoginPortLoaderFile
                        DisplayString,
                    netLoginPortExecuteFile
                        DisplayString
                }
            
            netLoginPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { netLoginPortEntry 1 }
            
            netLoginPortScriptUse OBJECT-TYPE
                SYNTAX INTEGER { disabled(1), enabled(2), required(3) }
                ACCESS read-write
                STATUS mandatory
                DESCRIPTION
                    "Control for the script action taken when a user 
                    logs in on the port.  Corresponds directly to PORT 
                    SCRIPT LOGIN and the value labeled 'Script Login:' 
                    in the PORT ALTERNATE CHARACTERISTICS display."
                ::= { netLoginPortEntry 2 }
            
            netLoginPortScriptEcho OBJECT-TYPE
                SYNTAX INTEGER { disabled(1), enabled(2) }
                ACCESS read-write
                STATUS mandatory
                DESCRIPTION
                    "Control for display of script operation on the port 
                    when running a script.  Corresponds directly to PORT 
                    SCRIPT ECHO and the presence of the label 'Script 
                    Echo' following the label 'Enabled Characteristics:' 
                    in the PORT CHARACTERISTICS display."
                ::= { netLoginPortEntry 3 }
            
            netLoginPortLoaderAddressType OBJECT-TYPE
                SYNTAX AddressType
                ACCESS read-only
                STATUS mandatory
                DESCRIPTION
                    "The type of network address contained in 
                    netLoginPortLoaderAddress.  'unknown' means no 
                    address has been defined.  'other' means no other 
                    type value applies.  'ip' is an Internet IP address.  
                    'ethernet' is an 802.3 MAC address.  Corresponds 
                    indirectly to the address part of the value labeled 
                    'Script Loaded From:' in the PORT STATUS display."
                ::= { netLoginPortEntry 4 }
            
            netLoginPortLoaderAddress OBJECT-TYPE
                SYNTAX OCTET STRING
                ACCESS read-only
                STATUS mandatory
                DESCRIPTION
                    "The network address of the server that provided the 
                    script for the current port login.  Corresponds 
                    directly the address part of the value labeled 
                    'Script Loaded From:' in the PORT STATUS display."
                ::= { netLoginPortEntry 5 }
            
            netLoginPortLoaderFile OBJECT-TYPE
                SYNTAX DisplayString
                ACCESS read-only
                STATUS mandatory
                DESCRIPTION
                    "The path and file name of the script used for the 
                    current port login.  Corresponds directly the file 
                    name  part of the value labeled 'Script Loaded 
                    From:' in the PORT STATUS display."
                ::= { netLoginPortEntry 6 }
            
            netLoginPortExecuteFile OBJECT-TYPE
                SYNTAX DisplayString (SIZE (0..40))
                ACCESS read-write
                STATUS mandatory
                DESCRIPTION
                    "The path and file name of a script to be executed 
                    immediately on the port.  Corresponds directly the 
                    file name in the SCRIPT command."
                ::= { netLoginPortEntry 7 }
            
            
            -- the Dial group
            
            -- Implementation of this group is mandatory for all MRV In-Reach
            -- systems that implement automatic dialing
            
            dialPortTable OBJECT-TYPE
                SYNTAX SEQUENCE OF DialPortEntry
                ACCESS not-accessible
                STATUS mandatory
                DESCRIPTION
                    "A list of dial character port entries."
                ::= { xDial 1 }
            
            dialPortEntry OBJECT-TYPE
                SYNTAX DialPortEntry
                ACCESS not-accessible
                STATUS mandatory
                DESCRIPTION
                    "Dial parameter values for a port."
                INDEX { dialPortIndex }
                ::= { dialPortTable 1 }
            
            DialPortEntry ::=
                SEQUENCE {
                    dialPortIndex
                        INTEGER,
                    dialPortDialback
                        INTEGER,
                    dialPortDialbackTimeout
                        INTEGER,
                    dialPortDialout
                        INTEGER,
                    dialPortDialbackNoUsername 
                        INTEGER
                }
            
            dialPortIndex OBJECT-TYPE
                SYNTAX INTEGER
                ACCESS read-only
                STATUS mandatory
                DESCRIPTION
                    "An index value that uniquely identifies a port.  
                    The port identified by a particular value of this 
                    index is the same port as identified by 
                    charPortIndex in the standard Character MIB."
                ::= { dialPortEntry 1 }
            
            dialPortDialback OBJECT-TYPE
                SYNTAX INTEGER { disabled(1), enabled(2) }
                ACCESS read-write
                STATUS mandatory
                DESCRIPTION
                    "Control for use of dialback when a user logs in on 
                    the port.  Corresponds directly to PORT DIALBACK and 
                    the presence of the label 'Dialback' following the 
                    label 'Enabled Characteristics:' in the PORT 
                    CHARACTERISTICS display."
                ::= { dialPortEntry 2 }
            
            dialPortDialbackTimeout OBJECT-TYPE
                SYNTAX INTEGER (5..60)
                ACCESS read-write
                STATUS mandatory
                DESCRIPTION
                    "The number of seconds to wait for remote modem 
                    response when dialing back.  Corresponds directly to 
                    PORT DIALBACK TIMEOUT and the value labeled 
                    'Dialback Timeout:' in the PORT ALTERNATE 
                    CHARACTERISTICS display."
                ::= { dialPortEntry 3 }

            dialPortDialout OBJECT-TYPE
                SYNTAX INTEGER { none(1), query(2), slip(3), ppp(4) }
                ACCESS read-write
                STATUS mandatory 
                DESCRIPTION
                    "A control to determine the state of a remote port after
                     it has been logged out from the remote side of the
                     connection.  none will log out the port, query will ask
                     user what to do, slip and ppp will revert
                     to those protocols"
                DEFVAL  { none }
                ::= { dialPortEntry 4 }

 	dialPortDialbackNoUsername OBJECT-TYPE
		SYNTAX INTEGER { disabled(1), enabled(2) }
		ACCESS read-write
		STATUS mandatory
		DESCRIPTION
		    "Control which when enabled on a dialback port will not
                     prompt for a username upon dialing back. Instead the 
                     original username is reused."
		DEFVAL { disabled }
		::= { dialPortEntry 5 }

            -- the Session Log group
            
            -- Implementation of this group is mandatory for all MRV In-Reach
            -- systems that implement logging session information
            
            sessionLogLimit OBJECT-TYPE
                SYNTAX INTEGER (0..1000)
                ACCESS read-write
                STATUS mandatory
                DESCRIPTION
                    "The maximum number of entries allowed in the 
                    Session Log table.  Corresponds directly to SERVER 
                    ACCOUNTING ENTRIES and the value labeled 'Accounting 
                    Entries:' in the SERVER CHARACTERISTICS display."
                ::= { xSessionLog 1 }
            
            -- Additional scalars follow Session Log table
            
            -- The Session Log table
            
            sessionLogTable OBJECT-TYPE
                SYNTAX SEQUENCE OF SessionLogEntry
                ACCESS not-accessible
                STATUS mandatory
                DESCRIPTION
                    "A list of session log entries."
                ::= { xSessionLog 2 }
            
            sessionLogEntry OBJECT-TYPE
                SYNTAX SessionLogEntry
                ACCESS not-accessible
                STATUS mandatory
                DESCRIPTION
                    "Parameter values for a session log entry."
                INDEX { sessionLogIndex }
                ::= { sessionLogTable 1 }
            
            SessionLogEntry ::=
                SEQUENCE {
                    sessionLogIndex
                        INTEGER,
                    sessionLogConnectionID
                        INTEGER,
                    sessionLogPort
                        INTEGER,
                    sessionLogEvent
                        INTEGER,
                    sessionLogEventDetail
                        INTEGER,
                    sessionLogUserName
                        DisplayString,
                    sessionLogRemoteName
                        DisplayString,
                    sessionLogConnectTime
                        DateTime,
                    sessionLogDisconnectTime
                        DateTime,
                    sessionLogInCharacters
                        Counter,
                    sessionLogOutCharacters
                        Counter,
                    sessionLogVerboseEvent
                        INTEGER,
                    sessionLogX25Direction
                        INTEGER,
                    sessionLogVerboseMessage
                        DisplayString,
                    sessionLogX25CallerAddress
                        OCTET STRING,
                    sessionLogX25CalledAddress
                        OCTET STRING,
                    sessionLogX25DisconnectCause
                        INTEGER,
                    sessionLogX25DisconnectDiagnostic
                        INTEGER
                }
            
            sessionLogIndex OBJECT-TYPE
                SYNTAX INTEGER
                ACCESS read-only
                STATUS mandatory
                DESCRIPTION
                    "The index number of a session log entry.  
                    Corresponds directly to the order of the displayed 
                    records in the SERVER ACCOUNTING display.  The 
                    maximum value is sessionLogLimit."
                ::= { sessionLogEntry 1 }
            
            sessionLogConnectionID OBJECT-TYPE
                SYNTAX INTEGER (1..65535)
                ACCESS read-only
                STATUS mandatory
                DESCRIPTION
                    "An indentifying number for records relating to the 
                    same connection, that is, the connect and disconnect 
                    records, either of which can be missing.  
                    Corresponds directly to value labeled 'Entry' the 
                    SERVER ACCOUNTING display."
                ::= { sessionLogEntry 2 }
            
            sessionLogPort OBJECT-TYPE
                SYNTAX INTEGER
                ACCESS read-only
                STATUS mandatory
                DESCRIPTION
                    "An index value that uniquely identifies the port 
                    where the event took place.  The port identified by 
                    a particular value of this index is the same port as 
                    identified by charPortIndex in the standard 
                    Character MIB.  Corresponds directly to the value 
                    labeled 'Port' in the SERVER ACCOUNTING display."
                ::= { sessionLogEntry 3 }
            
            sessionLogEvent OBJECT-TYPE
                SYNTAX INTEGER { login(1), connectLocal(2),
                                 connectRemote(3), disconnect(4),
                                 rCPConnect(5), rCPDisconnect(6),
                                 x25Connect(13), x25Disconnect(14),
                                 processDefined(15) }
                ACCESS read-only
                STATUS mandatory
                DESCRIPTION
                    "The type of event.  Corresponds directly to the 
                    alphabetic part of the value labeled 'Type' in the 
                    SERVER ACCOUNTING display. Type 15 is used by internal
                    processes that call the session log function with an
                    already formatted message. "
                ::= { sessionLogEntry 4 }
            
            sessionLogEventDetail OBJECT-TYPE
                SYNTAX INTEGER { none(1), protocolBadCircuit(2),
                                 protocolBadCredits(3),
                                 protocolBadStartOrRun(4),
                                 protocolBadRange(5),
                                 duplicateQueueID(6), noUsers(7),
                                 noServiceResourced(8),
                                 serviceUserDisconnect(9),
                                 serviceUnavailable(10),
                                 serverUserDisconnect(11),
                                 noNodeResources(12),
                                 systemShutdown(13),
                                 nodeUserdisconnect(14),
                                 badCircuitTimer(15),
                                 badServiceClass(16),
                                 badMessageOrSlot(17),
                                 timeout(18), noProgress(19),
                                 serviceNotOnPort(20), noSuchPort(21),
                                 badPassword(22), serviceBusy(23),
                                 noSuchService(24), 
                                 serviceDisabled(25),
                                 notInQueue(26), noImmeditatAccess(27),
                                 accessDenied(28),
                                 protocolBadSolicit(29),
                                 protocolBadReasonCode(30),
                                 unsupportedTest(31),
                                 domainTooLong(32),
                                 noSuchNode(33),
                                 noSuchServiceOnNode(34),
                                 rejectService(35),
                                 internetConnectDisabled(36) }
                ACCESS read-only
                STATUS mandatory
                DESCRIPTION
                    "The detailed reason for the event.  Corresponds 
                    directly to the numeric part of the value labeled 
                    'Type' in the SERVER ACCOUNTING display."
                ::= { sessionLogEntry 5 }
            
            sessionLogUserName OBJECT-TYPE
                SYNTAX DisplayString (SIZE (0..16))
                ACCESS read-only
                STATUS mandatory
                DESCRIPTION
                    "The user name logged in on the port when the event 
                    occurred.  Corresponds directly to the value labeled 
                    'Username' in the SERVER ACCOUNTING display."
                ::= { sessionLogEntry 6 }
            
            sessionLogRemoteName OBJECT-TYPE
                SYNTAX DisplayString (SIZE (0..17))
                ACCESS read-only
                STATUS mandatory
                DESCRIPTION
                    "The name of the session remote partner.  
                    Corresponds directly to the value labeled 
                    'Destination' in the SERVER ACCOUNTING display."
                ::= { sessionLogEntry 7 }
            
            sessionLogConnectTime OBJECT-TYPE
                SYNTAX DateTime
                ACCESS read-only
                STATUS mandatory
                DESCRIPTION
                    "The date and time that session connection occurred.  
                    Corresponds directly to the value labeled 'Connect 
                    Time' in the SERVER ACCOUNTING display."
                ::= { sessionLogEntry 8 }
            
            sessionLogDisconnectTime OBJECT-TYPE
                SYNTAX DateTime
                ACCESS read-only
                STATUS mandatory
                DESCRIPTION
                    "The date and time that session disconnection 
                    occurred.  Corresponds directly to the value labeled 
                    'Disconnect Time' in the SERVER ACCOUNTING 
                    display."
                ::= { sessionLogEntry 9 }
            
            sessionLogInCharacters OBJECT-TYPE
                SYNTAX Counter
                ACCESS read-only
                STATUS mandatory
                DESCRIPTION
                    "The number of characters that came into the port 
                    for the session.  Corresponds directly to the value 
                    labeled 'Bytes In' in the SERVER ACCOUNTING 
                    display."
                ::= { sessionLogEntry 10 }
            
            sessionLogOutCharacters OBJECT-TYPE
                SYNTAX Counter
                ACCESS read-only
                STATUS mandatory
                DESCRIPTION
                    "The number of characters that went out of the port 
                    for the session.  Corresponds directly to the value 
                    labeled 'Bytes Out' in the SERVER ACCOUNTING 
                    display."
                ::= { sessionLogEntry 11 }
            
            sessionLogVerboseEvent OBJECT-TYPE
                SYNTAX INTEGER { login(1), connectLocal(2),
                                 connectRemote(3), disconnect(4),
                                 connectRcp(5),
                                 disconnectRcp(6),
                                 telnetMaint(7),
                                 xremote(8),
                                 xprinter(9),
                                 lpd(12),
                                 connectX25(13),
                                 disconnectX25(14),
                                 userDefined(15) }
                ACCESS read-only
                STATUS mandatory
                DESCRIPTION
                    "When logging in 'verbose' mode, the event that 
                    occured."
                ::= { sessionLogEntry 12 }
            
            sessionLogX25Direction OBJECT-TYPE
                SYNTAX INTEGER { inbound(1), outbound(2) }
                ACCESS read-only
                STATUS mandatory
                DESCRIPTION
                    "The initial direction for an X.25 connection.
                     A value of 0 is returned if the session is
                     not X25"
                ::= { sessionLogEntry 13 }
            
            sessionLogVerboseMessage OBJECT-TYPE
                SYNTAX DisplayString
                ACCESS read-only
                STATUS mandatory
                DESCRIPTION
                    "Text describing the event that was logged."
                ::= { sessionLogEntry 14 }
            
            sessionLogX25CallerAddress OBJECT-TYPE
                SYNTAX OCTET STRING (SIZE (0..20))
                ACCESS read-only
                STATUS mandatory
                DESCRIPTION
                    "For an X.25 connection, the X.121 source address."
                ::= { sessionLogEntry 15 }
            
            sessionLogX25CalledAddress OBJECT-TYPE
                SYNTAX OCTET STRING (SIZE (0..20))
                ACCESS read-only
                STATUS mandatory
                DESCRIPTION
                    "For an X.25 connection, the X.121 destination 
                    address."
                ::= { sessionLogEntry 16 }
            
            sessionLogX25DisconnectCause OBJECT-TYPE
                SYNTAX INTEGER
                ACCESS read-only
                STATUS mandatory
                DESCRIPTION
                    "For a terminated X.25 connection, the standard, 
                    X.25 cause code."
                ::= { sessionLogEntry 17 }
            
            sessionLogX25DisconnectDiagnostic OBJECT-TYPE
                SYNTAX INTEGER
                ACCESS read-only
                STATUS mandatory
                DESCRIPTION
                    "For a terminated X.25 connection, the standard, 
                    X.25 diagnostic code."
                ::= { sessionLogEntry 18 }
            
            
            -- Additional scalars
            
            sessionLogHostType OBJECT-TYPE
                SYNTAX INTEGER { none(1), unix(2) }
                ACCESS read-write
                STATUS mandatory
                DESCRIPTION
                    "The type of host to which session log events are to 
                    be sent."
                ::= { xSessionLog 3 }
            
            sessionLogHostAddress OBJECT-TYPE
                SYNTAX OCTET STRING (SIZE (0..4))
                ACCESS read-write
                STATUS mandatory
                DESCRIPTION
                    "The address of the host to receive events."
                ::= { xSessionLog 4 }
            
            sessionLogVerbose OBJECT-TYPE
                SYNTAX INTEGER { disabled(1), enabled(2) }
                ACCESS read-write
                STATUS mandatory
                DESCRIPTION
                    "Control for verbose logging."
                ::= { xSessionLog 5 }
            
            sessionLogPriority OBJECT-TYPE
                SYNTAX INTEGER (0..7)
                ACCESS read-write
                STATUS mandatory
                DESCRIPTION
                    "The largest priority number for the system to log.  
                    Higher numbered (lower priority) events will not be 
                    logged."
                ::= { xSessionLog 6 }
            
            sessionLogEmpty OBJECT-TYPE
                SYNTAX INTEGER  { ready(1), execute(2) }
                ACCESS read-write
                STATUS mandatory
                DESCRIPTION
                    "Control to empty the log.  In response to a 
                    get-request or get-next-request, the agent always 
                    returns 'ready' for this value.  Setting the value 
                    to 'ready' has no effect.  Setting it to 'execute' 
                    causes the log to be emptied."
                ::= { xSessionLog 7 }

            sessionLogFacility OBJECT-TYPE
                SYNTAX INTEGER { local0(1), local1(2), local2(3),
                                 local3(4), local4(5), local5(6),
                                 local6(7), local7(8), user(9) }
                ACCESS read-write
                STATUS mandatory
                DESCRIPTION
                    "The UNIX facility level that server originated 
                     accounting messages are logged to."
                DEFVAL { user }
                ::= { xSessionLog 8 }

            sessionLogReliable OBJECT-TYPE
                SYNTAX INTEGER { disabled (1), enabled (2) }
                ACCESS read-write
                STATUS mandatory
                DESCRIPTION
                    "Control for reliable logging. Corresponds directly to the 
                    presence of the label 'Reliable Accounting' following the  
                    label 'Enabled Characteristics:' in the SERVER 
                    CHARACTERISTICS display."
                DEFVAL { disabled }
                ::= { xSessionLog 9 }

            sessionLogHostSecondaryType OBJECT-TYPE
                SYNTAX INTEGER { none (1), unix(2) }
                ACCESS read-write
                STATUS mandatory
                DESCRIPTION
                    "The type of secondary host to which session log events are
                     to be sent. This value should be set to unix when
                     configuring a non-zero sessionLogHostSecondaryAddress.
                     Corresponds to the presence of the label 'SYSLOGD Host2'
                     following the label 'Daemon(s)' in the SERVER UNIT 
                     display."
                DEFVAL { none  }
                ::= { xSessionLog 10 }

            sessionLogHostSecondaryAddress OBJECT-TYPE
                SYNTAX OCTET STRING (SIZE (0..4))
                ACCESS read-write
                STATUS mandatory
                DESCRIPTION
                    "The address of a secondary host to receive events.
                     Corresponds directly to the value labeled 
                     'SYSLOGD Host2' in the SERVER UNIT display."
                ::= { xSessionLog 11 }

            sessionLogZeroAccountingAll OBJECT-TYPE
                SYNTAX INTEGER { ready(1), execute(2)}
                ACCESS read-write
                STATUS mandatory
                DESCRIPTION
                    "A control to clear all entries in the accounting log 
                     including command log entries. Corresponds directly to 
                     the command CLEAR SERVER ACCOUNTING ALL. In response to 
                     a get-request or get-next-request the agent always returns
                     ready for this value."
                ::= { xSessionLog 12 }                


            sessionLogZeroCommandLogging OBJECT-TYPE
                SYNTAX INTEGER { ready(1), execute(2)}
                ACCESS read-write
                STATUS mandatory
                DESCRIPTION
                    "A control to clear all command log entries. Corresponds
                     directly to the command CLEAR SERVER COMMAND LOGGING. In
                     response to a get-request or get-next-request the agent 
                     always returns ready for this value."
                ::= { xSessionLog 13 }                

 	sessionLogTl1AutonomousLogSize OBJECT-TYPE
		SYNTAX INTEGER ( 0..1000)
		ACCESS read-write
		STATUS mandatory
		DESCRIPTION
		    "The size in bytes of the TL1 autonomous log, which 
                     records alarms. A change in log size will not take effect
                     until rebooting the unit."
		DEFVAL { 0 }
		::= { xSessionLog 14 }

 	sessionLogTl1CommandLogSize OBJECT-TYPE
		SYNTAX INTEGER ( 0..1000)
		ACCESS read-write
		STATUS mandatory
		DESCRIPTION
		    "The size in bytes of the TL1 command log, which records
                     all TL1 commands entered on this server. A change in log
                     size will not take effect until rebooting the unit."
		DEFVAL { 0 }
		::= { xSessionLog 15 }

            sessionLogZeroDataLogging OBJECT-TYPE
                SYNTAX INTEGER { ready(1), execute(2)}
                ACCESS read-write
                STATUS mandatory
                DESCRIPTION
                    "A control to clear all data log entries. Corresponds
                     directly to the command CLEAR SERVER DATA LOGGING. In
                     response to a get-request or get-next-request the agent 
                     always returns ready for this value."
                ::= { xSessionLog 16 }                

            sessionLogZeroAlarmLogging OBJECT-TYPE
                SYNTAX INTEGER { ready(1), execute(2)}
                ACCESS read-write
                STATUS mandatory
                DESCRIPTION
            	    "Control to clear all alarm log entries. In response to a
             	    get-request or a get-next-request the agent always returns
             	    ready for this value."
                ::= { xSessionLog 17 }                
 

            -- The Loaded and Parsed CCL Table

            cclParsedScriptTable OBJECT-TYPE
                SYNTAX SEQUENCE OF CclParsedScriptEntry
                ACCESS not-accessible
                STATUS mandatory
                DESCRIPTION
                    "A list of parsed CCL scripts."
                ::= { xCcl 1 }

            cclParsedScriptEntry OBJECT-TYPE
                SYNTAX CclParsedScriptEntry
                ACCESS not-accessible
                STATUS mandatory
                DESCRIPTION
                    "Parsed CCL script information."
                INDEX { cclScriptName }
                ::= { cclParsedScriptTable 1 }

            CclParsedScriptEntry ::=
                SEQUENCE {
                    cclScriptName
                        DisplayString,
                    cclScriptControl
                        INTEGER
                }

            cclScriptName OBJECT-TYPE
                SYNTAX DisplayString (SIZE (1..32))
                ACCESS read-only
                STATUS mandatory
                DESCRIPTION
                    "The name of a CCL script file that has been
                    loaded from a script server.  Corresponds directly
                    to the name in a SERVER CCL command and the value
                    labeled 'CCL name:' in the PORT CHARACTERISTICS
                    display."
                ::= { cclParsedScriptEntry 1 }

            cclScriptControl OBJECT-TYPE
                SYNTAX INTEGER { refresh(1), delete(2) }
                ACCESS read-write
                STATUS mandatory
                DESCRIPTION
                    "Control for maintaining the CCL script.  The
                    refresh action consists of retrieving the script
                    by name from a script server and parsing it into
                    an executable format.  This may be used to add an
                    entry to the table or refresh an existing entry with
                    a new version of the CCL script from the server.
                    This command may take ten seconds or more to complete
                    and may fail if the script file cannot be retrieved or
                    an error is encountered in parsing the CCL script.
                    An error value of genErr is returned upon refresh
                    failure. The refresh action corresponds directly to
                    the commnd: REFRESH SERVER CCL.  Setting this field
                    to delete causes a script that is NOT being referenced
                    by any ports to be removed from the list and its
                    memory freed.  This action corresponds directly to
                    the command: DELETE SERVER CCL.  An error value of
                    badValue is returned upon delete failure."
                DEFVAL { refresh }
                ::= { cclParsedScriptEntry 2 }

            -- The CCL Port Table

            cclPortTable OBJECT-TYPE
                SYNTAX SEQUENCE OF CclPortEntry
                ACCESS not-accessible
                STATUS mandatory
                DESCRIPTION
                    "A list of ccl character port entries."
                ::= { xCcl 2 }
            
            cclPortEntry OBJECT-TYPE
                SYNTAX CclPortEntry
                ACCESS not-accessible
                STATUS mandatory
                DESCRIPTION
                    "CCL parameter values for a port."
                INDEX { charPortIndex }
                ::= { cclPortTable 1 }
            
            CclPortEntry ::=
                SEQUENCE {
                    cclPortCclName
                        DisplayString,
                    cclPortModemAudible
                        INTEGER
                }

            cclPortCclName OBJECT-TYPE
                SYNTAX DisplayString (SIZE (0..32))
                ACCESS read-write
                STATUS mandatory
                DESCRIPTION
                    "The name of the ARAP modem CCL script file."
                ::= { cclPortEntry 1 }

            cclPortModemAudible OBJECT-TYPE
                SYNTAX INTEGER { disabled(1), enabled(2) }
                ACCESS read-write
                STATUS mandatory
                DESCRIPTION
                    "This boolean indicates if the CCL script should put
                    the modem into audible mode."
            ::= { cclPortEntry 2 }

-- The Data Broadcast Group Table

    broadcastGroupTable OBJECT-TYPE
	SYNTAX SEQUENCE OF BroadcastGroupEntry
	ACCESS not-accessible
	STATUS mandatory
	DESCRIPTION
		"A list of broadcast groups."
    ::= { xBroadcastGroup 1 }

    broadcastGroupEntry OBJECT-TYPE
	SYNTAX BroadcastGroupEntry
	ACCESS not-accessible
	STATUS mandatory
	DESCRIPTION
		"Broadcast group information."
	INDEX { broadcastGroupIndex }
    ::= { broadcastGroupTable 1 }

    BroadcastGroupEntry ::=
	SEQUENCE {
		broadcastGroupIndex
			INTEGER,
		broadcastGroupStatus
			INTEGER,
		broadcastGroupMaster
			INTEGER,
		broadcastGroupSlaves
			OCTET STRING,
		broadcastGroupSlavesBroadcastOnly
			OCTET STRING,
		broadcastGroupSlaveTcpPort
			INTEGER,
		broadcastGroupSlaveTcpBroadcastOnly
			INTEGER
	}

    broadcastGroupIndex OBJECT-TYPE
	SYNTAX INTEGER ( 1..10)
	ACCESS read-only
	STATUS mandatory
	DESCRIPTION
            "An index value that uniquely identifies a broadcast group."
    ::= { broadcastGroupEntry 1 }

    broadcastGroupStatus OBJECT-TYPE
	SYNTAX INTEGER { disabled(1), enabled(2) }
	ACCESS read-write
	STATUS mandatory
	DESCRIPTION
            "A status value for the broadcast group. The value 'enabled' means
             that the group is active and broadcasting data whereas 'disabled'
             means that the group is not active."
        DEFVAL { disabled }
    ::= { broadcastGroupEntry 2 } 

    broadcastGroupMaster OBJECT-TYPE
	SYNTAX INTEGER 
	ACCESS read-write
	STATUS mandatory
	DESCRIPTION
            "An index value that uniquely identifies the Master Broadcast Port
             for this group. The port provided in this object is the same port
             as identified by charPortIndex in the standard Character MIB."
    ::= { broadcastGroupEntry 3 } 

    broadcastGroupSlaves OBJECT-TYPE
	SYNTAX OCTET STRING 
	ACCESS read-write
	STATUS mandatory
	DESCRIPTION
            "A bitmap representing the ports included in this broadcast group.
             A bit with a value of '1' means the corresponding port is included
             in the broadcast group whereas a value of '0' indicates that the
             port is not part of the broadcast group."
    ::= { broadcastGroupEntry 4 } 

    broadcastGroupSlavesBroadcastOnly OBJECT-TYPE
	SYNTAX OCTET STRING
	ACCESS read-write
	STATUS mandatory
	DESCRIPTION
            "A bitmap representing the ports set up to discard input data and
             transmit only the broadcast data on the line. A bit set to '1' 
             means that the corresponding port will only broadcast the data and
             discard any input."
    ::= { broadcastGroupEntry 5 } 

    broadcastGroupSlaveTcpPort OBJECT-TYPE
	SYNTAX INTEGER (0..65554)
	ACCESS read-write
	STATUS mandatory
	DESCRIPTION
            "A TCP port number on which the broadcast group process will listen
             for incoming TCP connections. A client connected to this
             particular port will receive the data broadcast by the Master
             Port. A value of '0' indicates that no TCP port is defined."
        DEFVAL { 0 }
    ::= { broadcastGroupEntry 6 } 

    broadcastGroupSlaveTcpBroadcastOnly OBJECT-TYPE
	SYNTAX INTEGER { disabled(1), enabled(2) }
	ACCESS read-write
	STATUS mandatory
	DESCRIPTION
            "Specifies whether the TCP port will discard input characters 
             for the Master port so that the Master port operates in broadcast 
             only mode."
        DEFVAL { disabled }
    ::= { broadcastGroupEntry 7 }

-- The ICMP Ping Table

    pingHostsTable OBJECT-TYPE
	SYNTAX SEQUENCE OF PingHostsEntry
	ACCESS not-accessible
	STATUS mandatory
	DESCRIPTION
		"A list of ICMP ping hosts."
    ::= { xPingHosts 1 }

    pingHostsEntry OBJECT-TYPE
	SYNTAX PingHostsEntry
	ACCESS not-accessible
	STATUS mandatory
	DESCRIPTION
		"Ping Hosts information."
	INDEX { icmpPingHostIndex }
    ::= { pingHostsTable 1 }

    PingHostsEntry ::=
	SEQUENCE {
		icmpPingHostIndex
			INTEGER,
		icmpPingHostAddress
			 IpAddress,
		icmpPingHostDescription
			DisplayString,
		icmpPingHostNotificationType
			INTEGER,
		icmpPingHostPollingInterval		
			INTEGER,
		icmpPingHostMaximumRetries
			INTEGER,
		icmpPingHostTrapSeverityLevel
			INTEGER,
		icmpPingHostStatus
			INTEGER
	}

	    icmpPingHostIndex OBJECT-TYPE
		SYNTAX INTEGER ( 1..24)
		ACCESS read-only
		STATUS mandatory
		DESCRIPTION
	            "An index value that uniquely identifies a ping host."
	    ::= { pingHostsEntry 1 }

	    icmpPingHostAddress OBJECT-TYPE
		SYNTAX IpAddress
		ACCESS read-write
		STATUS mandatory
		DESCRIPTION
	            "The host address to be monitored to make sure it is
                     reachable using ICMP pings. This address must be
                     unique within the table, and must be Set to a non-zero
                     value prior to configuring the other attributes of
                     the ping host. A set-request with an IpAddress of
                     zero will make this entry inactive."
	    ::= { pingHostsEntry 2 }

	    icmpPingHostDescription OBJECT-TYPE
                SYNTAX DisplayString (SIZE (0..32))
		ACCESS read-write
		STATUS mandatory
		DESCRIPTION
	            "This is an optional description of the ping host."
	    ::= { pingHostsEntry 3 }

	    icmpPingHostNotificationType OBJECT-TYPE
	        SYNTAX  INTEGER { none (1), snmp (2) }
		ACCESS read-write
		STATUS mandatory
		DESCRIPTION
	            "Indicates the type of notification used, if any, 
                     when the ping host is determined to be unreachable.
                     If the type is snmp, a trap is sent to configured
                     trap clients."
	        DEFVAL { snmp }
	    ::= { pingHostsEntry 4 }

	    icmpPingHostPollingInterval OBJECT-TYPE
		SYNTAX INTEGER ( 5..65535)
		ACCESS read-write
		STATUS mandatory
		DESCRIPTION
	            "The time in seconds between sending an ICMP ping to
                     a ping host in order to check for reachability."
	    ::= { pingHostsEntry 5 }

	    icmpPingHostMaximumRetries OBJECT-TYPE
		SYNTAX INTEGER ( 1..255)
		ACCESS read-write
		STATUS mandatory
		DESCRIPTION
	            "The maximum consecutive failed attempts to reach the
                     host via ICMP ping before sending notification as 
                     specified by icmpPingHostNotificationType."
	    ::= { pingHostsEntry 6 }

	icmpPingHostTrapSeverityLevel OBJECT-TYPE
	       SYNTAX  INTEGER { indeterminate (2), warning (3), 
                        minor (4), major (5), critical (6) }
	       ACCESS  read-write
	       STATUS  mandatory
	       DESCRIPTION
	           "Indicates the severity level of a trap to be sent out
                    when the host is unreachable."
	       ::= { pingHostsEntry 7 }

	icmpPingHostStatus OBJECT-TYPE
	       SYNTAX  INTEGER { cleared (1), indeterminate (2), warning (3), 
                        minor (4), major (5), critical (6) }
	       ACCESS  read-only
	       STATUS  mandatory
	       DESCRIPTION
	           "Indicates the current status of the ping host. If the
                    host is reachable, the status is cleared. Otherwise, it
                    is the same as the icmpPingHostTrapSeverityLevel."
	       ::= { pingHostsEntry 8 }

	    -- Trap definitions
            -- These traps apply to InReach agents running V2.4 and above. 
            -- Earlier traps are defined in the MRV-IN-REACH-TRAP-MIB.

            -- The following contactClosureChanged trap is deprecated for
            -- agents running V3-1 and above. Refer to traps beginning at
            -- 10001 for the replacement traps.
	
           contactClosureChanged TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Indication that the contact closure transitioned to open or closed."
           ::= 30

           powerAlarmFuseBankA TRAP-TYPE
           ENTERPRISE mrvInReachProductDivision
           VARIABLES  {  
		basicPowerStatusFuseA,
		sysLocation
		}
           DESCRIPTION
               "Indicates that a fuse from bank A tripped its breaker, or that
                it went operational. However, it is unlikely that a trap would
                be issued when the fuse starts working."
           ::= 31

 	   powerAlarmFuseBankB TRAP-TYPE
           ENTERPRISE mrvInReachProductDivision
           VARIABLES  {  
		basicPowerStatusFuseB,
		sysLocation
		}
           DESCRIPTION
               "Indicates that a fuse from bank B tripped its breaker, or that
                it went operational. However, it is unlikely that a trap would
                be issued when the fuse starts working."
           ::= 32

 	   powerSupplyAlarmA TRAP-TYPE
           ENTERPRISE mrvInReachProductDivision
           VARIABLES  {  basicPowerSupplyStatusA,
		 sysLocation 
		}
           DESCRIPTION
               "Indicates that power supply A lost or regained power.
                However, it is unlikely that a trap would be issued when the
                power comes on."
           ::= 33

 	   powerSupplyAlarmB TRAP-TYPE
           ENTERPRISE mrvInReachProductDivision
           VARIABLES  {  basicPowerSupplyStatusB,
		sysLocation
		}
           DESCRIPTION
               "Indicates that power supply B lost or regained power.
                However, it is unlikely that a trap would be issued when the
                power comes on."
           ::= 34

           portInputSignalChange TRAP-TYPE
           ENTERPRISE mrvInReachProductDivision
           VARIABLES {  rs232InSigState, sysLocation, 	        
			rs232PortIndex }
           DESCRIPTION
              "Indicates that an input signal on a port has transitioned to
               the state indicated in the variable rs232InSigState."
           ::= 35

           portOutputSignalChange TRAP-TYPE
           ENTERPRISE mrvInReachProductDivision
           VARIABLES {  rs232OutSigState, sysLocation,
			rs232PortIndex }
           DESCRIPTION
              "Indicates that an output signal on a port has transitioned to
               the state indicated in the variable rs232OutSigState."
           ::= 36

           humidityThresholdExceeded TRAP-TYPE
           ENTERPRISE mrvInReachProductDivision
           VARIABLES {  basicHumidityValue,
                       basicTemperatureHumiditySensorName,
  		       sysLocation,
	               basicHumiditySensorIndex,
                       basicHumidityAlarmStatus
                     }
           DESCRIPTION
               "Indication that the humidity exceeded a threshhold and
                the value of the currrent humidity."
           ::= 37

           temperatureThresholdExceeded TRAP-TYPE
           ENTERPRISE mrvInReachProductDivision
           VARIABLES  {  
		basicTemperatureValue,
                basicTemperatureHumiditySensorName,
		sysLocation,
	        basicTemperatureSensorIndex,
                basicTemperatureAlarmStatus
		}
           DESCRIPTION
               "Indication that the temperature exceeded a threshhold and
                the value of the currrent temperature."
           ::= 38

           alarmMasterNotResponding TRAP-TYPE
           ENTERPRISE mrvInReachProductDivision
           VARIABLES { 
	        basicPortIndex, 
		sysLocation,
		basicPortAlarmMasterStatus
		 }
           DESCRIPTION
               "Indication that the high density alarm management device lost
                or regained contact with the inReach port to which it was 
                connected as indicated by the basicPortAlarmMasterStatus 
                variable."
          ::= 39

           alarmMasterInputStateChange TRAP-TYPE
           ENTERPRISE mrvInReachProductDivision
           VARIABLES { 
		basicAlarmMasterInputValue,
		basicAlarmMasterInputName,  
		sysLocation,
	        basicAlarmMasterInputPort,
                basicAlarmMasterInputStatus,
	        basicAlarmMasterInputSlot,
	        basicAlarmMasterInputPoint
		 }
           DESCRIPTION
               "Indication that the alarm input point within a high density alarm 
                management port transitioned to open or closed."
          ::= 41

           asciiToTrapTranslation  TRAP-TYPE
           ENTERPRISE mrvInReachProductDivision
           VARIABLES { 
                basicPortAsciiToTrapTranslationTrapSeverity,
                basicPortAsciiToTrapTranslationLastMessage
                 }
           DESCRIPTION
                "This trap contains ASCII data, which arrived at serial port,
                 was formatted as a trap, and sent out on the network."
           ::= 42
 
	powerMasterNotResponding TRAP-TYPE
        ENTERPRISE mrvInReachProductDivision
        VARIABLES  { 
           basicPortIndex,
           sysLocation,
	   basicPortPowerMasterDeviceStatus           
           }
	DESCRIPTION
	    "Indication that the power management port lost or regained 
             contact with the power unit to which it was connected as
             indicated by the basicPortPowerMasterDeviceStatus variable."
        ::= 43

	temperatureNormal TRAP-TYPE
        ENTERPRISE mrvInReachProductDivision
        VARIABLES  {  
            basicTemperatureValue,
            basicTemperatureHumiditySensorName,
            sysLocation,
	    basicTemperatureSensorIndex,
            basicTemperatureAlarmStatus
	    }

	DESCRIPTION
            "Indication that the temperature returned within bounds, and
             the value of the currrent temperature."
        ::= 44

	humidityNormal TRAP-TYPE
        ENTERPRISE mrvInReachProductDivision
        VARIABLES {  basicHumidityValue,
                    basicTemperatureHumiditySensorName,
                    sysLocation,
                    basicHumiditySensorIndex,
                    basicHumidityAlarmStatus
                     }
	DESCRIPTION
            "Indication that the humidity returned within bounds, and
             the currrent humidity reading."
        ::= 45

	alarmMasterSideAOff TRAP-TYPE
        ENTERPRISE mrvInReachProductDivision
        VARIABLES {  sysLocation,
    	            basicPortIndex
                     }
	DESCRIPTION
            "Indication that side A powered off in the attached IR7104
             alarm unit due to DC rail fluctuations."
        ::= 46

	alarmMasterSideBOff TRAP-TYPE
        ENTERPRISE mrvInReachProductDivision
        VARIABLES {  sysLocation,
    	            basicPortIndex
                     }
	DESCRIPTION
            "Indication that side B powered off in the attached IR7104 
             alarm unit due to DC rail fluctuations."
        ::= 47

	alarmMasterSideAOn TRAP-TYPE
        ENTERPRISE mrvInReachProductDivision
        VARIABLES {  sysLocation,
    	            basicPortIndex
                     }
	DESCRIPTION
            "Indication that side A powered on in the attached IR7104
             alarm unit after previous power off."
        ::= 48

	alarmMasterSideBOn TRAP-TYPE
        ENTERPRISE mrvInReachProductDivision
        VARIABLES {  sysLocation,
    	            basicPortIndex
                     }
	DESCRIPTION
            "Indication that side B powered on in the attached IR7104
             alarm unit after previous power off."
        ::= 49

        icmpPingHostNotReachable TRAP-TYPE
        ENTERPRISE mrvInReachProductDivision
        VARIABLES {  
		icmpPingHostAddress,
		icmpPingHostDescription,
		sysLocation,
		icmpPingHostPollingInterval,
		icmpPingHostMaximumRetries,
		icmpPingHostStatus
    	           }
	DESCRIPTION
            "Indication that the icmp Ping Host is not reachable after
             polling for icmpPingHostMaximumRetries."
        ::= 50

        icmpPingHostResponding TRAP-TYPE
        ENTERPRISE mrvInReachProductDivision
        VARIABLES {  
		icmpPingHostAddress,
		icmpPingHostDescription,
		sysLocation,
		icmpPingHostPollingInterval,
		icmpPingHostMaximumRetries,
		icmpPingHostStatus
    	           }
	DESCRIPTION
            "Indication that the icmp Ping Host is reachable again after
             a failure."
        ::= 51


--         The following alarm input traps replace the contactClosureChanged
--         trap 30 for InReach agents running IRV3-1 and above.

--         The alarm trap numbers have the format 100xx or 200xx, where xx 
--         represents the alarm input index. A leading '1' represents the alarm
--         condition, and a leading '2' represents the normal condition.

           alarmInputLowDensity0001Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 1 from a low density unit
                transitions to the alarm state."
           ::= 10001

           alarmInputLowDensity0001Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 1 from a low density unit 
                transitions to the normal state."
           ::= 20001

           alarmInputLowDensity0002Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 2 from a low density unit
                transitions to the alarm state."
           ::= 10002

           alarmInputLowDensity0002Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 2 from a low density unit 
                transitions to the normal state."
           ::= 20002

           alarmInputLowDensity0003Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 3 from a low density unit
                transitions to the alarm state."
           ::= 10003

           alarmInputLowDensity0003Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 3 from a low density unit 
                transitions to the normal state."
           ::= 20003

           alarmInputLowDensity0004Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 4 from a low density unit
                transitions to the alarm state."
           ::= 10004

           alarmInputLowDensity0004Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 4 from a low density unit 
                transitions to the normal state."
           ::= 20004

           alarmInputLowDensity0005Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 5 from a low density unit
                transitions to the alarm state."
           ::= 10005

           alarmInputLowDensity0005Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 5 from a low density unit 
                transitions to the normal state."
           ::= 20005

           alarmInputLowDensity0006Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 6 from a low density unit
                transitions to the alarm state."
           ::= 10006

           alarmInputLowDensity0006Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 6 from a low density unit 
                transitions to the normal state."
           ::= 20006

           alarmInputLowDensity0007Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 7 from a low density unit
                transitions to the alarm state."
           ::= 10007

           alarmInputLowDensity0007Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 7 from a low density unit 
                transitions to the normal state."
           ::= 20007

           alarmInputLowDensity0008Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 8 from a low density unit
                transitions to the alarm state."
           ::= 10008

           alarmInputLowDensity0008Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 8 from a low density unit 
                transitions to the normal state."
           ::= 20008

           alarmInputLowDensity0009Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 9 from a low density unit
                transitions to the alarm state."
           ::= 10009

           alarmInputLowDensity0009Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 9 from a low density unit 
                transitions to the normal state."
           ::= 20009

           alarmInputLowDensity0010Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 10 from a low density unit
                transitions to the alarm state."
           ::= 10010

           alarmInputLowDensity0010Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 10 from a low density unit 
                transitions to the normal state."
           ::= 20010

           alarmInputLowDensity0011Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 11 from a low density unit
                transitions to the alarm state."
           ::= 10011

           alarmInputLowDensity0011Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 11 from a low density unit 
                transitions to the normal state."
           ::= 20011

           alarmInputLowDensity0012Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 12 from a low density unit
                transitions to the alarm state."
           ::= 10012

           alarmInputLowDensity0012Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 12 from a low density unit 
                transitions to the normal state."
           ::= 20012

           alarmInputLowDensity0013Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 13 from a low density unit
                transitions to the alarm state."
           ::= 10013

           alarmInputLowDensity0013Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 13 from a low density unit 
                transitions to the normal state."
           ::= 20013

           alarmInputLowDensity0014Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 14 from a low density unit
                transitions to the alarm state."
           ::= 10014

           alarmInputLowDensity0014Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 14 from a low density unit 
                transitions to the normal state."
           ::= 20014

           alarmInputLowDensity0015Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 15 from a low density unit
                transitions to the alarm state."
           ::= 10015

           alarmInputLowDensity0015Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 15 from a low density unit 
                transitions to the normal state."
           ::= 20015

           alarmInputLowDensity0016Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 16 from a low density unit
                transitions to the alarm state."
           ::= 10016

           alarmInputLowDensity0016Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 16 from a low density unit 
                transitions to the normal state."
           ::= 20016

           alarmInputLowDensity0017Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 17 from a low density unit
                transitions to the alarm state."
           ::= 10017

           alarmInputLowDensity0017Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 17 from a low density unit 
                transitions to the normal state."
           ::= 20017

           alarmInputLowDensity0018Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 18 from a low density unit
                transitions to the alarm state."
           ::= 10018

           alarmInputLowDensity0018Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 18 from a low density unit 
                transitions to the normal state."
           ::= 20018

           alarmInputLowDensity0019Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 19 from a low density unit
                transitions to the alarm state."
           ::= 10019

           alarmInputLowDensity0019Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 19 from a low density unit 
                transitions to the normal state."
           ::= 20019

           alarmInputLowDensity0020Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 20 from a low density unit
                transitions to the alarm state."
           ::= 10020

           alarmInputLowDensity0020Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 20 from a low density unit 
                transitions to the normal state."
           ::= 20020

           alarmInputLowDensity0021Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 21 from a low density unit
                transitions to the alarm state."
           ::= 10021

           alarmInputLowDensity0021Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 21 from a low density unit 
                transitions to the normal state."
           ::= 20021

           alarmInputLowDensity0022Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 22 from a low density unit
                transitions to the alarm state."
           ::= 10022

           alarmInputLowDensity0022Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 22 from a low density unit 
                transitions to the normal state."
           ::= 20022

           alarmInputLowDensity0023Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 23 from a low density unit
                transitions to the alarm state."
           ::= 10023

           alarmInputLowDensity0023Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 23 from a low density unit 
                transitions to the normal state."
           ::= 20023

           alarmInputLowDensity0024Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 24 from a low density unit
                transitions to the alarm state."
           ::= 10024

           alarmInputLowDensity0024Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 24 from a low density unit 
                transitions to the normal state."
           ::= 20024

           alarmInputLowDensity0025Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 25 from a low density unit
                transitions to the alarm state."
           ::= 10025

           alarmInputLowDensity0025Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 25 from a low density unit 
                transitions to the normal state."
           ::= 20025

           alarmInputLowDensity0026Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 26 from a low density unit
                transitions to the alarm state."
           ::= 10026

           alarmInputLowDensity0026Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 26 from a low density unit 
                transitions to the normal state."
           ::= 20026

           alarmInputLowDensity0027Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 27 from a low density unit
                transitions to the alarm state."
           ::= 10027

           alarmInputLowDensity0027Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 27 from a low density unit 
                transitions to the normal state."
           ::= 20027

           alarmInputLowDensity0028Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 28 from a low density unit
                transitions to the alarm state."
           ::= 10028

           alarmInputLowDensity0028Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 28 from a low density unit 
                transitions to the normal state."
           ::= 20028

           alarmInputLowDensity0029Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 29 from a low density unit
                transitions to the alarm state."
           ::= 10029

           alarmInputLowDensity0029Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 29 from a low density unit 
                transitions to the normal state."
           ::= 20029

           alarmInputLowDensity0030Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 30 from a low density unit
                transitions to the alarm state."
           ::= 10030

           alarmInputLowDensity0030Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 30 from a low density unit 
                transitions to the normal state."
           ::= 20030

           alarmInputLowDensity0031Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 31 from a low density unit
                transitions to the alarm state."
           ::= 10031

           alarmInputLowDensity0031Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 31 from a low density unit 
                transitions to the normal state."
           ::= 20031

           alarmInputLowDensity0032Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 32 from a low density unit
                transitions to the alarm state."
           ::= 10032

           alarmInputLowDensity0032Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 32 from a low density unit 
                transitions to the normal state."
           ::= 20032

           alarmInputLowDensity0033Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 33 from a low density unit
                transitions to the alarm state."
           ::= 10033

           alarmInputLowDensity0033Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 33 from a low density unit 
                transitions to the normal state."
           ::= 20033

           alarmInputLowDensity0034Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 34 from a low density unit
                transitions to the alarm state."
           ::= 10034

           alarmInputLowDensity0034Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 34 from a low density unit 
                transitions to the normal state."
           ::= 20034

           alarmInputLowDensity0035Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 35 from a low density unit
                transitions to the alarm state."
           ::= 10035

           alarmInputLowDensity0035Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 35 from a low density unit 
                transitions to the normal state."
           ::= 20035

           alarmInputLowDensity0036Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 36 from a low density unit
                transitions to the alarm state."
           ::= 10036

           alarmInputLowDensity0036Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 36 from a low density unit 
                transitions to the normal state."
           ::= 20036

           alarmInputLowDensity0037Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 37 from a low density unit
                transitions to the alarm state."
           ::= 10037

           alarmInputLowDensity0037Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 37 from a low density unit 
                transitions to the normal state."
           ::= 20037

           alarmInputLowDensity0038Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 38 from a low density unit
                transitions to the alarm state."
           ::= 10038

           alarmInputLowDensity0038Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 38 from a low density unit 
                transitions to the normal state."
           ::= 20038

           alarmInputLowDensity0039Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 39 from a low density unit
                transitions to the alarm state."
           ::= 10039

           alarmInputLowDensity0039Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 39 from a low density unit 
                transitions to the normal state."
           ::= 20039

           alarmInputLowDensity0040Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 40 from a low density unit
                transitions to the alarm state."
           ::= 10040

           alarmInputLowDensity0040Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 40 from a low density unit 
                transitions to the normal state."
           ::= 20040

           alarmInputLowDensity0041Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 41 from a low density unit
                transitions to the alarm state."
           ::= 10041

           alarmInputLowDensity0041Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 41 from a low density unit 
                transitions to the normal state."
           ::= 20041

           alarmInputLowDensity0042Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 42 from a low density unit
                transitions to the alarm state."
           ::= 10042

           alarmInputLowDensity0042Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 42 from a low density unit 
                transitions to the normal state."
           ::= 20042

           alarmInputLowDensity0043Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 43 from a low density unit
                transitions to the alarm state."
           ::= 10043

           alarmInputLowDensity0043Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 43 from a low density unit 
                transitions to the normal state."
           ::= 20043

           alarmInputLowDensity0044Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 44 from a low density unit
                transitions to the alarm state."
           ::= 10044

           alarmInputLowDensity0044Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 44 from a low density unit 
                transitions to the normal state."
           ::= 20044

           alarmInputLowDensity0045Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 45 from a low density unit
                transitions to the alarm state."
           ::= 10045

           alarmInputLowDensity0045Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 45 from a low density unit 
                transitions to the normal state."
           ::= 20045

           alarmInputLowDensity0046Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 46 from a low density unit
                transitions to the alarm state."
           ::= 10046

           alarmInputLowDensity0046Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 46 from a low density unit 
                transitions to the normal state."
           ::= 20046

           alarmInputLowDensity0047Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 47 from a low density unit
                transitions to the alarm state."
           ::= 10047

           alarmInputLowDensity0047Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 47 from a low density unit 
                transitions to the normal state."
           ::= 20047

           alarmInputLowDensity0048Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 48 from a low density unit
                transitions to the alarm state."
           ::= 10048

           alarmInputLowDensity0048Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 48 from a low density unit 
                transitions to the normal state."
           ::= 20048

           alarmInputLowDensity0049Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 49 from a low density unit
                transitions to the alarm state."
           ::= 10049

           alarmInputLowDensity0049Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 49 from a low density unit 
                transitions to the normal state."
           ::= 20049

           alarmInputLowDensity0050Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 50 from a low density unit
                transitions to the alarm state."
           ::= 10050

           alarmInputLowDensity0050Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 50 from a low density unit 
                transitions to the normal state."
           ::= 20050
           alarmInputLowDensity0051Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 51 from a low density unit
                transitions to the alarm state."
           ::= 10051

           alarmInputLowDensity0051Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 51 from a low density unit 
                transitions to the normal state."
           ::= 20051

           alarmInputLowDensity0052Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 52 from a low density unit
                transitions to the alarm state."
           ::= 10052

           alarmInputLowDensity0052Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 52 from a low density unit 
                transitions to the normal state."
           ::= 20052

           alarmInputLowDensity0053Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 53 from a low density unit
                transitions to the alarm state."
           ::= 10053

           alarmInputLowDensity0053Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 53 from a low density unit 
                transitions to the normal state."
           ::= 20053

           alarmInputLowDensity0054Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 54 from a low density unit
                transitions to the alarm state."
           ::= 10054

           alarmInputLowDensity0054Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 54 from a low density unit 
                transitions to the normal state."
           ::= 20054

           alarmInputLowDensity0055Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 55 from a low density unit
                transitions to the alarm state."
           ::= 10055

           alarmInputLowDensity0055Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 55 from a low density unit 
                transitions to the normal state."
           ::= 20055

           alarmInputLowDensity0056Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 56 from a low density unit
                transitions to the alarm state."
           ::= 10056

           alarmInputLowDensity0056Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 56 from a low density unit 
                transitions to the normal state."
           ::= 20056

           alarmInputLowDensity0057Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 57 from a low density unit
                transitions to the alarm state."
           ::= 10057

           alarmInputLowDensity0057Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 57 from a low density unit 
                transitions to the normal state."
           ::= 20057

           alarmInputLowDensity0058Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 58 from a low density unit
                transitions to the alarm state."
           ::= 10058

           alarmInputLowDensity0058Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 58 from a low density unit 
                transitions to the normal state."
           ::= 20058

           alarmInputLowDensity0059Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 59 from a low density unit
                transitions to the alarm state."
           ::= 10059

           alarmInputLowDensity0059Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 59 from a low density unit 
                transitions to the normal state."
           ::= 20059

           alarmInputLowDensity0060Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 60 from a low density unit
                transitions to the alarm state."
           ::= 10060

           alarmInputLowDensity0060Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 60 from a low density unit 
                transitions to the normal state."
           ::= 20060
           alarmInputLowDensity0061Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 61 from a low density unit
                transitions to the alarm state."
           ::= 10061

           alarmInputLowDensity0061Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 61 from a low density unit 
                transitions to the normal state."
           ::= 20061

           alarmInputLowDensity0062Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 62 from a low density unit
                transitions to the alarm state."
           ::= 10062

           alarmInputLowDensity0062Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 62 from a low density unit 
                transitions to the normal state."
           ::= 20062

           alarmInputLowDensity0063Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 63 from a low density unit
                transitions to the alarm state."
           ::= 10063

           alarmInputLowDensity0063Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 63 from a low density unit 
                transitions to the normal state."
           ::= 20063

           alarmInputLowDensity0064Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 64 from a low density unit
                transitions to the alarm state."
           ::= 10064

           alarmInputLowDensity0064Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 64 from a low density unit 
                transitions to the normal state."
           ::= 20064

           alarmInputLowDensity0065Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 65 from a low density unit
                transitions to the alarm state."
           ::= 10065

           alarmInputLowDensity0065Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 65 from a low density unit 
                transitions to the normal state."
           ::= 20065

           alarmInputLowDensity0066Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 66 from a low density unit
                transitions to the alarm state."
           ::= 10066

           alarmInputLowDensity0066Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 66 from a low density unit 
                transitions to the normal state."
           ::= 20066

           alarmInputLowDensity0067Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 67 from a low density unit
                transitions to the alarm state."
           ::= 10067

           alarmInputLowDensity0067Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 67 from a low density unit 
                transitions to the normal state."
           ::= 20067

           alarmInputLowDensity0068Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 68 from a low density unit
                transitions to the alarm state."
           ::= 10068

           alarmInputLowDensity0068Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 68 from a low density unit 
                transitions to the normal state."
           ::= 20068

           alarmInputLowDensity0069Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 69 from a low density unit
                transitions to the alarm state."
           ::= 10069

           alarmInputLowDensity0069Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 69 from a low density unit 
                transitions to the normal state."
           ::= 20069

           alarmInputLowDensity0070Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 70 from a low density unit
                transitions to the alarm state."
           ::= 10070

           alarmInputLowDensity0070Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 70 from a low density unit 
                transitions to the normal state."
           ::= 20070
           alarmInputLowDensity0071Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 71 from a low density unit
                transitions to the alarm state."
           ::= 10071

           alarmInputLowDensity0071Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 71 from a low density unit 
                transitions to the normal state."
           ::= 20071

           alarmInputLowDensity0072Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 72 from a low density unit
                transitions to the alarm state."
           ::= 10072

           alarmInputLowDensity0072Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 72 from a low density unit 
                transitions to the normal state."
           ::= 20072

           alarmInputLowDensity0073Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 73 from a low density unit
                transitions to the alarm state."
           ::= 10073

           alarmInputLowDensity0073Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 73 from a low density unit 
                transitions to the normal state."
           ::= 20073

           alarmInputLowDensity0074Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 74 from a low density unit
                transitions to the alarm state."
           ::= 10074

           alarmInputLowDensity0074Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 74 from a low density unit 
                transitions to the normal state."
           ::= 20074

           alarmInputLowDensity0075Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 75 from a low density unit
                transitions to the alarm state."
           ::= 10075

           alarmInputLowDensity0075Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 75 from a low density unit 
                transitions to the normal state."
           ::= 20075

           alarmInputLowDensity0076Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 76 from a low density unit
                transitions to the alarm state."
           ::= 10076

           alarmInputLowDensity0076Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 76 from a low density unit 
                transitions to the normal state."
           ::= 20076

           alarmInputLowDensity0077Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 77 from a low density unit
                transitions to the alarm state."
           ::= 10077

           alarmInputLowDensity0077Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 77 from a low density unit 
                transitions to the normal state."
           ::= 20077

           alarmInputLowDensity0078Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 78 from a low density unit
                transitions to the alarm state."
           ::= 10078

           alarmInputLowDensity0078Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 78 from a low density unit 
                transitions to the normal state."
           ::= 20078

           alarmInputLowDensity0079Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 79 from a low density unit
                transitions to the alarm state."
           ::= 10079

           alarmInputLowDensity0079Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 79 from a low density unit 
                transitions to the normal state."
           ::= 20079

           alarmInputLowDensity0080Alarm TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 80 from a low density unit
                transitions to the alarm state."
           ::= 10080

           alarmInputLowDensity0080Normal TRAP-TYPE
           ENTERPRISE mrvInReachProductDivision
           VARIABLES { 
		basicContactClosureOrAlarmInputValue,
		basicContactClosureOrAlarmInputName,
		sysLocation,
	        basicContactClosureOrAlarmInputIndex,
                basicContactClosureOrAlarmInputStatus,
                basicContactClosureOrAlarmInputZone,
                basicContactClosureOrAlarmInputRelatedEquipment,
                basicContactClosureOrAlarmInputSiteId,
                basicContactClosureOrAlarmInputManufacturer,
                basicContactClosureOrAlarmInputModel
		 }
           DESCRIPTION
               "Generated when alarm point 80 from a low density unit 
                transitions to the normal state."
           ::= 20080




--
-- FILE: /users/sse/mibs/src/inReach/ir-alarm-mib.mib
--

-- $Id: ir-alarm-mib.mib,v 1.1 2002/06/27 15:49:08 sse Exp $
            



	     xAlarm          OBJECT IDENTIFIER ::= { mrvInReachProductDivision 49 }


	     -- This is a MIB module for all MRV In-Reach systems that
	     -- use high densitity alarm input systems, such as the 7104.
             -- Refer to the MRV-IN-REACH-CHARACTER-MIB to manage low density
             -- alarm inputs.

	     -- Copyright 2002 MRV Communications, Inc. All Rights Reserved.
	     -- Reproduction of this document is authorized on
	     -- condition that this copyright notice is included.
	     -- This MIB document embodies MRV Communications, Inc.'s 
	     -- proprietary intellectual property.  MRV Communications, Inc.
	     -- retains all title and ownership in this MIB, including any
	     -- revisions.
	     --
	     -- It is MRV Communications, Inc.'s intent to encourage the
	     -- widespread use of this MIB in connection with the management of
	     -- MRV Communications, Inc. products. MRV Communications,
	     -- Inc. grants vendors,end-users, and other interested parties a
	     -- non-exclusive license to use this MIB in connection with the
	     -- management of MRV Communications, Inc. products.
	     --
	     -- This MIB document is supplied "AS IS," and MRV 
	     -- Communications, Inc. makes no warranty, either express or
	     -- implied, as to the use operation, condition, or performance of
	     -- the MIB.





--         The following alarm input traps are used with the high density
--         alarm manager products, such as the 7104. The traps below replace
--         the alarmMasterInputStateChanged trap 41 for InReach agents running 
--         IRV3-1 software and above.  

--         The alarm trap numbers have the format 300xx or 400xx, where xx 
--         represents the alarm input index. A leading '3' represents the alarm
--         condition, and a leading '4' represents the normal condition.

           alarmInputHighDensity0001Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 1 from a high density unit
                transitions to the alarm state."
           ::= 30001

           alarmInputHighDensity0001Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 1 from a high density unit 
                transitions to the normal state."
           ::= 40001

           alarmInputHighDensity0002Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 2 from a high density unit
                transitions to the alarm state."
           ::= 30002

           alarmInputHighDensity0002Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 2 from a high density unit 
                transitions to the normal state."
           ::= 40002

           alarmInputHighDensity0003Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 3 from a high density unit
                transitions to the alarm state."
           ::= 30003

           alarmInputHighDensity0003Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 3 from a high density unit 
                transitions to the normal state."
           ::= 40003

           alarmInputHighDensity0004Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 4 from a high density unit
                transitions to the alarm state."
           ::= 30004

           alarmInputHighDensity0004Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 4 from a high density unit 
                transitions to the normal state."
           ::= 40004

           alarmInputHighDensity0005Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 5 from a high density unit
                transitions to the alarm state."
           ::= 30005

           alarmInputHighDensity0005Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 5 from a high density unit 
                transitions to the normal state."
           ::= 40005

           alarmInputHighDensity0006Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 6 from a high density unit
                transitions to the alarm state."
           ::= 30006

           alarmInputHighDensity0006Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 6 from a high density unit 
                transitions to the normal state."
           ::= 40006

           alarmInputHighDensity0007Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 7 from a high density unit
                transitions to the alarm state."
           ::= 30007

           alarmInputHighDensity0007Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 7 from a high density unit 
                transitions to the normal state."
           ::= 40007

           alarmInputHighDensity0008Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 8 from a high density unit
                transitions to the alarm state."
           ::= 30008

           alarmInputHighDensity0008Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 8 from a high density unit 
                transitions to the normal state."
           ::= 40008

           alarmInputHighDensity0009Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 9 from a high density unit
                transitions to the alarm state."
           ::= 30009

           alarmInputHighDensity0009Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 9 from a high density unit 
                transitions to the normal state."
           ::= 40009

           alarmInputHighDensity0010Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 10 from a high density unit
                transitions to the alarm state."
           ::= 30010

           alarmInputHighDensity0010Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 10 from a high density unit 
                transitions to the normal state."
           ::= 40010

           alarmInputHighDensity0011Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 11 from a high density unit
                transitions to the alarm state."
           ::= 30011

           alarmInputHighDensity0011Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 11 from a high density unit 
                transitions to the normal state."
           ::= 40011

           alarmInputHighDensity0012Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 12 from a high density unit
                transitions to the alarm state."
           ::= 30012

           alarmInputHighDensity0012Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 12 from a high density unit 
                transitions to the normal state."
           ::= 40012

           alarmInputHighDensity0013Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 13 from a high density unit
                transitions to the alarm state."
           ::= 30013

           alarmInputHighDensity0013Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 13 from a high density unit 
                transitions to the normal state."
           ::= 40013

           alarmInputHighDensity0014Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 14 from a high density unit
                transitions to the alarm state."
           ::= 30014

           alarmInputHighDensity0014Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 14 from a high density unit 
                transitions to the normal state."
           ::= 40014

           alarmInputHighDensity0015Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 15 from a high density unit
                transitions to the alarm state."
           ::= 30015

           alarmInputHighDensity0015Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 15 from a high density unit 
                transitions to the normal state."
           ::= 40015

           alarmInputHighDensity0016Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 16 from a high density unit
                transitions to the alarm state."
           ::= 30016

           alarmInputHighDensity0016Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 16 from a high density unit 
                transitions to the normal state."
           ::= 40016

           alarmInputHighDensity0017Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 17 from a high density unit
                transitions to the alarm state."
           ::= 30017

           alarmInputHighDensity0017Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 17 from a high density unit 
                transitions to the normal state."
           ::= 40017

           alarmInputHighDensity0018Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 18 from a high density unit
                transitions to the alarm state."
           ::= 30018

           alarmInputHighDensity0018Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 18 from a high density unit 
                transitions to the normal state."
           ::= 40018

           alarmInputHighDensity0019Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 19 from a high density unit
                transitions to the alarm state."
           ::= 30019

           alarmInputHighDensity0019Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 19 from a high density unit 
                transitions to the normal state."
           ::= 40019

           alarmInputHighDensity0020Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 20 from a high density unit
                transitions to the alarm state."
           ::= 30020

           alarmInputHighDensity0020Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 20 from a high density unit 
                transitions to the normal state."
           ::= 40020

           alarmInputHighDensity0021Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 21 from a high density unit
                transitions to the alarm state."
           ::= 30021

           alarmInputHighDensity0021Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 21 from a high density unit 
                transitions to the normal state."
           ::= 40021

           alarmInputHighDensity0022Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 22 from a high density unit
                transitions to the alarm state."
           ::= 30022

           alarmInputHighDensity0022Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 22 from a high density unit 
                transitions to the normal state."
           ::= 40022

           alarmInputHighDensity0023Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 23 from a high density unit
                transitions to the alarm state."
           ::= 30023

           alarmInputHighDensity0023Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 23 from a high density unit 
                transitions to the normal state."
           ::= 40023

           alarmInputHighDensity0024Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 24 from a high density unit
                transitions to the alarm state."
           ::= 30024

           alarmInputHighDensity0024Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 24 from a high density unit 
                transitions to the normal state."
           ::= 40024

           alarmInputHighDensity0025Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 25 from a high density unit
                transitions to the alarm state."
           ::= 30025

           alarmInputHighDensity0025Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 25 from a high density unit 
                transitions to the normal state."
           ::= 40025

           alarmInputHighDensity0026Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 26 from a high density unit
                transitions to the alarm state."
           ::= 30026

           alarmInputHighDensity0026Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 26 from a high density unit 
                transitions to the normal state."
           ::= 40026

           alarmInputHighDensity0027Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 27 from a high density unit
                transitions to the alarm state."
           ::= 30027

           alarmInputHighDensity0027Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 27 from a high density unit 
                transitions to the normal state."
           ::= 40027

           alarmInputHighDensity0028Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 28 from a high density unit
                transitions to the alarm state."
           ::= 30028

           alarmInputHighDensity0028Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 28 from a high density unit 
                transitions to the normal state."
           ::= 40028

           alarmInputHighDensity0029Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 29 from a high density unit
                transitions to the alarm state."
           ::= 30029

           alarmInputHighDensity0029Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 29 from a high density unit 
                transitions to the normal state."
           ::= 40029

           alarmInputHighDensity0030Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 30 from a high density unit
                transitions to the alarm state."
           ::= 30030

           alarmInputHighDensity0030Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 30 from a high density unit 
                transitions to the normal state."
           ::= 40030

           alarmInputHighDensity0031Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 31 from a high density unit
                transitions to the alarm state."
           ::= 30031

           alarmInputHighDensity0031Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 31 from a high density unit 
                transitions to the normal state."
           ::= 40031

           alarmInputHighDensity0032Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 32 from a high density unit
                transitions to the alarm state."
           ::= 30032

           alarmInputHighDensity0032Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 32 from a high density unit 
                transitions to the normal state."
           ::= 40032

           alarmInputHighDensity0033Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 33 from a high density unit
                transitions to the alarm state."
           ::= 30033

           alarmInputHighDensity0033Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 33 from a high density unit 
                transitions to the normal state."
           ::= 40033

           alarmInputHighDensity0034Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 34 from a high density unit
                transitions to the alarm state."
           ::= 30034

           alarmInputHighDensity0034Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 34 from a high density unit 
                transitions to the normal state."
           ::= 40034

           alarmInputHighDensity0035Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 35 from a high density unit
                transitions to the alarm state."
           ::= 30035

           alarmInputHighDensity0035Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 35 from a high density unit 
                transitions to the normal state."
           ::= 40035

           alarmInputHighDensity0036Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 36 from a high density unit
                transitions to the alarm state."
           ::= 30036

           alarmInputHighDensity0036Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 36 from a high density unit 
                transitions to the normal state."
           ::= 40036

           alarmInputHighDensity0037Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 37 from a high density unit
                transitions to the alarm state."
           ::= 30037

           alarmInputHighDensity0037Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 37 from a high density unit 
                transitions to the normal state."
           ::= 40037

           alarmInputHighDensity0038Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 38 from a high density unit
                transitions to the alarm state."
           ::= 30038

           alarmInputHighDensity0038Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 38 from a high density unit 
                transitions to the normal state."
           ::= 40038

           alarmInputHighDensity0039Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 39 from a high density unit
                transitions to the alarm state."
           ::= 30039

           alarmInputHighDensity0039Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 39 from a high density unit 
                transitions to the normal state."
           ::= 40039

           alarmInputHighDensity0040Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 40 from a high density unit
                transitions to the alarm state."
           ::= 30040

           alarmInputHighDensity0040Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 40 from a high density unit 
                transitions to the normal state."
           ::= 40040

           alarmInputHighDensity0041Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 41 from a high density unit
                transitions to the alarm state."
           ::= 30041

           alarmInputHighDensity0041Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 41 from a high density unit 
                transitions to the normal state."
           ::= 40041

           alarmInputHighDensity0042Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 42 from a high density unit
                transitions to the alarm state."
           ::= 30042

           alarmInputHighDensity0042Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 42 from a high density unit 
                transitions to the normal state."
           ::= 40042

           alarmInputHighDensity0043Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 43 from a high density unit
                transitions to the alarm state."
           ::= 30043

           alarmInputHighDensity0043Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 43 from a high density unit 
                transitions to the normal state."
           ::= 40043

           alarmInputHighDensity0044Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 44 from a high density unit
                transitions to the alarm state."
           ::= 30044

           alarmInputHighDensity0044Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 44 from a high density unit 
                transitions to the normal state."
           ::= 40044

           alarmInputHighDensity0045Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 45 from a high density unit
                transitions to the alarm state."
           ::= 30045

           alarmInputHighDensity0045Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 45 from a high density unit 
                transitions to the normal state."
           ::= 40045

           alarmInputHighDensity0046Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 46 from a high density unit
                transitions to the alarm state."
           ::= 30046

           alarmInputHighDensity0046Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 46 from a high density unit 
                transitions to the normal state."
           ::= 40046

           alarmInputHighDensity0047Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 47 from a high density unit
                transitions to the alarm state."
           ::= 30047

           alarmInputHighDensity0047Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 47 from a high density unit 
                transitions to the normal state."
           ::= 40047

           alarmInputHighDensity0048Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 48 from a high density unit
                transitions to the alarm state."
           ::= 30048

           alarmInputHighDensity0048Normal TRAP-TYPE
           ENTERPRISE mrvInReachProductDivision
           VARIABLES { 
		basicAlarmMasterInputValue,
		basicAlarmMasterInputName,
		sysLocation,
	        basicAlarmMasterInputPort,
                basicAlarmMasterInputStatus,
                basicAlarmMasterInputZone,
                basicAlarmMasterInputRelatedEquipment,
                basicAlarmMasterInputSiteId,
                basicAlarmMasterInputManufacturer,
                basicAlarmMasterInputModel
		 }
           DESCRIPTION
               "Generated when alarm point 48 from a high density unit 
                transitions to the normal state."
           ::= 40048

           alarmInputHighDensity0049Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 49 from a high density unit
                transitions to the alarm state."
           ::= 30049

           alarmInputHighDensity0049Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 49 from a high density unit 
                transitions to the normal state."
           ::= 40049

           alarmInputHighDensity0050Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 50 from a high density unit
                transitions to the alarm state."
           ::= 30050

           alarmInputHighDensity0050Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 50 from a high density unit 
                transitions to the normal state."
           ::= 40050
           alarmInputHighDensity0051Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 51 from a high density unit
                transitions to the alarm state."
           ::= 30051

           alarmInputHighDensity0051Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 51 from a high density unit 
                transitions to the normal state."
           ::= 40051

           alarmInputHighDensity0052Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 52 from a high density unit
                transitions to the alarm state."
           ::= 30052

           alarmInputHighDensity0052Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 52 from a high density unit 
                transitions to the normal state."
           ::= 40052

           alarmInputHighDensity0053Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 53 from a high density unit
                transitions to the alarm state."
           ::= 30053

           alarmInputHighDensity0053Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 53 from a high density unit 
                transitions to the normal state."
           ::= 40053

           alarmInputHighDensity0054Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 54 from a high density unit
                transitions to the alarm state."
           ::= 30054

           alarmInputHighDensity0054Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 54 from a high density unit 
                transitions to the normal state."
           ::= 40054

           alarmInputHighDensity0055Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 55 from a high density unit
                transitions to the alarm state."
           ::= 30055

           alarmInputHighDensity0055Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 55 from a high density unit 
                transitions to the normal state."
           ::= 40055

           alarmInputHighDensity0056Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 56 from a high density unit
                transitions to the alarm state."
           ::= 30056

           alarmInputHighDensity0056Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 56 from a high density unit 
                transitions to the normal state."
           ::= 40056

           alarmInputHighDensity0057Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 57 from a high density unit
                transitions to the alarm state."
           ::= 30057

           alarmInputHighDensity0057Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 57 from a high density unit 
                transitions to the normal state."
           ::= 40057

           alarmInputHighDensity0058Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 58 from a high density unit
                transitions to the alarm state."
           ::= 30058

           alarmInputHighDensity0058Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 58 from a high density unit 
                transitions to the normal state."
           ::= 40058

           alarmInputHighDensity0059Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 59 from a high density unit
                transitions to the alarm state."
           ::= 30059

           alarmInputHighDensity0059Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 59 from a high density unit 
                transitions to the normal state."
           ::= 40059

           alarmInputHighDensity0060Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 60 from a high density unit
                transitions to the alarm state."
           ::= 30060

           alarmInputHighDensity0060Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 60 from a high density unit 
                transitions to the normal state."
           ::= 40060
           alarmInputHighDensity0061Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 61 from a high density unit
                transitions to the alarm state."
           ::= 30061

           alarmInputHighDensity0061Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 61 from a high density unit 
                transitions to the normal state."
           ::= 40061

           alarmInputHighDensity0062Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 62 from a high density unit
                transitions to the alarm state."
           ::= 30062

           alarmInputHighDensity0062Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 62 from a high density unit 
                transitions to the normal state."
           ::= 40062

           alarmInputHighDensity0063Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 63 from a high density unit
                transitions to the alarm state."
           ::= 30063

           alarmInputHighDensity0063Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 63 from a high density unit 
                transitions to the normal state."
           ::= 40063

           alarmInputHighDensity0064Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 64 from a high density unit
                transitions to the alarm state."
           ::= 30064

           alarmInputHighDensity0064Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 64 from a high density unit 
                transitions to the normal state."
           ::= 40064

           alarmInputHighDensity0065Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 65 from a high density unit
                transitions to the alarm state."
           ::= 30065

           alarmInputHighDensity0065Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 65 from a high density unit 
                transitions to the normal state."
           ::= 40065

           alarmInputHighDensity0066Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 66 from a high density unit
                transitions to the alarm state."
           ::= 30066

           alarmInputHighDensity0066Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 66 from a high density unit 
                transitions to the normal state."
           ::= 40066

           alarmInputHighDensity0067Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 67 from a high density unit
                transitions to the alarm state."
           ::= 30067

           alarmInputHighDensity0067Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 67 from a high density unit 
                transitions to the normal state."
           ::= 40067

           alarmInputHighDensity0068Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 68 from a high density unit
                transitions to the alarm state."
           ::= 30068

           alarmInputHighDensity0068Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 68 from a high density unit 
                transitions to the normal state."
           ::= 40068

           alarmInputHighDensity0069Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 69 from a high density unit
                transitions to the alarm state."
           ::= 30069

           alarmInputHighDensity0069Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 69 from a high density unit 
                transitions to the normal state."
           ::= 40069

           alarmInputHighDensity0070Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 70 from a high density unit
                transitions to the alarm state."
           ::= 30070

           alarmInputHighDensity0070Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 70 from a high density unit 
                transitions to the normal state."
           ::= 40070

           alarmInputHighDensity0071Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 71 from a high density unit
                transitions to the alarm state."
           ::= 30071

           alarmInputHighDensity0071Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 71 from a high density unit 
                transitions to the normal state."
           ::= 40071

           alarmInputHighDensity0072Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 72 from a high density unit
                transitions to the alarm state."
           ::= 30072

           alarmInputHighDensity0072Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 72 from a high density unit 
                transitions to the normal state."
           ::= 40072

           alarmInputHighDensity0073Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 73 from a high density unit
                transitions to the alarm state."
           ::= 30073

           alarmInputHighDensity0073Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 73 from a high density unit 
                transitions to the normal state."
           ::= 40073

           alarmInputHighDensity0074Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 74 from a high density unit
                transitions to the alarm state."
           ::= 30074

           alarmInputHighDensity0074Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 74 from a high density unit 
                transitions to the normal state."
           ::= 40074

           alarmInputHighDensity0075Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 75 from a high density unit
                transitions to the alarm state."
           ::= 30075

           alarmInputHighDensity0075Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 75 from a high density unit 
                transitions to the normal state."
           ::= 40075

           alarmInputHighDensity0076Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 76 from a high density unit
                transitions to the alarm state."
           ::= 30076

           alarmInputHighDensity0076Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 76 from a high density unit 
                transitions to the normal state."
           ::= 40076

           alarmInputHighDensity0077Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 77 from a high density unit
                transitions to the alarm state."
           ::= 30077

           alarmInputHighDensity0077Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 77 from a high density unit 
                transitions to the normal state."
           ::= 40077

           alarmInputHighDensity0078Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 78 from a high density unit
                transitions to the alarm state."
           ::= 30078

           alarmInputHighDensity0078Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 78 from a high density unit 
                transitions to the normal state."
           ::= 40078

           alarmInputHighDensity0079Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 79 from a high density unit
                transitions to the alarm state."
           ::= 30079

           alarmInputHighDensity0079Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 79 from a high density unit 
                transitions to the normal state."
           ::= 40079

           alarmInputHighDensity0080Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 80 from a high density unit
                transitions to the alarm state."
           ::= 30080

           alarmInputHighDensity0080Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 80 from a high density unit 
                transitions to the normal state."
           ::= 40080

           alarmInputHighDensity0081Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 81 from a high density unit
                transitions to the alarm state."
           ::= 30081

           alarmInputHighDensity0081Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 81 from a high density unit 
                transitions to the normal state."
           ::= 40081

           alarmInputHighDensity0082Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 82 from a high density unit
                transitions to the alarm state."
           ::= 30082

           alarmInputHighDensity0082Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 82 from a high density unit 
                transitions to the normal state."
           ::= 40082

           alarmInputHighDensity0083Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 83 from a high density unit
                transitions to the alarm state."
           ::= 30083

           alarmInputHighDensity0083Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 83 from a high density unit 
                transitions to the normal state."
           ::= 40083

           alarmInputHighDensity0084Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 84 from a high density unit
                transitions to the alarm state."
           ::= 30084

           alarmInputHighDensity0084Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 84 from a high density unit 
                transitions to the normal state."
           ::= 40084

           alarmInputHighDensity0085Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 85 from a high density unit
                transitions to the alarm state."
           ::= 30085

           alarmInputHighDensity0085Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 85 from a high density unit 
                transitions to the normal state."
           ::= 40085

           alarmInputHighDensity0086Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 86 from a high density unit
                transitions to the alarm state."
           ::= 30086

           alarmInputHighDensity0086Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 86 from a high density unit 
                transitions to the normal state."
           ::= 40086

           alarmInputHighDensity0087Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 87 from a high density unit
                transitions to the alarm state."
           ::= 30087

           alarmInputHighDensity0087Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 87 from a high density unit 
                transitions to the normal state."
           ::= 40087

           alarmInputHighDensity0088Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 88 from a high density unit
                transitions to the alarm state."
           ::= 30088

           alarmInputHighDensity0088Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 88 from a high density unit 
                transitions to the normal state."
           ::= 40088

           alarmInputHighDensity0089Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 89 from a high density unit
                transitions to the alarm state."
           ::= 30089

           alarmInputHighDensity0089Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 89 from a high density unit 
                transitions to the normal state."
           ::= 40089

           alarmInputHighDensity0090Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 90 from a high density unit
                transitions to the alarm state."
           ::= 30090

           alarmInputHighDensity0090Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 90 from a high density unit 
                transitions to the normal state."
           ::= 40090

           alarmInputHighDensity0091Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 91 from a high density unit
                transitions to the alarm state."
           ::= 30091

           alarmInputHighDensity0091Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 91 from a high density unit 
                transitions to the normal state."
           ::= 40091

           alarmInputHighDensity0092Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 92 from a high density unit
                transitions to the alarm state."
           ::= 30092

           alarmInputHighDensity0092Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 92 from a high density unit 
                transitions to the normal state."
           ::= 40092

           alarmInputHighDensity0093Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 93 from a high density unit
                transitions to the alarm state."
           ::= 30093

           alarmInputHighDensity0093Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 93 from a high density unit 
                transitions to the normal state."
           ::= 40093

           alarmInputHighDensity0094Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 94 from a high density unit
                transitions to the alarm state."
           ::= 30094

           alarmInputHighDensity0094Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 94 from a high density unit 
                transitions to the normal state."
           ::= 40094

           alarmInputHighDensity0095Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 95 from a high density unit
                transitions to the alarm state."
           ::= 30095

           alarmInputHighDensity0095Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 95 from a high density unit 
                transitions to the normal state."
           ::= 40095

           alarmInputHighDensity0096Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 96 from a high density unit
                transitions to the alarm state."
           ::= 30096

           alarmInputHighDensity0096Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 96 from a high density unit 
                transitions to the normal state."
           ::= 40096

           alarmInputHighDensity0097Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 97 from a high density unit
                transitions to the alarm state."
           ::= 30097

           alarmInputHighDensity0097Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 97 from a high density unit 
                transitions to the normal state."
           ::= 40097

           alarmInputHighDensity0098Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 98 from a high density unit
                transitions to the alarm state."
           ::= 30098

           alarmInputHighDensity0098Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 98 from a high density unit 
                transitions to the normal state."
           ::= 40098

           alarmInputHighDensity0099Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 99 from a high density unit
                transitions to the alarm state."
           ::= 30099

           alarmInputHighDensity0099Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 99 from a high density unit 
                transitions to the normal state."
           ::= 40099

           alarmInputHighDensity0100Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 100 from a high density unit
                transitions to the alarm state."
           ::= 30100

           alarmInputHighDensity0100Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 100 from a high density unit 
                transitions to the normal state."
           ::= 40100

           alarmInputHighDensity0101Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 101 from a high density unit
                transitions to the alarm state."
           ::= 30101

           alarmInputHighDensity0101Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 101 from a high density unit 
                transitions to the normal state."
           ::= 40101

           alarmInputHighDensity0102Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 102 from a high density unit
                transitions to the alarm state."
           ::= 30102

           alarmInputHighDensity0102Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 102 from a high density unit 
                transitions to the normal state."
           ::= 40102

           alarmInputHighDensity0103Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 103 from a high density unit
                transitions to the alarm state."
           ::= 30103

           alarmInputHighDensity0103Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 103 from a high density unit 
                transitions to the normal state."
           ::= 40103

           alarmInputHighDensity0104Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 104 from a high density unit
                transitions to the alarm state."
           ::= 30104

           alarmInputHighDensity0104Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 104 from a high density unit 
                transitions to the normal state."
           ::= 40104

           alarmInputHighDensity0105Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 105 from a high density unit
                transitions to the alarm state."
           ::= 30105

           alarmInputHighDensity0105Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 105 from a high density unit 
                transitions to the normal state."
           ::= 40105

           alarmInputHighDensity0106Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 106 from a high density unit
                transitions to the alarm state."
           ::= 30106

           alarmInputHighDensity0106Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 106 from a high density unit 
                transitions to the normal state."
           ::= 40106

           alarmInputHighDensity0107Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 107 from a high density unit
                transitions to the alarm state."
           ::= 30107

           alarmInputHighDensity0107Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 107 from a high density unit 
                transitions to the normal state."
           ::= 40107

           alarmInputHighDensity0108Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 108 from a high density unit
                transitions to the alarm state."
           ::= 30108

           alarmInputHighDensity0108Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 108 from a high density unit 
                transitions to the normal state."
           ::= 40108

           alarmInputHighDensity0109Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 109 from a high density unit
                transitions to the alarm state."
           ::= 30109

           alarmInputHighDensity0109Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 109 from a high density unit 
                transitions to the normal state."
           ::= 40109

           alarmInputHighDensity0110Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 110 from a high density unit
                transitions to the alarm state."
           ::= 30110

           alarmInputHighDensity0110Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 110 from a high density unit 
                transitions to the normal state."
           ::= 40110

           alarmInputHighDensity0111Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 111 from a high density unit
                transitions to the alarm state."
           ::= 30111

           alarmInputHighDensity0111Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 111 from a high density unit 
                transitions to the normal state."
           ::= 40111

           alarmInputHighDensity0112Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 112 from a high density unit
                transitions to the alarm state."
           ::= 30112

           alarmInputHighDensity0112Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 112 from a high density unit 
                transitions to the normal state."
           ::= 40112

           alarmInputHighDensity0113Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 113 from a high density unit
                transitions to the alarm state."
           ::= 30113

           alarmInputHighDensity0113Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 113 from a high density unit 
                transitions to the normal state."
           ::= 40113

           alarmInputHighDensity0114Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 114 from a high density unit
                transitions to the alarm state."
           ::= 30114

           alarmInputHighDensity0114Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 114 from a high density unit 
                transitions to the normal state."
           ::= 40114

           alarmInputHighDensity0115Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 115 from a high density unit
                transitions to the alarm state."
           ::= 30115

           alarmInputHighDensity0115Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 115 from a high density unit 
                transitions to the normal state."
           ::= 40115

           alarmInputHighDensity0116Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 116 from a high density unit
                transitions to the alarm state."
           ::= 30116

           alarmInputHighDensity0116Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 116 from a high density unit 
                transitions to the normal state."
           ::= 40116

           alarmInputHighDensity0117Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 117 from a high density unit
                transitions to the alarm state."
           ::= 30117

           alarmInputHighDensity0117Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 117 from a high density unit 
                transitions to the normal state."
           ::= 40117

           alarmInputHighDensity0118Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 118 from a high density unit
                transitions to the alarm state."
           ::= 30118

           alarmInputHighDensity0118Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 118 from a high density unit 
                transitions to the normal state."
           ::= 40118

           alarmInputHighDensity0119Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 119 from a high density unit
                transitions to the alarm state."
           ::= 30119

           alarmInputHighDensity0119Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 119 from a high density unit 
                transitions to the normal state."
           ::= 40119

           alarmInputHighDensity0120Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 120 from a high density unit
                transitions to the alarm state."
           ::= 30120

           alarmInputHighDensity0120Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 120 from a high density unit 
                transitions to the normal state."
           ::= 40120

           alarmInputHighDensity0121Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 121 from a high density unit
                transitions to the alarm state."
           ::= 30121

           alarmInputHighDensity0121Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 121 from a high density unit 
                transitions to the normal state."
           ::= 40121

           alarmInputHighDensity0122Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 122 from a high density unit
                transitions to the alarm state."
           ::= 30122

           alarmInputHighDensity0122Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 122 from a high density unit 
                transitions to the normal state."
           ::= 40122

           alarmInputHighDensity0123Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 123 from a high density unit
                transitions to the alarm state."
           ::= 30123

           alarmInputHighDensity0123Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 123 from a high density unit 
                transitions to the normal state."
           ::= 40123

           alarmInputHighDensity0124Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 124 from a high density unit
                transitions to the alarm state."
           ::= 30124

           alarmInputHighDensity0124Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 124 from a high density unit 
                transitions to the normal state."
           ::= 40124

           alarmInputHighDensity0125Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 125 from a high density unit
                transitions to the alarm state."
           ::= 30125

           alarmInputHighDensity0125Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 125 from a high density unit 
                transitions to the normal state."
           ::= 40125

           alarmInputHighDensity0126Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 126 from a high density unit
                transitions to the alarm state."
           ::= 30126

           alarmInputHighDensity0126Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 126 from a high density unit 
                transitions to the normal state."
           ::= 40126

           alarmInputHighDensity0127Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 127 from a high density unit
                transitions to the alarm state."
           ::= 30127

           alarmInputHighDensity0127Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 127 from a high density unit 
                transitions to the normal state."
           ::= 40127

           alarmInputHighDensity0128Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 128 from a high density unit
                transitions to the alarm state."
           ::= 30128

           alarmInputHighDensity0128Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 128 from a high density unit 
                transitions to the normal state."
           ::= 40128

           alarmInputHighDensity0129Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 129 from a high density unit
                transitions to the alarm state."
           ::= 30129

           alarmInputHighDensity0129Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 129 from a high density unit 
                transitions to the normal state."
           ::= 40129

           alarmInputHighDensity0130Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 130 from a high density unit
                transitions to the alarm state."
           ::= 30130

           alarmInputHighDensity0130Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 130 from a high density unit 
                transitions to the normal state."
           ::= 40130

           alarmInputHighDensity0131Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 131 from a high density unit
                transitions to the alarm state."
           ::= 30131

           alarmInputHighDensity0131Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 131 from a high density unit 
                transitions to the normal state."
           ::= 40131

           alarmInputHighDensity0132Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 132 from a high density unit
                transitions to the alarm state."
           ::= 30132

           alarmInputHighDensity0132Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 132 from a high density unit 
                transitions to the normal state."
           ::= 40132

           alarmInputHighDensity0133Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 133 from a high density unit
                transitions to the alarm state."
           ::= 30133

           alarmInputHighDensity0133Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 133 from a high density unit 
                transitions to the normal state."
           ::= 40133

           alarmInputHighDensity0134Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 134 from a high density unit
                transitions to the alarm state."
           ::= 30134

           alarmInputHighDensity0134Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 134 from a high density unit 
                transitions to the normal state."
           ::= 40134

           alarmInputHighDensity0135Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 135 from a high density unit
                transitions to the alarm state."
           ::= 30135

           alarmInputHighDensity0135Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 135 from a high density unit 
                transitions to the normal state."
           ::= 40135

           alarmInputHighDensity0136Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 136 from a high density unit
                transitions to the alarm state."
           ::= 30136

           alarmInputHighDensity0136Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 136 from a high density unit 
                transitions to the normal state."
           ::= 40136

           alarmInputHighDensity0137Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 137 from a high density unit
                transitions to the alarm state."
           ::= 30137

           alarmInputHighDensity0137Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 137 from a high density unit 
                transitions to the normal state."
           ::= 40137

           alarmInputHighDensity0138Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 138 from a high density unit
                transitions to the alarm state."
           ::= 30138

           alarmInputHighDensity0138Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 138 from a high density unit 
                transitions to the normal state."
           ::= 40138

           alarmInputHighDensity0139Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 139 from a high density unit
                transitions to the alarm state."
           ::= 30139

           alarmInputHighDensity0139Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 139 from a high density unit 
                transitions to the normal state."
           ::= 40139

           alarmInputHighDensity0140Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 140 from a high density unit
                transitions to the alarm state."
           ::= 30140

           alarmInputHighDensity0140Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 140 from a high density unit 
                transitions to the normal state."
           ::= 40140

           alarmInputHighDensity0141Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 141 from a high density unit
                transitions to the alarm state."
           ::= 30141

           alarmInputHighDensity0141Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 141 from a high density unit 
                transitions to the normal state."
           ::= 40141

           alarmInputHighDensity0142Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 142 from a high density unit
                transitions to the alarm state."
           ::= 30142

           alarmInputHighDensity0142Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 142 from a high density unit 
                transitions to the normal state."
           ::= 40142

           alarmInputHighDensity0143Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 143 from a high density unit
                transitions to the alarm state."
           ::= 30143

           alarmInputHighDensity0143Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 143 from a high density unit 
                transitions to the normal state."
           ::= 40143

           alarmInputHighDensity0144Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 144 from a high density unit
                transitions to the alarm state."
           ::= 30144

           alarmInputHighDensity0144Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 144 from a high density unit 
                transitions to the normal state."
           ::= 40144

           alarmInputHighDensity0145Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 145 from a high density unit
                transitions to the alarm state."
           ::= 30145

           alarmInputHighDensity0145Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 145 from a high density unit 
                transitions to the normal state."
           ::= 40145

           alarmInputHighDensity0146Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 146 from a high density unit
                transitions to the alarm state."
           ::= 30146

           alarmInputHighDensity0146Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 146 from a high density unit 
                transitions to the normal state."
           ::= 40146

           alarmInputHighDensity0147Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 147 from a high density unit
                transitions to the alarm state."
           ::= 30147

           alarmInputHighDensity0147Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 147 from a high density unit 
                transitions to the normal state."
           ::= 40147

           alarmInputHighDensity0148Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 148 from a high density unit
                transitions to the alarm state."
           ::= 30148

           alarmInputHighDensity0148Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 148 from a high density unit 
                transitions to the normal state."
           ::= 40148

           alarmInputHighDensity0149Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 149 from a high density unit
                transitions to the alarm state."
           ::= 30149

           alarmInputHighDensity0149Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 149 from a high density unit 
                transitions to the normal state."
           ::= 40149

           alarmInputHighDensity0150Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 150 from a high density unit
                transitions to the alarm state."
           ::= 30150

           alarmInputHighDensity0150Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 150 from a high density unit 
                transitions to the normal state."
           ::= 40150

           alarmInputHighDensity0151Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 151 from a high density unit
                transitions to the alarm state."
           ::= 30151

           alarmInputHighDensity0151Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 151 from a high density unit 
                transitions to the normal state."
           ::= 40151

           alarmInputHighDensity0152Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 152 from a high density unit
                transitions to the alarm state."
           ::= 30152

           alarmInputHighDensity0152Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 152 from a high density unit 
                transitions to the normal state."
           ::= 40152

           alarmInputHighDensity0153Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 153 from a high density unit
                transitions to the alarm state."
           ::= 30153

           alarmInputHighDensity0153Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 153 from a high density unit 
                transitions to the normal state."
           ::= 40153

           alarmInputHighDensity0154Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 154 from a high density unit
                transitions to the alarm state."
           ::= 30154

           alarmInputHighDensity0154Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 154 from a high density unit 
                transitions to the normal state."
           ::= 40154

           alarmInputHighDensity0155Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 155 from a high density unit
                transitions to the alarm state."
           ::= 30155

           alarmInputHighDensity0155Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 155 from a high density unit 
                transitions to the normal state."
           ::= 40155

           alarmInputHighDensity0156Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 156 from a high density unit
                transitions to the alarm state."
           ::= 30156

           alarmInputHighDensity0156Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 156 from a high density unit 
                transitions to the normal state."
           ::= 40156

           alarmInputHighDensity0157Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 157 from a high density unit
                transitions to the alarm state."
           ::= 30157

           alarmInputHighDensity0157Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 157 from a high density unit 
                transitions to the normal state."
           ::= 40157

           alarmInputHighDensity0158Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 158 from a high density unit
                transitions to the alarm state."
           ::= 30158

           alarmInputHighDensity0158Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 158 from a high density unit 
                transitions to the normal state."
           ::= 40158

           alarmInputHighDensity0159Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 159 from a high density unit
                transitions to the alarm state."
           ::= 30159

           alarmInputHighDensity0159Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 159 from a high density unit 
                transitions to the normal state."
           ::= 40159

           alarmInputHighDensity0160Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 160 from a high density unit
                transitions to the alarm state."
           ::= 30160

           alarmInputHighDensity0160Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 160 from a high density unit 
                transitions to the normal state."
           ::= 40160

           alarmInputHighDensity0161Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 161 from a high density unit
                transitions to the alarm state."
           ::= 30161

           alarmInputHighDensity0161Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 161 from a high density unit 
                transitions to the normal state."
           ::= 40161

           alarmInputHighDensity0162Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 162 from a high density unit
                transitions to the alarm state."
           ::= 30162

           alarmInputHighDensity0162Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 162 from a high density unit 
                transitions to the normal state."
           ::= 40162

           alarmInputHighDensity0163Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 163 from a high density unit
                transitions to the alarm state."
           ::= 30163

           alarmInputHighDensity0163Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 163 from a high density unit 
                transitions to the normal state."
           ::= 40163

           alarmInputHighDensity0164Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 164 from a high density unit
                transitions to the alarm state."
           ::= 30164

           alarmInputHighDensity0164Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 164 from a high density unit 
                transitions to the normal state."
           ::= 40164

           alarmInputHighDensity0165Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 165 from a high density unit
                transitions to the alarm state."
           ::= 30165

           alarmInputHighDensity0165Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 165 from a high density unit 
                transitions to the normal state."
           ::= 40165

           alarmInputHighDensity0166Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 166 from a high density unit
                transitions to the alarm state."
           ::= 30166

           alarmInputHighDensity0166Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 166 from a high density unit 
                transitions to the normal state."
           ::= 40166

           alarmInputHighDensity0167Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 167 from a high density unit
                transitions to the alarm state."
           ::= 30167

           alarmInputHighDensity0167Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 167 from a high density unit 
                transitions to the normal state."
           ::= 40167

           alarmInputHighDensity0168Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 168 from a high density unit
                transitions to the alarm state."
           ::= 30168

           alarmInputHighDensity0168Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 168 from a high density unit 
                transitions to the normal state."
           ::= 40168

           alarmInputHighDensity0169Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 169 from a high density unit
                transitions to the alarm state."
           ::= 30169

           alarmInputHighDensity0169Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 169 from a high density unit 
                transitions to the normal state."
           ::= 40169

           alarmInputHighDensity0170Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 170 from a high density unit
                transitions to the alarm state."
           ::= 30170

           alarmInputHighDensity0170Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 170 from a high density unit 
                transitions to the normal state."
           ::= 40170

           alarmInputHighDensity0171Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 171 from a high density unit
                transitions to the alarm state."
           ::= 30171

           alarmInputHighDensity0171Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 171 from a high density unit 
                transitions to the normal state."
           ::= 40171

           alarmInputHighDensity0172Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 172 from a high density unit
                transitions to the alarm state."
           ::= 30172

           alarmInputHighDensity0172Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 172 from a high density unit 
                transitions to the normal state."
           ::= 40172

           alarmInputHighDensity0173Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 173 from a high density unit
                transitions to the alarm state."
           ::= 30173

           alarmInputHighDensity0173Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 173 from a high density unit 
                transitions to the normal state."
           ::= 40173

           alarmInputHighDensity0174Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 174 from a high density unit
                transitions to the alarm state."
           ::= 30174

           alarmInputHighDensity0174Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 174 from a high density unit 
                transitions to the normal state."
           ::= 40174

           alarmInputHighDensity0175Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 175 from a high density unit
                transitions to the alarm state."
           ::= 30175

           alarmInputHighDensity0175Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 175 from a high density unit 
                transitions to the normal state."
           ::= 40175

           alarmInputHighDensity0176Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 176 from a high density unit
                transitions to the alarm state."
           ::= 30176

           alarmInputHighDensity0176Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 176 from a high density unit 
                transitions to the normal state."
           ::= 40176

           alarmInputHighDensity0177Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 177 from a high density unit
                transitions to the alarm state."
           ::= 30177

           alarmInputHighDensity0177Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 177 from a high density unit 
                transitions to the normal state."
           ::= 40177

           alarmInputHighDensity0178Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 178 from a high density unit
                transitions to the alarm state."
           ::= 30178

           alarmInputHighDensity0178Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 178 from a high density unit 
                transitions to the normal state."
           ::= 40178

           alarmInputHighDensity0179Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 179 from a high density unit
                transitions to the alarm state."
           ::= 30179

           alarmInputHighDensity0179Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 179 from a high density unit 
                transitions to the normal state."
           ::= 40179

           alarmInputHighDensity0180Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 180 from a high density unit
                transitions to the alarm state."
           ::= 30180

           alarmInputHighDensity0180Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 180 from a high density unit 
                transitions to the normal state."
           ::= 40180

           alarmInputHighDensity0181Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 181 from a high density unit
                transitions to the alarm state."
           ::= 30181

           alarmInputHighDensity0181Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 181 from a high density unit 
                transitions to the normal state."
           ::= 40181

           alarmInputHighDensity0182Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 182 from a high density unit
                transitions to the alarm state."
           ::= 30182

           alarmInputHighDensity0182Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 182 from a high density unit 
                transitions to the normal state."
           ::= 40182

           alarmInputHighDensity0183Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 183 from a high density unit
                transitions to the alarm state."
           ::= 30183

           alarmInputHighDensity0183Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 183 from a high density unit 
                transitions to the normal state."
           ::= 40183

           alarmInputHighDensity0184Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 184 from a high density unit
                transitions to the alarm state."
           ::= 30184

           alarmInputHighDensity0184Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 184 from a high density unit 
                transitions to the normal state."
           ::= 40184

           alarmInputHighDensity0185Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 185 from a high density unit
                transitions to the alarm state."
           ::= 30185

           alarmInputHighDensity0185Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 185 from a high density unit 
                transitions to the normal state."
           ::= 40185

           alarmInputHighDensity0186Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 186 from a high density unit
                transitions to the alarm state."
           ::= 30186

           alarmInputHighDensity0186Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 186 from a high density unit 
                transitions to the normal state."
           ::= 40186

           alarmInputHighDensity0187Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 187 from a high density unit
                transitions to the alarm state."
           ::= 30187

           alarmInputHighDensity0187Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 187 from a high density unit 
                transitions to the normal state."
           ::= 40187

           alarmInputHighDensity0188Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 188 from a high density unit
                transitions to the alarm state."
           ::= 30188

           alarmInputHighDensity0188Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 188 from a high density unit 
                transitions to the normal state."
           ::= 40188

           alarmInputHighDensity0189Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 189 from a high density unit
                transitions to the alarm state."
           ::= 30189

           alarmInputHighDensity0189Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 189 from a high density unit 
                transitions to the normal state."
           ::= 40189

           alarmInputHighDensity0190Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 190 from a high density unit
                transitions to the alarm state."
           ::= 30190

           alarmInputHighDensity0190Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 190 from a high density unit 
                transitions to the normal state."
           ::= 40190

           alarmInputHighDensity0191Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 191 from a high density unit
                transitions to the alarm state."
           ::= 30191

           alarmInputHighDensity0191Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 191 from a high density unit 
                transitions to the normal state."
           ::= 40191

           alarmInputHighDensity0192Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 192 from a high density unit
                transitions to the alarm state."
           ::= 30192

           alarmInputHighDensity0192Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 192 from a high density unit 
                transitions to the normal state."
           ::= 40192

           alarmInputHighDensity0193Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 193 from a high density unit
                transitions to the alarm state."
           ::= 30193

           alarmInputHighDensity0193Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 193 from a high density unit 
                transitions to the normal state."
           ::= 40193

           alarmInputHighDensity0194Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 194 from a high density unit
                transitions to the alarm state."
           ::= 30194

           alarmInputHighDensity0194Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 194 from a high density unit 
                transitions to the normal state."
           ::= 40194

           alarmInputHighDensity0195Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 195 from a high density unit
                transitions to the alarm state."
           ::= 30195

           alarmInputHighDensity0195Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 195 from a high density unit 
                transitions to the normal state."
           ::= 40195

           alarmInputHighDensity0196Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 196 from a high density unit
                transitions to the alarm state."
           ::= 30196

           alarmInputHighDensity0196Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 196 from a high density unit 
                transitions to the normal state."
           ::= 40196

           alarmInputHighDensity0197Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 197 from a high density unit
                transitions to the alarm state."
           ::= 30197

           alarmInputHighDensity0197Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 197 from a high density unit 
                transitions to the normal state."
           ::= 40197

           alarmInputHighDensity0198Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 198 from a high density unit
                transitions to the alarm state."
           ::= 30198

           alarmInputHighDensity0198Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 198 from a high density unit 
                transitions to the normal state."
           ::= 40198

           alarmInputHighDensity0199Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 199 from a high density unit
                transitions to the alarm state."
           ::= 30199

           alarmInputHighDensity0199Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 199 from a high density unit 
                transitions to the normal state."
           ::= 40199

           alarmInputHighDensity0200Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 200 from a high density unit
                transitions to the alarm state."
           ::= 30200

           alarmInputHighDensity0200Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 200 from a high density unit 
                transitions to the normal state."
           ::= 40200

           alarmInputHighDensity0201Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 201 from a high density unit
                transitions to the alarm state."
           ::= 30201

           alarmInputHighDensity0201Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 201 from a high density unit 
                transitions to the normal state."
           ::= 40201

           alarmInputHighDensity0202Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 202 from a high density unit
                transitions to the alarm state."
           ::= 30202

           alarmInputHighDensity0202Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 202 from a high density unit 
                transitions to the normal state."
           ::= 40202

           alarmInputHighDensity0203Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 203 from a high density unit
                transitions to the alarm state."
           ::= 30203

           alarmInputHighDensity0203Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 203 from a high density unit 
                transitions to the normal state."
           ::= 40203

           alarmInputHighDensity0204Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 204 from a high density unit
                transitions to the alarm state."
           ::= 30204

           alarmInputHighDensity0204Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 204 from a high density unit 
                transitions to the normal state."
           ::= 40204

           alarmInputHighDensity0205Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 205 from a high density unit
                transitions to the alarm state."
           ::= 30205

           alarmInputHighDensity0205Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 205 from a high density unit 
                transitions to the normal state."
           ::= 40205

           alarmInputHighDensity0206Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 206 from a high density unit
                transitions to the alarm state."
           ::= 30206

           alarmInputHighDensity0206Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 206 from a high density unit 
                transitions to the normal state."
           ::= 40206

           alarmInputHighDensity0207Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 207 from a high density unit
                transitions to the alarm state."
           ::= 30207

           alarmInputHighDensity0207Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 207 from a high density unit 
                transitions to the normal state."
           ::= 40207

           alarmInputHighDensity0208Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 208 from a high density unit
                transitions to the alarm state."
           ::= 30208

           alarmInputHighDensity0208Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 208 from a high density unit 
                transitions to the normal state."
           ::= 40208

           alarmInputHighDensity0209Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 209 from a high density unit
                transitions to the alarm state."
           ::= 30209

           alarmInputHighDensity0209Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 209 from a high density unit 
                transitions to the normal state."
           ::= 40209

           alarmInputHighDensity0210Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 210 from a high density unit
                transitions to the alarm state."
           ::= 30210

           alarmInputHighDensity0210Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 210 from a high density unit 
                transitions to the normal state."
           ::= 40210

           alarmInputHighDensity0211Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 211 from a high density unit
                transitions to the alarm state."
           ::= 30211

           alarmInputHighDensity0211Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 211 from a high density unit 
                transitions to the normal state."
           ::= 40211

           alarmInputHighDensity0212Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 212 from a high density unit
                transitions to the alarm state."
           ::= 30212

           alarmInputHighDensity0212Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 212 from a high density unit 
                transitions to the normal state."
           ::= 40212

           alarmInputHighDensity0213Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 213 from a high density unit
                transitions to the alarm state."
           ::= 30213

           alarmInputHighDensity0213Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 213 from a high density unit 
                transitions to the normal state."
           ::= 40213

           alarmInputHighDensity0214Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 214 from a high density unit
                transitions to the alarm state."
           ::= 30214

           alarmInputHighDensity0214Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 214 from a high density unit 
                transitions to the normal state."
           ::= 40214

           alarmInputHighDensity0215Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 215 from a high density unit
                transitions to the alarm state."
           ::= 30215

           alarmInputHighDensity0215Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 215 from a high density unit 
                transitions to the normal state."
           ::= 40215

           alarmInputHighDensity0216Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 216 from a high density unit
                transitions to the alarm state."
           ::= 30216

           alarmInputHighDensity0216Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 216 from a high density unit 
                transitions to the normal state."
           ::= 40216

           alarmInputHighDensity0217Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 217 from a high density unit
                transitions to the alarm state."
           ::= 30217

           alarmInputHighDensity0217Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 217 from a high density unit 
                transitions to the normal state."
           ::= 40217

           alarmInputHighDensity0218Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 218 from a high density unit
                transitions to the alarm state."
           ::= 30218

           alarmInputHighDensity0218Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 218 from a high density unit 
                transitions to the normal state."
           ::= 40218

           alarmInputHighDensity0219Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 219 from a high density unit
                transitions to the alarm state."
           ::= 30219

           alarmInputHighDensity0219Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 219 from a high density unit 
                transitions to the normal state."
           ::= 40219

           alarmInputHighDensity0220Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 220 from a high density unit
                transitions to the alarm state."
           ::= 30220

           alarmInputHighDensity0220Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 220 from a high density unit 
                transitions to the normal state."
           ::= 40220

           alarmInputHighDensity0221Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 221 from a high density unit
                transitions to the alarm state."
           ::= 30221

           alarmInputHighDensity0221Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 221 from a high density unit 
                transitions to the normal state."
           ::= 40221

           alarmInputHighDensity0222Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 222 from a high density unit
                transitions to the alarm state."
           ::= 30222

           alarmInputHighDensity0222Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 222 from a high density unit 
                transitions to the normal state."
           ::= 40222

           alarmInputHighDensity0223Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 223 from a high density unit
                transitions to the alarm state."
           ::= 30223

           alarmInputHighDensity0223Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 223 from a high density unit 
                transitions to the normal state."
           ::= 40223

           alarmInputHighDensity0224Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 224 from a high density unit
                transitions to the alarm state."
           ::= 30224

           alarmInputHighDensity0224Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 224 from a high density unit 
                transitions to the normal state."
           ::= 40224

           alarmInputHighDensity0225Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 225 from a high density unit
                transitions to the alarm state."
           ::= 30225

           alarmInputHighDensity0225Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 225 from a high density unit 
                transitions to the normal state."
           ::= 40225

           alarmInputHighDensity0226Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 226 from a high density unit
                transitions to the alarm state."
           ::= 30226

           alarmInputHighDensity0226Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 226 from a high density unit 
                transitions to the normal state."
           ::= 40226

           alarmInputHighDensity0227Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 227 from a high density unit
                transitions to the alarm state."
           ::= 30227

           alarmInputHighDensity0227Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 227 from a high density unit 
                transitions to the normal state."
           ::= 40227

           alarmInputHighDensity0228Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 228 from a high density unit
                transitions to the alarm state."
           ::= 30228

           alarmInputHighDensity0228Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 228 from a high density unit 
                transitions to the normal state."
           ::= 40228

           alarmInputHighDensity0229Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 229 from a high density unit
                transitions to the alarm state."
           ::= 30229

           alarmInputHighDensity0229Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 229 from a high density unit 
                transitions to the normal state."
           ::= 40229

           alarmInputHighDensity0230Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 230 from a high density unit
                transitions to the alarm state."
           ::= 30230

           alarmInputHighDensity0230Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 230 from a high density unit 
                transitions to the normal state."
           ::= 40230

           alarmInputHighDensity0231Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 231 from a high density unit
                transitions to the alarm state."
           ::= 30231

           alarmInputHighDensity0231Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 231 from a high density unit 
                transitions to the normal state."
           ::= 40231

           alarmInputHighDensity0232Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 232 from a high density unit
                transitions to the alarm state."
           ::= 30232

           alarmInputHighDensity0232Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 232 from a high density unit 
                transitions to the normal state."
           ::= 40232

           alarmInputHighDensity0233Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 233 from a high density unit
                transitions to the alarm state."
           ::= 30233

           alarmInputHighDensity0233Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 233 from a high density unit 
                transitions to the normal state."
           ::= 40233

           alarmInputHighDensity0234Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 234 from a high density unit
                transitions to the alarm state."
           ::= 30234

           alarmInputHighDensity0234Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 234 from a high density unit 
                transitions to the normal state."
           ::= 40234

           alarmInputHighDensity0235Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 235 from a high density unit
                transitions to the alarm state."
           ::= 30235

           alarmInputHighDensity0235Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 235 from a high density unit 
                transitions to the normal state."
           ::= 40235

           alarmInputHighDensity0236Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 236 from a high density unit
                transitions to the alarm state."
           ::= 30236

           alarmInputHighDensity0236Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 236 from a high density unit 
                transitions to the normal state."
           ::= 40236

           alarmInputHighDensity0237Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 237 from a high density unit
                transitions to the alarm state."
           ::= 30237

           alarmInputHighDensity0237Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 237 from a high density unit 
                transitions to the normal state."
           ::= 40237

           alarmInputHighDensity0238Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 238 from a high density unit
                transitions to the alarm state."
           ::= 30238

           alarmInputHighDensity0238Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 238 from a high density unit 
                transitions to the normal state."
           ::= 40238

           alarmInputHighDensity0239Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 239 from a high density unit
                transitions to the alarm state."
           ::= 30239

           alarmInputHighDensity0239Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 239 from a high density unit 
                transitions to the normal state."
           ::= 40239

           alarmInputHighDensity0240Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 240 from a high density unit
                transitions to the alarm state."
           ::= 30240

           alarmInputHighDensity0240Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 240 from a high density unit 
                transitions to the normal state."
           ::= 40240

           alarmInputHighDensity0241Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 241 from a high density unit
                transitions to the alarm state."
           ::= 30241

           alarmInputHighDensity0241Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 241 from a high density unit 
                transitions to the normal state."
           ::= 40241

           alarmInputHighDensity0242Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 242 from a high density unit
                transitions to the alarm state."
           ::= 30242

           alarmInputHighDensity0242Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 242 from a high density unit 
                transitions to the normal state."
           ::= 40242

           alarmInputHighDensity0243Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 243 from a high density unit
                transitions to the alarm state."
           ::= 30243

           alarmInputHighDensity0243Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 243 from a high density unit 
                transitions to the normal state."
           ::= 40243

           alarmInputHighDensity0244Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 244 from a high density unit
                transitions to the alarm state."
           ::= 30244

           alarmInputHighDensity0244Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 244 from a high density unit 
                transitions to the normal state."
           ::= 40244

           alarmInputHighDensity0245Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 245 from a high density unit
                transitions to the alarm state."
           ::= 30245

           alarmInputHighDensity0245Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 245 from a high density unit 
                transitions to the normal state."
           ::= 40245

           alarmInputHighDensity0246Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 246 from a high density unit
                transitions to the alarm state."
           ::= 30246

           alarmInputHighDensity0246Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 246 from a high density unit 
                transitions to the normal state."
           ::= 40246

           alarmInputHighDensity0247Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 247 from a high density unit
                transitions to the alarm state."
           ::= 30247

           alarmInputHighDensity0247Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 247 from a high density unit 
                transitions to the normal state."
           ::= 40247

           alarmInputHighDensity0248Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 248 from a high density unit
                transitions to the alarm state."
           ::= 30248

           alarmInputHighDensity0248Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 248 from a high density unit 
                transitions to the normal state."
           ::= 40248

           alarmInputHighDensity0249Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 249 from a high density unit
                transitions to the alarm state."
           ::= 30249

           alarmInputHighDensity0249Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 249 from a high density unit 
                transitions to the normal state."
           ::= 40249

           alarmInputHighDensity0250Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 250 from a high density unit
                transitions to the alarm state."
           ::= 30250

           alarmInputHighDensity0250Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 250 from a high density unit 
                transitions to the normal state."
           ::= 40250

           alarmInputHighDensity0251Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 251 from a high density unit
                transitions to the alarm state."
           ::= 30251

           alarmInputHighDensity0251Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 251 from a high density unit 
                transitions to the normal state."
           ::= 40251

           alarmInputHighDensity0252Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 252 from a high density unit
                transitions to the alarm state."
           ::= 30252

           alarmInputHighDensity0252Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 252 from a high density unit 
                transitions to the normal state."
           ::= 40252

           alarmInputHighDensity0253Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 253 from a high density unit
                transitions to the alarm state."
           ::= 30253

           alarmInputHighDensity0253Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 253 from a high density unit 
                transitions to the normal state."
           ::= 40253

           alarmInputHighDensity0254Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 254 from a high density unit
                transitions to the alarm state."
           ::= 30254

           alarmInputHighDensity0254Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 254 from a high density unit 
                transitions to the normal state."
           ::= 40254

           alarmInputHighDensity0255Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 255 from a high density unit
                transitions to the alarm state."
           ::= 30255

           alarmInputHighDensity0255Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 255 from a high density unit 
                transitions to the normal state."
           ::= 40255

           alarmInputHighDensity0256Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 256 from a high density unit
                transitions to the alarm state."
           ::= 30256

           alarmInputHighDensity0256Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 256 from a high density unit 
                transitions to the normal state."
           ::= 40256

           alarmInputHighDensity0257Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 257 from a high density unit
                transitions to the alarm state."
           ::= 30257

           alarmInputHighDensity0257Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 257 from a high density unit 
                transitions to the normal state."
           ::= 40257

           alarmInputHighDensity0258Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 258 from a high density unit
                transitions to the alarm state."
           ::= 30258

           alarmInputHighDensity0258Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 258 from a high density unit 
                transitions to the normal state."
           ::= 40258

           alarmInputHighDensity0259Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 259 from a high density unit
                transitions to the alarm state."
           ::= 30259

           alarmInputHighDensity0259Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 259 from a high density unit 
                transitions to the normal state."
           ::= 40259

           alarmInputHighDensity0260Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 260 from a high density unit
                transitions to the alarm state."
           ::= 30260

           alarmInputHighDensity0260Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 260 from a high density unit 
                transitions to the normal state."
           ::= 40260

           alarmInputHighDensity0261Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 261 from a high density unit
                transitions to the alarm state."
           ::= 30261

           alarmInputHighDensity0261Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 261 from a high density unit 
                transitions to the normal state."
           ::= 40261

           alarmInputHighDensity0262Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 262 from a high density unit
                transitions to the alarm state."
           ::= 30262

           alarmInputHighDensity0262Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 262 from a high density unit 
                transitions to the normal state."
           ::= 40262

           alarmInputHighDensity0263Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 263 from a high density unit
                transitions to the alarm state."
           ::= 30263

           alarmInputHighDensity0263Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 263 from a high density unit 
                transitions to the normal state."
           ::= 40263

           alarmInputHighDensity0264Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 264 from a high density unit
                transitions to the alarm state."
           ::= 30264

           alarmInputHighDensity0264Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 264 from a high density unit 
                transitions to the normal state."
           ::= 40264

           alarmInputHighDensity0265Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 265 from a high density unit
                transitions to the alarm state."
           ::= 30265

           alarmInputHighDensity0265Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 265 from a high density unit 
                transitions to the normal state."
           ::= 40265

           alarmInputHighDensity0266Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 266 from a high density unit
                transitions to the alarm state."
           ::= 30266

           alarmInputHighDensity0266Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 266 from a high density unit 
                transitions to the normal state."
           ::= 40266

           alarmInputHighDensity0267Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 267 from a high density unit
                transitions to the alarm state."
           ::= 30267

           alarmInputHighDensity0267Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 267 from a high density unit 
                transitions to the normal state."
           ::= 40267

           alarmInputHighDensity0268Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 268 from a high density unit
                transitions to the alarm state."
           ::= 30268

           alarmInputHighDensity0268Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 268 from a high density unit 
                transitions to the normal state."
           ::= 40268

           alarmInputHighDensity0269Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 269 from a high density unit
                transitions to the alarm state."
           ::= 30269

           alarmInputHighDensity0269Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 269 from a high density unit 
                transitions to the normal state."
           ::= 40269

           alarmInputHighDensity0270Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 270 from a high density unit
                transitions to the alarm state."
           ::= 30270

           alarmInputHighDensity0270Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 270 from a high density unit 
                transitions to the normal state."
           ::= 40270

           alarmInputHighDensity0271Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 271 from a high density unit
                transitions to the alarm state."
           ::= 30271

           alarmInputHighDensity0271Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 271 from a high density unit 
                transitions to the normal state."
           ::= 40271

           alarmInputHighDensity0272Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 272 from a high density unit
                transitions to the alarm state."
           ::= 30272

           alarmInputHighDensity0272Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 272 from a high density unit 
                transitions to the normal state."
           ::= 40272

           alarmInputHighDensity0273Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 273 from a high density unit
                transitions to the alarm state."
           ::= 30273

           alarmInputHighDensity0273Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 273 from a high density unit 
                transitions to the normal state."
           ::= 40273

           alarmInputHighDensity0274Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 274 from a high density unit
                transitions to the alarm state."
           ::= 30274

           alarmInputHighDensity0274Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 274 from a high density unit 
                transitions to the normal state."
           ::= 40274

           alarmInputHighDensity0275Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 275 from a high density unit
                transitions to the alarm state."
           ::= 30275

           alarmInputHighDensity0275Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 275 from a high density unit 
                transitions to the normal state."
           ::= 40275

           alarmInputHighDensity0276Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 276 from a high density unit
                transitions to the alarm state."
           ::= 30276

           alarmInputHighDensity0276Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 276 from a high density unit 
                transitions to the normal state."
           ::= 40276

           alarmInputHighDensity0277Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 277 from a high density unit
                transitions to the alarm state."
           ::= 30277

           alarmInputHighDensity0277Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 277 from a high density unit 
                transitions to the normal state."
           ::= 40277

           alarmInputHighDensity0278Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 278 from a high density unit
                transitions to the alarm state."
           ::= 30278

           alarmInputHighDensity0278Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 278 from a high density unit 
                transitions to the normal state."
           ::= 40278

           alarmInputHighDensity0279Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 279 from a high density unit
                transitions to the alarm state."
           ::= 30279

           alarmInputHighDensity0279Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 279 from a high density unit 
                transitions to the normal state."
           ::= 40279

           alarmInputHighDensity0280Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 280 from a high density unit
                transitions to the alarm state."
           ::= 30280

           alarmInputHighDensity0280Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 280 from a high density unit 
                transitions to the normal state."
           ::= 40280

           alarmInputHighDensity0281Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 281 from a high density unit
                transitions to the alarm state."
           ::= 30281

           alarmInputHighDensity0281Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 281 from a high density unit 
                transitions to the normal state."
           ::= 40281

           alarmInputHighDensity0282Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 282 from a high density unit
                transitions to the alarm state."
           ::= 30282

           alarmInputHighDensity0282Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 282 from a high density unit 
                transitions to the normal state."
           ::= 40282

           alarmInputHighDensity0283Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 283 from a high density unit
                transitions to the alarm state."
           ::= 30283

           alarmInputHighDensity0283Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 283 from a high density unit 
                transitions to the normal state."
           ::= 40283

           alarmInputHighDensity0284Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 284 from a high density unit
                transitions to the alarm state."
           ::= 30284

           alarmInputHighDensity0284Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 284 from a high density unit 
                transitions to the normal state."
           ::= 40284

           alarmInputHighDensity0285Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 285 from a high density unit
                transitions to the alarm state."
           ::= 30285

           alarmInputHighDensity0285Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 285 from a high density unit 
                transitions to the normal state."
           ::= 40285

           alarmInputHighDensity0286Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 286 from a high density unit
                transitions to the alarm state."
           ::= 30286

           alarmInputHighDensity0286Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 286 from a high density unit 
                transitions to the normal state."
           ::= 40286

           alarmInputHighDensity0287Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 287 from a high density unit
                transitions to the alarm state."
           ::= 30287

           alarmInputHighDensity0287Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 287 from a high density unit 
                transitions to the normal state."
           ::= 40287

           alarmInputHighDensity0288Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 288 from a high density unit
                transitions to the alarm state."
           ::= 30288

           alarmInputHighDensity0288Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 288 from a high density unit 
                transitions to the normal state."
           ::= 40288

           alarmInputHighDensity0289Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 289 from a high density unit
                transitions to the alarm state."
           ::= 30289

           alarmInputHighDensity0289Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 289 from a high density unit 
                transitions to the normal state."
           ::= 40289

           alarmInputHighDensity0290Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 290 from a high density unit
                transitions to the alarm state."
           ::= 30290

           alarmInputHighDensity0290Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 290 from a high density unit 
                transitions to the normal state."
           ::= 40290

           alarmInputHighDensity0291Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 291 from a high density unit
                transitions to the alarm state."
           ::= 30291

           alarmInputHighDensity0291Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 291 from a high density unit 
                transitions to the normal state."
           ::= 40291

           alarmInputHighDensity0292Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 292 from a high density unit
                transitions to the alarm state."
           ::= 30292

           alarmInputHighDensity0292Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 292 from a high density unit 
                transitions to the normal state."
           ::= 40292

           alarmInputHighDensity0293Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 293 from a high density unit
                transitions to the alarm state."
           ::= 30293

           alarmInputHighDensity0293Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 293 from a high density unit 
                transitions to the normal state."
           ::= 40293

           alarmInputHighDensity0294Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 294 from a high density unit
                transitions to the alarm state."
           ::= 30294

           alarmInputHighDensity0294Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 294 from a high density unit 
                transitions to the normal state."
           ::= 40294

           alarmInputHighDensity0295Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 295 from a high density unit
                transitions to the alarm state."
           ::= 30295

           alarmInputHighDensity0295Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 295 from a high density unit 
                transitions to the normal state."
           ::= 40295

           alarmInputHighDensity0296Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 296 from a high density unit
                transitions to the alarm state."
           ::= 30296

           alarmInputHighDensity0296Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 296 from a high density unit 
                transitions to the normal state."
           ::= 40296

           alarmInputHighDensity0297Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 297 from a high density unit
                transitions to the alarm state."
           ::= 30297

           alarmInputHighDensity0297Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 297 from a high density unit 
                transitions to the normal state."
           ::= 40297

           alarmInputHighDensity0298Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 298 from a high density unit
                transitions to the alarm state."
           ::= 30298

           alarmInputHighDensity0298Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 298 from a high density unit 
                transitions to the normal state."
           ::= 40298

           alarmInputHighDensity0299Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 299 from a high density unit
                transitions to the alarm state."
           ::= 30299

           alarmInputHighDensity0299Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 299 from a high density unit 
                transitions to the normal state."
           ::= 40299

           alarmInputHighDensity0300Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 300 from a high density unit
                transitions to the alarm state."
           ::= 30300

           alarmInputHighDensity0300Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 300 from a high density unit 
                transitions to the normal state."
           ::= 40300

           alarmInputHighDensity0301Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 301 from a high density unit
                transitions to the alarm state."
           ::= 30301

           alarmInputHighDensity0301Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 301 from a high density unit 
                transitions to the normal state."
           ::= 40301

           alarmInputHighDensity0302Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 302 from a high density unit
                transitions to the alarm state."
           ::= 30302

           alarmInputHighDensity0302Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 302 from a high density unit 
                transitions to the normal state."
           ::= 40302

           alarmInputHighDensity0303Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 303 from a high density unit
                transitions to the alarm state."
           ::= 30303

           alarmInputHighDensity0303Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 303 from a high density unit 
                transitions to the normal state."
           ::= 40303

           alarmInputHighDensity0304Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 304 from a high density unit
                transitions to the alarm state."
           ::= 30304

           alarmInputHighDensity0304Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 304 from a high density unit 
                transitions to the normal state."
           ::= 40304

           alarmInputHighDensity0305Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 305 from a high density unit
                transitions to the alarm state."
           ::= 30305

           alarmInputHighDensity0305Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 305 from a high density unit 
                transitions to the normal state."
           ::= 40305

           alarmInputHighDensity0306Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 306 from a high density unit
                transitions to the alarm state."
           ::= 30306

           alarmInputHighDensity0306Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 306 from a high density unit 
                transitions to the normal state."
           ::= 40306

           alarmInputHighDensity0307Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 307 from a high density unit
                transitions to the alarm state."
           ::= 30307

           alarmInputHighDensity0307Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 307 from a high density unit 
                transitions to the normal state."
           ::= 40307

           alarmInputHighDensity0308Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 308 from a high density unit
                transitions to the alarm state."
           ::= 30308

           alarmInputHighDensity0308Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 308 from a high density unit 
                transitions to the normal state."
           ::= 40308

           alarmInputHighDensity0309Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 309 from a high density unit
                transitions to the alarm state."
           ::= 30309

           alarmInputHighDensity0309Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 309 from a high density unit 
                transitions to the normal state."
           ::= 40309

           alarmInputHighDensity0310Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 310 from a high density unit
                transitions to the alarm state."
           ::= 30310

           alarmInputHighDensity0310Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 310 from a high density unit 
                transitions to the normal state."
           ::= 40310

           alarmInputHighDensity0311Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 311 from a high density unit
                transitions to the alarm state."
           ::= 30311

           alarmInputHighDensity0311Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 311 from a high density unit 
                transitions to the normal state."
           ::= 40311

           alarmInputHighDensity0312Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 312 from a high density unit
                transitions to the alarm state."
           ::= 30312

           alarmInputHighDensity0312Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 312 from a high density unit 
                transitions to the normal state."
           ::= 40312

           alarmInputHighDensity0313Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 313 from a high density unit
                transitions to the alarm state."
           ::= 30313

           alarmInputHighDensity0313Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 313 from a high density unit 
                transitions to the normal state."
           ::= 40313

           alarmInputHighDensity0314Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 314 from a high density unit
                transitions to the alarm state."
           ::= 30314

           alarmInputHighDensity0314Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 314 from a high density unit 
                transitions to the normal state."
           ::= 40314

           alarmInputHighDensity0315Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 315 from a high density unit
                transitions to the alarm state."
           ::= 30315

           alarmInputHighDensity0315Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 315 from a high density unit 
                transitions to the normal state."
           ::= 40315

           alarmInputHighDensity0316Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 316 from a high density unit
                transitions to the alarm state."
           ::= 30316

           alarmInputHighDensity0316Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 316 from a high density unit 
                transitions to the normal state."
           ::= 40316

           alarmInputHighDensity0317Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 317 from a high density unit
                transitions to the alarm state."
           ::= 30317

           alarmInputHighDensity0317Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 317 from a high density unit 
                transitions to the normal state."
           ::= 40317

           alarmInputHighDensity0318Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 318 from a high density unit
                transitions to the alarm state."
           ::= 30318

           alarmInputHighDensity0318Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 318 from a high density unit 
                transitions to the normal state."
           ::= 40318

           alarmInputHighDensity0319Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 319 from a high density unit
                transitions to the alarm state."
           ::= 30319

           alarmInputHighDensity0319Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 319 from a high density unit 
                transitions to the normal state."
           ::= 40319

           alarmInputHighDensity0320Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 320 from a high density unit
                transitions to the alarm state."
           ::= 30320

           alarmInputHighDensity0320Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 320 from a high density unit 
                transitions to the normal state."
           ::= 40320

           alarmInputHighDensity0321Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 321 from a high density unit
                transitions to the alarm state."
           ::= 30321

           alarmInputHighDensity0321Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 321 from a high density unit 
                transitions to the normal state."
           ::= 40321

           alarmInputHighDensity0322Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 322 from a high density unit
                transitions to the alarm state."
           ::= 30322

           alarmInputHighDensity0322Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 322 from a high density unit 
                transitions to the normal state."
           ::= 40322

           alarmInputHighDensity0323Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 323 from a high density unit
                transitions to the alarm state."
           ::= 30323

           alarmInputHighDensity0323Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 323 from a high density unit 
                transitions to the normal state."
           ::= 40323

           alarmInputHighDensity0324Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 324 from a high density unit
                transitions to the alarm state."
           ::= 30324

           alarmInputHighDensity0324Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 324 from a high density unit 
                transitions to the normal state."
           ::= 40324

           alarmInputHighDensity0325Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 325 from a high density unit
                transitions to the alarm state."
           ::= 30325

           alarmInputHighDensity0325Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 325 from a high density unit 
                transitions to the normal state."
           ::= 40325

           alarmInputHighDensity0326Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 326 from a high density unit
                transitions to the alarm state."
           ::= 30326

           alarmInputHighDensity0326Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 326 from a high density unit 
                transitions to the normal state."
           ::= 40326

           alarmInputHighDensity0327Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 327 from a high density unit
                transitions to the alarm state."
           ::= 30327

           alarmInputHighDensity0327Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 327 from a high density unit 
                transitions to the normal state."
           ::= 40327

           alarmInputHighDensity0328Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 328 from a high density unit
                transitions to the alarm state."
           ::= 30328

           alarmInputHighDensity0328Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 328 from a high density unit 
                transitions to the normal state."
           ::= 40328

           alarmInputHighDensity0329Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 329 from a high density unit
                transitions to the alarm state."
           ::= 30329

           alarmInputHighDensity0329Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 329 from a high density unit 
                transitions to the normal state."
           ::= 40329

           alarmInputHighDensity0330Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 330 from a high density unit
                transitions to the alarm state."
           ::= 30330

           alarmInputHighDensity0330Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 330 from a high density unit 
                transitions to the normal state."
           ::= 40330

           alarmInputHighDensity0331Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 331 from a high density unit
                transitions to the alarm state."
           ::= 30331

           alarmInputHighDensity0331Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 331 from a high density unit 
                transitions to the normal state."
           ::= 40331

           alarmInputHighDensity0332Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 332 from a high density unit
                transitions to the alarm state."
           ::= 30332

           alarmInputHighDensity0332Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 332 from a high density unit 
                transitions to the normal state."
           ::= 40332

           alarmInputHighDensity0333Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 333 from a high density unit
                transitions to the alarm state."
           ::= 30333

           alarmInputHighDensity0333Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 333 from a high density unit 
                transitions to the normal state."
           ::= 40333

           alarmInputHighDensity0334Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 334 from a high density unit
                transitions to the alarm state."
           ::= 30334

           alarmInputHighDensity0334Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 334 from a high density unit 
                transitions to the normal state."
           ::= 40334

           alarmInputHighDensity0335Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 335 from a high density unit
                transitions to the alarm state."
           ::= 30335

           alarmInputHighDensity0335Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 335 from a high density unit 
                transitions to the normal state."
           ::= 40335

           alarmInputHighDensity0336Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 336 from a high density unit
                transitions to the alarm state."
           ::= 30336

           alarmInputHighDensity0336Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 336 from a high density unit 
                transitions to the normal state."
           ::= 40336

           alarmInputHighDensity0337Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 337 from a high density unit
                transitions to the alarm state."
           ::= 30337

           alarmInputHighDensity0337Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 337 from a high density unit 
                transitions to the normal state."
           ::= 40337

           alarmInputHighDensity0338Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 338 from a high density unit
                transitions to the alarm state."
           ::= 30338

           alarmInputHighDensity0338Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 338 from a high density unit 
                transitions to the normal state."
           ::= 40338

           alarmInputHighDensity0339Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 339 from a high density unit
                transitions to the alarm state."
           ::= 30339

           alarmInputHighDensity0339Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 339 from a high density unit 
                transitions to the normal state."
           ::= 40339

           alarmInputHighDensity0340Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 340 from a high density unit
                transitions to the alarm state."
           ::= 30340

           alarmInputHighDensity0340Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 340 from a high density unit 
                transitions to the normal state."
           ::= 40340

           alarmInputHighDensity0341Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 341 from a high density unit
                transitions to the alarm state."
           ::= 30341

           alarmInputHighDensity0341Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 341 from a high density unit 
                transitions to the normal state."
           ::= 40341

           alarmInputHighDensity0342Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 342 from a high density unit
                transitions to the alarm state."
           ::= 30342

           alarmInputHighDensity0342Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 342 from a high density unit 
                transitions to the normal state."
           ::= 40342

           alarmInputHighDensity0343Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 343 from a high density unit
                transitions to the alarm state."
           ::= 30343

           alarmInputHighDensity0343Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 343 from a high density unit 
                transitions to the normal state."
           ::= 40343

           alarmInputHighDensity0344Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 344 from a high density unit
                transitions to the alarm state."
           ::= 30344

           alarmInputHighDensity0344Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 344 from a high density unit 
                transitions to the normal state."
           ::= 40344

           alarmInputHighDensity0345Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 345 from a high density unit
                transitions to the alarm state."
           ::= 30345

           alarmInputHighDensity0345Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 345 from a high density unit 
                transitions to the normal state."
           ::= 40345

           alarmInputHighDensity0346Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 346 from a high density unit
                transitions to the alarm state."
           ::= 30346

           alarmInputHighDensity0346Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 346 from a high density unit 
                transitions to the normal state."
           ::= 40346

           alarmInputHighDensity0347Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 347 from a high density unit
                transitions to the alarm state."
           ::= 30347

           alarmInputHighDensity0347Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 347 from a high density unit 
                transitions to the normal state."
           ::= 40347

           alarmInputHighDensity0348Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 348 from a high density unit
                transitions to the alarm state."
           ::= 30348

           alarmInputHighDensity0348Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 348 from a high density unit 
                transitions to the normal state."
           ::= 40348

           alarmInputHighDensity0349Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 349 from a high density unit
                transitions to the alarm state."
           ::= 30349

           alarmInputHighDensity0349Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 349 from a high density unit 
                transitions to the normal state."
           ::= 40349

           alarmInputHighDensity0350Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 350 from a high density unit
                transitions to the alarm state."
           ::= 30350

           alarmInputHighDensity0350Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 350 from a high density unit 
                transitions to the normal state."
           ::= 40350

           alarmInputHighDensity0351Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 351 from a high density unit
                transitions to the alarm state."
           ::= 30351

           alarmInputHighDensity0351Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 351 from a high density unit 
                transitions to the normal state."
           ::= 40351

           alarmInputHighDensity0352Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 352 from a high density unit
                transitions to the alarm state."
           ::= 30352

           alarmInputHighDensity0352Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 352 from a high density unit 
                transitions to the normal state."
           ::= 40352

           alarmInputHighDensity0353Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 353 from a high density unit
                transitions to the alarm state."
           ::= 30353

           alarmInputHighDensity0353Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 353 from a high density unit 
                transitions to the normal state."
           ::= 40353

           alarmInputHighDensity0354Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 354 from a high density unit
                transitions to the alarm state."
           ::= 30354

           alarmInputHighDensity0354Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 354 from a high density unit 
                transitions to the normal state."
           ::= 40354

           alarmInputHighDensity0355Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 355 from a high density unit
                transitions to the alarm state."
           ::= 30355

           alarmInputHighDensity0355Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 355 from a high density unit 
                transitions to the normal state."
           ::= 40355

           alarmInputHighDensity0356Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 356 from a high density unit
                transitions to the alarm state."
           ::= 30356

           alarmInputHighDensity0356Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 356 from a high density unit 
                transitions to the normal state."
           ::= 40356

           alarmInputHighDensity0357Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 357 from a high density unit
                transitions to the alarm state."
           ::= 30357

           alarmInputHighDensity0357Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 357 from a high density unit 
                transitions to the normal state."
           ::= 40357

           alarmInputHighDensity0358Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 358 from a high density unit
                transitions to the alarm state."
           ::= 30358

           alarmInputHighDensity0358Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 358 from a high density unit 
                transitions to the normal state."
           ::= 40358

           alarmInputHighDensity0359Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 359 from a high density unit
                transitions to the alarm state."
           ::= 30359

           alarmInputHighDensity0359Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 359 from a high density unit 
                transitions to the normal state."
           ::= 40359

           alarmInputHighDensity0360Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 360 from a high density unit
                transitions to the alarm state."
           ::= 30360

           alarmInputHighDensity0360Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 360 from a high density unit 
                transitions to the normal state."
           ::= 40360

           alarmInputHighDensity0361Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 361 from a high density unit
                transitions to the alarm state."
           ::= 30361

           alarmInputHighDensity0361Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 361 from a high density unit 
                transitions to the normal state."
           ::= 40361

           alarmInputHighDensity0362Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 362 from a high density unit
                transitions to the alarm state."
           ::= 30362

           alarmInputHighDensity0362Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 362 from a high density unit 
                transitions to the normal state."
           ::= 40362

           alarmInputHighDensity0363Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 363 from a high density unit
                transitions to the alarm state."
           ::= 30363

           alarmInputHighDensity0363Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 363 from a high density unit 
                transitions to the normal state."
           ::= 40363

           alarmInputHighDensity0364Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 364 from a high density unit
                transitions to the alarm state."
           ::= 30364

           alarmInputHighDensity0364Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 364 from a high density unit 
                transitions to the normal state."
           ::= 40364

           alarmInputHighDensity0365Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 365 from a high density unit
                transitions to the alarm state."
           ::= 30365

           alarmInputHighDensity0365Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 365 from a high density unit 
                transitions to the normal state."
           ::= 40365

           alarmInputHighDensity0366Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 366 from a high density unit
                transitions to the alarm state."
           ::= 30366

           alarmInputHighDensity0366Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 366 from a high density unit 
                transitions to the normal state."
           ::= 40366

           alarmInputHighDensity0367Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 367 from a high density unit
                transitions to the alarm state."
           ::= 30367

           alarmInputHighDensity0367Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 367 from a high density unit 
                transitions to the normal state."
           ::= 40367

           alarmInputHighDensity0368Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 368 from a high density unit
                transitions to the alarm state."
           ::= 30368

           alarmInputHighDensity0368Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 368 from a high density unit 
                transitions to the normal state."
           ::= 40368

           alarmInputHighDensity0369Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 369 from a high density unit
                transitions to the alarm state."
           ::= 30369

           alarmInputHighDensity0369Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 369 from a high density unit 
                transitions to the normal state."
           ::= 40369

           alarmInputHighDensity0370Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 370 from a high density unit
                transitions to the alarm state."
           ::= 30370

           alarmInputHighDensity0370Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 370 from a high density unit 
                transitions to the normal state."
           ::= 40370

           alarmInputHighDensity0371Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 371 from a high density unit
                transitions to the alarm state."
           ::= 30371

           alarmInputHighDensity0371Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 371 from a high density unit 
                transitions to the normal state."
           ::= 40371

           alarmInputHighDensity0372Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 372 from a high density unit
                transitions to the alarm state."
           ::= 30372

           alarmInputHighDensity0372Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 372 from a high density unit 
                transitions to the normal state."
           ::= 40372

           alarmInputHighDensity0373Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 373 from a high density unit
                transitions to the alarm state."
           ::= 30373

           alarmInputHighDensity0373Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 373 from a high density unit 
                transitions to the normal state."
           ::= 40373

           alarmInputHighDensity0374Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 374 from a high density unit
                transitions to the alarm state."
           ::= 30374

           alarmInputHighDensity0374Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 374 from a high density unit 
                transitions to the normal state."
           ::= 40374

           alarmInputHighDensity0375Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 375 from a high density unit
                transitions to the alarm state."
           ::= 30375

           alarmInputHighDensity0375Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 375 from a high density unit 
                transitions to the normal state."
           ::= 40375

           alarmInputHighDensity0376Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 376 from a high density unit
                transitions to the alarm state."
           ::= 30376

           alarmInputHighDensity0376Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 376 from a high density unit 
                transitions to the normal state."
           ::= 40376

           alarmInputHighDensity0377Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 377 from a high density unit
                transitions to the alarm state."
           ::= 30377

           alarmInputHighDensity0377Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 377 from a high density unit 
                transitions to the normal state."
           ::= 40377

           alarmInputHighDensity0378Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 378 from a high density unit
                transitions to the alarm state."
           ::= 30378

           alarmInputHighDensity0378Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 378 from a high density unit 
                transitions to the normal state."
           ::= 40378

           alarmInputHighDensity0379Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 379 from a high density unit
                transitions to the alarm state."
           ::= 30379

           alarmInputHighDensity0379Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 379 from a high density unit 
                transitions to the normal state."
           ::= 40379

           alarmInputHighDensity0380Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 380 from a high density unit
                transitions to the alarm state."
           ::= 30380

           alarmInputHighDensity0380Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 380 from a high density unit 
                transitions to the normal state."
           ::= 40380

           alarmInputHighDensity0381Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 381 from a high density unit
                transitions to the alarm state."
           ::= 30381

           alarmInputHighDensity0381Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 381 from a high density unit 
                transitions to the normal state."
           ::= 40381

           alarmInputHighDensity0382Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 382 from a high density unit
                transitions to the alarm state."
           ::= 30382

           alarmInputHighDensity0382Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 382 from a high density unit 
                transitions to the normal state."
           ::= 40382

           alarmInputHighDensity0383Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 383 from a high density unit
                transitions to the alarm state."
           ::= 30383

           alarmInputHighDensity0383Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 383 from a high density unit 
                transitions to the normal state."
           ::= 40383

           alarmInputHighDensity0384Alarm TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 384 from a high density unit
                transitions to the alarm state."
           ::= 30384

           alarmInputHighDensity0384Normal TRAP-TYPE
           ENTERPRISE mrvInReachProductDivision
           VARIABLES { 
		basicAlarmMasterInputValue,
		basicAlarmMasterInputName,
		sysLocation,
	        basicAlarmMasterInputPort,
                basicAlarmMasterInputStatus,
        	basicAlarmMasterInputSlot,
		basicAlarmMasterInputPoint,
                basicAlarmMasterInputZone,
                basicAlarmMasterInputRelatedEquipment,
                basicAlarmMasterInputSiteId,
                basicAlarmMasterInputManufacturer,
                basicAlarmMasterInputModel
		 }
           DESCRIPTION
               "Generated when alarm point 384 from a high density unit 
                transitions to the normal state."
           ::= 40384




--
-- FILE: /users/sse/mibs/src/inReach/ir-decnet-mib.mib
--

-- $Id: ir-decnet-mib.mib,v 1.1 2002/06/27 15:45:16 sse Exp $


            xDecnet         OBJECT IDENTIFIER ::= { mrvInReachProductDivision 14 }

            -- MRV In-Reach DECnet groups

            xRcp            OBJECT IDENTIFIER ::= { xDecnet 1 }
            xPhiv           OBJECT IDENTIFIER ::= { xDecnet 2 }

            -- Phase IV subgroups

            xPhivRoute      OBJECT IDENTIFIER ::= { xPhiv 1 }
            xPhivCircuit    OBJECT IDENTIFIER ::= { xPhiv 2 }
            xPhivImport     OBJECT IDENTIFIER ::= { xPhiv 3 }
            xPhivImportArea OBJECT IDENTIFIER ::= { xPhiv 4 }
            xPhivExport     OBJECT IDENTIFIER ::= { xPhiv 5 }
            xPhivExportArea OBJECT IDENTIFIER ::= { xPhiv 6 }
            xPhivFilter     OBJECT IDENTIFIER ::= { xPhiv 7 }
            xPhivTraffic    OBJECT IDENTIFIER ::= { xPhiv 8 }




            -- This is a MIB module for all MRV In-Reach DECnet
            -- implementations.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the Remote Console group

            -- Implementation of this group is mandatory for all MRV In-Reach
            -- systems that implement DECnet remote console (RCP)

            rcpRemoteAddress OBJECT-TYPE
                SYNTAX OCTET STRING (SIZE (0..6))
                ACCESS read-only
                STATUS mandatory
                DESCRIPTION
                    "If a remote console session exists, the Ethernet 
                    address of the remote partner, otherwise zero 
                    length."
                ::= { xRcp 1 }


            -- the Phase IV group

            -- Implementation of this group is mandatory for all MRV In-Reach
            -- systems that implement DECnet Phase IV routing

            -- the Phase IV Route subgroup

            phivPathSelection OBJECT-TYPE
                SYNTAX INTEGER { roundRobin(1), samePath(2) }
                ACCESS read-write
                STATUS mandatory
                DESCRIPTION
                    "The algorithm used to balance traffic between equal 
                    next hop paths.  'roundRobin' selects the next hop 
                    using a round robin algorithm for each hop.  
                    'samePath' selects the next hop guaranteeing that 
                    all packets with the same source/destination pair 
                    will always use the same next hop."
                DEFVAL { roundRobin }
                ::= { xPhivRoute 1 }

            phivMaxPaths OBJECT-TYPE
                SYNTAX INTEGER (1..255)
                ACCESS read-write
                STATUS mandatory
                DESCRIPTION
                    "The maximum number of equal cost next hops that the 
                    router can remember and successfully load balance 
                    between."
                DEFVAL { 1 }
                ::= { xPhivRoute 2 }

            phivStatus OBJECT-TYPE
                SYNTAX INTEGER { active(1), disabled(2),
                                 noAddressSpecified(3),
                                 noInterfacesEnabled(4),
                                 badCost(5) }
                ACCESS read-only
                STATUS mandatory
                DESCRIPTION
                    "The status of the DECnet routing software."
                ::= { xPhivRoute 3 }


            -- the Phase IV Circuit subgroup

            phivCircuitTable OBJECT-TYPE
                SYNTAX SEQUENCE OF PhivCircuitEntry
                ACCESS not-accessible
                STATUS mandatory
                DESCRIPTION
                    "A list of DECnet circuit entries."
                ::= { xPhivCircuit 1 }

            phivCircuitEntry OBJECT-TYPE
                SYNTAX PhivCircuitEntry
                ACCESS not-accessible
                STATUS mandatory
                DESCRIPTION
                    "Parameter values for a DECnet circuit."
                INDEX { xPhivCircuitIndex }
                ::= { phivCircuitTable 1 }

            PhivCircuitEntry ::=
                SEQUENCE {
                    xPhivCircuitIndex
                        INTEGER,
                    phivCircuitRoutingTimer
                        INTEGER,
                    phivCircuitOperCost
                        INTEGER,
                    phivCircuitErrors
                        Counter,
                    phivCircuitLastError
                        INTEGER,
                    phivCircuitLastErrorTime
                        DateTime,
                    phivCircuitLastErrorData
                        OCTET STRING,
                    phivCircuitProtocolPriority
                        INTEGER,
                    phivCircuitRoutingPriority
                        INTEGER
                }

            xPhivCircuitIndex OBJECT-TYPE
                SYNTAX INTEGER
                ACCESS read-only
                STATUS mandatory
                DESCRIPTION
                    "Identification of a circuit entry.  Same as an 
                    interface index (ifIndex)."
                ::= { phivCircuitEntry 1 }

            phivCircuitRoutingTimer OBJECT-TYPE
                SYNTAX INTEGER (1..65535)
                ACCESS read-write
                STATUS mandatory
                DESCRIPTION
                    "The maximum time in seconds allowed between Routing 
                    updates on the circuit. Different values for LANs 
                    vs. WANs."
                DEFVAL { 40 }
                ::= { phivCircuitEntry 2 }

            phivCircuitOperCost OBJECT-TYPE
                SYNTAX INTEGER
                ACCESS read-only
                STATUS mandatory
                DESCRIPTION
                    "The actual cost associated with the circuit."
                ::= { phivCircuitEntry 3 }

            phivCircuitErrors OBJECT-TYPE
                SYNTAX Counter
                ACCESS read-only
                STATUS mandatory
                DESCRIPTION
                    "The number of routed DECnet packets received in 
                    error on this circuit."
                ::= { phivCircuitEntry 4 }

            phivCircuitLastError OBJECT-TYPE
                SYNTAX INTEGER { noError(1),
                                 addressOutOfRange(2),
                                 ageExceeded(3),
                                 destinationUnreachable(4),
                                 packetFormatError(5),
                                 packetOversized(6),
                                 partialRoutingUpdate(7),
                                 verificationReject(8) }
                ACCESS read-only
                STATUS mandatory
                DESCRIPTION
                    "The error of the last routed DECnet packet received 
                    in error on this circuit."
                ::= { phivCircuitEntry 5 }

            phivCircuitLastErrorTime OBJECT-TYPE
                SYNTAX DateTime
                ACCESS read-only
                STATUS mandatory
                DESCRIPTION
                    "The date and time that the last routed DECnet 
                    packet was received in error on this circuit."
                ::= { phivCircuitEntry 6 }

            phivCircuitLastErrorData OBJECT-TYPE
                SYNTAX OCTET STRING (SIZE (22))
                ACCESS read-only
                STATUS mandatory
                DESCRIPTION
                    "The first 22 bytes of the last routed DECnet packet 
                    received in error on this circuit."
                ::= { phivCircuitEntry 7 }

            phivCircuitProtocolPriority OBJECT-TYPE
                SYNTAX INTEGER { low(1), medium(3), high(5) }
                ACCESS read-write
                STATUS mandatory
                DESCRIPTION
                    "The priority at which all DECnet routed packets 
                    will be placed on the WAN output queue."
                DEFVAL { medium }
                ::= { phivCircuitEntry 8 }

            phivCircuitRoutingPriority OBJECT-TYPE
                SYNTAX INTEGER (0..127)
                ACCESS read-write
                STATUS mandatory
                DESCRIPTION
                    "Router's priority to be designated router on this 
                    circuit."
                DEFVAL { 64 }
                ::= { phivCircuitEntry 9 }


            -- the Phase IV Import Filter subgroup

            phivCircuitImportTable OBJECT-TYPE
                SYNTAX SEQUENCE OF PhivCircuitImportEntry
                ACCESS not-accessible
                STATUS mandatory
                DESCRIPTION
                    "A list of circuit import filter entries."
                ::= { xPhivImport 1 }

            phivCircuitImportEntry OBJECT-TYPE
                SYNTAX PhivCircuitImportEntry
                ACCESS not-accessible
                STATUS mandatory
                DESCRIPTION
                    "Parameter values for an import filter."
                INDEX { phivCircuitImportIf, phivCircuitImportAddr,
                        phivCircuitImportMask }
                ::= { phivCircuitImportTable 1 }

            PhivCircuitImportEntry ::=
                SEQUENCE {
                    phivCircuitImportIf
                        INTEGER,
                    phivCircuitImportAddr
                        PhivAddr,
                    phivCircuitImportMask
                        PhivAddr,
                    phivCircuitImportAction
                        INTEGER,
                    phivCircuitImportStatus
                        INTEGER
                }

            phivCircuitImportIf OBJECT-TYPE
                SYNTAX INTEGER
                ACCESS read-only
                STATUS mandatory
                DESCRIPTION
                    "The interface associated with the import routing 
                    filter."
                ::= { phivCircuitImportEntry 1 }

            phivCircuitImportAddr OBJECT-TYPE
                SYNTAX PhivAddr
                ACCESS read-only
                STATUS mandatory
                DESCRIPTION
                    "The address (node or area) to match against learned 
                    route entries to decide whether to import the entry 
                    to the routing database."
                ::= { phivCircuitImportEntry 2 }

            phivCircuitImportMask OBJECT-TYPE
                SYNTAX PhivAddr
                ACCESS read-only
                STATUS mandatory
                DESCRIPTION
                    "The mask which is ANDed with the address field as 
                    well as the route entries address to determine 
                    whether the address matches the route entry."
                ::= { phivCircuitImportEntry 3 }

            phivCircuitImportAction OBJECT-TYPE
                SYNTAX INTEGER { discard(1), accept(2) }
                ACCESS read-write
                STATUS mandatory
                DESCRIPTION
                    "The action to take if the address field along with 
                    the mask field matches the route entry."
                DEFVAL { accept }
                ::= { phivCircuitImportEntry 4 }

            phivCircuitImportStatus OBJECT-TYPE
                SYNTAX INTEGER { invalid(1), valid(2) }
                ACCESS read-write
                STATUS mandatory
                DESCRIPTION
                    "Setting to 'invalid' removes this import filter 
                    from the table. Setting to 'valid' has no effect."
                DEFVAL { valid }
                ::= { phivCircuitImportEntry 5 }


            -- the Phase IV Import Area Filters subgroup

            phivCircuitImportAreaTable OBJECT-TYPE
                SYNTAX SEQUENCE OF PhivCircuitImportAreaEntry
                ACCESS not-accessible
                STATUS mandatory
                DESCRIPTION
                    "A list of circuit import area filter entries."
                ::= { xPhivImportArea 1 }

            phivCircuitImportAreaEntry OBJECT-TYPE
                SYNTAX PhivCircuitImportAreaEntry
                ACCESS not-accessible
                STATUS mandatory
                DESCRIPTION
                    "Parameter values for an import area filter."
                INDEX { phivCircuitImportAreaIf,
                        phivCircuitImportAreaAddr,
                        phivCircuitImportAreaMask }
                ::= { phivCircuitImportAreaTable 1 }

            PhivCircuitImportAreaEntry ::=
                SEQUENCE {
                    phivCircuitImportAreaIf
                        INTEGER,
                    phivCircuitImportAreaAddr
                        PhivAddr,
                    phivCircuitImportAreaMask
                        PhivAddr,
                    phivCircuitImportAreaAction
                        INTEGER,
                    phivCircuitImportAreaStatus
                        INTEGER
                }

            phivCircuitImportAreaIf OBJECT-TYPE
                SYNTAX INTEGER
                ACCESS read-only
                STATUS mandatory
                DESCRIPTION
                    "The interface associated with the import area 
                    routing filter."
                ::= { phivCircuitImportAreaEntry 1 }

            phivCircuitImportAreaAddr OBJECT-TYPE
                SYNTAX PhivAddr
                ACCESS read-only
                STATUS mandatory
                DESCRIPTION
                    "The address (node or area) to match against learned 
                    route entries to decide whether to import the entry 
                    to the routing database."
                ::= { phivCircuitImportAreaEntry 2 }

            phivCircuitImportAreaMask OBJECT-TYPE
                SYNTAX PhivAddr
                ACCESS read-only
                STATUS mandatory
                DESCRIPTION
                    "The mask which is ANDed with the address field as 
                    well as the route entries address to determine 
                    whether the address matches the route entry."
                ::= { phivCircuitImportAreaEntry 3 }

            phivCircuitImportAreaAction OBJECT-TYPE
                SYNTAX INTEGER { discard(1), accept(2) }
                ACCESS read-write
                STATUS mandatory
                DESCRIPTION
                    "The action to take if the address field along with 
                    the mask field matches the route entry."
                DEFVAL { accept }
                ::= { phivCircuitImportAreaEntry 4 }

            phivCircuitImportAreaStatus OBJECT-TYPE
                SYNTAX INTEGER { invalid(1), valid(2) }
                ACCESS read-write
                STATUS mandatory
                DESCRIPTION
                    "Setting to 'invalid' removes this import area 
                    filter from the table.  Setting to 'valid' has no 
                    effect."
                DEFVAL { valid }
                ::= { phivCircuitImportAreaEntry 5 }


            -- the Phase IV Export Filters subgroup

            phivCircuitExportTable OBJECT-TYPE
                SYNTAX SEQUENCE OF PhivCircuitExportEntry
                ACCESS not-accessible
                STATUS mandatory
                DESCRIPTION
                    "A list of circuit export filter entries."
                ::= { xPhivExport 1 }

            phivCircuitExportEntry OBJECT-TYPE
                SYNTAX PhivCircuitExportEntry
                ACCESS not-accessible
                STATUS mandatory
                DESCRIPTION
                    "Parameter values for an export filter."
                INDEX { phivCircuitExportIf, phivCircuitExportAddr,
                        phivCircuitExportMask }
                ::= { phivCircuitExportTable 1 }

            PhivCircuitExportEntry ::=
                SEQUENCE {
                    phivCircuitExportIf
                        INTEGER,
                    phivCircuitExportAddr
                        PhivAddr,
                    phivCircuitExportMask
                        PhivAddr,
                    phivCircuitExportAction
                        INTEGER,
                    phivCircuitExportStatus
                        INTEGER
                }

            phivCircuitExportIf OBJECT-TYPE
                SYNTAX INTEGER
                ACCESS read-only
                STATUS mandatory
                DESCRIPTION
                    "The interface associated with the export routing 
                    filter."
                ::= { phivCircuitExportEntry 1 }

            phivCircuitExportAddr OBJECT-TYPE
                SYNTAX PhivAddr
                ACCESS read-only
                STATUS mandatory
                DESCRIPTION
                    "The address (node or area) to match against learned 
                    route entries to decide whether to export the entry 
                    to the routing database."
                ::= { phivCircuitExportEntry 2 }

            phivCircuitExportMask OBJECT-TYPE
                SYNTAX PhivAddr
                ACCESS read-only
                STATUS mandatory
                DESCRIPTION
                    "The mask which is ANDed with the address field as 
                    well as the route entries address to determine 
                    whether the address matches the route entry."
                ::= { phivCircuitExportEntry 3 }

            phivCircuitExportAction OBJECT-TYPE
                SYNTAX INTEGER { hide(1), advertise(2) }
                ACCESS read-write
                STATUS mandatory
                DESCRIPTION
                    "The action to take if the address field along with 
                    the mask field matches the route entry."
                DEFVAL { advertise }
                ::= { phivCircuitExportEntry 4 }

            phivCircuitExportStatus OBJECT-TYPE
                SYNTAX INTEGER { invalid(1), valid(2) }
                ACCESS read-write
                STATUS mandatory
                DESCRIPTION
                    "Setting to 'invalid' removes this export filter 
                    from the table.  Setting to 'valid' has no effect."
                DEFVAL { valid }
                ::= { phivCircuitExportEntry 5 }


            -- the Phase IV Export Area Filters subgroup

            phivCircuitExportAreaTable OBJECT-TYPE
                SYNTAX SEQUENCE OF PhivCircuitExportAreaEntry
                ACCESS not-accessible
                STATUS mandatory
                DESCRIPTION
                    "A list of circuit export area filter entries."
                ::= { xPhivExportArea 1 }

            phivCircuitExportAreaEntry OBJECT-TYPE
                SYNTAX PhivCircuitExportAreaEntry
                ACCESS not-accessible
                STATUS mandatory
                DESCRIPTION
                    "Parameter values for an export area filter."
                INDEX { phivCircuitExportAreaIf,
                        phivCircuitExportAreaAddr,
                        phivCircuitExportAreaMask }
                ::= { phivCircuitExportAreaTable 1 }

            PhivCircuitExportAreaEntry ::=
                SEQUENCE {
                    phivCircuitExportAreaIf
                        INTEGER,
                    phivCircuitExportAreaAddr
                        PhivAddr,
                    phivCircuitExportAreaMask
                        PhivAddr,
                    phivCircuitExportAreaAction
                        INTEGER,
                    phivCircuitExportAreaStatus
                        INTEGER
                }

            phivCircuitExportAreaIf OBJECT-TYPE
                SYNTAX INTEGER
                ACCESS read-only
                STATUS mandatory
                DESCRIPTION
                    "The interface associated with the export area 
                    routing filter."
                ::= { phivCircuitExportAreaEntry 1 }

            phivCircuitExportAreaAddr OBJECT-TYPE
                SYNTAX PhivAddr
                ACCESS read-only
                STATUS mandatory
                DESCRIPTION
                    "The address (node or area) to match against learned 
                    route entries to decide whether to export the entry 
                    to the routing database."
                ::= { phivCircuitExportAreaEntry 2 }

            phivCircuitExportAreaMask OBJECT-TYPE
                SYNTAX PhivAddr
                ACCESS read-only
                STATUS mandatory
                DESCRIPTION
                    "The mask which is ANDed with the address field as 
                    well as the route entries address to determine 
                    whether the address matches the route entry."
                ::= { phivCircuitExportAreaEntry 3 }

            phivCircuitExportAreaAction OBJECT-TYPE
                SYNTAX INTEGER { hide(1), advertise(2) }
                ACCESS read-write
                STATUS mandatory
                DESCRIPTION
                    "The action to take if the address field along with 
                    the mask field matches the route entry."
                DEFVAL { advertise }
                ::= { phivCircuitExportAreaEntry 4 }

            phivCircuitExportAreaStatus OBJECT-TYPE
                SYNTAX INTEGER { invalid(1), valid(2) }
                ACCESS read-write
                STATUS mandatory
                DESCRIPTION
                    "Setting to 'invalid' removes this export area 
                    filter from the table.  Setting to 'valid' has no 
                    effect."
                DEFVAL { valid }
                ::= { phivCircuitExportAreaEntry 5 }


            -- the Phase IV Filters subgroup

            phivCircuitFilterTable OBJECT-TYPE
                SYNTAX SEQUENCE OF PhivCircuitFilterEntry
                ACCESS not-accessible
                STATUS mandatory
                DESCRIPTION
                    "A list of circuit filter entries."
                ::= { xPhivFilter 1 }

            phivCircuitFilterEntry OBJECT-TYPE
                SYNTAX PhivCircuitFilterEntry
                ACCESS not-accessible
                STATUS mandatory
                DESCRIPTION
                    "Parameter values for a filter."
                INDEX { phivCircuitFilterIf,
                        phivCircuitFilterDstAddr,
                        phivCircuitFilterDstMask,
                        phivCircuitFilterSrcAddr,
                        phivCircuitFilterSrcMask }
                ::= { phivCircuitFilterTable 1 }

            PhivCircuitFilterEntry ::=
                SEQUENCE {
                    phivCircuitFilterIf
                        INTEGER,
                    phivCircuitFilterDstAddr
                        PhivAddr,
                    phivCircuitFilterDstMask
                        PhivAddr,
                    phivCircuitFilterSrcAddr
                        PhivAddr,
                    phivCircuitFilterSrcMask
                        PhivAddr,
                    phivCircuitFilterAction
                        INTEGER,
                    phivCircuitFilterStatus
                        INTEGER
                }

            phivCircuitFilterIf OBJECT-TYPE
                SYNTAX INTEGER
                ACCESS read-only
                STATUS mandatory
                DESCRIPTION
                    "The interface associated with the filter entry."
                ::= { phivCircuitFilterEntry 1 }

            phivCircuitFilterDstAddr OBJECT-TYPE
                SYNTAX PhivAddr
                ACCESS read-only
                STATUS mandatory
                DESCRIPTION
                    "The address (node or area) to match against the 
                    destination address of the packet to decide whether 
                    to forward the packet."
                ::= { phivCircuitFilterEntry 2 }

            phivCircuitFilterDstMask OBJECT-TYPE
                SYNTAX PhivAddr
                ACCESS read-only
                STATUS mandatory
                DESCRIPTION
                    "The mask which is ANDed with the destination 
                    address field and the packet's destination address 
                    to determine whether the address matches the 
                    packet's address."
                ::= { phivCircuitFilterEntry 3 }

            phivCircuitFilterSrcAddr OBJECT-TYPE
                SYNTAX PhivAddr
                ACCESS read-only
                STATUS mandatory
                DESCRIPTION
                    "The address (node or area) to match against the 
                    source address of the packet to decide whether to 
                    forward the packet."
                ::= { phivCircuitFilterEntry 4 }

            phivCircuitFilterSrcMask OBJECT-TYPE
                SYNTAX PhivAddr
                ACCESS read-only
                STATUS mandatory
                DESCRIPTION
                    "The mask which is ANDed with the source address 
                    field and the packet's source address to determine 
                    whether the address matches the packet's address."
                ::= { phivCircuitFilterEntry 5 }

            phivCircuitFilterAction OBJECT-TYPE
                SYNTAX INTEGER { discard(1), forward(2) }
                ACCESS read-write
                STATUS mandatory
                DESCRIPTION
                    "The action to take if the address fields along with 
                    the mask fields match the packet."
                DEFVAL { forward }
                ::= { phivCircuitFilterEntry 6 }

            phivCircuitFilterStatus OBJECT-TYPE
                SYNTAX INTEGER { invalid(1), valid(2) }
                ACCESS read-write
                STATUS mandatory
                DESCRIPTION
                    "Setting to 'invalid' removes this Filter filter 
                    from the table.  Setting to 'valid' has no effect."
                DEFVAL { valid }
                ::= { phivCircuitFilterEntry 7 }


            -- the Phase IV Traffic subgroup

            phivTrafficSort OBJECT-TYPE
                SYNTAX INTEGER { ready(1), execute(2) }
                ACCESS read-write
                STATUS mandatory
                DESCRIPTION
                    "Setting to 'execute' causes the most recent traffic 
                    information to be sorted into the phivTrafficTable. 
                    The sorting precedence is: decreasing percentage, 
                    increasing destination address, increasing source 
                    address, and increasing interface number.  Setting 
                    to 'ready' has no effect."
                ::= { xPhivTraffic 1 }

            phivTrafficTable OBJECT-TYPE
                SYNTAX SEQUENCE OF PhivTrafficEntry
                ACCESS not-accessible
                STATUS mandatory
                DESCRIPTION
                    "A list of traffic entries, sorted in the order 
                    specified by phivTrafficSort."
                ::= { xPhivTraffic 2 }

            phivTrafficEntry OBJECT-TYPE
                SYNTAX PhivTrafficEntry
                ACCESS not-accessible
                STATUS mandatory
                DESCRIPTION
                    "A traffic entry."
                INDEX { phivTrafficIndex }
                ::= { phivTrafficTable 1 }

            PhivTrafficEntry ::=
                SEQUENCE {
                    phivTrafficIndex
                        INTEGER,
                    phivTrafficPercent
                        INTEGER,
                    phivTrafficDst
                        PhivAddr,
                    phivTrafficSrc
                        PhivAddr,
                    phivTrafficIf
                        INTEGER
                }

            phivTrafficIndex OBJECT-TYPE
                SYNTAX INTEGER
                ACCESS read-only
                STATUS mandatory
                DESCRIPTION
                    "Identification of this traffic entry."
                ::= { phivTrafficEntry 1 }

            phivTrafficPercent OBJECT-TYPE
                SYNTAX INTEGER (0..1000)
                ACCESS read-only
                STATUS mandatory
                DESCRIPTION
                    "The percentage of total traffic that this traffic 
                    entry represents, in tenths of a percent."
                ::= { phivTrafficEntry 2 }

            phivTrafficDst OBJECT-TYPE
                SYNTAX PhivAddr
                ACCESS read-only
                STATUS mandatory
                DESCRIPTION
                    "The destination to which the traffic entry 
                    applies."
                ::= { phivTrafficEntry 3 }

            phivTrafficSrc OBJECT-TYPE
                SYNTAX PhivAddr
                ACCESS read-only
                STATUS mandatory
                DESCRIPTION
                    "The source to which the traffic entry applies."
                ::= { phivTrafficEntry 4 }

            phivTrafficIf OBJECT-TYPE
                SYNTAX INTEGER
                ACCESS read-only
                STATUS mandatory
                DESCRIPTION
                    "The inbound interface to which the traffic entry 
                    applies.  This value is the same as IfIndex."
                ::= { phivTrafficEntry 5 }


--
-- FILE: /users/sse/mibs/src/inReach/ir-ethernet-mib.mib
--

-- $Id: ir-ethernet-mib.mib,v 1.1 2002/06/27 15:40:56 sse Exp $


            xEthernet        OBJECT IDENTIFIER ::= { mrvInReachProductDivision 11 }

            -- This is the MIB module for MRV In-Reach Ethernet interfaces.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the Generic Ethernet group

            -- Implementation of this group is mandatory for all MRV In-Reach
            -- systems that have an Ethernet interface

            etherTable OBJECT-TYPE
                SYNTAX SEQUENCE OF EtherEntry
                ACCESS not-accessible
                STATUS mandatory
                DESCRIPTION
                    "A list of generic entries."
                ::= { xEthernet 1 }

            etherEntry OBJECT-TYPE
                SYNTAX EtherEntry
                ACCESS not-accessible
                STATUS mandatory
                DESCRIPTION
                    "Generic status and parameter values for an Ethernet 
                    interface."
                INDEX { etherIndex }
                ::= { etherTable 1 }

            EtherEntry ::=
                SEQUENCE {
                    etherIndex
                        INTEGER,
                    etherAlignmentErrors
                        Counter,
                    etherFCSErrors
                        Counter
                }

            etherIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherEntry 1 }

            etherAlignmentErrors OBJECT-TYPE
                SYNTAX Counter
                ACCESS read-only
                STATUS mandatory
                DESCRIPTION
                    "A count of frames received on a particular 
                    interface that are not an integral number of octets 
                    in length and do not pass the FCS check."
                ::= { etherEntry 2 }

            etherFCSErrors OBJECT-TYPE
                SYNTAX Counter
                ACCESS read-only
                STATUS mandatory
                DESCRIPTION
                    "A count of frames received on a particular 
                    interface that are an integral number of octets in 
                    length that do not pass the FCS check."
                ::= { etherEntry 3 }


            -- the Ethernet Transmit group

            -- Implementation of this group is mandatory for all MRV In-Reach
            -- systems that transmit messages on an Ethernet interface

            etherTxTable OBJECT-TYPE
                SYNTAX SEQUENCE OF EtherTxEntry
                ACCESS not-accessible
                STATUS mandatory
                DESCRIPTION
                    "A list of Ethernet transmit entries."
                ::= { xEthernet 2 }

            etherTxEntry OBJECT-TYPE
                SYNTAX EtherTxEntry
                ACCESS not-accessible
                STATUS mandatory
                DESCRIPTION
                    "Transmit status and parameter values for an 
                    Ethernet interface."
                INDEX { etherTxIndex }
                ::= { etherTxTable 1 }

            EtherTxEntry ::=
                SEQUENCE {
                    etherTxIndex
                        INTEGER,
                    etherTxSingleCollisionFrames
                        Counter,
                    etherTxMultipleCollisionFrames
                        Counter
                }

            etherTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherTxEntry 1 }

            etherTxSingleCollisionFrames OBJECT-TYPE
                SYNTAX Counter
                ACCESS read-only
                STATUS mandatory
                DESCRIPTION
                    "A count of successfully transmitted frames on a 
                    particular interface for which transmission is 
                    inhibited by exactly one collision.  A frame that is 
                    counted by an instance of this object is also 
                    counted by the corresponding instance of either the 
                    ifOutUcastPkts or ifOutNUcastPkts object and is not 
                    counted by the corresponding instance of the 
                    etherTxMultipleCollisionFrames object."
                ::= { etherTxEntry 2 }

            etherTxMultipleCollisionFrames OBJECT-TYPE
                SYNTAX Counter
                ACCESS read-only
                STATUS mandatory
                DESCRIPTION
                    "A count of successfully transmitted frames on a 
                    particular interface for which transmission is 
                    inhibited by more than one collision.  A frame that 
                    is counted by an instance of this object is also 
                    counted by the corresponding instance of either the 
                    ifOutUcastPkts or ifOutNUcastPkts object and is not 
                    counted by the corresponding instance of the 
                    etherTxSingleCollisionFrames object."
                ::= { etherTxEntry 3 }


            -- the Ethernet Multicast group

            -- Implementation of this group is optional;  it is
            -- appropriate for all MRV In-Reach systems on which the
            -- necessary monitoring is feasible

            etherMulticastTable OBJECT-TYPE
                SYNTAX SEQUENCE OF EtherMulticastEntry
                ACCESS not-accessible
                STATUS mandatory
                DESCRIPTION
                    "A list of etherMulticast entries."
                ::= { xEthernet 3 }

            etherMulticastEntry OBJECT-TYPE
                SYNTAX EtherMulticastEntry
                ACCESS not-accessible
                STATUS mandatory
                DESCRIPTION
                    "EtherMulticast status and parameter values for an 
                    Ethernet interface."
                INDEX { etherMulticastIndex }
                ::= { etherMulticastTable 1 }

            EtherMulticastEntry ::=
                SEQUENCE {
                    etherMulticastIndex
                        INTEGER,
                    etherMulticastBytesIn
                        Counter,
                    etherMulticastBytesOut
                        Counter
                }

            etherMulticastIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherMulticastEntry 1 }

            etherMulticastBytesIn OBJECT-TYPE
                SYNTAX Counter
                ACCESS read-only
                STATUS mandatory
                DESCRIPTION
                    "A count of frames successfully received on a 
                    particular interface and for which the destination 
                    address multicast bit was set.  Bytes that are 
                    counted by an instance of this object are also 
                    counted by the corresponding instance of the 
                    ifInOctets object."
                ::= { etherMulticastEntry 2 }

            etherMulticastBytesOut OBJECT-TYPE
                SYNTAX Counter
                ACCESS read-only
                STATUS mandatory
                DESCRIPTION
                    "A count of successfully frames successfully 
                    transmitted on a particular interface and for which 
                    the destination address multicast bit was set.  
                    Bytes that are counted by an instance of this object 
                    are also counted by the corresponding instance of 
                    the ifOutOctets object."
                ::= { etherMulticastEntry 3 }


            -- the Ethernet Extended Transmit group

            -- Implementation of this group is optional;  it is
            -- appropriate for all MRV In-Reach systems on which the
            -- necessary monitoring is feasible

            etherXTxTable OBJECT-TYPE
                SYNTAX SEQUENCE OF EtherXTxEntry
                ACCESS not-accessible
                STATUS mandatory
                DESCRIPTION
                    "A list of Ethernet extended transmit entries."
                ::= { xEthernet 4 }

            etherXTxEntry OBJECT-TYPE
                SYNTAX EtherXTxEntry
                ACCESS not-accessible
                STATUS mandatory
                DESCRIPTION
                    "Extended transmit status and parameter values for 
                    an Ethernet interface."
                INDEX { etherXTxIndex }
                ::= { etherXTxTable 1 }

            EtherXTxEntry ::=
                SEQUENCE {
                    etherXTxIndex
                        INTEGER,
                    etherXTxExcessiveCollisions
                        Counter
                }

            etherXTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherXTxEntry 1 }

            etherXTxExcessiveCollisions OBJECT-TYPE
                SYNTAX Counter
                ACCESS read-only
                STATUS mandatory
                DESCRIPTION
                    "A count of frames for which transmission on a 
                    particular interface fails due to excessive 
                    collisions."
                ::= { etherXTxEntry 2 }


--
-- FILE: /users/sse/mibs/src/inReach/ir-internet-mib.mib
--

-- $Id: ir-internet-mib.mib,v 1.1 2002/06/27 15:41:20 sse Exp $


            xInternetDep    OBJECT IDENTIFIER ::= { mrvInReachProductDivision 4 }
            xInternet       OBJECT IDENTIFIER ::= { mrvInReachProductDivision 10 }

            -- MRV In-Reach Internet subgroups

            xIp             OBJECT IDENTIFIER ::= { xInternet 1 }
            xTcp            OBJECT IDENTIFIER ::= { xInternet 2 }
            xSnmpAgent      OBJECT IDENTIFIER ::= { xInternet 3 }
            xDomainResolver OBJECT IDENTIFIER ::= { xInternet 4 }
            xSlip           OBJECT IDENTIFIER ::= { xInternet 5 }
            xTelnet         OBJECT IDENTIFIER ::= { xInternet 6 }
            xTn3270         OBJECT IDENTIFIER ::= { xInternet 7 }
            xKerberos       OBJECT IDENTIFIER ::= { xInternet 8 }
            xPortSecurity   OBJECT IDENTIFIER ::= { xInternet 9 }
            xXremote        OBJECT IDENTIFIER ::= { xInternet 10 }
            xRotary         OBJECT IDENTIFIER ::= { xInternet 11 }
            xEgp            OBJECT IDENTIFIER ::= { xInternet 12 }
            xOspf           OBJECT IDENTIFIER ::= { xInternet 13 }
            xRouterIp       OBJECT IDENTIFIER ::= { xInternet 14 }
            xRouterUdp      OBJECT IDENTIFIER ::= { xInternet 15 }
            xRouterPolicy   OBJECT IDENTIFIER ::= { xInternet 16 }
            -- number 17 reserved
            xRip            OBJECT IDENTIFIER ::= { xInternet 18 }
            xlpd            OBJECT IDENTIFIER ::= { xInternet 19 }
            xSecurID        OBJECT IDENTIFIER ::= { xInternet 20 }
            -- numbers 21, 22 reserved
            xSsh            OBJECT IDENTIFIER ::= { xInternet 23 }


            -- This is a MIB module for all MRV Communications systems that
            -- implement IP.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the IP group

            -- Implementation of this group is mandatory for all MRV In-Reach
            -- systems that implement IP

            ipGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xIp 1 }

            ipGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xIp 2 }

            ipAutoSubnetMask OBJECT-TYPE
                SYNTAX INTEGER { disabled(1), enabled(2) }
                ACCESS read-write
                STATUS deprecated
                DESCRIPTION
                    "A control for automatic determination of subnet 
                    mask.  'disabled' indicates the system must use the 
                    mask as configured by the network manager.  
                    'enabled' indicates that the system is to 
                    automatically change the subnet mask when the 
                    system's Internet address is changed.  Corresponds 
                    directly to SERVER INTERNET SUBNET MASK 
                    AUTOCONFIGURE and the value labeled 'Subnet Mask 
                    Autoconfigure:' in the SERVER INTERNET 
                    CHARACTERISTICS display."
                ::= { xIp 3 }

            ipReassembly OBJECT-TYPE
                SYNTAX INTEGER { disabled(1), enabled(2) }
                ACCESS read-write
                STATUS mandatory
                DESCRIPTION
                    "A control for reassembly of IP fragments.  
                    Corresponds directly to SERVER INTERNET REASSEMBLY 
                    and the value labeled 'Reassembly:' in the SERVER 
                    INTERNET CHARACTERISTICS display."
                ::= { xIp 4 }

            ipFragmentsQueuedHigh OBJECT-TYPE
                SYNTAX Gauge
                ACCESS read-only
                STATUS mandatory
                DESCRIPTION
                    "Highest number of IP fragments queued."
                ::= { xIp 5 }

            ipFragmentsQueuedCurrent OBJECT-TYPE
                SYNTAX Gauge
                ACCESS read-only
                STATUS mandatory
                DESCRIPTION
                    "Current number of IP fragments queued."
                ::= { xIp 6 }

            ipGenAdExtTable OBJECT-TYPE
                SYNTAX SEQUENCE OF IpGenAdExtEntry
                ACCESS not-accessible
                STATUS mandatory
                DESCRIPTION
                    "Table of additional fields indexed by local IP 
                    address.  An entry in this table is created or 
                    deleted when an entry in the MIB-II ipAddrTable is 
                    created or deleted.  Although MIB-II specifies the 
                    ipAddrTable as read-only, MRV In-Reach implementations 
                    typically implement it as read-write to support 
                    modification of local IP addresses, network masks, 
                    and such."
                ::= { xIp 7 }

            ipARPTimeout OBJECT-TYPE
                SYNTAX INTEGER (1..255)
                ACCESS read-write
                STATUS mandatory 
                DESCRIPTION
                    "A control to set the length of time in minutes 
                    before an unused ARP entry is purged from the ARP 
                    table. The default is 60 minutes. Corresponds
                    directly to the value labeled 'Translation Table TTL'
                    in the SERVER INTERNET CHARACTERISTICS display."
                ::= { xIp 8 } 

            ipGatewayPingInterval OBJECT-TYPE
                SYNTAX INTEGER (1..300)
                ACCESS read-write
                STATUS mandatory 
                DESCRIPTION
                    "A control to set the interval of time in seconds
                    between successive pings to the primary gateway
                    so as to determine its status.
                    The default is 60 seconds. Corresponds
                    directly to the value labeled 'Gateway Timeout'
                    in the SERVER INTERNET CHARACTERISTICS display."
                ::= { xIp 9 } 

 	ipConfigureBootp OBJECT-TYPE
		SYNTAX INTEGER { disabled(1), enabled(2) }
		ACCESS read-write
		STATUS mandatory
		DESCRIPTION
		    "Control to use the BOOTP protocol upon startup to learn
                     the unit's own internet address, subnet mask, primary and 
                     secondary gateway servers, domain name servers, time 
                     server and domain name."
		DEFVAL { enabled }
		::= { xIp 11 }

            -- the Generic Address Extensions table

            ipGenAdExtEntry OBJECT-TYPE
                SYNTAX IpGenAdExtEntry
                ACCESS not-accessible
                STATUS mandatory
                DESCRIPTION
                    "A particular entry."
                INDEX { ipAdEntAddr }
                ::= { ipGenAdExtTable 1 }

            IpGenAdExtEntry ::=
                SEQUENCE {
                    ipGenAdEntExtType
                        INTEGER,
                    ipGenAdEntExtBroadcast
                        IpAddress
                }

            ipGenAdEntExtType OBJECT-TYPE
                SYNTAX INTEGER { primary(1), rotary(2), slip(3),
                                 ppp(4) }
                ACCESS read-write
                STATUS mandatory
                DESCRIPTION
                    "The way this local IP address is used, which may 
                    imply alternate, more intuitive ways to set it.

                    primary   general purpose for ordinary use
                    rotary    identificaton for rotary selection
                    slip      use for SLIP connection
                    ppp       use for PPP connection
                    "
                DEFVAL { primary }
                ::= { ipGenAdExtEntry 1 }

            ipGenAdEntExtBroadcast OBJECT-TYPE
                SYNTAX IpAddress
                ACCESS read-write
                STATUS mandatory
                DESCRIPTION
                    "Outgoing IP broadcast address associated with this 
                    local address.  Value may be confined to logical 
                    compatibility with associated network mask."
                DEFVAL { 'ffffffff'h }    -- 255.255.255.255
                ::= { ipGenAdExtEntry 2 }


            -- the TCP group

            -- Implementation of this group is mandatory for all MRV In-Reach
            -- systems that implement TCP

            -- scalar parameters follow Port table

            -- the TCP Character Port table

            tcpPortTable OBJECT-TYPE
                SYNTAX SEQUENCE OF TcpPortEntry
                ACCESS not-accessible
                STATUS mandatory
                DESCRIPTION
                    "A list of TCP character port entries."
                ::= { xTcp 1 }

            tcpPortEntry OBJECT-TYPE
                SYNTAX TcpPortEntry
                ACCESS not-accessible
                STATUS mandatory
                DESCRIPTION
                    "TCP parameter values for a character port."
                INDEX { tcpPortIndex }
                ::= { tcpPortTable 1 }

            TcpPortEntry ::=
                SEQUENCE {
                    tcpPortIndex
                        INTEGER,
                    tcpPortConnectByAddress
                        INTEGER,
                    tcpPortWindowSize
                        INTEGER,
                    tcpPortKeepAliveLimit
                        INTEGER
                }

            tcpPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tcpPortEntry 1 }

            tcpPortConnectByAddress OBJECT-TYPE
                SYNTAX INTEGER { disabled(1), enabled(2) }
                ACCESS read-write
                STATUS mandatory
                DESCRIPTION
                    "A control for requesting outgoing connection by 
                    internet address.  'disabled' indicates outgoing 
                    connections must be by Domain name.  'enabled' 
                    indicates that outgoing connections may be requested 
                    by internet address.  Corresponds directly to PORT 
                    INTERNET CONNECTIONS and the presence of the label 
                    'Internet Connections' following the label 'Enabled 
                    Characteristics:' in the PORT CHARACTERISTICS 
                    display."
                ::= { tcpPortEntry 2 }

            tcpPortWindowSize OBJECT-TYPE
                SYNTAX INTEGER (64..8192)
                ACCESS read-write
                STATUS mandatory
                DESCRIPTION
                    "Size of the TCP window for TCP connections on the 
                    port.  Corresponds directly to PORT INTERNET TCP 
                    WINDOW SIZE and the value labeled 'TCP Window Size:' 
                    in the PORT ALTERNATE CHARACTERISTICS display."
                ::= { tcpPortEntry 3 }

            tcpPortKeepAliveLimit OBJECT-TYPE
                SYNTAX INTEGER (0..30)
                ACCESS read-write
                STATUS mandatory
                DESCRIPTION
                    "Number of minutes to maintain a TCP connection 
                    without response to keep-alive communication.  A 
                    value of zero indicates no limit."
                ::= { tcpPortEntry 4 }

            -- additional scalar parameters

            tcpResequencing OBJECT-TYPE
                SYNTAX INTEGER { disabled(1), enabled(2) }
                ACCESS read-write
                STATUS mandatory
                DESCRIPTION
                    "A control for keeping TCP messages received 
                    out-of-order to resequence them before using them.   
                    Corresponds directly to SERVER INTERNET TCP 
                    RESEQUENCING and the value labeled 'Resequencing:' 
                    in the SERVER INTERNET CHARACTERISTICS display."
                ::= { xTcp 2 }

            tcpQueuedSegs OBJECT-TYPE
                SYNTAX Gauge
                ACCESS read-only
                STATUS mandatory
                DESCRIPTION
                    "Number of TCP segments in the TCP receive queues.  
                    Corresponds directly to the value labeled 'TCP 
                    Packets Queued:' in the SERVER INTERNET COUNTERS 
                    display."
                ::= { xTcp 3 }

            tcpDiscardSegs OBJECT-TYPE
                SYNTAX Counter
                ACCESS read-only
                STATUS mandatory
                DESCRIPTION
                    "Number of TCP segments discarded due to exceeding 
                    the TCP receive queue limit.  Corresponds directly 
                    to the value labeled 'TCP Packets Discarded:' in the 
                    SERVER INTERNET COUNTERS display."
                ::= { xTcp 4 }

            tcpConnectTimer OBJECT-TYPE
                SYNTAX INTEGER (4..32)
                ACCESS read-write
                STATUS mandatory
                DESCRIPTION
                    "Number of seconds to attempt a TCP connection 
                    without a response from the other side. The default 
                    value is 32 seconds.  Corresponds directly to the 
                    SERVER INTERNET TCP CONNECT TIMER and the value 
                    labeled 'TCP Connect Timer' in the SERVER INTERNET 
                    CHARACTERISTICS display"
                ::= { xTcp 5 }

            tcpLocalPortBase OBJECT-TYPE
                SYNTAX INTEGER (1..32767)
                ACCESS read-write
                STATUS mandatory
                DESCRIPTION
                    "The value for port 0's tcp source port number."
                ::= { xTcp 6 }

            tcpLocalPortIncrement OBJECT-TYPE
                SYNTAX INTEGER (1..1024)
                ACCESS read-write
                STATUS mandatory
                DESCRIPTION
                    "The value by which the tcp source port number
                    increases for each port greater than port 0."
                ::= { xTcp 7 }

            tcpRoutingTblSz OBJECT-TYPE
                SYNTAX INTEGER (64..512)
                ACCESS read-write
                STATUS mandatory 
                DESCRIPTION
                    "A control to set the size of the working routing table.
                    The default is the current size of the table (64)."
                ::= {xTcp 8  } 

            tcpDataSendDelay OBJECT-TYPE
                SYNTAX INTEGER (0..3000)
                ACCESS read-write
                STATUS mandatory 
                DESCRIPTION
                    "A control to delay for the specified number of 10
                     millisecond ticks before sending the userdata string
                     over the telnet connection."
                DEFVAL { 50 }
                ::= {xTcp 9  } 

             tcpAckDelay OBJECT-TYPE
                SYNTAX INTEGER { disabled(1), enabled(2) }
                ACCESS read-write
                STATUS mandatory
                DESCRIPTION
                    "A Control to prevent sending a TCP ACK when we
                     we change TCP window size."
                DEFVAL { disabled }
                ::= {xTcp 10 }

             tcpRetransmitMin OBJECT-TYPE
                SYNTAX INTEGER (600..3000)
                ACCESS read-write
                STATUS mandatory
                DESCRIPTION
                    "Number of milliseconds for the initial TCP Retransmit
                     timer. This is the time at which a TCP session will
                     initially retransmit unacknowledged packets."
                DEFVAL { 640 }
                ::= {xTcp 11 }


             -- the SNMP Agent group

            -- Implementation of this group is mandatory for all MRV In-Reach
            -- systems that implement SNMP

            snmpAgentGetCommunity OBJECT-TYPE
                SYNTAX DisplayString (SIZE (0..32))
                ACCESS read-write
                STATUS mandatory
                DESCRIPTION
                    "The SNMP community name allowed to perform 
                    get-requests or get-next requests to this agent.  
                    Use of this value is case-insensitive.  If the size 
                    is 0, the agent does not check the community name 
                    for these operations.  Corresponds directly to 
                    SERVER INTERNET SNMP GET COMMUNITY and the value 
                    labeled 'Get Community:' in the SERVER INTERNET SNMP 
                    CHARACTERISTICS display."
                ::= { xSnmpAgent 1 }

            snmpAgentSetCommunity OBJECT-TYPE
                SYNTAX DisplayString (SIZE (0..32))
                ACCESS read-write
                STATUS mandatory
                DESCRIPTION
                    "The SNMP community name allowed to perform 
                    set-requests to this agent.  Use of this value is 
                    case-insensitive.  If the size is 0, the agent does 
                    not check the community name for these operations.  
                    Corresponds directly to SERVER INTERNET SNMP SET 
                    COMMUNITY and the value labeled 'Set Community:' in 
                    the SERVER INTERNET SNMP CHARACTERISTICS display."
                ::= { xSnmpAgent 2 }

            snmpAgentTrapCommunity OBJECT-TYPE
                SYNTAX DisplayString (SIZE (0..32))
                ACCESS read-write
                STATUS mandatory
                DESCRIPTION
                    "The SNMP community name sent in traps from this 
                    agent.  Use of this value preserves case.  
                    Corresponds directly to SERVER INTERNET SNMP TRAP 
                    COMMUNITY and the value labeled 'Trap Community:' in 
                    the SERVER INTERNET SNMP CHARACTERISTICS display."
                ::= { xSnmpAgent 3 }

            snmpAgentGetClientNumber OBJECT-TYPE
                SYNTAX INTEGER
                ACCESS read-only
                STATUS mandatory
                DESCRIPTION
                    "The number of client source addresses allowed to 
                    perform get-requests or get-next requests to this 
                    agent.  If the value is 0, the agent does not check 
                    source address for these operations.  Corresponds 
                    indirectly to the values labeled 'Get Client n:' in 
                    the SERVER INTERNET SNMP CHARACTERISTICS display."
                ::= { xSnmpAgent 4 }

            snmpAgentSetClientNumber OBJECT-TYPE
                SYNTAX INTEGER
                ACCESS read-only
                STATUS mandatory
                DESCRIPTION
                    "The number of client source addresses allowed to 
                    perform set-requests to this agent.  If the value is 
                    0, the agent does not check source address for these 
                    operations.  Corresponds indirectly to the values 
                    labeled 'Set Client n:' in the SERVER INTERNET SNMP 
                    CHARACTERISTICS display."
                ::= { xSnmpAgent 5 }

            snmpAgentTrapClientNumber OBJECT-TYPE
                SYNTAX INTEGER
                ACCESS read-only
                STATUS mandatory
                DESCRIPTION
                    "The number of client source addresses to which this 
                    agent sends traps.  If the value is 0, the agent 
                    does not perform this operation.  Corresponds 
                    indirectly to the values labeled 'Trap Client n:' in 
                    the SERVER INTERNET SNMP CHARACTERISTICS display."
                ::= { xSnmpAgent 6 }

            -- More individual objects follow 
            -- the Get Client table

            getClientTable OBJECT-TYPE
                SYNTAX SEQUENCE OF GetClientEntry
                ACCESS not-accessible
                STATUS mandatory
                DESCRIPTION
                    "A list of get client entries.  The number of 
                    entries is given by the value of 
                    snmpAgentGetClientNumber."
                ::= { xSnmpAgent 7 }

            getClientEntry OBJECT-TYPE
                SYNTAX GetClientEntry
                ACCESS not-accessible
                STATUS mandatory
                DESCRIPTION
                    "Parameter values for a get client."
                INDEX { getClientIndex }
                ::= { getClientTable 1 }

            GetClientEntry ::=
                SEQUENCE {
                    getClientIndex
                        INTEGER,
                    getClientEntryStatus
                        INTEGER,
                    getClientAddressType
                        AddressType,
                    getClientAddress
                        OCTET STRING
                }

            getClientIndex OBJECT-TYPE
                SYNTAX INTEGER
                ACCESS read-only
                STATUS mandatory
                DESCRIPTION
                    "Identification of a get client entry.  Corresponds 
                    directly to the number in the label 'Get Client n:' 
                    in the SERVER INTERNET SNMP CHARACTERISTICS 
                    display."
                ::= { getClientEntry 1 }

            getClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { getClientEntry 2 }

            getClientAddressType OBJECT-TYPE
                SYNTAX AddressType
                ACCESS read-write
                STATUS mandatory
                DESCRIPTION
                    "The type of network address contained in 
                    getClientAddress.  'unknown' means no address has 
                    been defined.  'other' means no other type value 
                    applies.  'ip' is an Internet IP address.  
                    'ethernet' is an 802.3 MAC address.  If 
                    getClientAddressType does not accompany 
                    getClientAddress in a set request, the default type 
                    is 'ip'.  Corresponds indirectly to the address 
                    value labeled 'Get Client n:' in the SERVER INTERNET 
                    SNMP CHARACTERISTICS display."
                DEFVAL { unknown }
                ::= { getClientEntry 3 }

            getClientAddress OBJECT-TYPE
                SYNTAX OCTET STRING
                ACCESS read-write
                STATUS mandatory
                DESCRIPTION
                    "The client's network address.  If 
                    getClientAddressType does not accompany 
                    getClientAddress in a set request, the default type 
                    is 'ip'.  Corresponds directly to the address value 
                    labeled 'Get Client n:' in the SERVER INTERNET SNMP 
                    CHARACTERISTICS display."
                DEFVAL { "" }  -- zero length
                ::= { getClientEntry 4 }


            -- the Set Client table

            setClientTable OBJECT-TYPE
                SYNTAX SEQUENCE OF SetClientEntry
                ACCESS not-accessible
                STATUS mandatory
                DESCRIPTION
                    "A list of set client entries.  The number of 
                    entries is given by the value of 
                    snmpAgentSetClientNumber."
                ::= { xSnmpAgent 8 }

            setClientEntry OBJECT-TYPE
                SYNTAX SetClientEntry
                ACCESS not-accessible
                STATUS mandatory
                DESCRIPTION
                    "Parameter values for a set client."
                INDEX { setClientIndex }
                ::= { setClientTable 1 }

            SetClientEntry ::=
                SEQUENCE {
                    setClientIndex
                        INTEGER,
                    setClientEntryStatus
                        INTEGER,
                    setClientAddressType
                        AddressType,
                    setClientAddress
                        OCTET STRING
                }

            setClientIndex OBJECT-TYPE
                SYNTAX INTEGER
                ACCESS read-only
                STATUS mandatory
                DESCRIPTION
                    "Identification of a set client entry.  Corresponds 
                    directly to the number in the label 'Set Client n:' 
                    in the SERVER INTERNET SNMP CHARACTERISTICS 
                    display."
                ::= { setClientEntry 1 }

            setClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { setClientEntry 2 }

            setClientAddressType OBJECT-TYPE
                SYNTAX AddressType
                ACCESS read-write
                STATUS mandatory
                DESCRIPTION
                    "The type of network address contained in 
                    setClientAddress.  'unknown' means no address has 
                    been defined.  'other' means no other type value 
                    applies.  'ip' is an Internet IP address.  
                    'ethernet' is an 802.3 MAC address.  If 
                    setClientAddressType does not accompany 
                    setClientAddress in a set request, the default type 
                    is 'ip'.  Corresponds indirectly to the address 
                    value labeled 'Set Client n:' in the SERVER INTERNET 
                    SNMP CHARACTERISTICS display."
                DEFVAL { unknown }
                ::= { setClientEntry 3 }

            setClientAddress OBJECT-TYPE
                SYNTAX OCTET STRING
                ACCESS read-write
                STATUS mandatory
                DESCRIPTION
                    "The client's network address.  When setting this 
                    value, the requester must supply 
                    setClientAddressType.  If setClientAddressType does 
                    not accompany setClientAddress in a set request, the 
                    default type is 'ip'.  Corresponds directly to the 
                    address value labeled 'Set Client n:' in the SERVER 
                    INTERNET SNMP CHARACTERISTICS display."
                DEFVAL { "" }  -- zero length
                ::= { setClientEntry 4 }


            -- the Trap Client table

            trapClientTable OBJECT-TYPE
                SYNTAX SEQUENCE OF TrapClientEntry
                ACCESS not-accessible
                STATUS mandatory
                DESCRIPTION
                    "A list of trap client entries.  The number of 
                    entries is given by the value of 
                    snmpAgentTrapClientNumber."
                ::= { xSnmpAgent 9 }

            trapClientEntry OBJECT-TYPE
                SYNTAX TrapClientEntry
                ACCESS not-accessible
                STATUS mandatory
                DESCRIPTION
                    "Parameter values for a trap client."
                INDEX { trapClientIndex }
                ::= { trapClientTable 1 }

            TrapClientEntry ::=
                SEQUENCE {
                    trapClientIndex
                        INTEGER,
                    trapClientEntryStatus
                        INTEGER,
                    trapClientAddressType
                        AddressType,
                    trapClientAddress
                        OCTET STRING
                }

            trapClientIndex OBJECT-TYPE
                SYNTAX INTEGER
                ACCESS read-only
                STATUS mandatory
                DESCRIPTION
                    "Identification of a trap client entry.  Corresponds 
                    directly to the number in the label 'Trap Client n:' 
                    in the SERVER INTERNET SNMP CHARACTERISTICS 
                    display."
                ::= { trapClientEntry 1 }

            trapClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { trapClientEntry 2 }

            trapClientAddressType OBJECT-TYPE
                SYNTAX AddressType
                ACCESS read-write
                STATUS mandatory
                DESCRIPTION
                    "The type of network address contained in 
                    trapClientAddress.  'unknown' means no address has 
                    been defined.  'other' means no other type value 
                    applies.  'ip' is an Internet IP address.  
                    'ethernet' is an 802.3 MAC address.  If 
                    trapClientAddressType does not accompany 
                    trapClientAddress in a set request, the default type 
                    is 'ip'.  Corresponds indirectly to the address 
                    value labeled 'Trap Client n:' in the SERVER 
                    INTERNET SNMP CHARACTERISTICS display."
                DEFVAL { unknown }
                ::= { trapClientEntry 3 }

            trapClientAddress OBJECT-TYPE
                SYNTAX OCTET STRING
                ACCESS read-write
                STATUS mandatory
                DESCRIPTION
                    "The client's network address.  When setting this 
                    value, the requester must supply 
                    trapClientAddressType.  If trapClientAddressType 
                    does not accompany trapClientAddress in a set 
                    request, the default type is 'ip'.  Corresponds 
                    directly to the address value labeled 'Trap Client 
                    n:' in the SERVER INTERNET SNMP CHARACTERISTICS 
                    display."
                DEFVAL { "" }  -- zero length
                ::= { trapClientEntry 4 }


            -- Additional individual SNMP agent objects

            snmpAgentAuthFailureAddress OBJECT-TYPE
                SYNTAX TypedAddress
                ACCESS read-only
                STATUS mandatory
                DESCRIPTION
                    "The address of the client to most recently fail 
                    SNMP authorization."
                ::= { xSnmpAgent 10 }

            snmpAgentCommunityAuthenticationAlways OBJECT-TYPE
                SYNTAX INTEGER { disabled(1), enabled(2) }
                ACCESS read-write
                STATUS mandatory
                DESCRIPTION
                  "When enabled, indicates that community string authentication
                   is done always for Gets, Sets, and GetNexts. When disabled,
                   community string authentication is done once; but bypassed
                   on subsequent Gets, Sets or GetNexts from the same address."
                DEFVAL { enabled }
                ::= { xSnmpAgent 14 }

            snmpAgentTrapClientPingHost1 OBJECT-TYPE
                SYNTAX INTEGER { disabled(1), enabled(2) }
                ACCESS read-only
                STATUS mandatory
                DESCRIPTION
                    "Configures the first trap client in the trapClientTable
                     as a ping host. The InReach server will poll the ping 
                     host at a specified interval to determine connectivity.
                     This feature is mutually exclusive with 
                     snmpAgentTrapClientQuerySourceHost1 and 
                     snmpAgentTrapClientQuerySourceHost2."                     
                DEFVAL { disabled }
                ::= { xSnmpAgent 15 }

            snmpAgentTrapClientPingHost2 OBJECT-TYPE
                SYNTAX INTEGER { disabled(1), enabled(2) }
                ACCESS read-only
                STATUS mandatory
                DESCRIPTION
                    "Configures the second trap client in the trapClientTable
                     as a ping host. The InReach server will poll the ping
                     host at a specified interval to determine connectivity.
                     This feature is mutually exclusive with 
                     snmpAgentTrapClientQuerySourceHost1 and 
                     snmpAgentTrapClientQuerySourceHost2."                     

                DEFVAL { disabled }
                ::= { xSnmpAgent 16 }

            snmpAgentTrapClientPingHost1PollInterval OBJECT-TYPE
                SYNTAX INTEGER (1..65535)
                ACCESS read-only
                STATUS mandatory
                DESCRIPTION
                    "Indicates the time in seconds between polling the 
                     first ping host."
                DEFVAL { 60 }
                ::= { xSnmpAgent 17 }

            snmpAgentTrapClientPingHost2PollInterval OBJECT-TYPE
                SYNTAX INTEGER (1..65535)
                ACCESS read-only
                STATUS mandatory
                DESCRIPTION
                    "Indicates the time in seconds between polling the 
                     second ping host."
                DEFVAL { 60 }
                ::= { xSnmpAgent 18 }

            snmpAgentTrapClientPingHost1PollRetries OBJECT-TYPE
                SYNTAX INTEGER (1..255)
                ACCESS read-only
                STATUS mandatory
                DESCRIPTION
                    "Indicates the maximum number of retries when polling
                     the first ping host before concluding that connectivity
                     is lost. When network connectivity is lost, PPP dial
                     backup procedures to a backup host are initiated."
                DEFVAL { 3 }
                ::= { xSnmpAgent 19 }

            snmpAgentTrapClientPingHost2PollRetries OBJECT-TYPE
                SYNTAX INTEGER (1..255)
                ACCESS read-only
                STATUS mandatory
                DESCRIPTION
                    "Indicates the maximum number of retries when polling
                     the second ping host before concluding that connectivity
                     is lost.  When network connectivity is lost, PPP dial
                     backup procedures to a backup host are initiated."
                DEFVAL { 3 }
                ::= { xSnmpAgent 20 }

            snmpAgentTrapClientQuerySourceHost1 OBJECT-TYPE
                SYNTAX INTEGER { disabled(1), enabled(2) }
                ACCESS read-only
                STATUS mandatory
                DESCRIPTION
                    "Configures the first trap client in the trapClientTable as
                     a query source host. When enabled the InReach server will
                     monitor incoming get-, get-next- and set-requests from
                     this host as an indicator of connectivity. This feature 
                     is mutually exclusive with snmpAgentTrapClientPingHost1
                     and snmpAgentTrapClientPingHost2."
                DEFVAL { disabled }
                ::= { xSnmpAgent 21 }

            snmpAgentTrapClientQuerySourceHost2 OBJECT-TYPE
                SYNTAX INTEGER { disabled(1), enabled(2) }
                ACCESS read-only
                STATUS mandatory
                DESCRIPTION
                    "Configures the second trap client in the trapClientTable 
                     as a query source host. When enabled the InReach server
                     will monitor incoming get-, get-next- and set-requests 
                     from this host as an indicator of connectivity. This 
                     feature is mutually exclusive with
                     snmpAgentTrapClientPingHost1 and
                     snmpAgentTrapClientPingHost2."
                DEFVAL { disabled }
                ::= { xSnmpAgent 22 }

            snmpAgentTrapClientQuerySourceHost1Timeout OBJECT-TYPE
                SYNTAX INTEGER (1..65535)
                ACCESS read-only
                STATUS mandatory
                DESCRIPTION
                    "Indicates the time in seconds between SNMP queries
                     from the first query source host before timing out
                     and considering connectivity lost to that host. When 
                     network connectivity is lost, PPP dial backup procedures
                     to a backup host are initiated."
                DEFVAL { 60 }
                ::= { xSnmpAgent 23 }

            snmpAgentTrapClientQuerySourceHost2Timeout OBJECT-TYPE
                SYNTAX INTEGER (1..65535)
                ACCESS read-only
                STATUS mandatory
                DESCRIPTION
                    "Indicates the time in seconds between SNMP queries
                     from the first query source host before timing out
                     and considering connectivity lost to that host. When 
                     network connectivity is lost, PPP dial backup procedures
                     to a backup host are initiated."
                DEFVAL { 60 }
                ::= { xSnmpAgent 24 }


            -- the Domain Resolver group

            -- Implementation of this group is mandatory for all MRV In-Reach
            -- systems that implement Domain name resolution

            domainResolverSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { xDomainResolver 1 }

            domainResolverAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { xDomainResolver 2 }

            domainResolverAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { xDomainResolver 3 }

            domainResolverTtl OBJECT-TYPE
                SYNTAX INTEGER (0..168)
                ACCESS read-write
                STATUS mandatory
                DESCRIPTION
                    "The number of hours to keep received Domain 
                    information.  Corresponds directly to SERVER 
                    INTERNET DOMAIN TTL and the value labeled ' Domain 
                    TTL:' in the SERVER INTERNET CHARACTERISTICS 
                    display."
                ::= { xDomainResolver 4 }

            domainResolverNameNumber OBJECT-TYPE
                SYNTAX INTEGER
                ACCESS read-only
                STATUS mandatory
                DESCRIPTION
                    "The number of Domain name mappings in this system's 
                    name cache."
                ::= { xDomainResolver 5 }


            -- the Name table

            nameTable OBJECT-TYPE
                SYNTAX SEQUENCE OF NameEntry
                ACCESS not-accessible
                STATUS mandatory
                DESCRIPTION
                    "A list of Domain name entries.  The number of 
                    entries is given by the value of 
                    domainResolverNameNumber."
                ::= { xDomainResolver 6 }

            nameEntry OBJECT-TYPE
                SYNTAX NameEntry
                ACCESS not-accessible
                STATUS mandatory
                DESCRIPTION
                    "Parameter values for a Domain name."
                INDEX { nameName, nameAddress }
                ::= { nameTable 1 }

            NameEntry ::=
                SEQUENCE {
                    nameName
                        DisplayString,
                    nameAddress
                        IpAddress,
                    nameStatus
                        INTEGER,
                    nameSource
                        INTEGER,
                    nameTtl
                        INTEGER
                }

            nameName OBJECT-TYPE
                SYNTAX DisplayString (SIZE (1..50))
                ACCESS read-only
                STATUS mandatory
                DESCRIPTION
                    "A fully qualified domain name.  Corresponds 
                    directly to the value labeled 'Domain Name' in the 
                    DOMAIN display."
                ::= { nameEntry 1 }

            nameAddress OBJECT-TYPE
                SYNTAX IpAddress
                ACCESS read-only
                STATUS mandatory
                DESCRIPTION
                    "An Internet address corresponding to the Domain 
                    name.  Corresponds directly to the value labeled 
                    'Internet Address' in the DOMAIN display."
                ::= { nameEntry 2 }

            nameStatus OBJECT-TYPE
                SYNTAX INTEGER { invalid(1), valid(2) }
                ACCESS read-write
                STATUS mandatory
                DESCRIPTION
                    "The status of the entry.  Set to 'invalid' to 
                    remove the entry, which corresponds directly to the 
                    PURGE DOMAIN command.  Actual removal of the entry 
                    is implementation specific."
                ::= { nameEntry 3 }

            nameSource OBJECT-TYPE
                SYNTAX INTEGER { manager(1), primary(2), secondary(3),
                                 rwho(4) }
                ACCESS read-only
                STATUS mandatory
                DESCRIPTION
                    "Source of this entry.  The value meanings are:

                    local       defined by manager (LOCAL)
                    primary     obtained from a primary name server
                    secondary   obtained from a secondary name server
                    rwho        obtained from rwho

                    Corresponds directly to the value labeled 'Source' 
                    in the DOMAIN display."
                ::= { nameEntry 4 }

            nameTtl OBJECT-TYPE
                SYNTAX INTEGER
                ACCESS read-only
                STATUS mandatory
                DESCRIPTION
                    "The number of minutes remaining in the entry's time 
                    to live.  Corresponds directly to the value labeled 
                    'TTL' in the DOMAIN display."
                ::= { nameEntry 5 }


            domainResolverPpp OBJECT IDENTIFIER ::= { xDomainResolver 7 }
            
            domainResolverPppPrimaryServer OBJECT-TYPE
                SYNTAX IpAddress
                ACCESS read-write
                STATUS mandatory
                DESCRIPTION
                    "The internet address of the primary Domain Name Server to
                     use in PPP IPCP negotiations. A value of 0.0.0.0 indicates
                     no address. Corresponds directly to the value labeled 
                     'Primary WINS Address:' in the SERVER INTERNET
                     CHARACTERISTICS display."
                ::= { domainResolverPpp 1 }

            domainResolverPppSecondaryServer OBJECT-TYPE
                SYNTAX IpAddress
                ACCESS read-write
                STATUS mandatory
                DESCRIPTION
                    "The internet address of the secondary Domain Name Server to
                     use in PPP IPCP negotiations. A value of 0.0.0.0 indicates
                     no address. Corresponds directly to the value labeled 
                     'Secondary WINS Address:' in the SERVER INTERNET
                     CHARACTERISTICS display."
                ::= { domainResolverPpp 2 }


            -- the SLIP group

            -- Implementation of this group is mandatory for all MRV In-Reach
            -- systems that implement SLIP ports

            slipTable OBJECT-TYPE
                SYNTAX SEQUENCE OF SlipEntry
                ACCESS not-accessible
                STATUS mandatory
                DESCRIPTION
                    "A list of SLIP character port entries."
                ::= { xSlip 1 }

            slipEntry OBJECT-TYPE
                SYNTAX SlipEntry
                ACCESS not-accessible
                STATUS mandatory
                DESCRIPTION
                    "Parameter values for a SLIP port."
                INDEX { slipIndex }
                ::= { slipTable 1 }

            SlipEntry ::=
                SEQUENCE {
                    slipIndex
                        INTEGER,
                    slipState
                        INTEGER,
                    slipLocalAddress
                        IpAddress,
                    slipRemoteAddress
                        IpAddress,
                    slipMask
                        IpAddress,
                    slipPortPacketsReceived
                        Counter,
                    slipPortPacketsSent
                        Counter,
                    slipPortPacketsDiscarded
                        Counter,
                    slipPortPacketLengthErrors
                        Counter,
                    slipPortPacketChecksumErrors
                        Counter,
                    slipNetworkPacketsReceived
                        Counter,
                    slipNetworkPacketsSent
                        Counter,
                    slipNetworkPacketsDiscarded
                        Counter
                }

            slipIndex OBJECT-TYPE
                SYNTAX INTEGER
                ACCESS read-only
                STATUS mandatory
                DESCRIPTION
                    "An index value that uniquely identifies a port that 
                    can run SLIP.  The port identified by a particular 
                    value of this index is the same port as identified 
                    by charPortIndex in the Proposed Standard Internet 
                    Character MIB."
                ::= { slipEntry 1 }

            slipState OBJECT-TYPE
                SYNTAX INTEGER { off(1), on(2), compressed(3) }
                ACCESS read-write
                STATUS mandatory
                DESCRIPTION
                    "A control indicating whether SLIP is in operation 
                    on the port.  Corresponds directly to PORT INTERNET 
                    SLIP and the value labeled 'SLIP' in the PORT 
                    CHARACTERISTICS display."
                ::= { slipEntry 2 }

            slipLocalAddress OBJECT-TYPE
                SYNTAX IpAddress
                ACCESS read-write
                STATUS mandatory
                DESCRIPTION
                    "The IP address assigned to the port.  Corresponds 
                    directly to PORT SLIP ADDRESS and the value labeled 
                    'SLIP Address:' in the PORT ALTERNATE 
                    CHARACTERISTICS display."
                ::= { slipEntry 3 }

            slipRemoteAddress OBJECT-TYPE
                SYNTAX IpAddress
                ACCESS read-write
                STATUS mandatory
                DESCRIPTION
                    "The IP address of the remote system attached to the 
                    port.  Corresponds directly to PORT SLIP REMOTE and 
                    the value labeled 'Remote SLIP Address:' in the PORT 
                    ALTERNATE CHARACTERISTICS display."
                ::= { slipEntry 4 }

            slipMask OBJECT-TYPE
                SYNTAX IpAddress
                ACCESS read-write
                STATUS mandatory
                DESCRIPTION
                    "The subnet mask to use for SLIP operation on the 
                    port.  Corresponds directly to PORT SLIP MASK and 
                    the value labeled 'SLIP Mask:' in the PORT ALTERNATE 
                    CHARACTERISTICS display."
                ::= { slipEntry 5 }

            slipPortPacketsReceived OBJECT-TYPE
                SYNTAX Counter
                ACCESS read-only
                STATUS mandatory
                DESCRIPTION
                    "The number of SLIP packets received from the port.  
                    Corresponds directly to the value labeled 'Serial 
                    Packets Received:' in the PORT COUNTERS display."
                ::= { slipEntry 6 }

            slipPortPacketsSent OBJECT-TYPE
                SYNTAX Counter
                ACCESS read-only
                STATUS mandatory
                DESCRIPTION
                    "The number of SLIP packets sent to the port.  
                    Corresponds directly to the value labeled 'Serial 
                    Packets Sent:' in the PORT COUNTERS display."
                ::= { slipEntry 7 }

            slipPortPacketsDiscarded OBJECT-TYPE
                SYNTAX Counter
                ACCESS read-only
                STATUS mandatory
                DESCRIPTION
                    "The number of SLIP packets received from the port 
                    and discarded.  Corresponds directly to the value 
                    labeled 'Serial Packets Discarded:' in the PORT 
                    COUNTERS display."
                ::= { slipEntry 8 }

            slipPortPacketLengthErrors OBJECT-TYPE
                SYNTAX Counter
                ACCESS read-only
                STATUS mandatory
                DESCRIPTION
                    "The number of SLIP packets received from the port 
                    with an incorrect number of bytes.  Corresponds 
                    directly to the value labeled 'Serial Packet Length 
                    Errors:' in the PORT COUNTERS display."
                ::= { slipEntry 9 }

            slipPortPacketChecksumErrors OBJECT-TYPE
                SYNTAX Counter
                ACCESS read-only
                STATUS mandatory
                DESCRIPTION
                    "The number of SLIP packets received from the port 
                    with an invalid checksum.  Corresponds directly to 
                    the value labeled 'Serial Packet Checksum Errors:' 
                    in the PORT COUNTERS display."
                ::= { slipEntry 10 }

            slipNetworkPacketsReceived OBJECT-TYPE
                SYNTAX Counter
                ACCESS read-only
                STATUS mandatory
                DESCRIPTION
                    "The number of SLIP packets received from the 
                    network for this port.  Corresponds directly to the 
                    value labeled 'Network Packets Received:' in the 
                    PORT COUNTERS display."
                ::= { slipEntry 11 }

            slipNetworkPacketsSent OBJECT-TYPE
                SYNTAX Counter
                ACCESS read-only
                STATUS mandatory
                DESCRIPTION
                    "The number of SLIP packets sent to the network from 
                    this port.  Corresponds directly to the value 
                    labeled 'Network Packets Sent:' in the PORT COUNTERS 
                    display."
                ::= { slipEntry 12 }

            slipNetworkPacketsDiscarded OBJECT-TYPE
                SYNTAX Counter
                ACCESS read-only
                STATUS mandatory
                DESCRIPTION
                    "The number of SLIP packets received from the 
                    network for this port and discarded.  Corresponds 
                    directly to the value labeled 'Network Packets 
                    Discarded:' in the PORT COUNTERS display."
                ::= { slipEntry 13 }


            -- the Telnet group

            -- Implementation of this group is mandatory for all MRV In-Reach
            -- systems that implement Telnet

            -- the Telnet Character Port table

            -- Ports in this table are either serial or parallel

            telnetPortTable OBJECT-TYPE
                SYNTAX SEQUENCE OF TelnetPortEntry
                ACCESS not-accessible
                STATUS mandatory
                DESCRIPTION
                    "A list of Telnet character port entries."
                ::= { xTelnet 1 }

            telnetPortEntry OBJECT-TYPE
                SYNTAX TelnetPortEntry
                ACCESS not-accessible
                STATUS mandatory
                DESCRIPTION
                    "Telnet parameter values for a character port."
                INDEX { telnetPortIndex }
                ::= { telnetPortTable 1 }

            TelnetPortEntry ::=
                SEQUENCE {
                    telnetPortIndex
                        INTEGER,
                    telnetPortIncomingTcpPort
                        INTEGER,
                    telnetPortOutgoingTcpPort
                        INTEGER,
                    telnetPortNewlineTranslation
                        INTEGER,
                    telnetPortTerminalType
                        DisplayString,
                    telnetPortEorReflection
                        INTEGER,
                    telnetPortBinaryMode
                        INTEGER,
                    telnetPortSendLocation
                        INTEGER,
                    telnetPortClientLocation
                        DisplayString,
                    telnetPortPassiveSendLocation
                        INTEGER
                }

            telnetPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetPortEntry 1 }

            telnetPortIncomingTcpPort OBJECT-TYPE
                SYNTAX INTEGER (1..32767)
                ACCESS read-write
                STATUS mandatory
                DESCRIPTION
                    "The TCP port number offered for incoming 
                    connections to this character port.  Corresponds 
                    directly to PORT TELNET REMOTE PORT and the value 
                    labeled 'Remote Port:' in the PORT TELNET 
                    CHARACTERISTICS display."
                ::= { telnetPortEntry 2 }

            telnetPortOutgoingTcpPort OBJECT-TYPE
                SYNTAX INTEGER
                ACCESS read-write
                STATUS mandatory
                DESCRIPTION
                    "The TCP port number used by default for outgoing 
                    connections from this character port.  Corresponds 
                    directly to PORT TELNET DEFAULT PORT and the value 
                    labeled 'Default Port:' in the PORT TELNET 
                    CHARACTERISTICS display."
                ::= { telnetPortEntry 3 }

            telnetPortNewlineTranslation OBJECT-TYPE
                SYNTAX INTEGER { none(1), cr(2), crNull(3), 
                                crLf(4), std(5), lfToCrLf(6) }
                ACCESS read-write
                STATUS mandatory
                DESCRIPTION
                    "Translation to apply to newline sequences (CR/NULL 
                    or CR/LF) received from the network, before sending 
                    the newline to the character port.  The value 
                    indicates the sequence sent to the character port, 
                    with 'none' meaning no translation.  The lfToCrLf 
                    value converts the newline character LF received
                    from the network to a CR/LF.  Corresponds
                    directly to PORT TELNET NEWLINE FILTERING and the 
                    value labeled 'Newline Filtering:' in the PORT 
                    TELNET CHARACTERISTICS display."
                ::= { telnetPortEntry 4 }

            telnetPortTerminalType OBJECT-TYPE
                SYNTAX DisplayString (SIZE (0..21))
                ACCESS read-write
                STATUS mandatory
                DESCRIPTION
                    "The terminal type character string for Telnet 
                    negotiations.  Corresponds directly to PORT TELNET 
                    TERMINALTYPE and the value labeled 'TerminalType:' 
                    in the PORT TELNET CHARACTERISTICS display."
                ::= { telnetPortEntry 5 }

            telnetPortEorReflection OBJECT-TYPE
                SYNTAX INTEGER { disabled(1), enabled(2) }
                ACCESS read-write
                STATUS mandatory
                DESCRIPTION
                    "Control for end-of-record handshake.  Corresponds 
                    directly to PORT TELNET EOR REFLECTION and the value 
                    labeled 'EOR Reflection:' in the PORT TELNET 
                    CHARACTERISTICS display."
                ::= { telnetPortEntry 6 }

            telnetPortBinaryMode OBJECT-TYPE
                SYNTAX INTEGER { flowControl(1), complete(2),
                                 disabled(3) }
                ACCESS read-write
                STATUS mandatory
                DESCRIPTION
                    "Control for operation of Telnet binary mode.  The 
                    value meanings are:

                    disabled      refuse binary mode negotiation
                                  (INTERACTIVE)
                    flowControl   pass all but XON and XOFF (PASTHRU)
                    complete      pass all characters (PASSALL)

                    Corresponds directly to PORT TELNET BINARY SESSION 
                    MODE and the value labeled 'Binary Session Mode:' in 
                    the PORT TELNET CHARACTERISTICS display."
                ::= { telnetPortEntry 7 }

            telnetPortSendLocation OBJECT-TYPE
                SYNTAX INTEGER { disabled(1), enabled(2) }
                ACCESS read-write
                STATUS mandatory
                DESCRIPTION
                    "A control indicating whether a Telnet session will 
                    initiate negotiation of the Send Location option. 
                    Corresponds directly to the PORT TELNET LOCATION and 
                    the value labeled 'Location' in the PORT TELNET 
                    CHARACTERISTICS display."
                ::= { telnetPortEntry 8 }

            telnetPortClientLocation OBJECT-TYPE
                SYNTAX DisplayString (SIZE (0..50))
                ACCESS read-only
                STATUS mandatory
                DESCRIPTION
                    "The location of the Telnet client port. Corresponds 
                    directly to the value labeled 'Telnet Client 
                    Location' in the SESSION display."
                ::= { telnetPortEntry 9 }
         
            telnetPortPassiveSendLocation OBJECT-TYPE
                SYNTAX INTEGER { disabled(1), enabled(2) }
                ACCESS read-write
                STATUS mandatory
                DESCRIPTION
                    "A control indicating whether a Telnet session will 
                    passively respond to negotiation of the Send Location
                    option. When disabled and telnetPortSendLocation is 
                    disabled, we will refuse to negotiate this option.
                    When telnetPortSendLocation is enabled, it takes 
                    precedence. Corresponds directly to the value labeled
                    'Passive Location' in the PORT TELNET CHARACTERISTICS
                    display."
                DEFVAL { enabled }
                ::= { telnetPortEntry 10 }
            

            -- the Telnet Serial Character Port table

            telnetSerialPortTable OBJECT-TYPE
                SYNTAX SEQUENCE OF TelnetSerialPortEntry
                ACCESS not-accessible
                STATUS mandatory
                DESCRIPTION
                    "A list of Telnet character port entries."
                ::= { xTelnet 2 }

            telnetSerialPortEntry OBJECT-TYPE
                SYNTAX TelnetSerialPortEntry
                ACCESS not-accessible
                STATUS mandatory
                DESCRIPTION
                    "Telnet parameter values for a character port."
                INDEX { telnetSerialPortIndex }
                ::= { telnetSerialPortTable 1 }

            TelnetSerialPortEntry ::=
                SEQUENCE {
                    telnetSerialPortIndex
                        INTEGER,
                    telnetSerialPortOptionDisplay
                        INTEGER,
                    telnetSerialPortCsiEscape
                        INTEGER,
                    telnetSerialPortEchoMode
                        INTEGER,
                    telnetSerialPortNewlineMode
                        INTEGER,
                    telnetSerialPortTransmitMode
                        INTEGER,
                    telnetSerialPortTransmitCharacterTimes
                        INTEGER,
                    telnetSerialPortAbortOutputCharacter
                        INTEGER,
                    telnetSerialPortAttentionCharacter
                        INTEGER,
                    telnetSerialPortEraseKeyCharacter
                        INTEGER,
                    telnetSerialPortEraseLineCharacter
                        INTEGER,
                    telnetSerialPortInterruptCharacter
                        INTEGER,
                    telnetSerialPortQueryCharacter
                        INTEGER,
                    telnetSerialPortSynchronizeCharacter
                        INTEGER,
                    telnetSerialPortUrgentBreak
                        INTEGER,
                    telnetSerialPortRs491
                        INTEGER,
                    telnetSerialPortTransmitBufferedTime
                        INTEGER,
                    telnetSerialPortInterpretInterruptAsBreak
                        INTEGER,
                    telnetSerialPortPass8d
                        INTEGER,
                    telnetSerialPortComControlClient
                        INTEGER,
                    telnetSerialPortComControlServer
                        INTEGER,
                    telnetSerialPortComControlServerRaisesDtr
                        INTEGER,
                    telnetSerialPortComControlClientTogglesDtr
                        INTEGER
                }

            telnetSerialPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetSerialPortEntry 1 }

            telnetSerialPortOptionDisplay OBJECT-TYPE
                SYNTAX INTEGER { disabled(1), enabled(2) }
                ACCESS read-write
                STATUS mandatory
                DESCRIPTION
                    "Control for display of Telnet option negotiations.  
                    Corresponds directly to PORT TELNET OPTION DISPLAY 
                    and the value labeled 'Option Display:' in the PORT 
                    TELNET CHARACTERISTICS display."
                ::= { telnetSerialPortEntry 2 }

            telnetSerialPortCsiEscape OBJECT-TYPE
                SYNTAX INTEGER { disabled(1), enabled(2) }
                ACCESS read-write
                STATUS mandatory
                DESCRIPTION
                    "Control for translation of 8-bit escape sequences 
                    received from the character port to 7-bit 
                    equivalents before transmission to the remote 
                    partner.  Corresponds directly to PORT TELNET CSI 
                    ESCAPE and the value labeled 'CSI Escape:' in the 
                    PORT TELNET CHARACTERISTICS display."
                ::= { telnetSerialPortEntry 3 }

            telnetSerialPortEchoMode OBJECT-TYPE
                SYNTAX INTEGER { local(1), remote(2), disabled(3), passive(4),
                                  character(5), line(6), noecho(7) }
                ACCESS read-write
                STATUS mandatory
                DESCRIPTION
                    "Control for who echoes characters that come from 
                    the character port.  The value meanings are:

                    local    terminal server echoes locally
                    remote   remote system echoes
                    disabled don't default to local echo
                    passive  don't initiate negotiating of echo
                    character initiate remote echo and suppress go ahead
                    line     reject remote echo and reject suppress go ahead
                    noecho   will not initiate echo, but will negotiate it

                    Corresponds directly to PORT TELNET ECHO MODE and 
                    the value labeled 'Echo Mode:' in the PORT TELNET 
                    CHARACTERISTICS display."
                ::= { telnetSerialPortEntry 4 }

            telnetSerialPortNewlineMode OBJECT-TYPE
                SYNTAX INTEGER { crNull(1), crLf(2), verbatim(3) }
                ACCESS read-write
                STATUS mandatory
                DESCRIPTION
                    "Translation to apply to newline (carriage return) 
                    received from the character port, before sending the 
                    newline to the remote partner.  The correspondence 
                    to command keywords is 'crNull' to NULL, 'crLF' to 
                    LINEFEED, and 'verbatim' to NOTHING (that is, no 
                    translation).  Corresponds directly to PORT TELNET 
                    NEWLINE and the value labeled 'Newline:' in the PORT 
                    TELNET CHARACTERISTICS display."
                ::= { telnetSerialPortEntry 5 }

            telnetSerialPortTransmitMode OBJECT-TYPE
                SYNTAX INTEGER { immediate(1), buffered(2), timed(3), controlchar(4) }
                ACCESS read-write
                STATUS mandatory
                DESCRIPTION
                    "Criterion for deciding to send to the remote 
                    partner characters received from the character port.  
                    Corresponds directly to PORT TELNET TRANSMIT and the 
                    value labeled 'Transmit:' in the PORT TELNET 
                    CHARACTERISTICS display."
                ::= { telnetSerialPortEntry 6 }

            telnetSerialPortTransmitCharacterTimes OBJECT-TYPE
                SYNTAX INTEGER (0..255)
                ACCESS read-write
                STATUS mandatory
                DESCRIPTION
                    "Number of character times to wait before 
                    transmitting when telnetSerialPortTransmitMode value 
                    is 'timed'.  Corresponds directly to PORT TELNET 
                    TRANSMIT IDLETIME and the value labeled 'Transmit:  
                    Idle Time -' in the PORT TELNET CHARACTERISTICS 
                    display. This object may only be set to values 1..255.
                    A value of 0 may be read if telnetSerialPortTransmitMode
                    has a value of immediate or buffered"
                ::= { telnetSerialPortEntry 7 }

            telnetSerialPortAbortOutputCharacter OBJECT-TYPE
                SYNTAX INTEGER (0..255)
                ACCESS read-write
                STATUS mandatory
                DESCRIPTION
                    "Character input from the character port to cause 
                    aborting output.  The value 0 indicates no character 
                    has this effect.  Corresponds directly to PORT 
                    TELNET ABORT OUTPUT and the value labeled 'Abort 
                    Output Character:' in the PORT TELNET 
                    CHARACTERISTICS display."
                ::= { telnetSerialPortEntry 8 }

            telnetSerialPortAttentionCharacter OBJECT-TYPE
                SYNTAX INTEGER (0..255)
                ACCESS read-write
                STATUS mandatory
                DESCRIPTION
                    "Character input from the character port to cause an 
                    attention notification to the remote partner.  The 
                    value 0 indicates no character has this effect.  
                    Corresponds directly to PORT TELNET ATTENTION and 
                    the value labeled 'Attention Character:' in the PORT 
                    TELNET CHARACTERISTICS display."
                ::= { telnetSerialPortEntry 9 }

            telnetSerialPortEraseKeyCharacter OBJECT-TYPE
                SYNTAX INTEGER (0..255)
                ACCESS read-write
                STATUS mandatory
                DESCRIPTION
                    "Character input from the character port to cause 
                    erasure of the previous input character.  The value 
                    0 indicates no character has this effect.  
                    Corresponds directly to PORT TELNET ERASE CHARACTER 
                    and the value labeled 'Erase Keystroke Character:' 
                    in the PORT TELNET CHARACTERISTICS display."
                ::= { telnetSerialPortEntry 10 }

            telnetSerialPortEraseLineCharacter OBJECT-TYPE
                SYNTAX INTEGER (0..255)
                ACCESS read-write
                STATUS mandatory
                DESCRIPTION
                    "Character input from the character port to cause 
                    erasure of the previous line of input.  The value 0 
                    indicates no character has this effect.  Corresponds 
                    directly to PORT TELNET ERASE LINE and the value 
                    labeled 'Erase Line Character:' in the PORT TELNET 
                    CHARACTERISTICS display."
                ::= { telnetSerialPortEntry 11 }

            telnetSerialPortInterruptCharacter OBJECT-TYPE
                SYNTAX INTEGER (0..255)
                ACCESS read-write
                STATUS mandatory
                DESCRIPTION
                    "Character input from the character port to cause 
                    sending an interrupt notification to the remote 
                    partner.  The value 0 indicates no character has 
                    this effect.  Corresponds directly to PORT TELNET 
                    INTERRUPT and the value labeled 'Interrupt 
                    Character:' in the PORT TELNET CHARACTERISTICS 
                    display."
                ::= { telnetSerialPortEntry 12 }

            telnetSerialPortQueryCharacter OBJECT-TYPE
                SYNTAX INTEGER (0..255)
                ACCESS read-write
                STATUS mandatory
                DESCRIPTION
                    "Character input from the character port to cause 
                    sending a status query to the remote partner.  The 
                    value 0 indicates no character has this effect.  
                    Corresponds directly to PORT TELNET QUERY and the 
                    value labeled 'Query Character:' in the PORT TELNET 
                    CHARACTERISTICS display."
                ::= { telnetSerialPortEntry 13 }

            telnetSerialPortSynchronizeCharacter OBJECT-TYPE
                SYNTAX INTEGER (0..255)
                ACCESS read-write
                STATUS mandatory
                DESCRIPTION
                    "Character input from the character port to cause 
                    sending a synchronization attempt to the remote 
                    partner.  The value 0 indicates no character has 
                    this effect.  Corresponds directly to PORT TELNET 
                    SYNCHRONIZE and the value labeled 'Synchronize 
                    Character:' in the PORT TELNET CHARACTERISTICS 
                    display."
                ::= { telnetSerialPortEntry 14 }

            telnetSerialPortUrgentBreak OBJECT-TYPE
                SYNTAX INTEGER { disabled(1), enabled(2) }
                ACCESS read-write
                STATUS mandatory
                DESCRIPTION
                    "Control for encoding breaks as Telnet urgent data.  
                    Corresponds directly to PORT TELNET URGENT BREAK and 
                    the value labeled 'Urgent Break:' in the PORT TELNET 
                    CHARACTERISTICS display."
                ::= { telnetSerialPortEntry 15 }

            telnetSerialPortRs491 OBJECT-TYPE
                SYNTAX INTEGER { disabled(1), enabled(2) }
                ACCESS read-write
                STATUS mandatory 
                DESCRIPTION
                   "A control to enable RS491 protocol processing on a port."
                DEFVAL  { disabled }
                ::= { telnetSerialPortEntry 16 }

            telnetSerialPortTransmitBufferedTime OBJECT-TYPE
                SYNTAX INTEGER (30..1500)
                ACCESS read-write
                STATUS mandatory
                DESCRIPTION
                   "Number of milliseconds to wait before transmitting
                    when telnetSerialPortTransmitMode value is 'timed'.
                    Corresponds directly to PORT TELNET TRANSMIT BUFFERED
                    and the value labeled 'Transmit: Buff Time -' in the
                    PORT TELNET CHARACTERISTICS display. This object may
                    only be set to values 30..1500. A value of 0 may be
                    read if telnetSerialPortTransmitMode has a value of
                    immediate, idletime or controlchar"
                DEFVAL   { 80 }
                ::= { telnetSerialPortEntry 17 }

            telnetSerialPortInterpretInterruptAsBreak OBJECT-TYPE
                SYNTAX INTEGER { enabled(1), disabled(2) }
                ACCESS read-write
                STATUS mandatory
                DESCRIPTION
                    "Control to interpret a Telnet Interrupt Character coming
                     from the network as a Telnet Break Character, and to send
                     a break out the serial port. This control is necessary 
                     for those devices which can send Telnet Interrupt but not
                     Telnet Break. Corresponds directly to the presence of 
                     'Telnet Interrupts Interpreted as Break' under the label 
                     'Enabled Characteristics' in the PORT TELNET 
                     CHARACTERISTICS display."
                DEFVAL { disabled }
                ::= { telnetSerialPortEntry 18 }

            telnetSerialPortPass8d OBJECT-TYPE
                SYNTAX INTEGER { enabled(1), disabled(2) }
                ACCESS read-write
                STATUS mandatory
                DESCRIPTION
                    "Control to pass unaltered the hexadecimal character '8D'.
                     This control is added to ensure that this character will
                     pass through directly in a session with 8-bit characters
                     and parity odd or even.  Corresponds directly to the 
                     presence of 'Telnet Pass 8D' under the label 'Enabled
                     Characteristics' in the PORT TELNET CHARACTERISTICS 
                     display."
                DEFVAL { disabled }
                ::= { telnetSerialPortEntry 19 }

            telnetSerialPortComControlClient OBJECT-TYPE
                SYNTAX INTEGER { enabled(1), disabled(2) }
                ACCESS read-write
                STATUS mandatory
                DESCRIPTION
                    "Control to begin Telnet comport control option negotiations
                     as a client when a Telnet session is initiated. The comport
                     control option enables a port to do outbound modem dialing
                     on a Telnet connection. Corresponds to the value labeled
                     'Client:' in the PORT TELNET COMPORTCONTROL CHARACTERISTICS
                     display."
                DEFVAL { disabled }
                ::= { telnetSerialPortEntry 20 }

            telnetSerialPortComControlServer OBJECT-TYPE
                SYNTAX INTEGER { enabled(1), disabled(2) }
                ACCESS read-write
                STATUS mandatory
                DESCRIPTION
                    "Control to begin Telnet comport control option negotiations
                     as a server when a Telnet session is initiated. Corresponds
                     to the value labeled 'Server:' in the PORT TELNET 
                     COMPORTCONTROL CHARACTERISTICS display."
                DEFVAL { disabled }
                ::= { telnetSerialPortEntry 21 }
 
            telnetSerialPortComControlServerRaisesDtr OBJECT-TYPE
                SYNTAX INTEGER { enabled(1), disabled(2) }
                ACCESS read-write
                STATUS mandatory
                DESCRIPTION
                    "Control for the client to request that the server raises
                     its DTR signal on the port at the begining of the Telnet 
                     connection. Corresponds to the value labeled 'Server 
                     Raises DTR:' in the PORT TELNET COMPORTCONTROL
                     CHARACTERISTICS display."
                DEFVAL { disabled }
                ::= { telnetSerialPortEntry 22 }
 
            telnetSerialPortComControlClientTogglesDtr OBJECT-TYPE
                SYNTAX INTEGER { enabled(1), disabled(2) }
                ACCESS read-write
                STATUS mandatory
                DESCRIPTION
                    "Control to respond to the server's notification that its 
                     DCD has come high (or low)  by raising (or lowering) DTR
                     accordingly on the local port. Corresponds to the value 
                     labeled 'Client Toggles DTR:' in the PORT TELNET 
                     COMPORTCONTROL CHARACTERISTICS display."
                DEFVAL { disabled }
                ::= { telnetSerialPortEntry 23 }
 

               


            -- the tn3270 group

            -- Implementation of this group is mandatory for all MRV In-Reach
            -- systems that implement tn3270

            tn3270DeviceNumber OBJECT-TYPE
                SYNTAX INTEGER
                ACCESS read-only
                STATUS mandatory
                DESCRIPTION
                    "The number of entries in the tn3270 Device table."
                ::= { xTn3270 1 }

            tn3270LanguageNumber OBJECT-TYPE
                SYNTAX INTEGER
                ACCESS read-only
                STATUS mandatory
                DESCRIPTION
                    "The number of entries in the tn3270 Language 
                    table."
                ::= { xTn3270 2 }

            tn3270PortKeymapStatus OBJECT-TYPE
                SYNTAX INTEGER { disabled(1), enabled(2) }
                ACCESS read-write
                STATUS mandatory
                DESCRIPTION
                    "Control for individual ports to create their own 
                    keymaps.  Corresponds directly to SERVER TN3270 PORT 
                    KEYMAPS and the value labeled 'Port Keymaps:' in the 
                    SERVER TN3270 display."
                ::= { xTn3270 3 }


            -- The tn3270 Device table

            tn3270DeviceTable OBJECT-TYPE
                SYNTAX SEQUENCE OF Tn3270DeviceEntry
                ACCESS not-accessible
                STATUS mandatory
                DESCRIPTION
                    "A list of tn3270 terminal device entries."
                ::= { xTn3270 4 }

            tn3270DeviceEntry OBJECT-TYPE
                SYNTAX Tn3270DeviceEntry
                ACCESS not-accessible
                STATUS mandatory
                DESCRIPTION
                    "Tn3270 parameter values for a terminal device 
                    entry."
                INDEX { tn3270DeviceName }
                ::= { tn3270DeviceTable 1 }

            Tn3270DeviceEntry ::=
                SEQUENCE {
                    tn3270DeviceName
                        DisplayString,
                    tn3270DeviceStatus
                        INTEGER,
                    tn3270DeviceType
                        DisplayString,
                    tn3270Device3278Model
                        INTEGER,
                    tn3270DeviceKeyNumber
                        INTEGER,
                    tn3270DeviceScreenNumber
                        INTEGER
                }

            tn3270DeviceName OBJECT-TYPE
                SYNTAX DisplayString (SIZE (1..8))
                ACCESS read-only
                STATUS mandatory
                DESCRIPTION
                    "The name of a generic terminal device.  Corresponds 
                    directly to SERVER TN3270 DEVICE and the value 
                    labeled 'Device Name:' in the SERVER TN3270 DEVICE 
                    display."
                ::= { tn3270DeviceEntry 1 }

            tn3270DeviceStatus OBJECT-TYPE
                SYNTAX INTEGER { invalid(1), valid(2) }
                ACCESS read-write
                STATUS mandatory
                DESCRIPTION
                    "Status of this entry.  Setting the value to 
                    'invalid' invalidates the entry, corresponding 
                    directly to the PURGE SERVER TN3270 DEVICE command.  
                    It is an implementation-specific matter as to 
                    whether the agent removes an invalidated entry from 
                    the table. If a new device table entry is added to
                    the table, the agent will copy the VT100 table as
                    a default. If one plans to add a new table entry, one
                    should not remove the VT100 entry."
                DEFVAL { valid }
                ::= { tn3270DeviceEntry 2 }

            tn3270DeviceType OBJECT-TYPE
                SYNTAX DisplayString (SIZE (0..21))
                ACCESS read-write
                STATUS mandatory
                DESCRIPTION
                    "The terminal type character string for use when 
                    tn3270DeviceTn3270Type is insufficient.  Corresponds 
                    directly to SERVER TN3270 DEVICE TERMINALTYPE and 
                    the value labeled 'TerminalType:' in the SERVER 
                    TN3270 DEVICE display."
                DEFVAL { "VT100" }
                ::= { tn3270DeviceEntry 3 }

            tn3270Device3278Model OBJECT-TYPE
                SYNTAX INTEGER { model2(1), model5(2) }
                ACCESS read-write
                STATUS mandatory
                DESCRIPTION
                    "The 3278 model for the device.  Corresponds 
                    directly to SERVER TN3270 DEVICE 3278Model and the 
                    value labeled '3278Model:' in the SERVER TN3270 
                    DEVICE display."
                DEFVAL { model2 }
                ::= { tn3270DeviceEntry 4 }

            tn3270DeviceKeyNumber OBJECT-TYPE
                SYNTAX INTEGER
                ACCESS read-only
                STATUS mandatory
                DESCRIPTION
                    "The number of Key table entries for this device."
                DEFVAL { 70 }
                ::= { tn3270DeviceEntry 5 }

            tn3270DeviceScreenNumber OBJECT-TYPE
                SYNTAX INTEGER
                ACCESS read-only
                STATUS mandatory
                DESCRIPTION
                    "The number of Screen table entries for this 
                    device."
                DEFVAL { 24 }
                ::= { tn3270DeviceEntry 6 }


            -- The Key table

            tn3270KeyTable OBJECT-TYPE
                SYNTAX SEQUENCE OF Tn3270KeyEntry
                ACCESS not-accessible
                STATUS mandatory
                DESCRIPTION
                    "A list of tn3270 key entries by device."
                ::= { xTn3270 5 }

            tn3270KeyEntry OBJECT-TYPE
                SYNTAX Tn3270KeyEntry
                ACCESS not-accessible
                STATUS mandatory
                DESCRIPTION
                    "Tn3270 parameter values for a key entry for a 
                    device."
                INDEX { tn3270KeyDeviceName, tn3270KeyName }
                ::= { tn3270KeyTable 1 }

            Tn3270KeyEntry ::=
                SEQUENCE {
                    tn3270KeyDeviceName
                        DisplayString,
                    tn3270KeyName
                        INTEGER,
                    tn3270KeyStatus
                        INTEGER,
                    tn3270KeyCharacterSequence
                        OCTET STRING,
                    tn3270KeyDescription
                        DisplayString
                }

            tn3270KeyDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270KeyEntry 1 }

            tn3270KeyName OBJECT-TYPE
                SYNTAX INTEGER { newline(1), tab(2), backtab(3),
                                 cursorup(4), cursorleft(5),
                                 cursorright(6), cursordown(7),
                                 home(8), delete(9), eraseeof(10),
                                 eraseinput(11), insert(12),
                                 flushinput(13), refresh(14),
                                 centsign(15), duplicate(16),
                                 fieldmark(17), scroll(18),
                                 status(19), reset(20),
                                 fastleft(21), fastright(22),
                                 showkeys(23), print(24),
                                 pf1(39), pf2(40), pf3(41),
                                 pf4(42), pf5(43), pf6(44),
                                 pf7(45), pf8(46), pf9(47), pf10(48),
                                 pf11(49), pf12(50), pf13(51),
                                 pf14(52), pf15(53), pf16(54),
                                 pf17(55), pf18(56), pf19(57),
                                 pf20(58), pf21(59), pf22(60),
                                 pf23(61), pf24(62), pa1(63),
                                 pa2(64), pa3(65), sysreq(66),
                                 enter(67), clear(68), cursorsel(69),
                                 test(70) }
                ACCESS read-only
                STATUS mandatory
                DESCRIPTION
                    "The key name to which this entry applies.  
                    Corresponds directly to the key portion of SERVER 
                    TN3270 DEVICE KEYMAP and the value labeled 
                    '3270-key' in the 'Keymap:' section of the SERVER 
                    TN3270 DEVICE display."
                ::= { tn3270KeyEntry 2 }

            tn3270KeyStatus OBJECT-TYPE
                SYNTAX INTEGER { invalid(1), valid(2) }
                ACCESS read-write
                STATUS deprecated
                DESCRIPTION
                    "Status of this entry.  Setting the value to 
                    'invalid' invalidates the entry.  It is an 
                    implementation-specific matter as to whether the 
                    agent removes an invalidated entry from the table."
                DEFVAL { valid }
                ::= { tn3270KeyEntry 3 }

            tn3270KeyCharacterSequence OBJECT-TYPE
                SYNTAX OCTET STRING (SIZE (0..8))
                ACCESS read-write
                STATUS mandatory
                DESCRIPTION
                    "The ASCII character sequence for the key.  
                    Corresponds directly to the escape-sequence portion 
                    of SERVER TN3270 DEVICE KEYMAP and the value labeled 
                    'KeyCode' in the 'Keymap:' section of the SERVER 
                    TN3270 DEVICE display."
                ::= { tn3270KeyEntry 4 }

            tn3270KeyDescription OBJECT-TYPE
                SYNTAX DisplayString (SIZE (0..5))
                ACCESS read-write
                STATUS mandatory
                DESCRIPTION
                    "Descriptive text for the key.  Corresponds directly 
                    to the description portion of SERVER TN3270 DEVICE 
                    KEYMAP and the value labeled 'Description' in the 
                    SERVER TN3270 DEVICE display."
                ::= { tn3270KeyEntry 5 }


            -- The Screen Action table

            tn3270ScreenTable OBJECT-TYPE
                SYNTAX SEQUENCE OF Tn3270ScreenEntry
                ACCESS not-accessible
                STATUS mandatory
                DESCRIPTION
                    "A list of tn3270 screen action entries by device."
                ::= { xTn3270 6 }

            tn3270ScreenEntry OBJECT-TYPE
                SYNTAX Tn3270ScreenEntry
                ACCESS not-accessible
                STATUS mandatory
                DESCRIPTION
                    "Tn3270 parameter values for a screen action entry 
                    for a device."
                INDEX { tn3270ScreenDeviceName, tn3270ScreenActionName }
                ::= { tn3270ScreenTable 1 }

            Tn3270ScreenEntry ::=
                SEQUENCE {
                    tn3270ScreenDeviceName
                        DisplayString,
                    tn3270ScreenActionName
                        INTEGER,
                    tn3270ScreenStatus
                        INTEGER,
                    tn3270ScreenCharacterSequence
                        OCTET STRING
                }

            tn3270ScreenDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270ScreenEntry 1 }

            tn3270ScreenActionName OBJECT-TYPE
                SYNTAX INTEGER { eraseeol(1), clearscr(2),
                                 movecursor(3), col132(4), col80(5),
                                 beep(6), charset(7), boldon(8),
                                 boldoff(9), blinkon(10),
                                 blinkoff(11), underscoreon(12),
                                 underscoreoff(13), reverseon(14),
                                 reverseoff(15),
                                 colorBlue(16), colorRed(17),
                                 colorPink(18), colorGreen(19),
                                 colorTurquoise(20),
                                 colorYellow(21), colorWhite(22),
                                 status1(26), status2(27),
                                 reset1(28), reset2(29),
                                 reset3(30), reset4(31),
                                 base(32), sgr(33) }
                ACCESS read-only
                STATUS mandatory
                DESCRIPTION
                    "The screen action to which this entry applies.  
                    Corresponds directly to the action portion of SERVER 
                    TN3270 DEVICE SCREENMAP and the value labeled 
                    'Terminal Function' in the 'Screenmap: section of 
                    the SERVER TN3270 DEVICE display."
                ::= { tn3270ScreenEntry 2 }

            tn3270ScreenStatus OBJECT-TYPE
                SYNTAX INTEGER { invalid(1), valid(2) }
                ACCESS read-write
                STATUS deprecated
                DESCRIPTION
                    "Status of this entry.  Setting the value to 
                    'invalid' invalidates the entry.  It is an 
                    implementation-specific matter as to whether the 
                    agent removes an invalidated entry from the table."
                DEFVAL { valid }
                ::= { tn3270ScreenEntry 3 }

            tn3270ScreenCharacterSequence OBJECT-TYPE
                SYNTAX OCTET STRING (SIZE (0..15))
                ACCESS read-write
                STATUS mandatory
                DESCRIPTION
                    "The ASCII character sequence for the screen action.  
                    Some actions may have a lesser length limit.  
                    Corresponds directly to the escape-sequence portion 
                    of SERVER TN3270 DEVICE SCREENMAP and the value 
                    labeled 'HexCode' in the 'Screenmap: section of the 
                    SERVER TN3270 DEVICE display."
                ::= { tn3270ScreenEntry 4 }


            -- The Language table

            tn3270LanguageTable OBJECT-TYPE
                SYNTAX SEQUENCE OF Tn3270LanguageEntry
                ACCESS not-accessible
                STATUS mandatory
                DESCRIPTION
                    "A list of tn3270 language entries."
                ::= { xTn3270 7 }

            tn3270LanguageEntry OBJECT-TYPE
                SYNTAX Tn3270LanguageEntry
                ACCESS not-accessible
                STATUS mandatory
                DESCRIPTION
                    "Tn3270 parameter values for a language entry."
                INDEX { tn3270LanguageName }
                ::= { tn3270LanguageTable 1 }

            Tn3270LanguageEntry ::=
                SEQUENCE {
                    tn3270LanguageName
                        DisplayString,
                    tn3270LanguageStatus
                        INTEGER
                }

            tn3270LanguageName OBJECT-TYPE
                SYNTAX DisplayString (SIZE (1..8))
                ACCESS read-only
                STATUS mandatory
                DESCRIPTION
                    "The name of language for character translation 
                    tables.  Corresponds directly to SERVER TN3270 
                    LANGUAGE and the value labeled 'Language Name:' in 
                    the SERVER LANGUAGE display."
                ::= { tn3270LanguageEntry 1 }

            tn3270LanguageStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table.
                    If a new device table entry is added to the table,
                    the agent will copy the USENGLSH table as the default." 
                DEFVAL { valid }
                ::= { tn3270LanguageEntry 2 }


            -- The Language EBCDIC to ASCII table

            eToALanguageTable OBJECT-TYPE
                SYNTAX SEQUENCE OF EToALanguageEntry
                ACCESS not-accessible
                STATUS mandatory
                DESCRIPTION
                    "A list of language EBCDIC to ASCII conversion 
                    entries."
                ::= { xTn3270 8 }

            eToALanguageEntry OBJECT-TYPE
                SYNTAX EToALanguageEntry
                ACCESS not-accessible
                STATUS mandatory
                DESCRIPTION
                    "EBCDIC to ASCII parameter values for a language 
                    entry."
                INDEX { eToALanguageName, eToAOffset }
                ::= { eToALanguageTable 1 }

            EToALanguageEntry ::=
                SEQUENCE {
                    eToALanguageName
                        DisplayString,
                    eToAOffset
                        INTEGER,
                    eToAValue
                        INTEGER
                }

            eToALanguageName OBJECT-TYPE
                SYNTAX DisplayString (SIZE (1..8))
                ACCESS read-only
                STATUS mandatory
                DESCRIPTION
                    "The name of language from the language table."
                ::= { eToALanguageEntry 1 }

            eToAOffset OBJECT-TYPE
                SYNTAX INTEGER (65..256)
                ACCESS read-only
                STATUS mandatory
                DESCRIPTION
                    "EBCDIC character offset plus one, that is, the 
                    value 1 corresponds to an operational offset of 0.  
                    Corresponds directly to the offset portion of SERVER 
                    TN3270 LANGUAGE and the hexadecimal labels around 
                    the conversion table labeled 'EBCDIC to ASCII' in 
                    the SERVER LANGUAGE display."
                ::= { eToALanguageEntry 2 }

            eToAValue OBJECT-TYPE
                SYNTAX INTEGER (32..255)
                ACCESS read-write
                STATUS mandatory
                DESCRIPTION
                    "ASCII character value for the EBCDIC offset.  
                    Corresponds directly to the value portion of SERVER 
                    TN3270 LANGUAGE and the values in the conversion 
                    table labeled 'EBCDIC to ASCII' in the SERVER 
                    LANGUAGE display."
                ::= { eToALanguageEntry 3 }


            -- The Language ASCII to EBCDIC table

            aToELanguageTable OBJECT-TYPE
                SYNTAX SEQUENCE OF AToELanguageEntry
                ACCESS not-accessible
                STATUS mandatory
                DESCRIPTION
                    "A list of language ASCII to EBCDIC conversion 
                    entries."
                ::= { xTn3270 9 }

            aToELanguageEntry OBJECT-TYPE
                SYNTAX AToELanguageEntry
                ACCESS not-accessible
                STATUS mandatory
                DESCRIPTION
                    "ASCII to EBCDIC parameter values for a language 
                    entry."
                INDEX { aToELanguageName, aToEOffset }
                ::= { aToELanguageTable 1 }

            AToELanguageEntry ::=
                SEQUENCE {
                    aToELanguageName
                        DisplayString,
                    aToEOffset
                        INTEGER,
                    aToEValue
                        INTEGER
                }

            aToELanguageName OBJECT-TYPE
                SYNTAX DisplayString (SIZE (1..8))
                ACCESS read-only
                STATUS mandatory
                DESCRIPTION
                    "The name of language from the language table."
                ::= { aToELanguageEntry 1 }

            aToEOffset OBJECT-TYPE
                SYNTAX INTEGER (33..256)
                ACCESS read-only
                STATUS mandatory
                DESCRIPTION
                    "ASCII character offset plus one, that is, the value 
                    1 corresponds to an operational offset of 0.  
                    Corresponds directly to the offset portion of SERVER 
                    TN3270 LANGUAGE and the hexadecimal labels around 
                    the conversion table labeled 'ASCII to EBCDIC' in 
                    the SERVER LANGUAGE display."
                ::= { aToELanguageEntry 2 }

            aToEValue OBJECT-TYPE
                SYNTAX INTEGER (0..255)
                ACCESS read-write
                STATUS mandatory
                DESCRIPTION
                    "EBCDIC character value for the ASCII offset.  
                    Corresponds directly to the value portion of SERVER 
                    TN3270 LANGUAGE and the values in the conversion 
                    table labeled 'ASCII to EBCDIC' in the SERVER 
                    LANGUAGE display."
                ::= { aToELanguageEntry 3 }


            -- the tn3270 Port table

            tn3270PortTable OBJECT-TYPE
                SYNTAX SEQUENCE OF Tn3270PortEntry
                ACCESS not-accessible
                STATUS mandatory
                DESCRIPTION
                    "A list of tn3270 character port entries."
                ::= { xTn3270 10 }

            tn3270PortEntry OBJECT-TYPE
                SYNTAX Tn3270PortEntry
                ACCESS not-accessible
                STATUS mandatory
                DESCRIPTION
                    "Parameter values for a tn3270 port."
                INDEX { tn3270PortIndex }
                ::= { tn3270PortTable 1 }

            Tn3270PortEntry ::=
                SEQUENCE {
                    tn3270PortIndex
                        INTEGER,
                    tn3270PortDeviceName
                        DisplayString,
                    tn3270PortLanguageName
                        DisplayString,
                    tn3270PortExtendedAttributes
                        INTEGER,
                    tn3270PortEorNegotiation
                        INTEGER,
                    tn3270PortErrorLock
                        INTEGER,
                    tn3270PortPrinterPort
                        INTEGER,
                    tn3270PortOutgoingTcpPort
                        INTEGER,
                    tn3270PortSpaceInsert
                        INTEGER,
                    tn3270PortTypeAhead
                        INTEGER,
                    tn3270PrefixKeyMap
                        INTEGER,
                    tn3270PortScanner
                        INTEGER
                }

            tn3270PortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tn3270PortEntry 1 }

            tn3270PortDeviceName OBJECT-TYPE
                SYNTAX DisplayString (SIZE (0..8))
                ACCESS read-write
                STATUS mandatory
                DESCRIPTION
                    "The name of a generic terminal device from the 
                    tn3270 device table.  Corresponds directly to PORT 
                    TELNET TN3270 DEVICE and the value labeled 'Tn3270 
                    Device:' in the PORT TELNET display."
                ::= { tn3270PortEntry 2 }

            tn3270PortLanguageName OBJECT-TYPE
                SYNTAX DisplayString (SIZE (0..8))
                ACCESS read-write
                STATUS mandatory
                DESCRIPTION
                    "The name of language from the tn3270 language 
                    table.  Corresponds directly to PORT TELNET TN3270 
                    LANGUAGE and the value labeled 'Tn3270 Language:' in 
                    the PORT TELNET display."
                ::= { tn3270PortEntry 3 }

            tn3270PortExtendedAttributes OBJECT-TYPE
                SYNTAX INTEGER { disabled(1), enabled(2) }
                ACCESS read-write
                STATUS mandatory
                DESCRIPTION
                    "A control indicating that certain 3270 extended 
                    attributes are supported on the port.  Corresponds 
                    directly to PORT TELNET TN3270 XTDATTRS and the 
                    label 'Tn3270 XtdAttrs' following the label 'Enabled 
                    Characteristics' in the PORT TELNET display."
                ::= { tn3270PortEntry 4 }

            tn3270PortEorNegotiation OBJECT-TYPE
                SYNTAX INTEGER { disabled(1), enabled(2) }
                ACCESS read-write
                STATUS mandatory
                DESCRIPTION
                    "A control for negotiation of the Telnet EOR option 
                    when establishing a tn3270 session on the port.  
                    Corresponds directly to PORT TELNET TN3270 EOR and 
                    the label 'Tn3270 EOR' following the label 'Enabled 
                    Characteristics' in the PORT TELNET display."
                ::= { tn3270PortEntry 5 }

            tn3270PortErrorLock OBJECT-TYPE
                SYNTAX INTEGER { disabled(1), enabled(2) }
                ACCESS read-write
                STATUS mandatory
                DESCRIPTION
                    "A control for requiring use the RESET key when the 
                    host reports an error during a tn3270 session on the 
                    port.  Corresponds directly to PORT TELNET TN3270 
                    ERRORLOCK and the label 'Tn3270 ErrorLock' following 
                    the label 'Enabled Characteristics' in the PORT 
                    TELNET display."
                ::= { tn3270PortEntry 6 }

            tn3270PortPrinterPort OBJECT-TYPE
                SYNTAX INTEGER
                ACCESS read-write
                STATUS mandatory
                DESCRIPTION
                    "The port number of the tn3270 printer.  Corresponds 
                    directly to PORT TELNET TN3270 PRINTER and the value 
                    labeled 'Tn3270 Printer:' in the PORT TELNET 
                    display."
                ::= { tn3270PortEntry 7 }

            tn3270PortOutgoingTcpPort OBJECT-TYPE
                SYNTAX INTEGER (1..32767)
                ACCESS read-write
                STATUS mandatory
                DESCRIPTION
                    "The TCP port which is used for a TN3270 session when
                     connecting to a remote host from this serial port. 
                     Corresponds directly to the value labeled 'Tn3270 Default 
                     Port:' in the PORT TELNET CHARACTERISTICS display."
                DEFVAL { 23 }
                ::= { tn3270PortEntry 8 }
           
          tn3270PortSpaceInsert OBJECT-TYPE
            SYNTAX INTEGER { disabled(1), enabled(2) }
            ACCESS read-write
            STATUS mandatory
            DESCRIPTION
                "Control to allow insert mode within a space filled field, and
                 write characters over EBCDIC spaces.  Corresponds directly to
                 the presence of 'Tn3270 Space_Insert' under the label 'Enabled
                 Characteristics' in the PORT TELNET CHARACTERISTICS display."
            DEFVAL { disabled }
            ::= { tn3270PortEntry 9 }
           
          tn3270PortTypeAhead OBJECT-TYPE
            SYNTAX INTEGER { disabled(1), enabled(2) }
            ACCESS read-write  
            STATUS mandatory
            DESCRIPTION
                "Control to permit typing ahead in a tn3270 session prior to
                 receiving a response from the host for the previous command
                 entered. Corresponds directly to the presence of
                 'Tn3270 TypeAhead' under the label 'Enabled Characteristics'
                 in the PORT TELNET CHARACTERISTICS display."
            DEFVAL { enabled }
            ::= { tn3270PortEntry 10 }

          tn3270PrefixKeyMap OBJECT-TYPE
            SYNTAX INTEGER { disabled(1), enabled(2) }
            ACCESS read-write
            STATUS mandatory
            DESCRIPTION
                "Control to prepend a prefix function to another function key.
                 When the operator hits the key the prepended function(s) and
                 then the main function for the key are transmitted to the host.
                 Corresponds directly to the presence of 'Tn3270 PrefixKeyMap'
                 under the label 'Enabled Characteristics' in the PORT
                 TELNET CHARACTERISTICS display."
            DEFVAL { disabled  }
            ::= { tn3270PortEntry 11 }

          tn3270PortScanner OBJECT-TYPE
            SYNTAX INTEGER { disabled(1), enabled(2) }
            ACCESS read-write
            STATUS mandatory
            DESCRIPTION
                "Indicates that this is a tn3270 scanner port. Corresponds
                 directly to the presence of 'Tn3270 SCANNER' under the
                 label 'Enabled Characteristics' in the PORT TELNET
                 CHARACTERISTICS display."
            DEFVAL { disabled  }
            ::= { tn3270PortEntry 12 }



            -- the Kerberos group

            -- Implementation of this group is mandatory for all MRV In-Reach
            -- systems that implement a Kerberos client

            kerbStatus OBJECT-TYPE
                SYNTAX INTEGER { none(1), login(2) }
                ACCESS read-write
                STATUS mandatory
                DESCRIPTION
                    "A control indicating the level of Kerberos 
                    operation on the system.  Corresponds directly to 
                    SERVER KERBEROS STATUS and the value labeled 
                    'Kerberos Security:' in the SERVER KERBEROS 
                    display."
                ::= { xKerberos 1 }

            kerbRealm OBJECT-TYPE
                SYNTAX DisplayString (SIZE (0..40))
                ACCESS read-write
                STATUS mandatory
                DESCRIPTION
                    "The Kerberos realm with which the kerbServerName1 
                    and kerbServerName2 are associated.  Corresponds 
                    directly to SERVER KERBEROS REALM and the value 
                    labeled 'Kerberos Realm:' in the SERVER KERBEROS 
                    display."
                ::= { xKerberos 2 }

            kerbQueryLimit OBJECT-TYPE
                SYNTAX INTEGER (1..16)
                ACCESS read-write
                STATUS mandatory
                DESCRIPTION
                    "The maximum number of attempts the system can make 
                    when trying to verify a Kerberos ID.  Corresponds 
                    directly to SERVER KERBEROS QUERY LIMIT and the 
                    value labeled 'Kerberos Query Limit:' in the SERVER 
                    KERBEROS display."
                ::= { xKerberos 3 }

            kerbMasterName OBJECT-TYPE
                SYNTAX DisplayString (SIZE (0..50))
                ACCESS read-write
                STATUS mandatory
                DESCRIPTION
                    "The Domain name of the Kerberos master host system, 
                    which holds the Kerberos database.  Corresponds 
                    directly to SERVER KERBEROS MASTER and the value 
                    labeled 'Kerberos Master:' in the SERVER KERBEROS 
                    display."
                ::= { xKerberos 4 }

            kerbServerName1 OBJECT-TYPE
                SYNTAX DisplayString (SIZE (0..50))
                ACCESS read-write
                STATUS mandatory
                DESCRIPTION
                    "The Domain name of the first Kerberos server to try 
                    when the system verifys a Kerberos ID.  Corresponds 
                    directly to SERVER KERBEROS PRIMARY SERVER and the 
                    value labeled 'Kerberos Primary Server:' in the 
                    SERVER KERBEROS display."
                ::= { xKerberos 5 }

            kerbServerName2 OBJECT-TYPE
                SYNTAX DisplayString (SIZE (0..50))
                ACCESS read-write
                STATUS mandatory
                DESCRIPTION
                    "The Domain name of the Kerberos server to try when 
                    the system verifys a Kerberos ID and cannot reach 
                    the Kerberos primary server.  Corresponds directly 
                    to SERVER KERBEROS SECONDARY SERVER and the value 
                    labeled 'Kerberos Secondary Server:' in the SERVER 
                    KERBEROS display."
                ::= { xKerberos 6 }

            kerbInsecureLogins OBJECT-TYPE
                SYNTAX Counter
                ACCESS read-only
                STATUS mandatory
                DESCRIPTION
                    "The number of user logins on ports for which 
                    Kerberos user verification is not enabled.  
                    Corresponds directly to the value labeled 'Logins 
                    without Kerberos:' in the SERVER KERBEROS display."
                ::= { xKerberos 7 }

            kerbSecureLogins OBJECT-TYPE
                SYNTAX Counter
                ACCESS read-only
                STATUS mandatory
                DESCRIPTION
                    "The number of successful user logins on ports for 
                    which Kerberos user verification is enabled.  
                    Corresponds directly to the value labeled 
                    'Successful Logins:' in the SERVER KERBEROS 
                    display."
                ::= { xKerberos 8 }

            kerbSecureLoginsFailed OBJECT-TYPE
                SYNTAX Counter
                ACCESS read-only
                STATUS mandatory
                DESCRIPTION
                    "The number of verification failures due to 
                    incorrect ID or password for attempted user logins 
                    on ports for which Kerberos user verification is 
                    enabled.  Corresponds directly to the value labeled 
                    'Unsuccessful Logins:' in the SERVER KERBEROS 
                    display."
                ::= { xKerberos 9 }

            kerbPasswordChangeFailed OBJECT-TYPE
                SYNTAX Counter
                ACCESS read-only
                STATUS mandatory
                DESCRIPTION
                    "The number of user failures to change their 
                    Kerberos password due to invalid old password or new 
                    password verification.  Corresponds directly to the 
                    value labeled 'Password Change Failures:' in the 
                    SERVER KERBEROS display."
                ::= { xKerberos 10 }

            kerbError OBJECT-TYPE
                SYNTAX INTEGER
                ACCESS read-only
                STATUS mandatory
                DESCRIPTION
                    "The error number of the most recent 
                    Kerberos-related failure.  Corresponds directly to 
                    the value labeled 'Last Kerberos Error:' in the 
                    SERVER KERBEROS display.  For a list of error 
                    numbers and their meanings, consult relevant MRV In-Reach 
                    or Kerberos documentation."
                ::= { xKerberos 11 }

            kerbErrorTime OBJECT-TYPE
                SYNTAX DateTime
                ACCESS read-only
                STATUS mandatory
                DESCRIPTION
                    "The date and time that kerbError was last updated.  
                    Corresponds directly to the value labeled 
                    'Occurred:' in the SERVER KERBEROS display."
                ::= { xKerberos 12 }

            kerbMasterAccess OBJECT-TYPE
                SYNTAX Counter
                ACCESS read-only
                STATUS mandatory
                DESCRIPTION
                    "The number of times the system successfully 
                    accessed the Kerberos master host.  Corresponds 
                    directly to the value labeled 'Attempts to access:', 
                    'Master', and 'Successful:' in the SERVER KERBEROS 
                    display."
                ::= { xKerberos 13 }

            kerbMasterAccessFailed OBJECT-TYPE
                SYNTAX Counter
                ACCESS read-only
                STATUS mandatory
                DESCRIPTION
                    "The number of times the system failed access to the 
                    Kerberos master host.  Corresponds directly to the 
                    value labeled 'Attempts to access:', 'Master', and 
                    'Unsuccessful:' in the SERVER KERBEROS display."
                ::= { xKerberos 14 }

            kerbServerAccess1 OBJECT-TYPE
                SYNTAX Counter
                ACCESS read-only
                STATUS mandatory
                DESCRIPTION
                    "The number of times the system successfully 
                    accessed the Kerberos primary server.  Corresponds 
                    directly to the value labeled 'Attempts to access:', 
                    'Server1', and 'Successful:' in the SERVER KERBEROS 
                    display."
                ::= { xKerberos 15 }

            kerbServerAccessFailed1 OBJECT-TYPE
                SYNTAX Counter
                ACCESS read-only
                STATUS mandatory
                DESCRIPTION
                    "The number of times the system failed access to the 
                    Kerberos primary server.  Corresponds directly to 
                    the value labeled 'Attempts to access:', 'Server1', 
                    and 'Unsuccessful:' in the SERVER KERBEROS 
                    display."
                ::= { xKerberos 16 }

            kerbServerAccess2 OBJECT-TYPE
                SYNTAX Counter
                ACCESS read-only
                STATUS mandatory
                DESCRIPTION
                    "The number of times the system successfully 
                    accessed the Kerberos secondary server.  Corresponds 
                    directly to the value labeled 'Attempts to access:', 
                    'Server2', and 'Successful:' in the SERVER KERBEROS 
                    display."
                ::= { xKerberos 17 }

            kerbServerAccessFailed2 OBJECT-TYPE
                SYNTAX Counter
                ACCESS read-only
                STATUS mandatory
                DESCRIPTION
                    "The number of times the system failed access to the 
                    Kerberos secondary server.  Corresponds directly to 
                    the value labeled 'Attempts to access:', 'Server2', 
                    and 'Unsuccessful:' in the SERVER KERBEROS 
                    display."
                ::= { xKerberos 18 }

            -- additional scalar values below


            -- the Kerberos Port table

            kerbPortTable OBJECT-TYPE
                SYNTAX SEQUENCE OF KerbPortEntry
                ACCESS not-accessible
                STATUS mandatory
                DESCRIPTION
                    "A list of Kerberos character port entries."
                ::= { xKerberos 19 }

            kerbPortEntry OBJECT-TYPE
                SYNTAX KerbPortEntry
                ACCESS not-accessible
                STATUS mandatory
                DESCRIPTION
                    "Parameter values for a Kerberos port."
                INDEX { kerbPortIndex }
                ::= { kerbPortTable 1 }

            KerbPortEntry ::=
                SEQUENCE {
                    kerbPortIndex
                        INTEGER,
                    kerbPortStatus
                        INTEGER
                }

            kerbPortIndex OBJECT-TYPE
                SYNTAX INTEGER
                ACCESS read-only
                STATUS mandatory
                DESCRIPTION
                    "An index value that uniquely identifies a port 
                    could relate to Kerberos.  The port identified by a 
                    particular value of this index is the same port as 
                    identified by charPortIndex in the Proposed Standard 
                    Internet Character MIB."
                ::= { kerbPortEntry 1 }

            kerbPortStatus OBJECT-TYPE
                SYNTAX INTEGER { none(1), login(2) }
                ACCESS read-write
                STATUS mandatory
                DESCRIPTION
                    "A control indicating the level of Kerberos 
                    operation on the port.  Corresponds directly to PORT 
                    KERBEROS and the value 'Kerberos' following the 
                    label 'Enabled Characteristics' in the PORT 
                    CHARACTERISTICS display."
                ::= { kerbPortEntry 2 }

            -- additional scalars

            kerbServerPort OBJECT-TYPE
                SYNTAX INTEGER { standardPort(88), experimentalPort(750) }
                ACCESS read-write
                STATUS mandatory
                DESCRIPTION
                    "The UDP port number on the Kerberos server where
                    Kerberos messages are sent."
                ::= { xKerberos 20 }


            -- the Port Security group

            -- Implementation of this group is mandatory for all MRV In-Reach
            -- systems that implement Internet port security

            psEntryNumber OBJECT-TYPE
                SYNTAX INTEGER
                ACCESS read-only
                STATUS mandatory
                DESCRIPTION
                    "The number of security entries in this system's 
                    port security table with psEntryStatus of 'valid'."
                ::= { xPortSecurity 1 }

            psEntryNumberLimit OBJECT-TYPE
                SYNTAX INTEGER
                ACCESS read-only
                STATUS mandatory
                DESCRIPTION
                    "The maximum number of security entries in this 
                    system's port security table."
                ::= { xPortSecurity 2 }

            psEntryInvalidIndex OBJECT-TYPE
                SYNTAX INTEGER
                ACCESS read-only
                STATUS mandatory
                DESCRIPTION
                    "A value of psEntryIndex for an entry that has 
                    psEntryStatus of 'invalid'.  A management station 
                    may choose this value when adding a new entry.  
                    Collisions between independent management stations 
                    simultaneously using the same number are beyond the 
                    scope of this document."
                ::= { xPortSecurity 3 }


            -- the Port Security table

            psPortTable OBJECT-TYPE
                SYNTAX SEQUENCE OF PsPortEntry
                ACCESS not-accessible
                STATUS mandatory
                DESCRIPTION
                    "A list of port security character port entries."
                ::= { xPortSecurity 4 }

            psPortEntry OBJECT-TYPE
                SYNTAX PsPortEntry
                ACCESS not-accessible
                STATUS mandatory
                DESCRIPTION
                    "Port security parameter values for a port."
                INDEX { psPortIndex }
                ::= { psPortTable 1 }

            PsPortEntry ::=
                SEQUENCE {
                    psPortIndex
                        INTEGER,
                    psPortDefaultInboundAccess
                        INTEGER,
                    psPortDefaultOutboundAccess
                        INTEGER,
                    psClrInternetSecurity
                        INTEGER
                }

            psPortIndex OBJECT-TYPE
                SYNTAX INTEGER
                ACCESS read-only
                STATUS mandatory
                DESCRIPTION
                    "An index value that uniquely identifies a port for 
                    security purposes.  The port identified by a 
                    particular value of this index is the same port as 
                    identified by charPortIndex in the Proposed Standard 
                    Internet Character MIB."
                ::= { psPortEntry 1 }

            psPortDefaultInboundAccess OBJECT-TYPE
                SYNTAX INTEGER { allow(1), deny(2) }
                ACCESS read-write
                STATUS mandatory
                DESCRIPTION
                    "The default access to the port for incoming TCP 
                    connections.  Corresponds directly to PORT INTERNET 
                    SECURITY DEFAULT INBOUND and the value labeled 
                    'Inbound Default:' in the PORT INTERNET SECURITY 
                    display."
                ::= { psPortEntry 2 }

            psPortDefaultOutboundAccess OBJECT-TYPE
                SYNTAX INTEGER { allow(1), deny(2) }
                ACCESS read-write
                STATUS mandatory
                DESCRIPTION
                    "The default access to the port for outgoing TCP 
                    connections.  Corresponds directly to PORT INTERNET 
                    SECURITY DEFAULT OUTBOUND and the value labeled 
                    'Outbound Default:' in the PORT INTERNET SECURITY 
                    display."
                ::= { psPortEntry 3 }

            psClrInternetSecurity OBJECT-TYPE
                SYNTAX INTEGER { disabled(1), enabled(2) }
                ACCESS read-write
                STATUS mandatory
                DESCRIPTION
                   "A control for if the internet security entries for this
                   port will be cleared upon port logout. The default is
                   disabled."
                ::={ psPortEntry 4 }

            -- the Port Security table

            psTable OBJECT-TYPE
                SYNTAX SEQUENCE OF PsEntry
                ACCESS not-accessible
                STATUS mandatory
                DESCRIPTION
                    "A list of port security entries."
                ::= { xPortSecurity 5 }

            psEntry OBJECT-TYPE
                SYNTAX PsEntry
                ACCESS not-accessible
                STATUS mandatory
                DESCRIPTION
                    "Port security parameter values for an entry for a 
                    port."
                INDEX { psEntryIndex }
                ::= { psTable 1 }

            PsEntry ::=
                SEQUENCE {
                    psEntryIndex
                        INTEGER,
                    psEntryStatus
                        INTEGER,
                    psEntryAddress
                        IpAddress,
                    psEntryMask
                        IpAddress,
                    psEntryAccess
                        INTEGER,
                    psEntryDirection
                        INTEGER,
                    psEntryPortMap
                        OCTET STRING
                }

            psEntryIndex OBJECT-TYPE
                SYNTAX INTEGER
                ACCESS read-only
                STATUS mandatory
                DESCRIPTION
                    "A small, numeric distinguisher for port security 
                    entries.  When adding a new entry, the client should 
                    specify an unused value, such as 
                    psEntryInvalidIndex.  Corresponds directly to the 
                    value labeled 'Entry' in the SERVER INTERNET 
                    SECURITY display."
                ::= { psEntry 1 }

            psEntryStatus OBJECT-TYPE
                SYNTAX INTEGER { invalid(1), valid(2) }
                ACCESS read-write
                STATUS mandatory
                DESCRIPTION
                    "Status of this entry.  Setting the value to 
                    'invalid' invalidates the entry, corresponding 
                    directly to the CLEAR INTERNET SECURITY command.  It 
                    is an implementation-specific matter as to whether 
                    the agent removes an invalidated entry from the 
                    table. Setting this object to 'valid' has no effect.
                    When creating a new instance, one must set 
                    psEntryAddress, psEntryMask, psEntryAccess,
                    psEntryDirection and psEntryPortList for the new
                    instance in the same physical set request. Furthermore,
                    if one wishes to change an entry, one must first
                    delete it and then add it with its new values."
                DEFVAL { valid }
                ::= { psEntry 2 }

            psEntryAddress OBJECT-TYPE
                SYNTAX IpAddress
                ACCESS read-write
                STATUS mandatory
                DESCRIPTION
                    "The IP address to which the entry pertains.  
                    Corresponds directly to the PORT INTERNET SECURITY 
                    internet address and the value labeled 'Internet 
                    Address' in the SERVER INTERNET SECURITY display."
                ::= { psEntry 3 }

            psEntryMask OBJECT-TYPE
                SYNTAX IpAddress
                ACCESS read-write
                STATUS mandatory
                DESCRIPTION
                    "The mask applied to psEntryAddress when making a 
                    security check based on this entry.  Corresponds 
                    directly to PORT INTERNET SECURITY MASK and the 
                    value labeled 'Security Mask' in the SERVER INTERNET 
                    SECURITY display."
                ::= { psEntry 4 }

            psEntryAccess OBJECT-TYPE
                SYNTAX INTEGER { allow(1), deny(2) }
                ACCESS read-write
                STATUS mandatory
                DESCRIPTION
                    "The access to the port for TCP connections when 
                    making a security check based on this entry.  
                    Corresponds directly to PORT INTERNET SECURITY ALLOW 
                    or DENY and the value labeled 'Access' in the SERVER 
                    INTERNET SECURITY display."
                ::= { psEntry 5 }

            psEntryDirection OBJECT-TYPE
                SYNTAX INTEGER { inbound(1), outbound(2) }
                ACCESS read-write
                STATUS mandatory
                DESCRIPTION
                    "The direction of TCP connections to which this 
                    entry applies.  Corresponds directly to PORT 
                    INTERNET SECURITY INBOUND or OUTBOUND and the value 
                    labeled 'Direction' in the SERVER INTERNET SECURITY 
                    display."
                ::= { psEntry 6 }

            psEntryPortMap OBJECT-TYPE
                SYNTAX OCTET STRING
                ACCESS read-write
                STATUS mandatory
                DESCRIPTION
                    "The list of character ports to which this entry 
                    applies.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to PORT INTERNET SECURITY and 
                    the value labeled 'Ports' in the SERVER INTERNET 
                    SECURITY display."
                ::= { psEntry 7 }


            -- the XREMOTE group

            -- Implementation of this group is mandatory for all MRV In-Reach
            -- systems that implement XREMOTE

            xremoteServerName1 OBJECT-TYPE
                SYNTAX DisplayString (SIZE (0..50))
                ACCESS read-write
                STATUS mandatory
                DESCRIPTION
                    "The Domain name of the first XREMOTE font server to 
                    try for downloading fonts.  Corresponds directly to 
                    SERVER XREMOTE PRIMARY SERVER and the value labeled 
                    'Xremote Primary Font Server:' in the SERVER XREMOTE 
                    display."
                ::= { xXremote 1 }

            xremoteServerName2 OBJECT-TYPE
                SYNTAX DisplayString (SIZE (0..50))
                ACCESS read-write
                STATUS mandatory
                DESCRIPTION
                    "The Domain name of the XREMOTE font server to try 
                    for downloading fonts and the primary font server 
                    does not respond.  Corresponds directly to SERVER 
                    XREMOTE SECONDARY SERVER and the value labeled 
                    'Xremote Secondary Font Server:' in the SERVER 
                    XREMOTE display."
                ::= { xXremote 2 }

            xremoteServerAccess1 OBJECT-TYPE
                SYNTAX Counter
                ACCESS read-only
                STATUS mandatory
                DESCRIPTION
                    "The number of times the system successfully 
                    accessed the XREMOTE primary font server.  
                    Corresponds directly to the value labeled 'Attempts 
                    to access:', 'Server1', and 'Successful:' in the 
                    SERVER XREMOTE display."
                ::= { xXremote 3 }

            xremoteServerAccessFailed1 OBJECT-TYPE
                SYNTAX Counter
                ACCESS read-only
                STATUS mandatory
                DESCRIPTION
                    "The number of times the system failed access to the 
                    XREMOTE primary font server.  Corresponds directly 
                    to the value labeled 'Attempts to access:', 
                    'Server1', and 'Unsuccessful:' in the SERVER XREMOTE 
                    display."
                ::= { xXremote 4 }

            xremoteServerAccess2 OBJECT-TYPE
                SYNTAX Counter
                ACCESS read-only
                STATUS mandatory
                DESCRIPTION
                    "The number of times the system successfully 
                    accessed the XREMOTE secondary font server.  
                    Corresponds directly to the value labeled 'Attempts 
                    to access:', 'Server2', and 'Successful:' in the 
                    SERVER XREMOTE display."
                ::= { xXremote 5 }

            xremoteServerAccessFailed2 OBJECT-TYPE
                SYNTAX Counter
                ACCESS read-only
                STATUS mandatory
                DESCRIPTION
                    "The number of times the system failed access to the 
                    XREMOTE secondary font server.  Corresponds directly 
                    to the value labeled 'Attempts to access:', 
                    'Server2', and 'Unsuccessful:' in the SERVER XREMOTE 
                    display."
                ::= { xXremote 6 }

            xremoteSessions OBJECT-TYPE
                SYNTAX Gauge
                ACCESS read-only
                STATUS mandatory
                DESCRIPTION
                    "The number of connected XREMOTE sessions.  
                    Corresponds directly to the value labeled 'Current 
                    Number of Xremote Sessions:' in the SERVER XREMOTE 
                    display."
                ::= { xXremote 7 }

            -- Additional individual objects follow port table


            -- the XREMOTE Port table

            xremotePortTable OBJECT-TYPE
                SYNTAX SEQUENCE OF XremotePortEntry
                ACCESS not-accessible
                STATUS mandatory
                DESCRIPTION
                    "A list of XREMOTE character port entries."
                ::= { xXremote 8 }

            xremotePortEntry OBJECT-TYPE
                SYNTAX XremotePortEntry
                ACCESS not-accessible
                STATUS mandatory
                DESCRIPTION
                    "XREMOTE parameter values for a port."
                INDEX { xremotePortIndex }
                ::= { xremotePortTable 1 }

            XremotePortEntry ::=
                SEQUENCE {
                    xremotePortIndex
                        INTEGER,
                    xremotePortXremote
                        INTEGER,
                    xremotePortXdmQuery
                        INTEGER,
                    xremotePortXdmHost
                        DisplayString
                }

            xremotePortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { xremotePortEntry 1 }

            xremotePortXremote OBJECT-TYPE
                SYNTAX INTEGER { disabled(1), enabled(2) }
                ACCESS read-write
                STATUS mandatory
                DESCRIPTION
                    "Control for use of XREMOTE on the port.  
                    Corresponds directly to PORT XREMOTE and the 
                    presence of the label 'Xremote' following the label 
                    'Enabled Characteristics:' in the PORT 
                    CHARACTERISTICS display."
                ::= { xremotePortEntry 2 }

            xremotePortXdmQuery OBJECT-TYPE
                SYNTAX INTEGER { specific(1), broadcast(2),
                                 indirect(3) }
                ACCESS read-write
                STATUS mandatory
                DESCRIPTION
                    "The type of query message issued by a port when 
                    searching for an X Display Manager (XDM). 
                    Corresponds directly to the PORT XDM QUERY and the 
                    'XDM Query:' in the PORT ALTERNATE CHARACTERISTICS 
                    display"
                ::= { xremotePortEntry 3 }

            xremotePortXdmHost OBJECT-TYPE
                SYNTAX DisplayString (SIZE (0..50))
                ACCESS read-write
                STATUS mandatory
                DESCRIPTION
                    "The Domain name or Internet address of the X 
                    Display Manager (XDM) for a port. Corresponds 
                    directly to the PORT XDM HOST and the 'XDM Host:' in 
                    the PORT ALTERNATE CHARACTERISTICS display"
                ::= { xremotePortEntry 4 }

            -- Additional individual objects

            xremoteServerClients OBJECT-TYPE
                SYNTAX Gauge
                ACCESS read-only
                STATUS mandatory
                DESCRIPTION
                    "The number of active X clients.  Corresponds 
                    directly to the value labeled 'Current Number of 
                    XClients:' in the SERVER XREMOTE display."
                ::= { xXremote 9 }


            -- the Rotary group

            -- Implementation of this group is mandatory for all MRV In-Reach
            -- systems that implement rotaries

            rotaryNumber OBJECT-TYPE
                SYNTAX INTEGER
                ACCESS read-only
                STATUS mandatory
                DESCRIPTION
                    "The number of entries in the Rotary  table."
                ::= { xRotary 1 }


            -- The Rotary  table

            rotaryTable OBJECT-TYPE
                SYNTAX SEQUENCE OF RotaryEntry
                ACCESS not-accessible
                STATUS mandatory
                DESCRIPTION
                    "A list of rotary  entries."
                ::= { xRotary 2 }

            rotaryEntry OBJECT-TYPE
                SYNTAX RotaryEntry
                ACCESS not-accessible
                STATUS mandatory
                DESCRIPTION
                    "Parameter values for a rotary."
                INDEX { rotaryAddress }
                ::= { rotaryTable 1 }

            RotaryEntry ::=
                SEQUENCE {
                    rotaryAddress
                        IpAddress,
                    rotaryStatus
                        INTEGER,
                    rotaryPortMap
                        OCTET STRING
                }

            rotaryAddress OBJECT-TYPE
                SYNTAX IpAddress
                ACCESS read-only
                STATUS mandatory
                DESCRIPTION
                    "The internet address to be recognized as a rotary.  
                    Corresponds directly to the ip-address portion of 
                    SERVER INTERNET ROTARY and the value labeled 
                    'Internet Address' in the SERVER INTERNET ROTARY 
                    display."
                ::= { rotaryEntry 1 }

            rotaryStatus OBJECT-TYPE
                SYNTAX INTEGER { invalid(1), valid(2) }
                ACCESS read-write
                STATUS mandatory
                DESCRIPTION
                    "Status of this entry.  Setting the value to 
                    'invalid' invalidates the entry, corresponding 
                    directly to the CLEAR SERVER INTERNET ROTARY 
                    command.  It is an implementation-specific matter as 
                    to whether the agent removes an invalidated entry 
                    from the table. Setting the value to 'valid' in 
                    conjunction with a new rotaryAddress will add a 
                    new entry to the table. When adding a new entry,
                    one should also specify a rotaryPortMap as the DEFVAL
                    of 0..0 for rotaryPortMap is meaningless."
                DEFVAL { valid }
                ::= { rotaryEntry 2 }

            rotaryPortMap OBJECT-TYPE
                SYNTAX OCTET STRING
                ACCESS read-write
                STATUS mandatory
                DESCRIPTION
                    "The list of character ports that compose the 
                    rotary.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to port-list portion of SERVER 
                    INTERNET ROTARY and the value labeled 'Ports' in the 
                    SERVER INTERNET ROTARY display."
                DEFVAL { "" }  -- zero length
                ::= { rotaryEntry 3 }


            -- the EGP group

            -- Implementation of this group is mandatory for all MRV In-Reach
            -- systems that implement EGP

            egpRouting OBJECT-TYPE
                SYNTAX INTEGER { disabled(1), enabled(2) }
                ACCESS read-write
                STATUS mandatory
                DESCRIPTION
                    "Control for EGP routing services."
                ::= { xEgp 1 }

            egpStatus OBJECT-TYPE
                SYNTAX INTEGER { active(1), noMemory(2), noIpRouting(3),
                                 noEgpRouting(4), noNeighbors(5),
                                 noAS(6) }
                ACCESS read-only
                STATUS mandatory
                DESCRIPTION
                    "Status of the EGP routing services indicating why 
                    it is not running."
                ::= { xEgp 2 }

            egpNbrTable OBJECT-TYPE
                SYNTAX SEQUENCE OF EgpNbrEntry
                ACCESS not-accessible
                STATUS mandatory
                DESCRIPTION
                    "The EGP neighbor table."
                ::= { xEgp 3 }

            egpNbrEntry OBJECT-TYPE
                SYNTAX EgpNbrEntry
                ACCESS not-accessible
                STATUS mandatory
                DESCRIPTION
                    "Information about this entity's relationship with a 
                    particular EGP neighbor."
                INDEX { egpNbrAddr }
                ::= { egpNbrTable 1 }

            EgpNbrEntry ::=
                SEQUENCE {
                    egpNbrAddr
                        IpAddress,
                    egpNbrIntervalDead
                        INTEGER,
                    egpNbrStatus
                        INTEGER
                }

            egpNbrAddr OBJECT-TYPE
                SYNTAX IpAddress
                ACCESS read-only
                STATUS mandatory
                DESCRIPTION
                    "The IP address of this entry's EGP neighbor."
                ::= { egpNbrEntry 1 }

            egpNbrIntervalDead OBJECT-TYPE
                SYNTAX INTEGER (0..65535)
                ACCESS read-write
                STATUS mandatory
                DESCRIPTION
                    "The interval upon entering the cease or idle state 
                    before automatically assuming a Start Event has 
                    occured.  If a neighbor does not respond within 5 
                    minutes, a Stop Event will automatically occur.  The 
                    interval is in hundredths of seconds."
                DEFVAL { 30000 }
                ::= { egpNbrEntry 2 }

            egpNbrStatus OBJECT-TYPE
                SYNTAX INTEGER { invalid(1), valid(2) }
                ACCESS read-write
                STATUS mandatory
                DESCRIPTION
                    "The status of the entry for this neighbor.  Set to 
                    'invalid' to remove the entry."
                DEFVAL { valid }
                ::= { egpNbrEntry 3 }


            -- the OSPF group

            -- Implementation of this group is mandatory for all MRV In-Reach
            -- systems that implement OSPF

            ospfAutoConfigure OBJECT-TYPE
                SYNTAX INTEGER { disabled(1), enabled(2) }
                ACCESS read-write
                STATUS mandatory
                DESCRIPTION
                    "Control whether OSPF will automatically configure 
                    itself."
                ::= { xOspf 1 }

            ospfStatus OBJECT-TYPE
                SYNTAX INTEGER { active(1), noMemory(2), noIpRouting(3),
                                 noOspfRouting(4), noAreas(5),
                                 noInterfaces(6), noRtrId(7), 
                                 noBackBoneAndVirtualInterfaces(8),
                                 noBackBoneAndInterface(9),
                                 noBackBone(10) }
                ACCESS read-only
                STATUS mandatory
                DESCRIPTION
                    "Status of the OSPF routing services indicating why 
                    it is not running."
                ::= { xOspf 2 }

            -- the OSPF Interface Metric table

            ospfIfMtrcTable OBJECT-TYPE
                SYNTAX SEQUENCE OF OspfIfMtrcEntry
                ACCESS not-accessible
                STATUS mandatory
                DESCRIPTION
                    "The TOS metrics for a non-virtual interface 
                    identified by the interface index."
                ::= { xOspf 3 }

            ospfIfMtrcEntry OBJECT-TYPE
                SYNTAX OspfIfMtrcEntry
                ACCESS not-accessible
                STATUS mandatory
                DESCRIPTION
                    "A particular TOS metric for a non-virtual interface 
                    identified by the interface index."
                INDEX { ospfIfMtrcIpAddress, ospfIfMtrcAddressLessIf,
                        ospfIfMtrcTos }
                ::= { ospfIfMtrcTable 1 }

            OspfIfMtrcEntry ::=
                SEQUENCE {
                    ospfIfMtrcIpAddress
                        IpAddress,
                    ospfIfMtrcAddressLessIf
                        INTEGER,
                    ospfIfMtrcTos
                        INTEGER,
                    ospfIfMtrcCostActual
                        INTEGER
                }

            ospfIfMtrcIpAddress OBJECT-TYPE
                SYNTAX IpAddress
                ACCESS read-only
                STATUS mandatory
                DESCRIPTION
                    "Same as ospfIfMetricIpAddress in OSPF MIB, the IP 
                    address of this OSPF interface."
                REFERENCE
                    "OSPF Version 2 Management Information Base, RFC 
                    1253"
                ::= { ospfIfMtrcEntry 1 }

            ospfIfMtrcAddressLessIf OBJECT-TYPE
                SYNTAX INTEGER
                ACCESS read-only
                STATUS mandatory
                DESCRIPTION
                    "Same as ospfIfMetricAddressLessIf in OSPF MIB, for 
                    the purpose of easing the instancing of addressed 
                    and addressless interfaces.  This variable takes the 
                    value 0 on interfaces with IP Addresses, and the 
                    value of ifIndex for interfaces having no IP 
                    Address."
                REFERENCE
                    "OSPF Version 2 Management Information Base, RFC 
                    1253"
                ::= { ospfIfMtrcEntry 2 }

            ospfIfMtrcTos OBJECT-TYPE
                SYNTAX INTEGER ( 1..16 )
                ACCESS read-only
                STATUS mandatory
                DESCRIPTION
                    "Same as ospfIfMetricTOS in OSPF MIB, the type of 
                    service metric being referenced."
                REFERENCE
                    "OSPF Version 2 Management Information Base, RFC 
                    1253"
                ::= { ospfIfMtrcEntry 3 }

            ospfIfMtrcCostActual OBJECT-TYPE
                SYNTAX INTEGER ( 1..65535 )
                ACCESS read-only
                STATUS mandatory
                DESCRIPTION
                    "The actual cost of the metric in case it was set to 
                    auto."
                ::= { ospfIfMtrcEntry 4 }

            -- the OSPF Interface table

            ospfXIfTable OBJECT-TYPE
                SYNTAX SEQUENCE OF OspfXIfEntry
                ACCESS not-accessible
                STATUS mandatory
                DESCRIPTION
                    "The TOS metrics for a non-virtual interface 
                    identified by the interface index."
                ::= { xOspf 4 }

            ospfXIfEntry OBJECT-TYPE
                SYNTAX OspfXIfEntry
                ACCESS not-accessible
                STATUS mandatory
                DESCRIPTION
                    "Interface parameters for OSPF."
                INDEX { ospfXIfIpAddress, ospfXIfAddressLessIf }
                ::= { ospfXIfTable 1 }

            OspfXIfEntry ::=
                SEQUENCE {
                    ospfXIfIpAddress
                        IpAddress,
                    ospfXIfAddressLessIf
                        INTEGER,
                    ospfXIfTypeActual
                        INTEGER,
                    ospfXIfStatus
                        INTEGER
                }

            ospfXIfIpAddress OBJECT-TYPE
                SYNTAX IpAddress
                ACCESS read-only
                STATUS mandatory
                DESCRIPTION
                    "Same as ospfIfIpAddress in OSPF MIB, the IP address 
                    of this OSPF interface."
                REFERENCE
                    "OSPF Version 2 Management Information Base, RFC 
                    1253"
                ::= { ospfXIfEntry 1 }

            ospfXIfAddressLessIf OBJECT-TYPE
                SYNTAX INTEGER
                ACCESS read-only
                STATUS mandatory
                DESCRIPTION
                    "Same as ospfIfAddressLessIf in OSPF MIB, for the 
                    purpose of easing the instancing of addressed and 
                    addressless interfaces.  This variable takes the 
                    value 0 on interfaces with IP Addresses, and the 
                    value of ifIndex for interfaces having no IP 
                    Address."
                REFERENCE
                    "OSPF Version 2 Management Information Base, RFC 
                    1253"
                ::= { ospfXIfEntry 2 }

            ospfXIfTypeActual OBJECT-TYPE
                SYNTAX INTEGER { broadcast(1), nonbroadcast(2),
                                 pointToPoint(3) }
                ACCESS read-only
                STATUS mandatory
                DESCRIPTION
                    "The interface type."
                ::= { ospfXIfEntry 3 }

            ospfXIfStatus OBJECT-TYPE
                SYNTAX INTEGER { invalid(1), valid(2) }
                ACCESS read-write
                STATUS mandatory
                DESCRIPTION
                    "The status of the interface entry, including the 
                    entry in the standard OSPF MIB.  Set to 'invalid' to 
                    remove the entry."
                DEFVAL { valid }
                ::= { ospfXIfEntry 4 }

            -- the OSPF Area table

            ospfXAreaTable OBJECT-TYPE
                SYNTAX SEQUENCE OF OspfXAreaEntry
                ACCESS not-accessible
                STATUS mandatory
                DESCRIPTION
                    "Parameters for an OSPF area."
                ::= { xOspf 5 }

            ospfXAreaEntry OBJECT-TYPE
                SYNTAX OspfXAreaEntry
                ACCESS not-accessible
                STATUS mandatory
                DESCRIPTION
                    "An area entry."
                INDEX { ospfXAreaId }
                ::= { ospfXAreaTable 1 }

            OspfXAreaEntry ::=
                SEQUENCE {
                    ospfXAreaId
                        IpAddress,
                    ospfXAreaStatus
                        INTEGER
                }

            ospfXAreaId OBJECT-TYPE
                SYNTAX IpAddress
                ACCESS read-only
                STATUS mandatory
                DESCRIPTION
                    "Same as ospfAreaId in OSPF MIB, the ID of the 
                    area."
                REFERENCE
                    "OSPF Version 2 Management Information Base, RFC 
                    1253"
                ::= { ospfXAreaEntry 1 }

            ospfXAreaStatus OBJECT-TYPE
                SYNTAX INTEGER { invalid(1), valid(2) }
                ACCESS read-write
                STATUS mandatory
                DESCRIPTION
                    "The status of the area entry, including the entry 
                    in the standard OSPF MIB.  Set to 'invalid' to 
                    remove the entry."
                DEFVAL { valid }
                ::= { ospfXAreaEntry 2 }


            -- the Router IP group

            -- Implementation of this group is mandatory for all MRV In-Reach
            -- systems that implement IP and do through routing

            ipAdExtTable OBJECT-TYPE
                SYNTAX SEQUENCE OF IpAdExtEntry
                ACCESS not-accessible
                STATUS mandatory
                DESCRIPTION
                    "Table of additional fields indexed by local IP 
                    address.  An entry in this table is created or 
                    deleted when an entry in the ipAddrTable is created 
                    or deleted."
                ::= { xRouterIp 1 }

            ipAdExtEntry OBJECT-TYPE
                SYNTAX IpAdExtEntry
                ACCESS not-accessible
                STATUS mandatory
                DESCRIPTION
                    "A particular entry."
                INDEX { ipAdEntExtAddress }
                ::= { ipAdExtTable 1 }

            IpAdExtEntry ::=
                SEQUENCE {
                    ipAdEntExtAddress
                        IpAddress,
                    ipAdEntExtProxyArp
                        INTEGER,
                    ipAdEntExtRip
                        INTEGER
                }

            ipAdEntExtAddress OBJECT-TYPE
                SYNTAX IpAddress
                ACCESS read-only
                STATUS mandatory
                DESCRIPTION
                    "Same as ipAdEntAddr, a local address representing a 
                    network connection."
                ::= { ipAdExtEntry 1 }

            ipAdEntExtProxyArp OBJECT-TYPE
                SYNTAX INTEGER { enabled(2), disabled(1) }   
                ACCESS read-write
                STATUS mandatory
                DESCRIPTION
                    "Controls whether proxy ARP is active for this local 
                    address."
                DEFVAL { disabled }
                ::= { ipAdExtEntry 2 }

            ipAdEntExtRip OBJECT-TYPE
                SYNTAX INTEGER { enabled(2), disabled(1) }   
                ACCESS read-only
                STATUS deprecated
                DESCRIPTION
                    "Controls whether RIP as a router discovery protocol 
                    is active for this local address."
                DEFVAL { disabled }
                ::= { ipAdExtEntry 3 }


            -- the IP Router Interface table

            ipRouterIfTable OBJECT-TYPE
                SYNTAX SEQUENCE OF IpRouterIfEntry
                ACCESS not-accessible
                STATUS mandatory
                DESCRIPTION
                    "Table of IP router values indexed by interface."
                ::= { xRouterIp 2 }

            ipRouterIfEntry OBJECT-TYPE
                SYNTAX IpRouterIfEntry
                ACCESS not-accessible
                STATUS mandatory
                DESCRIPTION
                    "A particular entry."
                INDEX { ipRouterIfIndex }
                ::= { ipRouterIfTable 1 }

            IpRouterIfEntry ::=
                SEQUENCE {
                    ipRouterIfIndex
                        INTEGER,
                    ipRouterIfProtocolPriority
                        INTEGER,
                    ipRouterIfMTU
                        INTEGER,
                    ipRouterIfRDP
                        INTEGER,
                    ipRouterIfArpPacketsIn
                        Counter,
                    ipRouterIfArpPacketsOut
                        Counter,
                    ipRouterIfPacketsIn
                        Counter,
                    ipRouterIfPacketsOut
                        Counter,
                    ipRouterIfForwardsIn
                        Counter,
                    ipRouterIfForwardsOut
                        Counter
                }

            ipRouterIfIndex OBJECT-TYPE
                SYNTAX INTEGER
                ACCESS read-only
                STATUS mandatory
                DESCRIPTION
                    "The index of the interface; same as IfIndex."
                ::= { ipRouterIfEntry 1 }

            ipRouterIfProtocolPriority OBJECT-TYPE
                SYNTAX INTEGER { low(1), medium(3), high(5) }
                ACCESS read-write
                STATUS mandatory
                DESCRIPTION
                    "The priority at which all Internet routed packets 
                    will be placed on the WAN output queue."
                DEFVAL { medium }
                ::= { ipRouterIfEntry 2 }

            ipRouterIfMTU OBJECT-TYPE
                SYNTAX INTEGER (128..65535)
                ACCESS read-write
                STATUS mandatory
                DESCRIPTION
                    "The size of the largest datagram that IP can
                     transmit on this interface.  The default value
                     is actually hardware dependent."
                DEFVAL { 1500 }
                ::= { ipRouterIfEntry 3 }

            ipRouterIfRDP OBJECT-TYPE
                SYNTAX INTEGER { enabled(1), disabled(2) }
                ACCESS read-write
                STATUS mandatory
                DESCRIPTION
                    "Control for whether the router side of the Router 
                    Discovery Protocol is running on this interface."
                DEFVAL { disabled }
                ::= { ipRouterIfEntry 4 }

            ipRouterIfArpPacketsIn OBJECT-TYPE
                SYNTAX Counter
                ACCESS read-only
                STATUS mandatory
                DESCRIPTION
                    "The number of ARP packets received on this 
                    interface."
                ::= { ipRouterIfEntry 5 }

            ipRouterIfArpPacketsOut OBJECT-TYPE
                SYNTAX Counter
                ACCESS read-only
                STATUS mandatory
                DESCRIPTION
                    "The number of ARP packets sent on this interface."
                ::= { ipRouterIfEntry 6 }

            ipRouterIfPacketsIn OBJECT-TYPE
                SYNTAX Counter
                ACCESS read-only
                STATUS mandatory
                DESCRIPTION
                    "The number of IP packets received on this 
                    interface."
                ::= { ipRouterIfEntry 7 }

            ipRouterIfPacketsOut OBJECT-TYPE
                SYNTAX Counter
                ACCESS read-only
                STATUS mandatory
                DESCRIPTION
                    "The number of IP packets sent on this interface."
                ::= { ipRouterIfEntry 8 }

            ipRouterIfForwardsIn OBJECT-TYPE
                SYNTAX Counter
                ACCESS read-only
                STATUS mandatory
                DESCRIPTION
                    "The number of IP packets received on this interface 
                    that were forwarded."
                ::= { ipRouterIfEntry 9 }

            ipRouterIfForwardsOut OBJECT-TYPE
                SYNTAX Counter
                ACCESS read-only
                STATUS mandatory
                DESCRIPTION
                    "The number of IP packets sent on this interface 
                    that were forwarded."
                ::= { ipRouterIfEntry 10 }


            -- the IP Router Traffic subgroup

            -- Implementation of this subgroup is mandatory for all
            -- MRV In-Reach IP router systems that implement traffic
            -- monitoring

            xIpTraffic   OBJECT IDENTIFIER ::= { xRouterIp 3 }

            ipTrafficSort OBJECT-TYPE
                SYNTAX INTEGER { ready(1), execute(2) }
                ACCESS read-write
                STATUS mandatory
                DESCRIPTION
                    "Setting to 'execute' causes the most recent traffic 
                    information to be sorted into the ipTrafficTable. 
                    The sorting precedence is: decreasing percentage, 
                    increasing destination address, increasing source 
                    address, and increasing interface number.  Setting 
                    to 'ready' has no effect."
                ::= { xIpTraffic 1 }

            -- Note:  additional individual objects follow table

            ipTrafficTable OBJECT-TYPE
                SYNTAX SEQUENCE OF IpTrafficEntry
                ACCESS not-accessible
                STATUS mandatory
                DESCRIPTION
                    "A list of traffic entries, sorted in the order 
                    specified by ipTrafficSort."
                ::= { xIpTraffic 2 }

            ipTrafficEntry OBJECT-TYPE
                SYNTAX IpTrafficEntry
                ACCESS not-accessible
                STATUS mandatory
                DESCRIPTION
                    "A traffic entry."
                INDEX { ipTrafficIndex }
                ::= { ipTrafficTable 1 }

            IpTrafficEntry ::=
                SEQUENCE {
                    ipTrafficIndex
                        INTEGER,
                    ipTrafficPercent
                         INTEGER,
                    ipTrafficDstAddr
                        IpAddress,
                    ipTrafficSrcAddr
                        IpAddress,
                    ipTrafficProtocol
                         INTEGER,
                    ipTrafficDstPort
                         INTEGER,
                    ipTrafficSrcPort
                         INTEGER,
                    ipTrafficIf
                        INTEGER

                }

            ipTrafficIndex OBJECT-TYPE
                SYNTAX INTEGER
                ACCESS read-only
                STATUS mandatory
                DESCRIPTION
                    "Identification of this traffic entry."
                ::= { ipTrafficEntry 1 }

            ipTrafficPercent OBJECT-TYPE
                SYNTAX INTEGER 
                ACCESS read-only
                STATUS mandatory
                DESCRIPTION
                    "The percentage of total traffic that this traffic 
                    entry represents, in tenths of a percent."
                ::= { ipTrafficEntry 2 }

            ipTrafficDstAddr OBJECT-TYPE
                SYNTAX IpAddress
                ACCESS read-only
                STATUS mandatory
                DESCRIPTION
                    "The destination IP address of the traffic entry."
                ::= { ipTrafficEntry 3 }

            ipTrafficSrcAddr OBJECT-TYPE
                SYNTAX IpAddress
                ACCESS read-only
                STATUS mandatory
                DESCRIPTION
                    "The source IP address of the traffic entry."
                ::= { ipTrafficEntry 4 }

            ipTrafficProtocol OBJECT-TYPE
                SYNTAX INTEGER ( 0..255 )
                ACCESS read-only
                STATUS mandatory
                DESCRIPTION
                    "The IP protocol type of the traffic entry."
                ::= { ipTrafficEntry 5 }

            ipTrafficDstPort OBJECT-TYPE
                SYNTAX INTEGER ( 0..65535 )
                ACCESS read-only
                STATUS mandatory
                DESCRIPTION
                    "The destination TCP/UDP port of the traffic 
                    entry."
                ::= { ipTrafficEntry 6 }

            ipTrafficSrcPort OBJECT-TYPE
                SYNTAX INTEGER ( 0..65535 )
                ACCESS read-only
                STATUS mandatory
                DESCRIPTION
                    "The source TCP/UDP port of the traffic entry."
                ::= { ipTrafficEntry 7 }

            ipTrafficIf OBJECT-TYPE
                SYNTAX INTEGER
                ACCESS read-only
                STATUS mandatory
                DESCRIPTION
                    "The inbound interface to which the traffic entry 
                    applies.  This value is the same as IfIndex."
                ::= { ipTrafficEntry 8 }

            -- additional individual objects

            ipTrafficMonitoring OBJECT-TYPE
                SYNTAX INTEGER { enabled(1), disabled(2) }
                ACCESS read-write
                STATUS mandatory
                DESCRIPTION
                    "Control for whether the router side of the Router 
                    Discovery Protocol is running on this interface."
                ::= { xIpTraffic 3 }

            -- IP Net to Media table extension

            xIpNetToMediaTable OBJECT-TYPE
                SYNTAX SEQUENCE OF XIpNetToMediaEntry
                ACCESS not-accessible
                STATUS mandatory
                DESCRIPTION
                    "MRV In-Reach extensions to the IP Address Translation 
                    Table."
                ::= { xRouterIp 4 }

            xIpNetToMediaEntry OBJECT-TYPE
                SYNTAX XIpNetToMediaEntry
                ACCESS not-accessible
                STATUS mandatory
                DESCRIPTION
                    "Entry parameters."
                INDEX { ifIndex, ipNetToMediaNetAddress }
                ::= { xIpNetToMediaTable 1 }

            XIpNetToMediaEntry ::=
                SEQUENCE {
                    xIpNetToMediaCircuit
                        INTEGER,
                    xIpNetToMediaReverseArp
                        INTEGER
                }

            xIpNetToMediaCircuit OBJECT-TYPE
                SYNTAX INTEGER
                ACCESS read-write
                STATUS mandatory
                DESCRIPTION
                    "An additional identifier for the circuit (i.e. 
                    Frame Relay DLCI or X.25 VC) which the entry 
                    extends."
                ::= { xIpNetToMediaEntry 1 }

            xIpNetToMediaReverseArp OBJECT-TYPE
                SYNTAX INTEGER { disabled(1), enabled(2) }
                ACCESS read-write
                STATUS mandatory
                DESCRIPTION
                    "Whether reverse ARP is supported on this entry."
                ::= { xIpNetToMediaEntry 2 }


            -- the Router UDP group

            -- Implementation of this group is mandatory for all MRV In-Reach
            -- systems that implement UDP and do through routing

            -- Individual objects follow the UDP Port table

            -- the UDP Broadcast Server table

            udpBcstServerTable OBJECT-TYPE
                SYNTAX SEQUENCE OF UdpBcstServerEntry
                ACCESS not-accessible
                STATUS mandatory
                DESCRIPTION
                    "Table of servers to whom UDP broadcast messages 
                    will be forwarded."
                ::= { xRouterUdp 1 }

            udpBcstServerEntry OBJECT-TYPE
                SYNTAX UdpBcstServerEntry
                ACCESS not-accessible
                STATUS mandatory
                DESCRIPTION
                    "A particular entry."
                INDEX { udpBcstServerAddress }
                ::= { udpBcstServerTable 1 }

            UdpBcstServerEntry ::=
                SEQUENCE {
                    udpBcstServerAddress
                        IpAddress,
                    udpBcstServerStatus
                        INTEGER
                }

            udpBcstServerAddress OBJECT-TYPE
                SYNTAX IpAddress
                ACCESS read-only
                STATUS mandatory
                DESCRIPTION
                    "Internet address of the server."
                ::= { udpBcstServerEntry 1 }

            udpBcstServerStatus OBJECT-TYPE
                SYNTAX INTEGER { invalid(1), valid(2) }
                ACCESS read-write
                STATUS mandatory
                DESCRIPTION
                    "The status of the server.  Set to 'invalid' to 
                    remove the entry."
                DEFVAL { valid }
                ::= { udpBcstServerEntry 2 }


            -- the UDP Broadcast Port table

            udpBcstPortTable OBJECT-TYPE
                SYNTAX SEQUENCE OF UdpBcstPortEntry
                ACCESS not-accessible
                STATUS mandatory
                DESCRIPTION
                    "Table of incoming UDP destination port numbers for 
                    which UDP broadcasts will be forwarded."
                ::= { xRouterUdp 2 }

            udpBcstPortEntry OBJECT-TYPE
                SYNTAX UdpBcstPortEntry
                ACCESS not-accessible
                STATUS mandatory
                DESCRIPTION
                    "A particular entry."
                INDEX { udpBcstPort }
                ::= { udpBcstPortTable 1 }

            UdpBcstPortEntry ::=
                SEQUENCE {
                    udpBcstPort
                        INTEGER,
                    udpBcstPortStatus
                        INTEGER
                }

            udpBcstPort OBJECT-TYPE
                SYNTAX INTEGER
                ACCESS read-only
                STATUS mandatory
                DESCRIPTION
                    "The incoming destination UDP port number."
                ::= { udpBcstPortEntry 1 }

            udpBcstPortStatus OBJECT-TYPE
                SYNTAX INTEGER { invalid(1), valid(2) }
                ACCESS read-write
                STATUS mandatory
                DESCRIPTION
                    "The status of broadcast forwarding for the port.  
                    Set to 'invalid' to remove the entry."
                DEFVAL { valid }
                ::= { udpBcstPortEntry 2 }


            -- Individual objects

            udpBcstRouting OBJECT-TYPE
                SYNTAX INTEGER { disabled(1), enabled(2) }
                ACCESS read-write
                STATUS mandatory
                DESCRIPTION
                    "The indication of whether this entity forwards UDP 
                    broadcasts."
                DEFVAL { disabled }
                ::= { xRouterUdp 3 }


            -- the Router Policy group

            -- Implementation of this group is mandatory for all MRV In-Reach
            -- systems that implement routing policy and do through
            -- routing

            -- the Router Policy group contains three subgroups:

            xImport OBJECT IDENTIFIER ::= { xRouterPolicy 1 }
            xExport OBJECT IDENTIFIER ::= { xRouterPolicy 2 }
            xFilter OBJECT IDENTIFIER ::= { xRouterPolicy 3 }

            -- the Import subgroup

            -- the EGP Import table

            impEgpRuleTable OBJECT-TYPE
                SYNTAX SEQUENCE OF ImpEgpRuleEntry
                ACCESS not-accessible
                STATUS mandatory
                DESCRIPTION
                    "The EGP import table."
                ::= { xImport 1 }

            impEgpRuleEntry OBJECT-TYPE
                SYNTAX ImpEgpRuleEntry
                ACCESS not-accessible
                STATUS mandatory
                DESCRIPTION
                    "An EGP import rule.  Each rule is keyed by the 
                    Autonomous System of the EGP neighbor and the IP 
                    network of the route learned from the  neighbor.  
                    The AS can be set to a wild card as can the IP 
                    network. When a route is learned from a neighbor, 
                    the most specific import rule is applied to the 
                    route.  The route is either accepted or discarded 
                    and its metrics are applied according to the rule.  
                    An exact match on the AS and IP network is the most 
                    exact rule.  An exact match on the AS and a wild 
                    card match on the IP network is the 2nd most exact 
                    rule. A wild card match on the AS and an exact match 
                    on the IP network is the 3rd most exact match.  
                    Finally, a total wild card match is the least exact 
                    rule."
                INDEX { impEgpRuleAs, impEgpRuleNetwork }
                ::= { impEgpRuleTable 1 }

            ImpEgpRuleEntry ::=
                SEQUENCE { 
                    impEgpRuleAs
                        INTEGER,
                    impEgpRuleNetwork
                        IpAddress,
                    impEgpRuleAction
                        INTEGER,
                    impEgpRulePreference
                        INTEGER,
                    impEgpRuleType
                        INTEGER,
                    impEgpRuleMetricAction
                        INTEGER,
                    impEgpRuleMetric
                        INTEGER,
                    impEgpRuleStatus
                        INTEGER
                }

            impEgpRuleAs OBJECT-TYPE
                SYNTAX INTEGER ( 0..65535 )
                ACCESS read-only
                STATUS mandatory
                DESCRIPTION
                    "The Autonomous System of the neighbor.  The value 
                    65535 is a wild card matching any AS number."
                ::= { impEgpRuleEntry 1 }

            impEgpRuleNetwork OBJECT-TYPE
                SYNTAX IpAddress
                ACCESS read-only
                STATUS mandatory
                DESCRIPTION
                    "The IP network learned from the neighbor.  The 
                    value 255.255.255.255 is a wild card matching any 
                    network."
                ::= { impEgpRuleEntry 2 }

            impEgpRuleAction OBJECT-TYPE
                SYNTAX INTEGER { discard(1), accept(2) }
                ACCESS read-write
                STATUS mandatory
                DESCRIPTION
                    "Control whether the route is learned or 
                    discarded."
                DEFVAL { accept }
                ::= { impEgpRuleEntry 3 }

            impEgpRulePreference OBJECT-TYPE
                SYNTAX INTEGER ( 1..255 )
                ACCESS read-write
                STATUS mandatory
                DESCRIPTION
                    "Preference to be stored with the route. The lower 
                    preference is preferred."
                DEFVAL { 2 }
                ::= { impEgpRuleEntry 4 }

            impEgpRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impEgpRuleEntry 5 }

            impEgpRuleMetricAction OBJECT-TYPE
                SYNTAX INTEGER { replace(1), increment(2),
                                 decrement(3) }
                ACCESS read-write
                STATUS mandatory
                DESCRIPTION
                    "How to apply the impEgpRuleMetric field to the 
                    metric learned with the route before storing it in 
                    the routing table."
                DEFVAL { increment }
                ::= { impEgpRuleEntry 6 }

            impEgpRuleMetric OBJECT-TYPE
                SYNTAX INTEGER (0..16777215)
                ACCESS read-write
                STATUS mandatory
                DESCRIPTION
                    "Metric value to be applied to the metric learned 
                    learned with the route before storing it in the 
                    routing table."
                DEFVAL { 0 }
                ::= { impEgpRuleEntry 7 }

            impEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impEgpRuleEntry 8 }

            -- the OSPF Import table

            impOspfRuleTable OBJECT-TYPE
                SYNTAX SEQUENCE OF ImpOspfRuleEntry
                ACCESS not-accessible
                STATUS mandatory
                DESCRIPTION
                    "The OSPF import table."
                ::= { xImport 2 }

            impOspfRuleEntry OBJECT-TYPE
                SYNTAX ImpOspfRuleEntry
                ACCESS not-accessible
                STATUS mandatory
                DESCRIPTION
                    "An OSPF import rule.  Each rule is keyed by the IP 
                    network of the route and the AS from which it was 
                    learned.  The Ip network and the AS can both be set 
                    to a wild card.  When an OSPF route is added to the 
                    routing table, the most specific import rule is 
                    applied to set the preference of the route.  An 
                    exact match on the Ip network and on the AS is the 
                    most exact rule.  An exact match on the IP network 
                    and a wild card match on the AS is the 2nd most 
                    exact rule.  A wild card match on both the  on the 
                    AS and IP network is the next and least exact 
                    rule."
                INDEX { impOspfRuleNetwork }
                ::= { impOspfRuleTable 1 }

            ImpOspfRuleEntry ::=
                SEQUENCE {
                    impOspfRuleNetwork
                        IpAddress,
                    impOspfRulePreference
                        INTEGER,
                    impOspfRuleStatus
                        INTEGER
                }

            impOspfRuleNetwork OBJECT-TYPE
                SYNTAX IpAddress
                ACCESS read-only
                STATUS mandatory
                DESCRIPTION
                    "The IP network of the route.  The value 
                    255.255.255.255 is a wild card matching any 
                    network."
                ::= { impOspfRuleEntry 1 }

            impOspfRulePreference OBJECT-TYPE
                SYNTAX INTEGER ( 1..255 )
                ACCESS read-write
                STATUS mandatory
                DESCRIPTION
                    "Preference to be stored with the route. The lower 
                    preference is preferred."
                DEFVAL { 8 }
                ::= { impOspfRuleEntry 2 }

            impOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { impOspfRuleEntry 3 }

            -- the RIP Import table

            impRipRuleTable OBJECT-TYPE
                SYNTAX SEQUENCE OF ImpRipRuleEntry
                ACCESS not-accessible
                STATUS mandatory
                DESCRIPTION
                    "The RIP import table."
                ::= { xImport 3 }

            impRipRuleEntry OBJECT-TYPE
                SYNTAX ImpRipRuleEntry
                ACCESS not-accessible
                STATUS mandatory
                DESCRIPTION
                    "A RIP import rule.  Each rule is keyed by the 
                    interface and the IP network of the route learned 
                    from the neighbor.  The route is either accepted or 
                    discarded and its metrics are applied according to 
                    the rule.  An exact match on the IP network is the 
                    rule that will be applied.  If an exact match does 
                    not exist, the rule with the wild card IP network is 
                    used."
                INDEX { impRipRuleFromIf, impRipRuleNetwork }
                ::= { impRipRuleTable 1 }

            ImpRipRuleEntry ::=
                SEQUENCE {
                    impRipRuleFromIf
                        IpAddress,
                    impRipRuleNetwork
                        IpAddress,
                    impRipRuleAction
                        INTEGER,
                    impRipRulePreference
                        INTEGER,
                    impRipRuleType
                        INTEGER,
                    impRipRuleMetricAction
                        INTEGER,
                    impRipRuleMetric
                        INTEGER,
                    impRipRuleStatus
                        INTEGER
                }

            impRipRuleFromIf OBJECT-TYPE
                SYNTAX IpAddress
                ACCESS read-only
                STATUS mandatory
                DESCRIPTION
                    "The interface index of the interface where the rule 
                    applies, same as ifIndex."
                ::= { impRipRuleEntry 1 }

            impRipRuleNetwork OBJECT-TYPE
                SYNTAX IpAddress
                ACCESS read-only
                STATUS mandatory
                DESCRIPTION
                    "The IP network learned from the neighbor.  The 
                    value 255.255.255.255 is a wild card matching any 
                    network."
                ::= { impRipRuleEntry 2 }

            impRipRuleAction OBJECT-TYPE
                SYNTAX INTEGER { discard(1), accept(2) }
                ACCESS read-write
                STATUS mandatory
                DESCRIPTION
                    "Control whether the route is learned or 
                    discarded."
                DEFVAL { accept }
                ::= { impRipRuleEntry 3 }

            impRipRulePreference OBJECT-TYPE
                SYNTAX INTEGER ( 0..255 )
                ACCESS read-write
                STATUS mandatory
                DESCRIPTION
                    "Preference to be stored with the route. The lower 
                    preference are preferred."
                DEFVAL { 12 }
                ::= { impRipRuleEntry 4 }

            impRipRuleType OBJECT-TYPE
                SYNTAX INTEGER ( 1..2 )
                ACCESS read-write
                STATUS mandatory
                DESCRIPTION
                    "Type to be stored with the route. The type is based 
                    on the OSPF external type and used to help compare 
                    metrics.  Type 1 is preferred over type 2."
                DEFVAL { 1 }
                ::= { impRipRuleEntry 5 }

            impRipRuleMetricAction OBJECT-TYPE
                SYNTAX INTEGER { replace(1), increment(2), decrement(3) }
                ACCESS read-write
                STATUS mandatory
                DESCRIPTION
                    "How to apply the impRipRuleMetric field to the 
                    metric learned with the route before storing it in 
                    the routing table."
                DEFVAL { increment }
                ::= { impRipRuleEntry 6 }

            impRipRuleMetric OBJECT-TYPE
                SYNTAX INTEGER (0..16777215)
                ACCESS read-write
                STATUS mandatory
                DESCRIPTION
                    "Metric value to be applied to the metric learned 
                    learned with the route before storing it in the 
                    routing table."
                DEFVAL { 0 }
                ::= { impRipRuleEntry 7 }

            impRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { impRipRuleEntry 8 }

            -- the ISIS Import table

            impIsisRuleTable OBJECT-TYPE
            	SYNTAX SEQUENCE OF ImpIsisRuleEntry
            	ACCESS not-accessible
            	STATUS mandatory
            	DESCRIPTION
            		"The Isis import table."
            	::= { xImport 4 }
            
            impIsisRuleEntry OBJECT-TYPE
            	SYNTAX ImpIsisRuleEntry
            	ACCESS not-accessible
            	STATUS mandatory
            	DESCRIPTION
            		"An Isis import rule.  Each rule is keyed by the IP
                    network of the route learned from the neighbor.  The
                    route is either accepted or discarded and its metrics
                    are applied according to the rule.  An exact match on the
                    IP network is the rule that will be applied.  If an exact
            		match does not exist, the rule with the wild card IP
                    network is used."
            	INDEX { impIsisRuleNetwork }
            	::= { impIsisRuleTable 1 }
            
            ImpIsisRuleEntry ::=
            	SEQUENCE {
            		impIsisRuleNetwork
            			IpAddress,
            		impIsisRuleAction
            			INTEGER,
            		impIsisRulePreference
            			INTEGER,
            		impIsisRuleType
            			INTEGER,
            		impIsisRuleMetricAction
            			INTEGER,
            		impIsisRuleMetric
            			INTEGER,
            		impIsisRuleStatus
            			INTEGER
            	}
            
            impIsisRuleNetwork OBJECT-TYPE
            	SYNTAX IpAddress
            	ACCESS read-only
            	STATUS mandatory
            	DESCRIPTION
            		"The IP network learned from the neighbor.  The value
                    255.255.255.255 is a wild card matching any network."
            	::= { impIsisRuleEntry 1 }
            
            impIsisRuleAction OBJECT-TYPE
            	SYNTAX INTEGER { discard(1), accept(2) }
            	ACCESS read-write
            	STATUS mandatory
            	DESCRIPTION
            		"Control whether the route is learned or discarded."
            	DEFVAL { accept }
            	::= { impIsisRuleEntry 2 }
            
            impIsisRulePreference OBJECT-TYPE
            	SYNTAX INTEGER ( 0..255 )
            	ACCESS read-write
            	STATUS mandatory
            	DESCRIPTION
            		"Preference to be stored with the route. The lower
                    preference are preferred."
            	DEFVAL { 6 }
            	::= { impIsisRuleEntry 3 }
            
            impIsisRuleType OBJECT-TYPE
            	SYNTAX INTEGER ( 1..2 )
            	ACCESS read-write
            	STATUS mandatory
            	DESCRIPTION
            		"Type to be stored with the route. The type is based on
                    the OSPF external type and used to help compare metrics.
                    Type 1 is preferred over type 2."
            	DEFVAL { 1 }
            	::= { impIsisRuleEntry 4 }
            
            impIsisRuleMetricAction OBJECT-TYPE
            	SYNTAX INTEGER { replace(1), increment(2), decrement(3) }
            	ACCESS read-write
            	STATUS mandatory
            	DESCRIPTION
            		"How to apply the impIsisRuleMetric field to the metric
                    learned with the route before storing it in the routing
                    table."
            	DEFVAL { increment }
            	::= { impIsisRuleEntry 5 }
            
            impIsisRuleMetric OBJECT-TYPE
            	SYNTAX INTEGER 
            	ACCESS read-write
            	STATUS mandatory
            	DESCRIPTION
            		"Metric value to be applied to the metric learned learned
                    with the route before storing it in the routing table."
            	DEFVAL { 0 }
            	::= { impIsisRuleEntry 6 }
            
            impIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { impIsisRuleEntry 7 }


            -- the Export subgroup

            expEgpToEgpRuleTable OBJECT-TYPE
                SYNTAX SEQUENCE OF ExpEgpToEgpRuleEntry
                ACCESS not-accessible
                STATUS mandatory
                DESCRIPTION
                    "The EGP to EGP export table."
                ::= { xExport 1 }

            expEgpToEgpRuleEntry OBJECT-TYPE
                SYNTAX ExpEgpToEgpRuleEntry
                ACCESS not-accessible
                STATUS mandatory
                DESCRIPTION
                    "An EGP to EGP export rule.  Each rule is keyed by 
                    the Autonomous  System of the EGP neighbor, the IP 
                    network of the EGP route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows: 

                            To As  IP Network     From AS  Rank

                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expEgpToEgpRuleToAs, expEgpToEgpRuleNetwork,
                        expEgpToEgpRuleFromAs }
                ::= { expEgpToEgpRuleTable 1 }

            ExpEgpToEgpRuleEntry ::=
                SEQUENCE {
                    expEgpToEgpRuleToAs
                        INTEGER,
                    expEgpToEgpRuleNetwork
                        IpAddress,
                    expEgpToEgpRuleFromAs
                        INTEGER,
                    expEgpToEgpRuleAction
                        INTEGER,
                    expEgpToEgpRuleMetricAction
                        INTEGER,
                    expEgpToEgpRuleMetric
                        INTEGER,
                    expEgpToEgpRuleStatus
                        INTEGER
                }

            expEgpToEgpRuleToAs OBJECT-TYPE
                SYNTAX INTEGER ( 0..65535 )
                ACCESS read-only
                STATUS mandatory
                DESCRIPTION
                    "The Autonomous System of the neighbor.  The value 
                    65535 is  a wild card matching any AS number."
                ::= { expEgpToEgpRuleEntry 1 }

            expEgpToEgpRuleNetwork OBJECT-TYPE
                SYNTAX IpAddress 
                ACCESS read-only
                STATUS mandatory
                DESCRIPTION
                    "The IP network of the route in the route table.  
                    The value 255.255.255.255 is a wild card matching 
                    any network."
                ::= { expEgpToEgpRuleEntry 2 }

            expEgpToEgpRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToEgpRuleEntry 3 }

            expEgpToEgpRuleAction OBJECT-TYPE
                SYNTAX INTEGER { hide(1), advertise(2) }
                ACCESS read-write
                STATUS mandatory
                DESCRIPTION
                    "Control whether the route is advertised or not."
                DEFVAL { advertise }
                ::= { expEgpToEgpRuleEntry 4 }

            expEgpToEgpRuleMetricAction OBJECT-TYPE
                SYNTAX INTEGER { replace(1), increment(2),
                                 decrement(3) }
                ACCESS read-write
                STATUS mandatory
                DESCRIPTION
                    "How to apply the expEgpToEgpRuleMetric field to the 
                    metric in the route table entry before the route is 
                    advertised."
                DEFVAL { increment }
                ::= { expEgpToEgpRuleEntry 5 }

            expEgpToEgpRuleMetric OBJECT-TYPE
                SYNTAX INTEGER (0..16777215)
                ACCESS read-write
                STATUS mandatory
                DESCRIPTION
                    "Metric value to be applied to the metric in the 
                    route table entry before the route is advertised."
                DEFVAL { 0 }
                ::= { expEgpToEgpRuleEntry 6 }

            expEgpToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToEgpRuleEntry 7 }

            -- ospf to egp

            expOspfToEgpRuleTable OBJECT-TYPE
                SYNTAX SEQUENCE OF ExpOspfToEgpRuleEntry
                ACCESS not-accessible
                STATUS mandatory
                DESCRIPTION
                    "The OSPF to EGP export table."
                ::= { xExport 2 }

            expOspfToEgpRuleEntry OBJECT-TYPE
                SYNTAX ExpOspfToEgpRuleEntry
                ACCESS not-accessible
                STATUS mandatory
                DESCRIPTION
                    "An OSPF to EGP export rule.  Each rule is keyed by 
                    the Autonomous  System of the EGP neighbor, the IP 
                    network of the OSPF route in the  routing table, and 
                    the Autonomous System from which the route was 
                    learned.  The neighbor (to) AS can be set to a wild 
                    card as can the IP network and the (from) AS.  The 
                    route is either accepted to be  advertised to the 
                    neighbor or discarded from being advertised, and its 
                    metric is applied according to the rule.  The best 
                    match is as  follows:

                            To As  IP Network     From AS  Rank

                            exact       exact       exact   1st
                            exact       exact   wild card   2nd
                            exact   wild card       exact   3rd
                            exact   wild card   wild card   4th
                        wild card       exact       exact   5th
                        wild card       exact   wild card   6th
                        wild card   wild card       exact   7th
                        wild card   wild card   wild card   8th
                    "
                INDEX { expOspfToEgpRuleToAs, expOspfToEgpRuleNetwork,
                        expOspfToEgpRuleFromAs }
                ::= { expOspfToEgpRuleTable 1 }

            ExpOspfToEgpRuleEntry ::=
                SEQUENCE {
                    expOspfToEgpRuleToAs
                        INTEGER,
                    expOspfToEgpRuleNetwork
                        IpAddress,
                    expOspfToEgpRuleFromAs
                        INTEGER,
                    expOspfToEgpRuleAction
                        INTEGER,
                    expOspfToEgpRuleMetricAction
                        INTEGER,
                    expOspfToEgpRuleMetric
                        INTEGER,
                    expOspfToEgpRuleStatus
                        INTEGER
                }

            expOspfToEgpRuleToAs OBJECT-TYPE
                SYNTAX INTEGER ( 0..65535 )
                ACCESS read-only
                STATUS mandatory
                DESCRIPTION
                    "The Autonomous System of the neighbor.  The value 
                    65535 is  a wild card matching any AS number."
                ::= { expOspfToEgpRuleEntry 1 }

            expOspfToEgpRuleNetwork OBJECT-TYPE
                SYNTAX IpAddress
                ACCESS read-only
                STATUS mandatory
                DESCRIPTION
                    "The IP network of the route in the route table.  
                    The value 255.255.255.255 is a wild card matching 
                    any network."
                ::= { expOspfToEgpRuleEntry 2 }

            expOspfToEgpRuleFromAs OBJECT-TYPE
                SYNTAX INTEGER ( 0..65535 )
                ACCESS read-only
                STATUS mandatory
                DESCRIPTION
                    "The Autonomous System of the route in the route 
                    table.  Local indicates that the route was not an 
                    external OSPF route.  The  value 65535 is a wild 
                    card matching any AS number, and the value 65534 is 
                    for routes within the local AS."
                ::= { expOspfToEgpRuleEntry 3 }

            expOspfToEgpRuleAction OBJECT-TYPE
                SYNTAX INTEGER { hide(1), advertise(2) }
                ACCESS read-write
                STATUS mandatory
                DESCRIPTION
                    "Control whether the route is advertised or not."
                DEFVAL { advertise }
                ::= { expOspfToEgpRuleEntry 4 }

            expOspfToEgpRuleMetricAction OBJECT-TYPE
                SYNTAX INTEGER { replace(1), increment(2),
                                 decrement(3) }
                ACCESS read-write
                STATUS mandatory
                DESCRIPTION
                    "How to apply the expOspfToEgpRuleMetric field to 
                    the metric in the route table entry before the route 
                    is advertised."
                DEFVAL { increment }
                ::= { expOspfToEgpRuleEntry 5 }

            expOspfToEgpRuleMetric OBJECT-TYPE
                SYNTAX INTEGER (0..16777215)
                ACCESS read-write
                STATUS mandatory
                DESCRIPTION
                    "Metric value to be applied to the metric in the 
                    route table entry before the route is advertised."
                DEFVAL { 0 }
                ::= { expOspfToEgpRuleEntry 6 }

            expOspfToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expOspfToEgpRuleEntry 7 }

            -- static to egp

            expStaticToEgpRuleTable OBJECT-TYPE
                SYNTAX SEQUENCE OF ExpStaticToEgpRuleEntry
                ACCESS not-accessible
                STATUS mandatory
                DESCRIPTION
                    "The Static to EGP export table."
                ::= { xExport 3 }

            expStaticToEgpRuleEntry OBJECT-TYPE
                SYNTAX ExpStaticToEgpRuleEntry
                ACCESS not-accessible
                STATUS mandatory
                DESCRIPTION
                    "An Static to EGP export rule.  Each rule is keyed 
                    by the Autonomous  System of the EGP neighbor and 
                    the IP network of the Static route in the  routing 
                    table.  The neighbor (to) AS can be set to a wild 
                    card as can the IP network.  The route is either 
                    accepted to be advertised to the  neighbor or 
                    discarded from being advertised, and its metric is 
                    applied  according to the rule.  The best match is 
                    as follows:

                            To As  IP Network  Rank

                            exact       exact   1st
                            exact   wild card   2nd
                        wild card       exact   3rd
                        wild card   wild card   4th
                    "
                INDEX { expStaticToEgpRuleToAs,
                        expStaticToEgpRuleNetwork }
                ::= { expStaticToEgpRuleTable 1 }

            ExpStaticToEgpRuleEntry ::=
                SEQUENCE {
                    expStaticToEgpRuleToAs
                        INTEGER,
                    expStaticToEgpRuleNetwork
                        IpAddress,
                    expStaticToEgpRuleAction
                        INTEGER,
                    expStaticToEgpRuleMetricAction
                        INTEGER,
                    expStaticToEgpRuleMetric
                        INTEGER,
                    expStaticToEgpRuleStatus
                        INTEGER
                }

            expStaticToEgpRuleToAs OBJECT-TYPE
                SYNTAX INTEGER ( 0..65535 )
                ACCESS read-only
                STATUS mandatory
                DESCRIPTION
                    "The Autonomous System of the neighbor.  The value 
                    65535 is  a wild card matching any AS number."
                ::= { expStaticToEgpRuleEntry 1 }

            expStaticToEgpRuleNetwork OBJECT-TYPE
                SYNTAX IpAddress
                ACCESS read-only
                STATUS mandatory
                DESCRIPTION
                    "The IP network of the route in the route table.  
                    The value 255.255.255.255 is a wild card matching 
                    any network."
                ::= { expStaticToEgpRuleEntry 2 }

            expStaticToEgpRuleAction OBJECT-TYPE
                SYNTAX INTEGER { hide(1), advertise(2) }
                ACCESS read-write
                STATUS mandatory
                DESCRIPTION
                    "Control whether the route is advertised or not."
                DEFVAL { advertise }
                ::= { expStaticToEgpRuleEntry 3 }

            expStaticToEgpRuleMetricAction OBJECT-TYPE
                SYNTAX INTEGER { replace(1), increment(2),
                                 decrement(3) }
                ACCESS read-write
                STATUS mandatory
                DESCRIPTION
                    "How to apply the expStaticToEgpRuleMetric field to 
                    the metric in the route table entry before the route 
                    is advertised."
                DEFVAL { increment }
                ::= { expStaticToEgpRuleEntry 4 }

            expStaticToEgpRuleMetric OBJECT-TYPE
                SYNTAX INTEGER (0..16777215)
                ACCESS read-write
                STATUS mandatory
                DESCRIPTION
                    "Metric value to be applied to the metric in the 
                    route table entry before the route is advertised."
                DEFVAL { 0 }
                ::= { expStaticToEgpRuleEntry 5 }

            expStaticToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expStaticToEgpRuleEntry 6 }

            -- egp to ospf

            expEgpToOspfRuleTable OBJECT-TYPE
                SYNTAX SEQUENCE OF ExpEgpToOspfRuleEntry
                ACCESS not-accessible
                STATUS mandatory
                DESCRIPTION
                    "The EGP to OSPF export table."
                ::= { xExport 4 }

            expEgpToOspfRuleEntry OBJECT-TYPE
                SYNTAX ExpEgpToOspfRuleEntry
                ACCESS not-accessible
                STATUS mandatory
                DESCRIPTION
                    "An EGP to OSPF export rule.  Each rule is keyed by 
                    the IP network  of the EGP route in the routing 
                    table, and the Autonomous System  from which the 
                    route was learned.  The Ip network can be set to a 
                    wild card as can the (from) AS.  The route is either 
                    accepted to be  advertised to the neighbor or 
                    discarded from being advertised, and its metric is 
                    applied according to the rule.  The best match is as  
                    follows:

                       IP Network     From AS  Rank

                            exact       exact   1st
                            exact   wild card   2nd
                        wild card       exact   3rd
                        wild card   wild card   4th
                    "
                INDEX { expEgpToOspfRuleNetwork, expEgpToOspfRuleFromAs }
                ::= { expEgpToOspfRuleTable 1 }

            ExpEgpToOspfRuleEntry ::=
                SEQUENCE {
                    expEgpToOspfRuleNetwork
                        IpAddress,
                    expEgpToOspfRuleFromAs
                        INTEGER,
                    expEgpToOspfRuleAction
                        INTEGER,
                    expEgpToOspfRuleStatus
                        INTEGER
                }

            expEgpToOspfRuleNetwork OBJECT-TYPE
                SYNTAX IpAddress
                ACCESS read-only
                STATUS mandatory
                DESCRIPTION
                    "The IP network of the route in the route table.  
                    The value 255.255.255.255 is a wild card matching 
                    any network."
                ::= { expEgpToOspfRuleEntry 1 }

            expEgpToOspfRuleFromAs OBJECT-TYPE
                SYNTAX INTEGER ( 0..65535 )
                ACCESS read-only
                STATUS mandatory
                DESCRIPTION
                    "The Autonomous System of the route in the route 
                    table.  The value 65535 is  a wild card matching any 
                    AS number."
                ::= { expEgpToOspfRuleEntry 2 }

            expEgpToOspfRuleAction OBJECT-TYPE
                SYNTAX INTEGER { hide(1), advertise(2) }
                ACCESS read-write
                STATUS mandatory
                DESCRIPTION
                    "Control whether the route is advertised or not."
                DEFVAL { advertise }
                ::= { expEgpToOspfRuleEntry 3 }

            expEgpToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is  automatically readded with default values."
                DEFVAL { valid }
                ::= { expEgpToOspfRuleEntry 4 }

            -- rip to egp

            expRipToEgpRuleTable OBJECT-TYPE
                SYNTAX SEQUENCE OF ExpRipToEgpRuleEntry
                ACCESS not-accessible
                STATUS mandatory
                DESCRIPTION
                    "The Rip to EGP export table."
                ::= { xExport 5 }

            expRipToEgpRuleEntry OBJECT-TYPE
                SYNTAX ExpRipToEgpRuleEntry
                ACCESS not-accessible
                STATUS mandatory
                DESCRIPTION
                    "An Rip to EGP export rule.  Each rule is keyed by 
                    the Autonomous System of the EGP neighbor and the IP 
                    network of the Rip route in the routing table.  The 
                    neighbor (to) AS can be set to a wild card as can 
                    the IP network.  The route is either accepted to be 
                    advertised to the neighbor or discarded from being 
                    advertised, and its metric is applied according to 
                    the rule.  The best match is as follows:

                    To As       IP Network   Best Match Rank

                    exact       exact        1st
                    exact       wild card    2nd
                    wild card   exact        3rd
                    wild card   wild card    4th
                    "
                INDEX { expRipToEgpRuleToAs,
                        expRipToEgpRuleNetwork }
                ::= { expRipToEgpRuleTable 1 }

            ExpRipToEgpRuleEntry ::=
                SEQUENCE {
                    expRipToEgpRuleToAs
                        INTEGER,
                    expRipToEgpRuleNetwork
                        IpAddress,
                    expRipToEgpRuleAction
                        INTEGER,
                    expRipToEgpRuleMetricAction
                        INTEGER,
                    expRipToEgpRuleMetric
                        INTEGER,
                    expRipToEgpRuleStatus
                        INTEGER
                }

            expRipToEgpRuleToAs OBJECT-TYPE
                SYNTAX INTEGER ( 0..65535 )
                ACCESS read-only
                STATUS mandatory
                DESCRIPTION
                    "The Autonomous System of the neighbor.  The value 
                    65535 is a wild card matching any AS number."
                ::= { expRipToEgpRuleEntry 1 }

            expRipToEgpRuleNetwork OBJECT-TYPE
                SYNTAX IpAddress
                ACCESS read-only
                STATUS mandatory
                DESCRIPTION
                    "The IP network of the route in the route table.  
                    The value 255.255.255.255 is a wild card matching 
                    any network."
                ::= { expRipToEgpRuleEntry 2 }

            expRipToEgpRuleAction OBJECT-TYPE
                SYNTAX INTEGER { hide(1), advertise(2) }
                ACCESS read-write
                STATUS mandatory
                DESCRIPTION
                    "Control whether the route is advertised or not."
                DEFVAL { advertise }
                ::= { expRipToEgpRuleEntry 3 }

            expRipToEgpRuleMetricAction OBJECT-TYPE
                SYNTAX INTEGER { replace(1), increment(2), decrement(3) }
                ACCESS read-write
                STATUS mandatory
                DESCRIPTION
                    "How to apply the expRipToEgpRuleMetric field to the 
                    metric in the route table entry before the route is 
                    advertised."
                DEFVAL { increment }
                ::= { expRipToEgpRuleEntry 4 }

            expRipToEgpRuleMetric OBJECT-TYPE
                SYNTAX INTEGER (0..16777215)
                ACCESS read-write
                STATUS mandatory
                DESCRIPTION
                    "Metric value to be applied to the metric in the 
                    route table entry before the route is advertised."
                DEFVAL { 0 }
                ::= { expRipToEgpRuleEntry 5 }

            expRipToEgpRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToEgpRuleEntry 6 }

            -- rip to ospf

            expRipToOspfRuleTable OBJECT-TYPE
                SYNTAX SEQUENCE OF ExpRipToOspfRuleEntry
                ACCESS not-accessible
                STATUS mandatory
                DESCRIPTION
                    "The RIP to OSPF export table."
                ::= { xExport 6 }

            expRipToOspfRuleEntry OBJECT-TYPE
                SYNTAX ExpRipToOspfRuleEntry
                ACCESS not-accessible
                STATUS mandatory
                DESCRIPTION
                    "A RIP to OSPF export rule.  Each rule is keyed by 
                    the IP network of the RIP route in the routing 
                    table.  The IP network can be set to a wild card.  
                    The route is either accepted to be advertised to the 
                    neighbor or discarded from being advertised, and its 
                    metric is applied according to the rule.  The best 
                    match is as follows:

                    IP Network     Best Match Rank

                    exact          1st
                    wild card      2nd
                    "
                INDEX { expRipToOspfRuleNetwork }
                ::= { expRipToOspfRuleTable 1 }

            ExpRipToOspfRuleEntry ::=
                SEQUENCE {
                    expRipToOspfRuleNetwork
                        IpAddress,
                    expRipToOspfRuleAction
                        INTEGER,
                    expRipToOspfRuleStatus
                        INTEGER
                }

            expRipToOspfRuleNetwork OBJECT-TYPE
                SYNTAX IpAddress
                ACCESS read-only
                STATUS mandatory
                DESCRIPTION
                    "The IP network of the route in the route table.  
                    The value 255.255.255.255 is a wild card matching 
                    any network."
                ::= { expRipToOspfRuleEntry 1 }

            expRipToOspfRuleAction OBJECT-TYPE
                SYNTAX INTEGER { hide(1), advertise(2) }
                ACCESS read-write
                STATUS mandatory
                DESCRIPTION
                    "Control whether the route is advertised or not."
                DEFVAL { advertise }
                ::= { expRipToOspfRuleEntry 2 }

            expRipToOspfRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToOspfRuleEntry 3 }


            -- egp to rip

            expEgpToRipRuleTable OBJECT-TYPE
                SYNTAX SEQUENCE OF ExpEgpToRipRuleEntry
                ACCESS not-accessible
                STATUS mandatory
                DESCRIPTION
                    "The EGP to RIP export table."
                ::= { xExport 7 }

            expEgpToRipRuleEntry OBJECT-TYPE
                SYNTAX ExpEgpToRipRuleEntry
                ACCESS not-accessible
                STATUS mandatory
                DESCRIPTION
                    "An EGP to RIP export rule.  Each rule is keyed by 
                    the Autonomous System of the EGP neighbor, the IP 
                    network of the EGP route in the routing table, and 
                    the Autonomous System from which the route was 
                    learned.  The IP network can be set to a wild card 
                    as can the the from AS.  The route is either 
                    accepted to be advertised to the neighbor or 
                    discarded from being advertised, and its metric is 
                    applied according to the rule.  The best match is as 
                    follows:

                    IP Network   From AS     Best Match Rank

                    exact        exact       1st
                    exact        wild card   2nd
                    wild card    exact       3rd
                    wild card    wild card   4th
                    "
                INDEX { expEgpToRipRuleToIf, expEgpToRipRuleNetwork,
                        expEgpToRipRuleFromAs }
                ::= { expEgpToRipRuleTable 1 }

            ExpEgpToRipRuleEntry ::=
                SEQUENCE {
                    expEgpToRipRuleToIf
                        IpAddress,
                    expEgpToRipRuleNetwork
                        IpAddress,
                    expEgpToRipRuleFromAs
                        INTEGER,
                    expEgpToRipRuleAction
                        INTEGER,
                    expEgpToRipRuleMetricAction
                        INTEGER,
                    expEgpToRipRuleMetric
                        INTEGER,
                    expEgpToRipRuleStatus
                        INTEGER
                }

            expEgpToRipRuleToIf OBJECT-TYPE
                SYNTAX IpAddress 
                ACCESS read-only
                STATUS mandatory
                DESCRIPTION
                    "The IP address of the RIP interface to which the 
                    rule applies."
                ::= { expEgpToRipRuleEntry 1 }

            expEgpToRipRuleNetwork OBJECT-TYPE
                SYNTAX IpAddress 
                ACCESS read-only
                STATUS mandatory
                DESCRIPTION
                    "The IP network of the route in the route table.  
                    The value 255.255.255.255 is a wild card matching 
                    any network."
                ::= { expEgpToRipRuleEntry 2 }

            expEgpToRipRuleFromAs OBJECT-TYPE
                SYNTAX INTEGER ( 0..65535 )
                ACCESS read-only
                STATUS mandatory
                DESCRIPTION
                    "The Autonomous System of the route in the route 
                    table.  The value 65535 is a wild card matching any 
                    AS number."
                ::= { expEgpToRipRuleEntry 3 }

            expEgpToRipRuleAction OBJECT-TYPE
                SYNTAX INTEGER { hide(1), advertise(2) }
                ACCESS read-write
                STATUS mandatory
                DESCRIPTION
                    "Control whether the route is advertised or not."
                DEFVAL { advertise }
                ::= { expEgpToRipRuleEntry 4 }

            expEgpToRipRuleMetricAction OBJECT-TYPE
                SYNTAX INTEGER { replace(1), increment(2), decrement(3) }
                ACCESS read-write
                STATUS mandatory
                DESCRIPTION
                    "How to apply the expEgpToRipRuleMetric field to the 
                    metric in the route table entry before the route is 
                    advertised."
                DEFVAL { increment }
                ::= { expEgpToRipRuleEntry 5 }

            expEgpToRipRuleMetric OBJECT-TYPE
                SYNTAX INTEGER (0..16777215)
                ACCESS read-write
                STATUS mandatory
                DESCRIPTION
                    "Metric value to be applied to the metric in the 
                    route table entry before the route is advertised."
                DEFVAL { 0 }
                ::= { expEgpToRipRuleEntry 6 }

            expEgpToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expEgpToRipRuleEntry 7 }

            -- Ospf to rip

            expOspfToRipRuleTable OBJECT-TYPE
                SYNTAX SEQUENCE OF ExpOspfToRipRuleEntry
                ACCESS not-accessible
                STATUS mandatory
                DESCRIPTION
                    "The OSPF to RIP export table."
                ::= { xExport 8 }

            expOspfToRipRuleEntry OBJECT-TYPE
                SYNTAX ExpOspfToRipRuleEntry
                ACCESS not-accessible
                STATUS mandatory
                DESCRIPTION
                    "An Ospf to RIP export rule.  Each rule is keyed by 
                    the Autonomous System of the Ospf neighbor, the IP 
                    network of the Ospf route in the routing table, and 
                    the Autonomous System from which the route was 
                    learned.  The IP network can be set to a wild card 
                    as can the the from AS.  The route is either 
                    accepted to be advertised to the neighbor or 
                    discarded from being advertised, and its metric is 
                    applied according to the rule.  The best match is as 
                    follows:

                    IP Network   From AS     Best Match Rank

                    exact        exact       1st
                    exact        wild card   2nd
                    wild card    exact       3rd
                    wild card    wild card   4th
                    "
                INDEX { expOspfToRipRuleToIf, expOspfToRipRuleNetwork,
                        expOspfToRipRuleFromAs }
                ::= { expOspfToRipRuleTable 1 }

            ExpOspfToRipRuleEntry ::=
                SEQUENCE {
                    expOspfToRipRuleToIf
                        IpAddress,
                    expOspfToRipRuleNetwork
                        IpAddress,
                    expOspfToRipRuleFromAs
                        INTEGER,
                    expOspfToRipRuleAction
                        INTEGER,
                    expOspfToRipRuleMetricAction
                        INTEGER,
                    expOspfToRipRuleMetric
                        INTEGER,
                    expOspfToRipRuleStatus
                        INTEGER
                }

            expOspfToRipRuleToIf OBJECT-TYPE
                SYNTAX IpAddress
                ACCESS read-only
                STATUS mandatory
                DESCRIPTION
                    "The IP address of the RIP interface to which the 
                    rule applies."
                ::= { expOspfToRipRuleEntry 1 }

            expOspfToRipRuleNetwork OBJECT-TYPE
                SYNTAX IpAddress 
                ACCESS read-only
                STATUS mandatory
                DESCRIPTION
                    "The IP network of the route in the route table.  
                    The value 255.255.255.255 is a wild card matching 
                    any network."
                ::= { expOspfToRipRuleEntry 2 }

            expOspfToRipRuleFromAs OBJECT-TYPE
                SYNTAX INTEGER ( 0..65535 )
                ACCESS read-only
                STATUS mandatory
                DESCRIPTION
                    "The Autonomous System of the route in the route 
                    table.  The value 65535 is a wild card matching any 
                    AS number, and the value 65534 is for routes within 
                    the local AS."
                ::= { expOspfToRipRuleEntry 3 }

            expOspfToRipRuleAction OBJECT-TYPE
                SYNTAX INTEGER { hide(1), advertise(2) }
                ACCESS read-write
                STATUS mandatory
                DESCRIPTION
                    "Control whether the route is advertised or not."
                DEFVAL { advertise }
                ::= { expOspfToRipRuleEntry 4 }

            expOspfToRipRuleMetricAction OBJECT-TYPE
                SYNTAX INTEGER { replace(1), increment(2), decrement(3) }
                ACCESS read-write
                STATUS mandatory
                DESCRIPTION
                    "How to apply the expOspfToRipRuleMetric field to 
                    the metric in the route table entry before the route 
                    is advertised."
                DEFVAL { increment }
                ::= { expOspfToRipRuleEntry 5 }

            expOspfToRipRuleMetric OBJECT-TYPE
                SYNTAX INTEGER (0..16777215)
                ACCESS read-write
                STATUS mandatory
                DESCRIPTION
                    "Metric value to be applied to the metric in the 
                    route table entry before the route is advertised."
                DEFVAL { 0 }
                ::= { expOspfToRipRuleEntry 6 }

            expOspfToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values.  The 
                    same is true for the all wild cards where the AS is 
                    set to local"
                DEFVAL { valid }
                ::= { expOspfToRipRuleEntry 7 }

            -- rip to rip

            expRipToRipRuleTable OBJECT-TYPE
                SYNTAX SEQUENCE OF ExpRipToRipRuleEntry
                ACCESS not-accessible
                STATUS mandatory
                DESCRIPTION
                    "The Rip to Rip export table."
                ::= { xExport 9 }

            expRipToRipRuleEntry OBJECT-TYPE
                SYNTAX ExpRipToRipRuleEntry
                ACCESS not-accessible
                STATUS mandatory
                DESCRIPTION
                    "An Rip to Rip export rule.  Each rule is keyed by 
                    the IP network of the Rip route in the routing 
                    table.  The neighbor IP network can be set to a wild 
                    card.  The route is either accepted to be advertised 
                    to the neighbor or discarded from being advertised, 
                    and its metric is applied according to the rule.  
                    The best match is as follows:

                    IP Network   Best Match Rank

                    exact        1st
                    wild card    2nd
                    "
                INDEX { expRipToRipRuleToIf, expRipToRipRuleNetwork }
                ::= { expRipToRipRuleTable 1 }

            ExpRipToRipRuleEntry ::=
                SEQUENCE {
                    expRipToRipRuleToIf
                        IpAddress,
                    expRipToRipRuleNetwork
                        IpAddress,
                    expRipToRipRuleAction
                        INTEGER,
                    expRipToRipRuleMetricAction
                        INTEGER,
                    expRipToRipRuleMetric
                        INTEGER,
                    expRipToRipRuleStatus
                        INTEGER
                }

            expRipToRipRuleToIf OBJECT-TYPE
                SYNTAX IpAddress
                ACCESS read-only
                STATUS mandatory
                DESCRIPTION
                    "The IP address of the RIP interface to which the 
                    rule applies."
                ::= { expRipToRipRuleEntry 1 }

            expRipToRipRuleNetwork OBJECT-TYPE
                SYNTAX IpAddress
                ACCESS read-only
                STATUS mandatory
                DESCRIPTION
                    "The IP network of the route in the route table.  
                    The value 255.255.255.255 is a wild card matching 
                    any network."
                ::= { expRipToRipRuleEntry 2 }

            expRipToRipRuleAction OBJECT-TYPE
                SYNTAX INTEGER { hide(1), advertise(2) }
                ACCESS read-write
                STATUS mandatory
                DESCRIPTION
                    "Control whether the route is advertised or not."
                DEFVAL { advertise }
                ::= { expRipToRipRuleEntry 3 }

            expRipToRipRuleMetricAction OBJECT-TYPE
                SYNTAX INTEGER { replace(1), increment(2), decrement(3) }
                ACCESS read-write
                STATUS mandatory
                DESCRIPTION
                    "How to apply the expRipToRipRuleMetric field to the 
                    metric in the route table entry before the route is 
                    advertised."
                DEFVAL { increment }
                ::= { expRipToRipRuleEntry 4 }

            expRipToRipRuleMetric OBJECT-TYPE
                SYNTAX INTEGER (0..16777215)
                ACCESS read-write
                STATUS mandatory
                DESCRIPTION
                    "Metric value to be applied to the metric in the 
                    route table entry before the route is advertised."
                DEFVAL { 0 }
                ::= { expRipToRipRuleEntry 5 }

            expRipToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expRipToRipRuleEntry 6 }

            -- static to rip

            expStaticToRipRuleTable OBJECT-TYPE
                SYNTAX SEQUENCE OF ExpStaticToRipRuleEntry
                ACCESS not-accessible
                STATUS mandatory
                DESCRIPTION
                    "The Static to Rip export table."
                ::= { xExport 10 }

            expStaticToRipRuleEntry OBJECT-TYPE
                SYNTAX ExpStaticToRipRuleEntry
                ACCESS not-accessible
                STATUS mandatory
                DESCRIPTION
                    "An Static to Rip export rule.  Each rule is keyed 
                    by the IP network of the Static route in the routing 
                    table.  The neighbor IP network can be set to a wild 
                    card.  The route is either accepted to be advertised 
                    to the neighbor or discarded from being advertised, 
                    and its metric is applied according to the rule.  
                    The best match is as follows:

                    IP Network   Best Match Rank

                    exact        1st
                    wild card    2nd
                    "
                INDEX { expStaticToRipRuleToIf,
                        expStaticToRipRuleNetwork }
                ::= { expStaticToRipRuleTable 1 }

            ExpStaticToRipRuleEntry ::=
                SEQUENCE {
                    expStaticToRipRuleToIf
                        IpAddress,
                    expStaticToRipRuleNetwork
                        IpAddress,
                    expStaticToRipRuleAction
                        INTEGER,
                    expStaticToRipRuleMetricAction
                        INTEGER,
                    expStaticToRipRuleMetric
                        INTEGER,
                    expStaticToRipRuleStatus
                        INTEGER
                }

            expStaticToRipRuleToIf OBJECT-TYPE
                SYNTAX IpAddress
                ACCESS read-only
                STATUS mandatory
                DESCRIPTION
                    "The IP address of the RIP interface to which the 
                    rule applies."
                ::= { expStaticToRipRuleEntry 1 }

            expStaticToRipRuleNetwork OBJECT-TYPE
                SYNTAX IpAddress
                ACCESS read-only
                STATUS mandatory
                DESCRIPTION
                    "The IP network of the route in the route table.  
                    The value 255.255.255.255 is a wild card matching 
                    any network."
                ::= { expStaticToRipRuleEntry 2 }

            expStaticToRipRuleAction OBJECT-TYPE
                SYNTAX INTEGER { hide(1), advertise(2) }
                ACCESS read-write
                STATUS mandatory
                DESCRIPTION
                    "Control whether the route is advertised or not."
                DEFVAL { advertise }
                ::= { expStaticToRipRuleEntry 3 }

            expStaticToRipRuleMetricAction OBJECT-TYPE
                SYNTAX INTEGER { replace(1), increment(2), decrement(3) }
                ACCESS read-write
                STATUS mandatory
                DESCRIPTION
                    "How to apply the expStaticToRipRuleMetric field to 
                    the metric in the route table entry before the route 
                    is advertised."
                DEFVAL { increment }
                ::= { expStaticToRipRuleEntry 4 }

            expStaticToRipRuleMetric OBJECT-TYPE
                SYNTAX INTEGER (0..16777215)
                ACCESS read-write
                STATUS mandatory
                DESCRIPTION
                    "Metric value to be applied to the metric in the 
                    route table entry before the route is advertised."
                DEFVAL { 0 }
                ::= { expStaticToRipRuleEntry 5 }

            expStaticToRipRuleStatus OBJECT-TYPE
                SYNTAX INTEGER { invalid(1), valid(2) }
                ACCESS read-write
                STATUS mandatory
                DESCRIPTION
                    "The status of the rule.  Set to 'invalid' to remove 
                    the rule.  If the all wild card rule is removed, it 
                    is automatically readded with default values."
                DEFVAL { valid }
                ::= { expStaticToRipRuleEntry 6 }

            -- Isis to egp
            
            expIsisToEgpRuleTable OBJECT-TYPE
            	SYNTAX SEQUENCE OF ExpIsisToEgpRuleEntry
            	ACCESS not-accessible
            	STATUS mandatory
            	DESCRIPTION
            		"The Isis to EGP export table."
            	::= { xExport 11 }
            
            expIsisToEgpRuleEntry OBJECT-TYPE
            	SYNTAX ExpIsisToEgpRuleEntry
            	ACCESS not-accessible
            	STATUS mandatory
            	DESCRIPTION
            		"An Isis to EGP export rule.  Each rule is keyed by the Autonomous 
            		System of the EGP neighbor and the IP network of the Isis route in the 
            		routing table.  The neighbor (to) AS can be set to a wild card as can
            		the IP network.  The route is either accepted to be advertised to the 
            		neighbor or discarded from being advertised, and its metric is applied 
            		according to the rule.  The best match is as follows:
            
            				To As       IP Network      Best Match Rank
            
            				exact		exact			1st
            				exact		wild card		2nd
            				wild card	exact			3rd
            				wild card	wild card		4th
            
            		."
            	INDEX { expIsisToEgpRuleToAs, expIsisToEgpRuleNetwork }
            	::= { expIsisToEgpRuleTable 1 }
            
            ExpIsisToEgpRuleEntry ::=
            	SEQUENCE {
            		expIsisToEgpRuleToAs
            			INTEGER,
            		expIsisToEgpRuleNetwork
            			IpAddress,
            		expIsisToEgpRuleAction
            			INTEGER,
            		expIsisToEgpRuleMetricAction
            			INTEGER,
            		expIsisToEgpRuleMetric
            			INTEGER,
            		expIsisToEgpRuleStatus
            			INTEGER
            	}
            
            expIsisToEgpRuleToAs OBJECT-TYPE
            	SYNTAX INTEGER ( 0..65535 )
            	ACCESS read-only
            	STATUS mandatory
            	DESCRIPTION
            		"The Autonomous System of the neighbor.  The value 65535 is 
            		a wild card matching any AS number."
            	::= { expIsisToEgpRuleEntry 1 }
            
            expIsisToEgpRuleNetwork OBJECT-TYPE
            	SYNTAX IpAddress
            	ACCESS read-only
            	STATUS mandatory
            	DESCRIPTION
            		"The IP network of the route in the route table.  The value 
            		255.255.255.255	is a wild card matching any network."
            	::= { expIsisToEgpRuleEntry 2 }
            
            expIsisToEgpRuleAction OBJECT-TYPE
            	SYNTAX INTEGER { hide(1), advertise(2) }
            	ACCESS read-write
            	STATUS mandatory
            	DESCRIPTION
            		"Control whether the route is advertised or not."
            	DEFVAL { advertise }
            	::= { expIsisToEgpRuleEntry 3 }
            
            expIsisToEgpRuleMetricAction OBJECT-TYPE
            	SYNTAX INTEGER { replace(1), increment(2), decrement(3) }
            	ACCESS read-write
            	STATUS mandatory
            	DESCRIPTION
            		"How to apply the expIsisToEgpRuleMetric field to the metric in the route
            		table entry before the route is advertised."
            	DEFVAL { increment }
            	::= { expIsisToEgpRuleEntry 4 }
            
            expIsisToEgpRuleMetric OBJECT-TYPE
            	SYNTAX INTEGER 
            	ACCESS read-write
            	STATUS mandatory
            	DESCRIPTION
            		"Metric value to be applied to the metric in the route table entry
            		before the route is advertised."
            	DEFVAL { 0 }
            	::= { expIsisToEgpRuleEntry 5 }
            
            expIsisToEgpRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToEgpRuleEntry 6 }
            
            
            -- Isis to ospf
            
            expIsisToOspfRuleTable OBJECT-TYPE
            	SYNTAX SEQUENCE OF ExpIsisToOspfRuleEntry
            	ACCESS not-accessible
            	STATUS mandatory
            	DESCRIPTION
            		"The Isis to Ospf export table."
            	::= { xExport 12 }
            
            expIsisToOspfRuleEntry OBJECT-TYPE
            	SYNTAX ExpIsisToOspfRuleEntry
            	ACCESS not-accessible
            	STATUS mandatory
            	DESCRIPTION
            		"An Isis to Ospf export rule.  Each rule is keyed by the IP network of
            		the Isis route in the routing table.  The IP network can be set to a
            		wild card.  The route is either accepted to be advertised to the 
            		neighbor or discarded from being advertised, and its metric is applied 
            		according to the rule.  The best match is as follows:
            
            				IP Network      Best Match Rank
            
            				exact			1st
            				wild card		2nd
            
            		."
            	INDEX { expIsisToOspfRuleNetwork }
            	::= { expIsisToOspfRuleTable 1 }
            
            ExpIsisToOspfRuleEntry ::=
            	SEQUENCE {
            		expIsisToOspfRuleNetwork
            			IpAddress,
            		expIsisToOspfRuleAction
            			INTEGER,
            		expIsisToOspfRuleStatus
            			INTEGER
            	}
            
            expIsisToOspfRuleNetwork OBJECT-TYPE
            	SYNTAX IpAddress
            	ACCESS read-only
            	STATUS mandatory
            	DESCRIPTION
            		"The IP network of the route in the route table.  The value 
            		255.255.255.255	is a wild card matching any network."
            	::= { expIsisToOspfRuleEntry 1 }
            
            expIsisToOspfRuleAction OBJECT-TYPE
            	SYNTAX INTEGER { hide(1), advertise(2) }
            	ACCESS read-write
            	STATUS mandatory
            	DESCRIPTION
            		"Control whether the route is advertised or not."
            	DEFVAL { advertise }
            	::= { expIsisToOspfRuleEntry 2 }
            
            expIsisToOspfRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToOspfRuleEntry 3 }
            
            
            -- Isis to Rip
            
            expIsisToRipRuleTable OBJECT-TYPE
            	SYNTAX SEQUENCE OF ExpIsisToRipRuleEntry
            	ACCESS not-accessible
            	STATUS mandatory
            	DESCRIPTION
            		"The Isis to Rip export table."
            	::= { xExport 13 }
            
            expIsisToRipRuleEntry OBJECT-TYPE
            	SYNTAX ExpIsisToRipRuleEntry
            	ACCESS not-accessible
            	STATUS mandatory
            	DESCRIPTION
             		"An Isis to Rip export rule.  Each rule is keyed by the IP
                    network of the Isis route in the routing table.  The IP
                    network can be set to a	wild card.  The route is either
                    accepted to be advertised to the neighbor or discarded
                    from being advertised, and its metric is applied 
            		according to the rule.  The best match is as follows:
            
            				IP Network      Best Match Rank
            
            				exact			1st
            				wild card		2nd
            
            		."
            	INDEX { expIsisToRipRuleNetwork }
            	::= { expIsisToRipRuleTable 1 }
            
            ExpIsisToRipRuleEntry ::=
            	SEQUENCE {
                    expIsisToRipRuleToIf
                        IpAddress,
            		expIsisToRipRuleNetwork
            			IpAddress,
            		expIsisToRipRuleAction
            			INTEGER,
            		expIsisToRipRuleMetricAction
            			INTEGER,
            		expIsisToRipRuleMetric
            			INTEGER,
            		expIsisToRipRuleStatus
            			INTEGER
            	}
            
            expIsisToRipRuleToIf OBJECT-TYPE
                SYNTAX IpAddress
                ACCESS read-only
                STATUS mandatory
                DESCRIPTION
                    "The IP address of the RIP interface to which the 
                    rule applies."
                ::= { expIsisToRipRuleEntry 1 }

            expIsisToRipRuleNetwork OBJECT-TYPE
            	SYNTAX IpAddress
            	ACCESS read-only
            	STATUS mandatory
            	DESCRIPTION
            		"The IP network of the route in the route table.  The value 
            		255.255.255.255	is a wild card matching any network."
            	::= { expIsisToRipRuleEntry 2 }
            
            expIsisToRipRuleAction OBJECT-TYPE
            	SYNTAX INTEGER { hide(1), advertise(2) }
            	ACCESS read-write
            	STATUS mandatory
            	DESCRIPTION
            		"Control whether the route is advertised or not."
            	DEFVAL { advertise }
            	::= { expIsisToRipRuleEntry 3 }
            
            expIsisToRipRuleMetricAction OBJECT-TYPE
            	SYNTAX INTEGER { replace(1), increment(2), decrement(3) }
            	ACCESS read-write
            	STATUS mandatory
            	DESCRIPTION
            		"How to apply the expIsisToRipRuleMetric field to the metric in the route
            		table entry before the route is advertised."
            	DEFVAL { increment }
            	::= { expIsisToRipRuleEntry 4 }
            
            expIsisToRipRuleMetric OBJECT-TYPE
            	SYNTAX INTEGER 
            	ACCESS read-write
            	STATUS mandatory
            	DESCRIPTION
            		"Metric value to be applied to the metric in the route table entry
            		before the route is advertised."
            	DEFVAL { 0 }
            	::= { expIsisToRipRuleEntry 5 }
            
            expIsisToRipRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expIsisToRipRuleEntry 6 }
            
            
            -- egp to Isis
            
            expEgpToIsisRuleTable OBJECT-TYPE
            	SYNTAX SEQUENCE OF ExpEgpToIsisRuleEntry
            	ACCESS not-accessible
            	STATUS mandatory
            	DESCRIPTION
            		"The EGP to Isis export table."
            	::= { xExport 14 }
            
            expEgpToIsisRuleEntry OBJECT-TYPE
            	SYNTAX ExpEgpToIsisRuleEntry
            	ACCESS not-accessible
            	STATUS mandatory
            	DESCRIPTION
            		"An EGP to Isis export rule.  Each rule is keyed by the Autonomous 
            		System of the EGP neighbor, the IP network of the EGP route in the 
            		routing table, and the Autonomous System from which the route was
            		learned.  The IP network can be set to a wild card as can the
            		from AS.  The route is either accepted to be advertised to the 
            		neighbor or discarded from being advertised, and its metric is applied 
            		according to the rule.  The best match is as follows:
            
            				IP Network      From AS			Best Match Rank
            
            				exact			exact			1st
            				exact			wild card		2nd
            				wild card		exact			3rd
            				wild card		wild card		4th
            
            		."
            	INDEX { expEgpToIsisRuleNetwork, expEgpToIsisRuleFromAs }
            	::= { expEgpToIsisRuleTable 1 }
            
            ExpEgpToIsisRuleEntry ::=
            	SEQUENCE {
            		expEgpToIsisRuleNetwork
            			IpAddress,
            		expEgpToIsisRuleFromAs
            			INTEGER,
            		expEgpToIsisRuleAction
            			INTEGER,
            		expEgpToIsisRuleMetricType
            			INTEGER,
            		expEgpToIsisRuleDefaultMetricAction
            			INTEGER,
            		expEgpToIsisRuleDefaultMetric
            			INTEGER,
            		expEgpToIsisRuleDelayMetricAction
            			INTEGER,
            		expEgpToIsisRuleDelayMetric
            			INTEGER,
            		expEgpToIsisRuleErrorMetricAction
            			INTEGER,
            		expEgpToIsisRuleErrorMetric
            			INTEGER,
            		expEgpToIsisRuleExpenseMetricAction
            			INTEGER,
            		expEgpToIsisRuleExpenseMetric
            			INTEGER,
            		expEgpToIsisRuleStatus
            			INTEGER
            	}
            
            expEgpToIsisRuleNetwork OBJECT-TYPE
            	SYNTAX IpAddress 
            	ACCESS read-only
            	STATUS mandatory
            	DESCRIPTION
            		"The IP network of the route in the route table.  The value 
            		255.255.255.255	is a wild card matching any network."
            	::= { expEgpToIsisRuleEntry 1 }
            
            expEgpToIsisRuleFromAs OBJECT-TYPE
            	SYNTAX INTEGER ( 0..65535 )
            	ACCESS read-only
            	STATUS mandatory
            	DESCRIPTION
            		"The Autonomous System of the route in the route table.  The value 
            		65535 is a wild card matching any AS number."
            	::= { expEgpToIsisRuleEntry 2 }
            
            expEgpToIsisRuleAction OBJECT-TYPE
            	SYNTAX INTEGER { hide(1), advertise(2) }
            	ACCESS read-write
            	STATUS mandatory
            	DESCRIPTION
            		"Control whether the route is advertised or not."
            	DEFVAL { advertise }
            	::= { expEgpToIsisRuleEntry 3 }
            
            expEgpToIsisRuleMetricType OBJECT-TYPE
            	SYNTAX INTEGER { internal(1), external(2) }
            	ACCESS read-write
            	STATUS mandatory
            	DESCRIPTION
            		"Whether to advertise the metric as Internal or External."
            	DEFVAL { external }
            	::= { expEgpToIsisRuleEntry 4 }
            
            expEgpToIsisRuleDefaultMetricAction OBJECT-TYPE
            	SYNTAX INTEGER { replace(1), increment(2), decrement(3) }
            	ACCESS read-write
            	STATUS mandatory
            	DESCRIPTION
            		"How to apply the expEgpToIsisDefaultRuleMetric field to the metric in the route
            		table entry before the route is advertised."
            	DEFVAL { increment }
            	::= { expEgpToIsisRuleEntry 5 }
            
            expEgpToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expEgpToIsisRuleEntry 6 }
            
            expEgpToIsisRuleDelayMetricAction OBJECT-TYPE
            	SYNTAX INTEGER { replace(1), increment(2), decrement(3) }
            	ACCESS read-write
            	STATUS mandatory
            	DESCRIPTION
            		"How to apply the expEgpToIsisDelayRuleMetric field to the metric in the 
            		route table entry before the route is advertised."
            	DEFVAL { replace }
            	::= { expEgpToIsisRuleEntry 7 }
            
            expEgpToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expEgpToIsisRuleEntry 8 }
            
            expEgpToIsisRuleErrorMetricAction OBJECT-TYPE
            	SYNTAX INTEGER { replace(1), increment(2), decrement(3) }
            	ACCESS read-write
            	STATUS mandatory
            	DESCRIPTION
            		"How to apply the expEgpToIsisErrorRuleMetric field to the metric in the route
            		table entry before the route is advertised."
            	DEFVAL { replace }
            	::= { expEgpToIsisRuleEntry 9 }
            
            expEgpToIsisRuleErrorMetric OBJECT-TYPE
            	SYNTAX INTEGER 
            	ACCESS read-write
            	STATUS mandatory
            	DESCRIPTION
            		"Error metric value to be applied to the metric in the route table entry
            		before the route is advertised."
            	DEFVAL { 0 }
            	::= { expEgpToIsisRuleEntry 10 }
            
            expEgpToIsisRuleExpenseMetricAction OBJECT-TYPE
            	SYNTAX INTEGER { replace(1), increment(2), decrement(3) }
            	ACCESS read-write
            	STATUS mandatory
            	DESCRIPTION
            		"How to apply the expEgpToIsisExpenseRuleMetric field to the metric in the route
            		table entry before the route is advertised."
            	DEFVAL { replace }
            	::= { expEgpToIsisRuleEntry 11 }
            
            expEgpToIsisRuleExpenseMetric OBJECT-TYPE
            	SYNTAX INTEGER 
            	ACCESS read-write
            	STATUS mandatory
            	DESCRIPTION
            		"Expense metric value to be applied to the metric in the route table entry
            		before the route is advertised."
            	DEFVAL { 0 }
            	::= { expEgpToIsisRuleEntry 12 }
            
            expEgpToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expEgpToIsisRuleEntry 13 }
            
            
            -- Ospf to Isis
            
            expOspfToIsisRuleTable OBJECT-TYPE
            	SYNTAX SEQUENCE OF ExpOspfToIsisRuleEntry
            	ACCESS not-accessible
            	STATUS mandatory
            	DESCRIPTION
            		"The Ospf to Isis export table."
            	::= { xExport 15 }
            
            expOspfToIsisRuleEntry OBJECT-TYPE
            	SYNTAX ExpOspfToIsisRuleEntry
            	ACCESS not-accessible
            	STATUS mandatory
            	DESCRIPTION
            		"An Ospf to Isis export rule.  Each rule is keyed by the
                    Autonomous System of the Ospf neighbor, the IP network of
                    the Ospf route in the routing table, and the Autonomous
                    System from which the route was learned.  The IP network
                    can be set to a wild card as can the the from AS.  The
                    route is either accepted to be advertised to the neighbor
                    or discarded from being advertised, and its metric is
                    applied according to the rule.  The best match is as
                    follows:
            
            				IP Network      From AS			Best Match Rank
            
            				exact			exact			1st
            				exact			wild card		2nd
            				wild card		exact			3rd
            				wild card		wild card		4th
            
            		."
            	INDEX { expOspfToIsisRuleNetwork, expOspfToIsisRuleFromAs }
            	::= { expOspfToIsisRuleTable 1 }
            
            ExpOspfToIsisRuleEntry ::=
            	SEQUENCE {
            		expOspfToIsisRuleNetwork
            			IpAddress,
            		expOspfToIsisRuleFromAs
            			INTEGER,
            		expOspfToIsisRuleAction
            			INTEGER,
            		expOspfToIsisRuleMetricType
            			INTEGER,
            		expOspfToIsisRuleDefaultMetricAction
            			INTEGER,
            		expOspfToIsisRuleDefaultMetric
            			INTEGER,
            		expOspfToIsisRuleDelayMetricAction
            			INTEGER,
            		expOspfToIsisRuleDelayMetric
            			INTEGER,
            		expOspfToIsisRuleErrorMetricAction
            			INTEGER,
            		expOspfToIsisRuleErrorMetric
            			INTEGER,
            		expOspfToIsisRuleExpenseMetricAction
            			INTEGER,
            		expOspfToIsisRuleExpenseMetric
            			INTEGER,
            		expOspfToIsisRuleStatus
            			INTEGER
            	}
            
            expOspfToIsisRuleNetwork OBJECT-TYPE
            	SYNTAX IpAddress 
            	ACCESS read-only
            	STATUS mandatory
            	DESCRIPTION
            		"The IP network of the route in the route table.  The value
            		255.255.255.255	is a wild card matching any network."
            	::= { expOspfToIsisRuleEntry 1 }
            
            expOspfToIsisRuleFromAs OBJECT-TYPE
            	SYNTAX INTEGER ( 0..65535 )
            	ACCESS read-only
            	STATUS mandatory
            	DESCRIPTION
            		"The Autonomous System of the route in the route table.
                    The value 65535 is a wild card matching any AS number,
                    and the value 65534 is for routes within the local AS."
            	::= { expOspfToIsisRuleEntry 2 }
            
            expOspfToIsisRuleAction OBJECT-TYPE
            	SYNTAX INTEGER { hide(1), advertise(2) }
            	ACCESS read-write
            	STATUS mandatory
            	DESCRIPTION
            		"Control whether the route is advertised or not."
            	DEFVAL { advertise }
            	::= { expOspfToIsisRuleEntry 3 }
            
            expOspfToIsisRuleMetricType OBJECT-TYPE
            	SYNTAX INTEGER { internal(1), external(2) }
            	ACCESS read-write
            	STATUS mandatory
            	DESCRIPTION
            		"Whether to advertise the metric as Internal or External."
            	DEFVAL { external }
            	::= { expOspfToIsisRuleEntry 4 }
            
            expOspfToIsisRuleDefaultMetricAction OBJECT-TYPE
            	SYNTAX INTEGER { replace(1), increment(2), decrement(3) }
            	ACCESS read-write
            	STATUS mandatory
            	DESCRIPTION
            		"How to apply the expOspfToIsisDefaultRuleMetric field to
                    the metric in the route table entry before the route is
                    advertised."
            	DEFVAL { increment }
            	::= { expOspfToIsisRuleEntry 5 }
            
            expOspfToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expOspfToIsisRuleEntry 6 }
            
            expOspfToIsisRuleDelayMetricAction OBJECT-TYPE
            	SYNTAX INTEGER { replace(1), increment(2), decrement(3) }
            	ACCESS read-write
            	STATUS mandatory
            	DESCRIPTION
            		"How to apply the expOspfToIsisDelayRuleMetric field to the metric in the route
            		table entry before the route is advertised."
            	DEFVAL { replace }
            	::= { expOspfToIsisRuleEntry 7 }
            
            expOspfToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expOspfToIsisRuleEntry 8 }
            
            expOspfToIsisRuleErrorMetricAction OBJECT-TYPE
            	SYNTAX INTEGER { replace(1), increment(2), decrement(3) }
            	ACCESS read-write
            	STATUS mandatory
            	DESCRIPTION
            		"How to apply the expOspfToIsisErrorRuleMetric field to the metric in the route
            		table entry before the route is advertised."
            	DEFVAL { replace }
            	::= { expOspfToIsisRuleEntry 9 }
            
            expOspfToIsisRuleErrorMetric OBJECT-TYPE
            	SYNTAX INTEGER 
            	ACCESS read-write
            	STATUS mandatory
            	DESCRIPTION
            		"Error metric value to be applied to the metric in the route table entry
            		before the route is advertised."
            	DEFVAL { 0 }
            	::= { expOspfToIsisRuleEntry 10 }
            
            expOspfToIsisRuleExpenseMetricAction OBJECT-TYPE
            	SYNTAX INTEGER { replace(1), increment(2), decrement(3) }
            	ACCESS read-write
            	STATUS mandatory
            	DESCRIPTION
            		"How to apply the expOspfToIsisExpenseRuleMetric field to the metric in the route
            		table entry before the route is advertised."
            	DEFVAL { replace }
            	::= { expOspfToIsisRuleEntry 11 }
            
            expOspfToIsisRuleExpenseMetric OBJECT-TYPE
            	SYNTAX INTEGER 
            	ACCESS read-write
            	STATUS mandatory
            	DESCRIPTION
            		"Expense metric value to be applied to the metric in the route table entry
            		before the route is advertised."
            	DEFVAL { 0 }
            	::= { expOspfToIsisRuleEntry 12 }
            
            expOspfToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values.  The same is
            		true for the all wild cards where the AS is set to local"
            	DEFVAL { valid }
            	::= { expOspfToIsisRuleEntry 13 }
            
            
            -- Rip to Isis
            
            expRipToIsisRuleTable OBJECT-TYPE
            	SYNTAX SEQUENCE OF ExpRipToIsisRuleEntry
            	ACCESS not-accessible
            	STATUS mandatory
            	DESCRIPTION
            		"The Isis to Isis export table."
            	::= { xExport 16 }
            
            expRipToIsisRuleEntry OBJECT-TYPE
            	SYNTAX ExpRipToIsisRuleEntry
            	ACCESS not-accessible
            	STATUS mandatory
            	DESCRIPTION
            		"An Isis to Isis export rule.  Each rule is keyed by the
                    IP network of the Isis route in the routing table.  The
                    neighbor IP network can be set to a wild card.  The route
                    is either accepted to be advertised to the neighbor or
                    discarded from being advertised, and its metric is applied
                    according to the rule.  The best match is as follows:
            
            				IP Network      Best Match Rank
            
            				exact			1st
            				wild card		2nd
            
            		."
            	INDEX { expRipToIsisRuleNetwork }
            	::= { expRipToIsisRuleTable 1 }
            
            ExpRipToIsisRuleEntry ::=
            	SEQUENCE {
            		expRipToIsisRuleNetwork
            			IpAddress,
            		expRipToIsisRuleAction
            			INTEGER,
            		expRipToIsisRuleMetricType
            			INTEGER,
            		expRipToIsisRuleDefaultMetricAction
            			INTEGER,
            		expRipToIsisRuleDefaultMetric
            			INTEGER,
            		expRipToIsisRuleDelayMetricAction
            			INTEGER,
            		expRipToIsisRuleDelayMetric
            			INTEGER,
            		expRipToIsisRuleErrorMetricAction
            			INTEGER,
            		expRipToIsisRuleErrorMetric
            			INTEGER,
            		expRipToIsisRuleExpenseMetricAction
            			INTEGER,
            		expRipToIsisRuleExpenseMetric
            			INTEGER,
            		expRipToIsisRuleStatus
            			INTEGER
            	}
            
            expRipToIsisRuleNetwork OBJECT-TYPE
            	SYNTAX IpAddress
            	ACCESS read-only
            	STATUS mandatory
            	DESCRIPTION
            		"The IP network of the route in the route table.  The value 
            		255.255.255.255	is a wild card matching any network."
            	::= { expRipToIsisRuleEntry 1 }
            
            expRipToIsisRuleAction OBJECT-TYPE
            	SYNTAX INTEGER { hide(1), advertise(2) }
            	ACCESS read-write
            	STATUS mandatory
            	DESCRIPTION
            		"Control whether the route is advertised or not."
            	DEFVAL { advertise }
            	::= { expRipToIsisRuleEntry 2 }
            
            expRipToIsisRuleMetricType OBJECT-TYPE
            	SYNTAX INTEGER { internal(1), external(2) }
            	ACCESS read-write
            	STATUS mandatory
            	DESCRIPTION
            		"Whether to advertise the metric as Internal or External."
            	DEFVAL { external }
            	::= { expRipToIsisRuleEntry 3 }
            
            expRipToIsisRuleDefaultMetricAction OBJECT-TYPE
            	SYNTAX INTEGER { replace(1), increment(2), decrement(3) }
            	ACCESS read-write
            	STATUS mandatory
            	DESCRIPTION
            		"How to apply the expRipToIsisDefaultRuleMetric field to the metric in the route
            		table entry before the route is advertised."
            	DEFVAL { increment }
            	::= { expRipToIsisRuleEntry 4 }
            
            expRipToIsisRuleDefaultMetric OBJECT-TYPE
            	SYNTAX INTEGER 
            	ACCESS read-write
            	STATUS mandatory
            	DESCRIPTION
            		"Default metric value to be applied to the metric in the route table entry
            		before the route is advertised."
            	DEFVAL { 1 }
            	::= { expRipToIsisRuleEntry 5 }
            
            expRipToIsisRuleDelayMetricAction OBJECT-TYPE
            	SYNTAX INTEGER { replace(1), increment(2), decrement(3) }
            	ACCESS read-write
            	STATUS mandatory
            	DESCRIPTION
            		"How to apply the expRipToIsisDelayRuleMetric field to the metric in the route
            		table entry before the route is advertised."
            	DEFVAL { replace }
            	::= { expRipToIsisRuleEntry 6 }
            
            expRipToIsisRuleDelayMetric OBJECT-TYPE
            	SYNTAX INTEGER 
            	ACCESS read-write
            	STATUS mandatory
            	DESCRIPTION
            		"Delay metric value to be applied to the metric in the route table entry
            		before the route is advertised."
            	DEFVAL { 0 }
            	::= { expRipToIsisRuleEntry 7 }
            
            expRipToIsisRuleErrorMetricAction OBJECT-TYPE
            	SYNTAX INTEGER { replace(1), increment(2), decrement(3) }
            	ACCESS read-write
            	STATUS mandatory
            	DESCRIPTION
            		"How to apply the expRipToIsisErrorRuleMetric field to the metric in the route
            		table entry before the route is advertised."
            	DEFVAL { replace }
            	::= { expRipToIsisRuleEntry 8 }
            
            expRipToIsisRuleErrorMetric OBJECT-TYPE
            	SYNTAX INTEGER 
            	ACCESS read-write
            	STATUS mandatory
            	DESCRIPTION
            		"Error metric value to be applied to the metric in the
                    route table entry before the route is advertised."
            	DEFVAL { 0 }
            	::= { expRipToIsisRuleEntry 9 }
            
            expRipToIsisRuleExpenseMetricAction OBJECT-TYPE
            	SYNTAX INTEGER { replace(1), increment(2), decrement(3) }
            	ACCESS read-write
            	STATUS mandatory
            	DESCRIPTION
            		"How to apply the expRipToIsisExpenseRuleMetric field to
                    the metric in the route	table entry before the route is
                    advertised."
            	DEFVAL { replace }
            	::= { expRipToIsisRuleEntry 10 }
            
            expRipToIsisRuleExpenseMetric OBJECT-TYPE
            	SYNTAX INTEGER 
            	ACCESS read-write
            	STATUS mandatory
            	DESCRIPTION
            		"Expense metric value to be applied to the metric in the
                    route table entry before the route is advertised."
            	DEFVAL { 0 }
            	::= { expRipToIsisRuleEntry 11 }
            
            expRipToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expRipToIsisRuleEntry 12 }
            
            
            
            -- Static to Isis
            
            expStaticToIsisRuleTable OBJECT-TYPE
            	SYNTAX SEQUENCE OF ExpStaticToIsisRuleEntry
            	ACCESS not-accessible
            	STATUS mandatory
            	DESCRIPTION
            		"The Static to Isis export table."
            	::= { xExport 17 }
            
            expStaticToIsisRuleEntry OBJECT-TYPE
            	SYNTAX ExpStaticToIsisRuleEntry
            	ACCESS not-accessible
            	STATUS mandatory
            	DESCRIPTION
            		"An Static to Isis export rule.  Each rule is keyed by the
                    IP network of the Static route in the routing table.  The
                    neighbor IP network can be set to a wild card.  The route
                    is either accepted to be advertised to the neighbor or
                    discarded from being advertised, and its metric is applied
                    according to the rule.  The best match is as follows:
            
            				IP Network      Best Match Rank
            
            				exact			1st
            				wild card		2nd
            
            		."
            	INDEX { expStaticToIsisRuleNetwork }
            	::= { expStaticToIsisRuleTable 1 }
            
            ExpStaticToIsisRuleEntry ::=
            	SEQUENCE {
            		expStaticToIsisRuleNetwork
            			IpAddress,
            		expStaticToIsisRuleAction
            			INTEGER,
            		expStaticToIsisRuleMetricType
            			INTEGER,
            		expStaticToIsisRuleDefaultMetricAction
            			INTEGER,
            		expStaticToIsisRuleDefaultMetric
            			INTEGER,
            		expStaticToIsisRuleDelayMetricAction
            			INTEGER,
            		expStaticToIsisRuleDelayMetric
            			INTEGER,
            		expStaticToIsisRuleErrorMetricAction
            			INTEGER,
            		expStaticToIsisRuleErrorMetric
            			INTEGER,
            		expStaticToIsisRuleExpenseMetricAction
            			INTEGER,
            		expStaticToIsisRuleExpenseMetric
            			INTEGER,
            		expStaticToIsisRuleStatus
            			INTEGER
            	}
            
            expStaticToIsisRuleNetwork OBJECT-TYPE
            	SYNTAX IpAddress
            	ACCESS read-only
            	STATUS mandatory
            	DESCRIPTION
            		"The IP network of the route in the route table.  The value
            		255.255.255.255	is a wild card matching any network."
            	::= { expStaticToIsisRuleEntry 1 }
            
            expStaticToIsisRuleAction OBJECT-TYPE
            	SYNTAX INTEGER { hide(1), advertise(2) }
            	ACCESS read-write
            	STATUS mandatory
            	DESCRIPTION
            		"Control whether the route is advertised or not."
            	DEFVAL { advertise }
            	::= { expStaticToIsisRuleEntry 2 }
            
            expStaticToIsisRuleMetricType OBJECT-TYPE
            	SYNTAX INTEGER { internal(1), external(2) }
            	ACCESS read-write
            	STATUS mandatory
            	DESCRIPTION
            		"Whether to advertise the metric as Internal or External."
            	DEFVAL { external }
            	::= { expStaticToIsisRuleEntry 3 }
            
            expStaticToIsisRuleDefaultMetricAction OBJECT-TYPE
            	SYNTAX INTEGER { replace(1), increment(2), decrement(3) }
            	ACCESS read-write
            	STATUS mandatory
            	DESCRIPTION
            		"How to apply the expStaticToIsisDefaultRuleMetric field
                    to the metric in the route table entry before the route
                    is advertised."
            	DEFVAL { increment }
            	::= { expStaticToIsisRuleEntry 4 }
            
            expStaticToIsisRuleDefaultMetric OBJECT-TYPE
            	SYNTAX INTEGER 
            	ACCESS read-write
            	STATUS mandatory
            	DESCRIPTION
            		"Default metric value to be applied to the metric in the
                    route table entry before the route is advertised."
            	DEFVAL { 1 }
            	::= { expStaticToIsisRuleEntry 5 }
            
            expStaticToIsisRuleDelayMetricAction OBJECT-TYPE
            	SYNTAX INTEGER { replace(1), increment(2), decrement(3) }
            	ACCESS read-write
            	STATUS mandatory
            	DESCRIPTION
            		"How to apply the expStaticToIsisDelayRuleMetric field
                    to the metric in the route table entry before the route
                    is advertised."
            	DEFVAL { replace }
            	::= { expStaticToIsisRuleEntry 6 }
            
            expStaticToIsisRuleDelayMetric OBJECT-TYPE
            	SYNTAX INTEGER 
            	ACCESS read-write
            	STATUS mandatory
            	DESCRIPTION
            		"Delay metric value to be applied to the metric in the
                    route table entry before the route is advertised."
            	DEFVAL { 0 }
            	::= { expStaticToIsisRuleEntry 7 }
            
            expStaticToIsisRuleErrorMetricAction OBJECT-TYPE
            	SYNTAX INTEGER { replace(1), increment(2), decrement(3) }
            	ACCESS read-write
            	STATUS mandatory
            	DESCRIPTION
            		"How to apply the expStaticToIsisErrorRuleMetric field
                    to the metric in the route table entry before the route
                    is advertised."
            	DEFVAL { replace }
            	::= { expStaticToIsisRuleEntry 8 }
            
            expStaticToIsisRuleErrorMetric OBJECT-TYPE
            	SYNTAX INTEGER 
            	ACCESS read-write
            	STATUS mandatory
            	DESCRIPTION
            		"Error metric value to be applied to the metric in the
                    route table entry before the route is advertised."
            	DEFVAL { 0 }
            	::= { expStaticToIsisRuleEntry 9 }
            
            expStaticToIsisRuleExpenseMetricAction OBJECT-TYPE
            	SYNTAX INTEGER { replace(1), increment(2), decrement(3) }
            	ACCESS read-write
            	STATUS mandatory
            	DESCRIPTION
            		"How to apply the expStaticToIsisExpenseRuleMetric field
                    to the metric in the route table entry before the route
                    is advertised."
            	DEFVAL { replace }
            	::= { expStaticToIsisRuleEntry 10 }
            
            expStaticToIsisRuleExpenseMetric OBJECT-TYPE
            	SYNTAX INTEGER 
            	ACCESS read-write
            	STATUS mandatory
            	DESCRIPTION
            		"Expense metric value to be applied to the metric in the
                    route table entry before the route is advertised."
            	DEFVAL { 0 }
            	::= { expStaticToIsisRuleEntry 11 }
            
            expStaticToIsisRuleStatus OBJECT-TYPE
            	SYNTAX INTEGER { invalid(1), valid(2) }
            	ACCESS read-write
            	STATUS mandatory
            	DESCRIPTION
            		"The status of the rule.  Set to 'invalid' to remove
            		the rule.  If the all wild card rule is removed, it is 
            		automatically readded with default values."
            	DEFVAL { valid }
            	::= { expStaticToIsisRuleEntry 12 }


            -- the Filter subgroup

            -- Note: individual parameters follow table

            ipIfFilterTable OBJECT-TYPE
                SYNTAX SEQUENCE OF IpIfFilterEntry
                ACCESS not-accessible
                STATUS deprecated
                DESCRIPTION
                    "Table of filter entries."
                ::= { xFilter 1 }

            ipIfFilterEntry OBJECT-TYPE
                SYNTAX IpIfFilterEntry
                ACCESS not-accessible
                STATUS deprecated
                DESCRIPTION
                    "A particular entry."
                INDEX { ipIfFilterIndex, ipIfFilterProtocol,
                        ipIfFilterDstPort, ipIfFilterSrcPort,
                        ipIfFilterDstAddr, ipIfFilterDstMask,
                        ipIfFilterSrcAddr, ipIfFilterSrcMask }
                ::= { ipIfFilterTable 1 }

            IpIfFilterEntry ::=
                SEQUENCE {
                    ipIfFilterIndex
                        INTEGER,
                    ipIfFilterDstAddr
                        IpAddress,
                    ipIfFilterDstMask
                        IpAddress,
                    ipIfFilterSrcAddr
                        IpAddress,
                    ipIfFilterSrcMask
                         IpAddress,
                    ipIfFilterProtocol
                         INTEGER,
                    ipIfFilterDstPort
                         INTEGER,
                    ipIfFilterSrcPort
                         INTEGER,
                    ipIfFilterAction
                         INTEGER,
                    ipIfFilterStatus
                         INTEGER
                }

            ipIfFilterIndex OBJECT-TYPE
                SYNTAX INTEGER
                ACCESS read-only
                STATUS deprecated
                DESCRIPTION
                    "The interface index with which this entry is 
                    associated.  This value is the same as IfIndex."
                ::= { ipIfFilterEntry 1 }

            ipIfFilterDstAddr OBJECT-TYPE
                SYNTAX IpAddress
                ACCESS read-only
                STATUS deprecated
                DESCRIPTION
                    "The destination IP address to use in the filter 
                    match."
                ::= { ipIfFilterEntry 2 }

            ipIfFilterDstMask OBJECT-TYPE
                SYNTAX IpAddress
                ACCESS read-only
                STATUS deprecated
                DESCRIPTION
                    "The destination IP mask to use in the filter 
                    match."
                ::= { ipIfFilterEntry 3 }

            ipIfFilterSrcAddr OBJECT-TYPE
                SYNTAX IpAddress
                ACCESS read-only
                STATUS deprecated
                DESCRIPTION
                    "The source IP address to use in the filter match."
                ::= { ipIfFilterEntry 4 }

            ipIfFilterSrcMask OBJECT-TYPE
                SYNTAX IpAddress
                ACCESS read-only
                STATUS deprecated
                DESCRIPTION
                    "The source IP mask to use in the filter match."
                ::= { ipIfFilterEntry 5 }

            ipIfFilterProtocol OBJECT-TYPE
                SYNTAX INTEGER ( 0..256 )
                ACCESS read-only
                STATUS deprecated
                DESCRIPTION
                    "The protocol to use in the filter match.  The value 
                    256 indicates any protocol."
                ::= { ipIfFilterEntry 6 }

            ipIfFilterDstPort OBJECT-TYPE
                SYNTAX INTEGER ( 0..65536 )
                ACCESS read-only
                STATUS deprecated
                DESCRIPTION
                    "The destination port to use in the filter match.  
                    This field only applies to TCP and UDP protocol 
                    packets.  The value 65536 indicates any destination 
                    port."
                ::= { ipIfFilterEntry 7 }

            ipIfFilterSrcPort OBJECT-TYPE
                SYNTAX INTEGER ( 0..65536 )
                ACCESS read-only
                STATUS deprecated
                DESCRIPTION
                    "The source port to use in the filter match.  This 
                    field only applies to TCP and UDP protocol packets.  
                    The value 65536 indicates any source port."
                ::= { ipIfFilterEntry 8 }

            ipIfFilterAction OBJECT-TYPE
                SYNTAX INTEGER { discard(1), forward(2) }
                ACCESS read-write
                STATUS deprecated
                DESCRIPTION
                    "Control whether the packet for which this filter is 
                    the best match should be forwarded or discarded."
                DEFVAL { forward }
                ::= { ipIfFilterEntry 9 }

            ipIfFilterStatus OBJECT-TYPE
                SYNTAX INTEGER { invalid(1), valid(2) }
                ACCESS read-write
                STATUS deprecated
                DESCRIPTION
                    "The status of the filter entry.  Set to 'invalid' 
                    to remove the entry."
                DEFVAL { valid }
                ::= { ipIfFilterEntry 10 }

            -- individual parameters

            ipFilterState OBJECT-TYPE
                SYNTAX INTEGER { disabled(1), enabled(2) }
                ACCESS read-write
                STATUS mandatory
                DESCRIPTION
                    "The indication of whether this system does IP 
                    filtering."
                ::= { xFilter 2 }


            -- new filter table

            ipIfFilter2Table OBJECT-TYPE
                SYNTAX SEQUENCE OF IpIfFilter2Entry
                ACCESS not-accessible
                STATUS mandatory
                DESCRIPTION
                    "Table of filter entries."
                ::= { xFilter 3 }

            ipIfFilter2Entry OBJECT-TYPE
                SYNTAX IpIfFilter2Entry
                ACCESS not-accessible
                STATUS mandatory
                DESCRIPTION
                    "A particular entry."
                INDEX { ipIfFilter2Index, ipIfFilter2Protocol,
                        ipIfFilter2DstPortStart, ipIfFilter2DstPortEnd,
						ipIfFilter2TcpSyn,
                        ipIfFilter2SrcPortStart, ipIfFilter2SrcPortEnd,
                        ipIfFilter2DstMask, ipIfFilter2DstAddr,
                        ipIfFilter2SrcMask, ipIfFilter2SrcAddr }
                ::= { ipIfFilter2Table 1 }

            IpIfFilter2Entry ::=
                SEQUENCE {
                    ipIfFilter2Index
                        INTEGER,
                    ipIfFilter2DstAddr
                        IpAddress,
                    ipIfFilter2DstMask
                        IpAddress,
                    ipIfFilter2SrcAddr
                        IpAddress,
                    ipIfFilter2SrcMask
                         IpAddress,
                    ipIfFilter2Protocol
                         INTEGER,
                    ipIfFilter2DstPortStart
                         INTEGER,
                    ipIfFilter2SrcPortStart
                         INTEGER,
                    ipIfFilter2Action
                         INTEGER,
                    ipIfFilter2Status
                         INTEGER,
					ipIfFilter2DstPortEnd
						 INTEGER,
					ipIfFilter2SrcPortEnd
						 INTEGER,
					ipIfFilter2TcpSyn
						 INTEGER,
					ipIfFilter2ProtocolPriority
						 INTEGER
                }

            ipIfFilter2Index OBJECT-TYPE
                SYNTAX INTEGER
                ACCESS read-only
                STATUS mandatory
                DESCRIPTION
                    "The interface index with which this entry is 
                    associated.  This value is the same as IfIndex."
                ::= { ipIfFilter2Entry 1 }

            ipIfFilter2DstAddr OBJECT-TYPE
                SYNTAX IpAddress
                ACCESS read-only
                STATUS mandatory
                DESCRIPTION
                    "The destination IP address to use in the filter 
                    match."
                ::= { ipIfFilter2Entry 2 }

            ipIfFilter2DstMask OBJECT-TYPE
                SYNTAX IpAddress
                ACCESS read-only
                STATUS mandatory
                DESCRIPTION
                    "The destination IP mask to use in the filter 
                    match."
                ::= { ipIfFilter2Entry 3 }

            ipIfFilter2SrcAddr OBJECT-TYPE
                SYNTAX IpAddress
                ACCESS read-only
                STATUS mandatory
                DESCRIPTION
                    "The source IP address to use in the filter match."
                ::= { ipIfFilter2Entry 4 }

            ipIfFilter2SrcMask OBJECT-TYPE
                SYNTAX IpAddress
                ACCESS read-only
                STATUS mandatory
                DESCRIPTION
                    "The source IP mask to use in the filter match."
                ::= { ipIfFilter2Entry 5 }

            ipIfFilter2Protocol OBJECT-TYPE
                SYNTAX INTEGER ( 0..256 )
                ACCESS read-only
                STATUS mandatory
                DESCRIPTION
                    "The protocol to use in the filter match.  The value 
                    256 indicates any protocol."
                ::= { ipIfFilter2Entry 6 }

            ipIfFilter2DstPortStart OBJECT-TYPE
                SYNTAX INTEGER ( 0..65535 )
                ACCESS read-only
                STATUS mandatory
                DESCRIPTION
                    "The starting destination port in a range of 
					destination ports to use in the filter match.  
                    This field only applies to TCP and UDP protocol 
                    packets."
                ::= { ipIfFilter2Entry 7 }

            ipIfFilter2SrcPortStart OBJECT-TYPE
                SYNTAX INTEGER ( 0..65535 )
                ACCESS read-only
                STATUS mandatory
                DESCRIPTION
                    "The starting source port in a range of 
					source ports to use in the filter match.  
                    This field only applies to TCP and UDP protocol 
                    packets."
                ::= { ipIfFilter2Entry 8 }

            ipIfFilter2Action OBJECT-TYPE
                SYNTAX INTEGER { discard(1), forward(2) }
                ACCESS read-write
                STATUS mandatory
                DESCRIPTION
                    "Control whether the packet for which this filter is 
                    the best match should be forwarded or discarded."
                DEFVAL { forward }
                ::= { ipIfFilter2Entry 9 }

            ipIfFilter2Status OBJECT-TYPE
                SYNTAX INTEGER { invalid(1), valid(2) }
                ACCESS read-write
                STATUS mandatory
                DESCRIPTION
                    "The status of the filter entry.  Set to 'invalid' 
                    to remove the entry."
                DEFVAL { valid }
                ::= { ipIfFilter2Entry 10 }

            ipIfFilter2DstPortEnd OBJECT-TYPE
                SYNTAX INTEGER ( 0..65535 )
                ACCESS read-only
                STATUS mandatory
                DESCRIPTION
                    "The ending destination port in a range of 
					destination ports to use in the filter match.  
                    This field only applies to TCP and UDP protocol 
                    packets.  This filed must also be greater or
					equal to the ipIfFilter2DstPortStart field."
                ::= { ipIfFilter2Entry 11 }

            ipIfFilter2SrcPortEnd OBJECT-TYPE
                SYNTAX INTEGER ( 0..65535 )
                ACCESS read-only
                STATUS mandatory
                DESCRIPTION
                    "The starting source port in a range of 
					source ports to use in the filter match.  
                    This field only applies to TCP and UDP protocol 
                    packets.  This filed must also be greater or
					equal to the ipIfFilter2SrcPortStart field."
                ::= { ipIfFilter2Entry 12 }

            ipIfFilter2TcpSyn OBJECT-TYPE
                SYNTAX INTEGER { off(1), on(2), all(3) }
                ACCESS read-only
                STATUS mandatory
                DESCRIPTION
                    "The value of the TCP SYN and ACK bit to
					ues in the filter match.  This field only
					applies to TCP packets.  On indicates
					that the SYN bit is on and the ACK bit is 
					off.  Off is any other combination."
                ::= { ipIfFilter2Entry 13 }

            ipIfFilter2ProtocolPriority OBJECT-TYPE
                SYNTAX INTEGER { low(1), medium(3), high(5), none(256) }
                ACCESS read-write
                STATUS mandatory
                DESCRIPTION
                    "Control the priority at which the packet for which
					this filter is the best match should be placed on 
					the WAN output queue.  None indicates that the 
					sending interfaces protocol priority should be used." 
                DEFVAL { none }
                ::= { ipIfFilter2Entry 14 }

            -- the RIP group

            -- Implementation of this group is mandatory for all MRV In-Reach
            -- systems that implement RIP and route traffic through

            ripState OBJECT-TYPE
                SYNTAX INTEGER { disabled(1), enabled(2) }
                ACCESS read-write
                STATUS mandatory
                DESCRIPTION
                    "The indication of whether this system participates 
                    in RIP."
                DEFVAL { disabled }
                ::= { xRip 1 }

            ripStatus OBJECT-TYPE
                SYNTAX INTEGER { active(1), ripDisabled(2),
                                 ipDisabled(3), noNetworksEnabled(4),
                                 noMemory(5) }
                ACCESS read-only
                STATUS mandatory
                DESCRIPTION
                    "The status of the RIP software."
                ::= { xRip 2 }

            -- the RIP Network table

            ripNetTable OBJECT-TYPE
                SYNTAX SEQUENCE OF RipNetEntry
                ACCESS not-accessible
                STATUS mandatory
                DESCRIPTION
                    "Table of RIP entries."
                ::= { xRip 3 }

            ripNetEntry OBJECT-TYPE
                SYNTAX RipNetEntry
                ACCESS not-accessible
                STATUS mandatory
                DESCRIPTION
                    "A particular entry."
                INDEX { ripNetNet }
                ::= { ripNetTable 1 }

            RipNetEntry ::=
                SEQUENCE {
                    ripNetNet
                        IpAddress,
                    ripNetState
                        INTEGER,
                    ripNetRipsIn
                         Counter,
                    ripNetRipsOut
                         Counter,
                    ripNetAlgorithm
                        INTEGER
                }

            ripNetNet OBJECT-TYPE
                SYNTAX IpAddress
                ACCESS read-only
                STATUS mandatory
                DESCRIPTION
                    "The IP Network to which this entry applies."
                ::= { ripNetEntry 1 }

            ripNetState OBJECT-TYPE
                SYNTAX INTEGER { disabled(1), routerDiscovery(2),
                                 full(3) }
                ACCESS read-write
                STATUS mandatory
                DESCRIPTION
                    "This value controls the RIP protocol on this 
                    network."
                DEFVAL { full }
                ::= { ripNetEntry 2 }

            ripNetRipsIn OBJECT-TYPE
                SYNTAX Counter
                ACCESS read-only
                STATUS mandatory
                DESCRIPTION
                    "The number of RIP packets received from routers on 
                    this IP network."
                ::= { ripNetEntry 3 }

            ripNetRipsOut OBJECT-TYPE
                SYNTAX Counter
                ACCESS read-only
                STATUS mandatory
                DESCRIPTION
                    "The number of RIP packets sent to routers on this 
                    IP network."
                ::= { ripNetEntry 4 }

            ripNetAlgorithm OBJECT-TYPE
                SYNTAX INTEGER { poisonedReverse(1), splitHorizon(2) }
                ACCESS read-write
                STATUS mandatory
                DESCRIPTION
                    "This value controls the RIP algorithm on this 
                    network."
                ::= { ripNetEntry 5 }

            --  the lpd group

            --  Implementation of this group is mandatory for all MRV In-Reach 
            --  systems that implement lpd.

            --  The lpd Queue table

            lpdQueueTable OBJECT-TYPE
                SYNTAX SEQUENCE OF LpdQueueEntry
                ACCESS not-accessible
                STATUS mandatory
                DESCRIPTION
                    "A list of lpd queues on the server."
                ::= { xlpd 1 }

            lpdQueueEntry OBJECT-TYPE
                SYNTAX LpdQueueEntry
                ACCESS not-accessible
                STATUS mandatory
                DESCRIPTION
                    "Lpd parameter values plus counters for an 
                     individual lpd queue."
                INDEX { lpdQueueName }
                ::= { lpdQueueTable 1 }

            LpdQueueEntry ::=
                SEQUENCE {
                    lpdQueueStatus
                        INTEGER,
                    lpdQueueName
                        DisplayString,
                    lpdQueuePorts
                        OCTET STRING,
                    lpdQueueEnabled
                        INTEGER,
                    lpdQueueLfConversion
                        INTEGER,
                    lpdQueueTotalJobs
                        Gauge,
                    lpdQueueActiveJobs
                        Gauge,
                    lpdQueueWaitingJobs
                        Gauge,
                    lpdQueueProcessedJobs
                        Counter,
                    lpdQueueFormFeed
                        INTEGER,
                    lpdQueueBypass
                        INTEGER
                }

            lpdQueueStatus OBJECT-TYPE
                SYNTAX INTEGER { invalid(1), valid(2) }
                ACCESS read-write
                STATUS mandatory
                DESCRIPTION
                    "Status of this entry.  Setting the value to
                    'invalid' invalidates the entry, corresponding
                    directly to the CLEAR/PURGE SERVER LPD QUEUE 
                    command.  Setting the value to 'valid' validates
                    (creates) the entry, corresonding directly to 
                    the DEF/SET SERVER LPD QUEUE and lpd create 
                    commands."
                DEFVAL { valid }
                ::= { lpdQueueEntry 1 }

            lpdQueueName OBJECT-TYPE
                SYNTAX DisplayString (SIZE (1..16))
                ACCESS read-only
                STATUS mandatory
                DESCRIPTION
                    "Name of the LPD queue, case sensitive."
                ::= { lpdQueueEntry 2 }

            lpdQueuePorts OBJECT-TYPE
                SYNTAX OCTET STRING (SIZE (16))
                ACCESS read-write
                STATUS mandatory
                DESCRIPTION
                    "List of ports assigned to the queue.  An lpd queue 
                     can be associated with more than 1 port.  This 
                     object corresponds to the port-list in the
                     DEF/SET SERVER LPD QUEUE and lpc/create commands.
		     The OCTET STRING contains a bitmap, with one bit for
                     each port, and enough octets for all the ports on
                     the system.  Port numbers are as defined for
                     charPortIndex in the Character MIB [11].
                     Corresponding bit numbers start with 1 as the
                     high-order bit of the first octet. "
                ::= { lpdQueueEntry 3 }

            lpdQueueEnabled OBJECT-TYPE
                SYNTAX INTEGER { disabled(1), enabled(2) }
                ACCESS read-write
                STATUS mandatory
                DESCRIPTION
                    "Flag indicates if the queue is enabled.  A 'disabled'
                     queue will reject print requests from remote systems.
                     A 'enabled' queue accepts requests for printing."
		DEFVAL { disabled }
                ::= { lpdQueueEntry 4 }

            lpdQueueLfConversion OBJECT-TYPE
                SYNTAX INTEGER { lf(1), lfcr(2) }
                ACCESS read-write
                STATUS mandatory
                DESCRIPTION
                    "Flag indicates if the queue is converting linefeeds
                     to linefeeds, carriagereturns.  'lfcr' does the
                     converion, 'lf' does not."
		DEFVAL { lf }
                ::= { lpdQueueEntry 5 }

            lpdQueueTotalJobs OBJECT-TYPE
                SYNTAX Gauge
                ACCESS read-only
                STATUS mandatory
                DESCRIPTION
                    "The total number of jobs on the queue.  This number
                     should be equal to the number of active and waiting
                     jobs.  (lpdQueueActive + lpdQueueWaiting)"
                ::= { lpdQueueEntry 6 }

            lpdQueueActiveJobs OBJECT-TYPE
                SYNTAX Gauge
                ACCESS read-only
                STATUS mandatory
                DESCRIPTION
                    "The number of active jobs on the queue.  An active 
                     job is a job that has been assigned a port is in the
                     process of receiving data from a remote host and 
                     sending it out the port."
                ::= { lpdQueueEntry 7 }

            lpdQueueWaitingJobs OBJECT-TYPE
                SYNTAX Gauge
                ACCESS read-only
                STATUS mandatory
                DESCRIPTION
                    "The number of waiting jobs on the queue.  A waiting
                     job is a job that needs a port to send its data to.
                     This implies that the ports associated with this
                     queue are busy."
                ::= { lpdQueueEntry 8 }

            lpdQueueProcessedJobs OBJECT-TYPE
                SYNTAX Counter
                ACCESS read-only
                STATUS mandatory
                DESCRIPTION
                    "The total number of jobs processed by this queue
                     since server boot."
                ::= { lpdQueueEntry 9 }

            lpdQueueFormFeed OBJECT-TYPE
                SYNTAX INTEGER { formfeedafter(1), formfeedbefore(2),
                               formfeednone(3) }
                ACCESS read-write
                STATUS mandatory 
                DESCRIPTION
                     "A control to determine how we will send out a formfeed
                     when printing a lpd job. formfeedafter:  Send after job,
                     formfeedbefore: Send before job,
                     formfeednone: Send no formfeed."
                DEFVAL  { formfeedafter }
                ::= { lpdQueueEntry 10 }

            lpdQueueBypass OBJECT-TYPE 
                SYNTAX INTEGER { disabled(1), enabled(2) }
                ACCESS read-write
                STATUS mandatory
                DESCRIPTION
                     "Control for a queue to bypass a LPD port which has output
                      inhibited via flow control. Corresponds directly to the 
                      value labeled 'Bypass' in the SERVER LPD QUEUE display."
                DEFVAL { disabled }
                ::= { lpdQueueEntry 11 }
                

            -- lpd Job table

            lpdJobTable OBJECT-TYPE
                SYNTAX SEQUENCE OF LpdJobEntry
                ACCESS not-accessible
                STATUS mandatory
                DESCRIPTION
                    "A list of lpd jobs."
                ::= { xlpd 2 }

            lpdJobEntry OBJECT-TYPE
                SYNTAX LpdJobEntry
                ACCESS not-accessible
                STATUS mandatory
                DESCRIPTION
                    "A single lpd Job."
                INDEX { lpdQueueName, lpdJobNumber }
                ::= { lpdJobTable 1 }

            LpdJobEntry ::=
                SEQUENCE {
                    lpdJobStatus
                        INTEGER,
                    lpdJobNumber
                        INTEGER,
                    lpdJobAssignedPort
                        INTEGER,
                    lpdJobFileSize
                        INTEGER,
                    lpdJobHostName
                        DisplayString,
                    lpdJobFileName
                        DisplayString,
                    lpdJobState
                        INTEGER
                }

            lpdJobStatus OBJECT-TYPE
                SYNTAX INTEGER {invalid(1), valid(2)}
                ACCESS read-write
                STATUS mandatory
                DESCRIPTION
                    "Status of this entry.  Setting this object to
                     'invalid' will remove the job from the queue.  
                     Setting this object ot 'valid' has no effect since
                     the only way to create an lpd job is with the lpd
                     protocol."
                ::= { lpdJobEntry 1 }
        
            lpdJobNumber OBJECT-TYPE
                SYNTAX INTEGER (1..5000)
                ACCESS read-only
                STATUS mandatory
                DESCRIPTION
                    "The queue relative job number for this lpd job.  
                     Job numbers are assigned as jobs are accepted onto
                     the queue.  Job numbers are reset to 1 when they
                     reach a value greater than 1000 and the queue goes
                     empty."
                ::= { lpdJobEntry 2 }
        
            lpdJobAssignedPort OBJECT-TYPE
                SYNTAX INTEGER (0..256)
                ACCESS read-only
                STATUS mandatory
                DESCRIPTION
                    "The number of the port assigned to the lpd job."
                ::= { lpdJobEntry 3 }
        
            lpdJobFileSize OBJECT-TYPE
                SYNTAX INTEGER (0..2147483647)
                ACCESS read-only
                STATUS mandatory
                DESCRIPTION
                    "The size of the file being sent from the remote 
                     system."
                ::= { lpdJobEntry 4 }
        
            lpdJobHostName OBJECT-TYPE
                SYNTAX DisplayString (SIZE (1..34))
                ACCESS read-only
                STATUS mandatory
                DESCRIPTION
                    "The name of the host sending the job."
                ::= { lpdJobEntry 5 }
        
            lpdJobFileName OBJECT-TYPE
                SYNTAX DisplayString (SIZE (1..34))
                ACCESS read-only
                STATUS mandatory
                DESCRIPTION
                    "The name of the file being sent."
                ::= { lpdJobEntry 6 }

            lpdJobState OBJECT-TYPE
                SYNTAX INTEGER { initialized(1), waiting(2), 
                                 assigned(3), printingData(4),
                                 printingControl(5), aborted(6),
                                 completed(7), error(8),
                                 flushing(9) }
                ACCESS read-only
                STATUS mandatory
                DESCRIPTION
                    "The current state of the lpd job.  A typical job
                     transistions through the following states:
                     initialize->waiting->assigned->printingdata->
                     printingcontrol->completed."
                ::= { lpdJobEntry 7 }


            -- the SecurID group
            
            -- Implementation of this group is mandatory for all MRV In-Reach
            -- systems that implement a SecurID client
            
            securIDServerName0 OBJECT-TYPE
                SYNTAX DisplayString (SIZE (0..50))
                ACCESS read-write
                STATUS mandatory
                DESCRIPTION
                    "The Domain name of the first SecurID server to try 
                    when the system verifies a SecurID PASSCODE.  Corresponds 
                    directly to SERVER SECURID SERVER0 and the 
                    value labeled 'SecurID Server0:' in the 
                    SERVER SECURID display."
                ::= { xSecurID 1 }
            
            securIDServerName1 OBJECT-TYPE
                SYNTAX DisplayString (SIZE (0..50))
                ACCESS read-write
                STATUS mandatory
                DESCRIPTION
                    "The Domain name of the second SecurID server to try 
                    when the system verifies a SecurID PASSCODE.  Corresponds 
                    directly to SERVER SECURID SERVER1 and the 
                    value labeled 'SecurID Server1:' in the 
                    SERVER SECURID display."
                ::= { xSecurID 2 }
            
            securIDServerName2 OBJECT-TYPE
                SYNTAX DisplayString (SIZE (0..50))
                ACCESS read-write
                STATUS mandatory
                DESCRIPTION
                    "The Domain name of the third SecurID server to try 
                    when the system verifies a SecurID PASSCODE.  Corresponds 
                    directly to SERVER SECURID SERVER2 and the 
                    value labeled 'SecurID Server2:' in the 
                    SERVER SECURID display."
                ::= { xSecurID 3 }
            
            securIDServerName3 OBJECT-TYPE
                SYNTAX DisplayString (SIZE (0..50))
                ACCESS read-write
                STATUS mandatory
                DESCRIPTION
                    "The Domain name of the fourth SecurID server to try 
                    when the system verifies a SecurID PASSCODE.  Corresponds 
                    directly to SERVER SECURID SERVER3 and the 
                    value labeled 'SecurID Server3:' in the 
                    SERVER SECURID display."
                ::= { xSecurID 4 }
            
            securIDServerName4 OBJECT-TYPE
                SYNTAX DisplayString (SIZE (0..50))
                ACCESS read-write
                STATUS mandatory
                DESCRIPTION
                    "The Domain name of the fifth SecurID server to try 
                    when the system verifies a SecurID PASSCODE.  Corresponds 
                    directly to SERVER SECURID SERVER4 and the 
                    value labeled 'SecurID Server4:' in the 
                    SERVER SECURID display."
                ::= { xSecurID 5 }
            
            securIDMaxRetries OBJECT-TYPE
                SYNTAX INTEGER (1..10)
                ACCESS read-write
                STATUS mandatory
                DESCRIPTION
                    "The maximum number of times the server will 
                    try any single SecurID server to validate a
                    PASSCODE.  Corresponds directly to SERVER SECURID 
                    ACMMAXRETRIES and the value labeled 'SecurID 
                    ACMMAXRETRIES:' in the SERVER SECURID display."
                ::= { xSecurID 6 }
            
            securIDBaseTimeout OBJECT-TYPE
                SYNTAX INTEGER (1..10)
                ACCESS read-write
                STATUS mandatory
                DESCRIPTION
                    "The initial timeout value to be used between prompts
                    for a SecurID PASSCODE.
                    Corresponds directly to SERVER SECURID 
                    ACMBASETIMEOUT and the value labeled 'SecurID 
                    ACMBASETIMEOUT:' in the SERVER SECURID display."
                ::= { xSecurID 7 }
            
            securIDPort OBJECT-TYPE
                SYNTAX INTEGER (1..32767)
                ACCESS read-write
                STATUS mandatory
                DESCRIPTION
                    "The UDP port number to be used when communicating
                    with the SecurID servers. Corresponds directly to 
                    SERVER SECURID ACM_PORT and the value labeled 'SecurID 
                    ACM_PORT:' in the SERVER SECURID display."
                ::= { xSecurID 8 }
            
            securIDQueryLimit OBJECT-TYPE
                SYNTAX INTEGER (1..10)
                ACCESS read-write
                STATUS mandatory
                DESCRIPTION
                    "The maximum number of times a user will be queried 
                    for a SecurID PASSCODE before being logged out.
                    Corresponds directly to 
                    SERVER SECURID QUERY LIMIT and the value labeled 'SecurID 
                    Query Limit:' in the SERVER SECURID display."
                ::= { xSecurID 9 }
            
            securIDEncryptionMode OBJECT-TYPE
                SYNTAX INTEGER { sdiBlockCipher(1), des(2) }
                ACCESS read-write
                STATUS mandatory
                DESCRIPTION
                    "The type of encryption to use in SecurID validation.
                    Corresponds directly to the value labeled 'Encryption
                    Mode' in the SERVER SECURID display."
                ::= { xSecurID 10 }
            
            securIDInsecureLogins OBJECT-TYPE
                SYNTAX Counter
                ACCESS read-only
                STATUS mandatory
                DESCRIPTION
                    "The number of user logins on ports for which 
                    SecurID user verification is not enabled.  
                    Corresponds directly to the value labeled 'Logins 
                    without SecurID:' in the SERVER SECURID display."
                ::= { xSecurID 11 }
            
            securIDSecureLogins OBJECT-TYPE
                SYNTAX Counter
                ACCESS read-only
                STATUS mandatory
                DESCRIPTION
                    "The number of successful user logins on ports for 
                    which SecurID user verification is enabled.  
                    Corresponds directly to the value labeled 
                    'Successful Logins:' in the SERVER SECURID 
                    display."
                ::= { xSecurID 12 }
            
            securIDSecureLoginsFailed OBJECT-TYPE
                SYNTAX Counter
                ACCESS read-only
                STATUS mandatory
                DESCRIPTION
                    "The number of verification failures due to 
                    incorrect PASSCODE for attempted user logins 
                    on ports for which SecurID user verification is 
                    enabled.  Corresponds directly to the value labeled 
                    'Unsuccessful Logins:' in the SERVER SECURID 
                    display."
                ::= { xSecurID 13 }
            
            securIDServerAccess0 OBJECT-TYPE
                SYNTAX Counter
                ACCESS read-only
                STATUS mandatory
                DESCRIPTION
                    "The number of times the system successfully 
                    accessed the SecurID server0.  Corresponds 
                    directly to the value labeled 'Attempts to access:', 
                    'Server0', and 'Successful:' in the SERVER SECURID 
                    display."
                ::= { xSecurID 14 }
            
            securIDServerAccessFailed0 OBJECT-TYPE
                SYNTAX Counter
                ACCESS read-only
                STATUS mandatory
                DESCRIPTION
                    "The number of times the system unsuccessfully 
                    accessed the SecurID server0.  Corresponds 
                    directly to the value labeled 'Attempts to access:', 
                    'Server0', and 'UnSuccessful:' in the SERVER SECURID 
                    display."
                ::= { xSecurID 15 }
            
            securIDServerAccess1 OBJECT-TYPE
                SYNTAX Counter
                ACCESS read-only
                STATUS mandatory
                DESCRIPTION
                    "The number of times the system successfully 
                    accessed the SecurID server1.  Corresponds 
                    directly to the value labeled 'Attempts to access:', 
                    'Server1', and 'Successful:' in the SERVER SECURID 
                    display."
                ::= { xSecurID 16 }
            
            securIDServerAccessFailed1 OBJECT-TYPE
                SYNTAX Counter
                ACCESS read-only
                STATUS mandatory
                DESCRIPTION
                    "The number of times the system unsuccessfully 
                    accessed the SecurID server1.  Corresponds 
                    directly to the value labeled 'Attempts to access:', 
                    'Server1', and 'UnSuccessful:' in the SERVER SECURID 
                    display."
                ::= { xSecurID 17 }
            
            securIDServerAccess2 OBJECT-TYPE
                SYNTAX Counter
                ACCESS read-only
                STATUS mandatory
                DESCRIPTION
                    "The number of times the system successfully 
                    accessed the SecurID server2.  Corresponds 
                    directly to the value labeled 'Attempts to access:', 
                    'Server2', and 'Successful:' in the SERVER SECURID 
                    display."
                ::= { xSecurID 18 }
            
            securIDServerAccessFailed2 OBJECT-TYPE
                SYNTAX Counter
                ACCESS read-only
                STATUS mandatory
                DESCRIPTION
                    "The number of times the system unsuccessfully 
                    accessed the SecurID server2.  Corresponds 
                    directly to the value labeled 'Attempts to access:', 
                    'Server2', and 'UnSuccessful:' in the SERVER SECURID 
                    display."
                ::= { xSecurID 19 }
            
            securIDServerAccess3 OBJECT-TYPE
                SYNTAX Counter
                ACCESS read-only
                STATUS mandatory
                DESCRIPTION
                    "The number of times the system successfully 
                    accessed the SecurID server3.  Corresponds 
                    directly to the value labeled 'Attempts to access:', 
                    'Server3', and 'Successful:' in the SERVER SECURID 
                    display."
                ::= { xSecurID 20 }
            
            securIDServerAccessFailed3 OBJECT-TYPE
                SYNTAX Counter
                ACCESS read-only
                STATUS mandatory
                DESCRIPTION
                    "The number of times the system unsuccessfully 
                    accessed the SecurID server3.  Corresponds 
                    directly to the value labeled 'Attempts to access:', 
                    'Server3', and 'UnSuccessful:' in the SERVER SECURID 
                    display."
                ::= { xSecurID 21 }
            
            securIDServerAccess4 OBJECT-TYPE
                SYNTAX Counter
                ACCESS read-only
                STATUS mandatory
                DESCRIPTION
                    "The number of times the system successfully 
                    accessed the SecurID server4.  Corresponds 
                    directly to the value labeled 'Attempts to access:', 
                    'Server4', and 'Successful:' in the SERVER SECURID 
                    display."
                ::= { xSecurID 22 }
            
            securIDServerAccessFailed4 OBJECT-TYPE
                SYNTAX Counter
                ACCESS read-only
                STATUS mandatory
                DESCRIPTION
                    "The number of times the system unsuccessfully 
                    accessed the SecurID server4.  Corresponds 
                    directly to the value labeled 'Attempts to access:', 
                    'Server4', and 'UnSuccessful:' in the SERVER SECURID 
                    display."
                ::= { xSecurID 23 }
            
            securIDErrorPortIndex OBJECT-TYPE
                SYNTAX INTEGER (0..40)
                ACCESS read-only
                STATUS mandatory
                DESCRIPTION
                    "The index of the most recent port on which a SecurID 
                    access violation occurred.  Corresponds 
                    directly to the value labeled 'Last Unsuccessful
                    Login:' in the SERVER SECURID display."
                ::= { xSecurID 24 }
            
            securIDError OBJECT-TYPE
                SYNTAX INTEGER (0..40)
                ACCESS read-only
                STATUS mandatory
                DESCRIPTION
                    "The error number of the most recent SecurID-related
                    error.  Corresponds directly to the value labeled 
                    'Reason:' in the SERVER SECURID display.  See
                    MRV In-Reach documentation for a complete list of 
                    error numbers and their meaning."
                ::= { xSecurID 25 }
            
            securIDErrorUsername OBJECT-TYPE
                SYNTAX DisplayString (SIZE (0..17))
                ACCESS read-only
                STATUS mandatory
                DESCRIPTION
                    "The username associated with the most recent
                    SecurID-related error.  Corresponds directly to the value
                    labeled 'Username:' in the SERVER SECURID display."
                ::= { xSecurID 26 }
            
            
            -- the SecurID Port table
            
            securIDPortTable OBJECT-TYPE
                SYNTAX SEQUENCE OF SecurIDPortEntry
                ACCESS not-accessible
                STATUS mandatory
                DESCRIPTION
                    "A list of SecurID character port entries."
                ::= { xSecurID 27 }
            
            securIDPortEntry OBJECT-TYPE
                SYNTAX SecurIDPortEntry
                ACCESS not-accessible
                STATUS mandatory
                DESCRIPTION
                    "Parameter values for a SecurID port."
                INDEX { securIDPortIndex }
                ::= { securIDPortTable 1 }
            
            SecurIDPortEntry ::=
                SEQUENCE {
                    securIDPortIndex
                        INTEGER,
                    securIDPortStatus
                        INTEGER
                }
            
            securIDPortIndex OBJECT-TYPE
                SYNTAX INTEGER
                ACCESS read-only
                STATUS mandatory
                DESCRIPTION
                    "An index value that uniquely identifies a port 
                    could relate to SecurID.  The port identified by a 
                    particular value of this index is the same port as 
                    identified by charPortIndex in the Proposed Standard 
                    Internet Character MIB."
                ::= { securIDPortEntry 1 }
            
            securIDPortStatus OBJECT-TYPE
                SYNTAX INTEGER { disabled(1), enabled(2) }
                ACCESS read-write
                STATUS mandatory
                DESCRIPTION
                    "A control indicating the level of SecurID 
                    operation on the port.  Corresponds directly to PORT 
                    SECURID and the value 'SecurID' following the 
                    label 'Enabled Characteristics' in the PORT 
                    CHARACTERISTICS display."
                ::= { securIDPortEntry 2 }


-- the SSH Port Table

sshPortTable OBJECT-TYPE
   SYNTAX SEQUENCE OF SshPortEntry
   ACCESS not-accessible
   STATUS mandatory
   DESCRIPTION
      "A list of SSH port entries"
   ::= { xSsh 1 }

sshPortEntry OBJECT-TYPE
   SYNTAX SshPortEntry
   ACCESS not-accessible
   STATUS mandatory
   DESCRIPTION
      "Parameter values for an SSH port."
   INDEX { sshPortIndex }
   ::= { sshPortTable 1 }

SshPortEntry ::=
   SEQUENCE {
      sshPortIndex
         INTEGER,
      sshPortIncomingTcpPort
         INTEGER,
      sshPortNewlineFiltering
         INTEGER,
      sshPortNewline
         INTEGER,
      sshPortTransmitBufferedTime
         INTEGER,
      sshPortRemoteProtocol
         INTEGER,
      sshPortBreakSequence
         OCTET STRING
   }

sshPortIndex  OBJECT-TYPE
   SYNTAX INTEGER
   ACCESS read-only
   STATUS mandatory
   DESCRIPTION
      "An index value that uniquely identifies an SSH port. The port 
       identified by a particular value of this index is the same port as 
       identified by charPortIndex in the proposed standard Internet 
       Character MIB."
   ::= { sshPortEntry 1 }                

sshPortIncomingTcpPort  OBJECT-TYPE
   SYNTAX INTEGER (1..32767)
   ACCESS read-write
   STATUS mandatory
   DESCRIPTION
      "Specifies the TCP port number used to identify the port when a SSH
       connection request arrives at the server. The default for a physical
       port is 2022 + 100 * port's physical port number. The default is 22
       for virtual ports. Corresponds directly to the value labeled 'Remote 
       Port:' in the PORT SSH CHARACTERISTICS display."
   ::= { sshPortEntry 2 }                

sshPortNewlineFiltering  OBJECT-TYPE
   SYNTAX INTEGER { none(1), crToCrLf(2), crToCrNull(3), crLfToCr(4),
                    crLfToCrNull(5), crNullToCr(6), crNullToCrLf(7) }
   ACCESS read-write
   STATUS mandatory
   DESCRIPTION
      "Translation to apply to newline sequences (CR/NULL or CR/LF) received
       from the network during a SSH session, before sending the newline to 
       the character port. The value indicates which input sequence is 
       converted to which output sequence and sent to the 
       character port, with 'none' meaning no translation.
       Corresponds directly to the value labeled 'Newline Filtering:'
       in the PORT SSH CHARACTERISTICS display."
   DEFVAL { none }
   ::= { sshPortEntry 3 }                

sshPortNewline  OBJECT-TYPE
   SYNTAX INTEGER { none(1), crToCrLf(2), crToCrNull(3), crLfToCr(4),
                    crLfToCrNull(5), crNullToCr(6), crNullToCrLf(7) }
   ACCESS read-write
   STATUS mandatory
   DESCRIPTION
      "Translation to apply to newline (carriage return) received from the 
       character port during an SSH session, before sending the newline to the
       remote partner. Corresponds directly to the value labeled 'Newline:' 
       in the PORT SSH CHARACTERISTICS display."
   DEFVAL { none }       
   ::= { sshPortEntry 4 }                

sshPortTransmitBufferedTime  OBJECT-TYPE
   SYNTAX INTEGER (30..1500)
   ACCESS read-write
   STATUS mandatory
   DESCRIPTION
      "Number of milliseconds to wait before transmitting data received from 
       a character port during an interactive SSH session. 
       Corresponds directly to the value labeled 'Transmit Buffered Time:' in
       the PORT SSH CHARACTERISTICS display."
   DEFVAL { 80 } 
   ::= { sshPortEntry 5 }                

sshPortRemoteProtocol  OBJECT-TYPE
   SYNTAX INTEGER { ssh(1), telnet(2), both(3) }
   ACCESS read-write
   STATUS mandatory
   DESCRIPTION
      "Indicates which remote protocols will be accepted at this port.
       Corresponds indirectly to the presence of 'Telnet' or 'SSH' under the 
       label 'Enabled Characteristics:' in the PORT SSH CHARACTERISTICS 
       display. If both protocols are accepted at the port, the choice of 
       protocol is determined by which features are enabled on the server with
       SSH taking precedence over Telnet."
   DEFVAL { both }
   ::= { sshPortEntry 6 }                

sshPortBreakSequence  OBJECT-TYPE
   SYNTAX OCTET STRING (SIZE (0..4))
   ACCESS read-write
   STATUS mandatory
   DESCRIPTION
      "A sequence of characters, which together define the break function. If
       this string is received from the SSH connection from across the network,
       the port will send a hardware break out of the serial port. The first
       character must be a carriage return ('\r'), and no more carriage
       returns may appear in the sequence. The second character must not be
       a NULL, or a line-feed ('\n'). Send a NULL to remove the break sequence.
       If the sequence exists, it must have two to four characters."
   ::= { sshPortEntry 7 }                


sshCipherMask  OBJECT-TYPE
   SYNTAX OCTET STRING (SIZE (2)) 
   ACCESS read-write 
   STATUS mandatory
   DESCRIPTION
      "This is a list of the encryption methods supported.
       The OCTET STRING contains a bitmap, with one bit for each cipher type.
       Corresponding bit numbers start with 0 as the low-order bit of the
       second octet. The following bit positions are defined:  
       none(0), des(2), tripleDes(3), and blowfish(6). Corresponds directly to
       the value labeled 'SSH Cipher Enabled:' in the SERVER SSH 
       CHARACTERISTICS display."
   ::= { xSsh 2 }                

sshAuthenticationTimeout  OBJECT-TYPE
   SYNTAX INTEGER (1..120)
   ACCESS read-write
   STATUS mandatory
   DESCRIPTION
      "The timeout in minutes before disconnecting if no successful 
       authentication of SSH parties has been made. Corresponds directly to 
       the value labeled 'Authentication Timeout:' in the SERVER SSH 
       CHARACTERISTICS display."
   DEFVAL { 5 }
   ::= { xSsh 3 }                

sshHostKeyLength  OBJECT-TYPE
   SYNTAX INTEGER (512..2048)
   ACCESS read-write
   STATUS mandatory
   DESCRIPTION
      "The bit length of the SSH host encryption key. When modified, the 
      desired change does not occur until the next system initialization.
      Corresponds directly to the value labeled 'Host Key Length:' in the 
      SERVER SSH CHARACTERISTICS display."
   DEFVAL { 1024 }
   ::= { xSsh 4 }                

sshHostKeyGenerate  OBJECT-TYPE
   SYNTAX INTEGER { ready(1), generate(2), update(3) }
   ACCESS read-write
   STATUS mandatory
   DESCRIPTION
      "For a set-request with a value of generate or update, a new host key
       will be generated in the background. When modified with generate, the
       desired change does not occur until the next system initialization
       whereas when modified with update the change goes into effect upon
       completion of the new key.   

       In response to a get-request or a get-next-request the agent will
       respond ready except when a host key is being created in which case 
       the agent responds generate."
   ::= { xSsh 5 }                
  
sshServerKeyLength  OBJECT-TYPE
   SYNTAX INTEGER (512..2048)
   ACCESS read-write
   STATUS mandatory
   DESCRIPTION
      "The bit length of the SSH server encryption key. The difference between
       the server and host key lengths should be greater than 128 bits.
      Corresponds directly to the value labeled 'Server Key Length:' in the 
      SERVER SSH CHARACTERISTICS display."
   DEFVAL { 768 }
   ::= { xSsh 6 }                

sshServerKeyTtl  OBJECT-TYPE
   SYNTAX INTEGER (30..1440)
   ACCESS read-write
   STATUS mandatory
   DESCRIPTION
      "The time in minutes that the server key remains valid. After this time
       the server key is automatically re-generated. Corresponds directly to
       the value labeled 'Server Key Timeout:' in the SERVER SSH 
       CHARACTERISTICS display."
   DEFVAL { 60 }
   ::= { xSsh 7 }                

   sshServerMaxBufferSize OBJECT-TYPE
	SYNTAX INTEGER (4096..262144)
	ACCESS read-write
	STATUS mandatory
	DESCRIPTION
	    "The size of the four buffers used by SSH for input and
	     output. These buffers are used for data coming from the 
             console, going to the network, coming from the network and
	     going to the console."
	DEFVAL { 4096 }
	::= { xSsh 8 }






--
-- FILE: /users/sse/mibs/src/inReach/ir-ipx-mib.mib
--

-- $Id: ir-ipx-mib.mib,v 1.1 2002/06/27 15:43:00 sse Exp $


            xIpx            OBJECT IDENTIFIER ::= { mrvInReachProductDivision 15 }

            -- MRV In-Reach IPX subgroups

            xIpxSystem      OBJECT IDENTIFIER ::= { xIpx 1 }
            xIpxIf          OBJECT IDENTIFIER ::= { xIpx 2 }
            xIpxNetbios     OBJECT IDENTIFIER ::= { xIpx 3 }
            xIpxRip         OBJECT IDENTIFIER ::= { xIpx 4 }
            xIpxSap         OBJECT IDENTIFIER ::= { xIpx 5 }
	    xIpxFilter      OBJECT IDENTIFIER ::= { xIpx 6 }
            -- number 7 reserved
            xIpxPrinter     OBJECT IDENTIFIER ::= { xIpx 8 }


            -- This is a MIB module for all MRV In-Reach systems that
            -- implement IPX.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the System group

            -- Implementation of this group is mandatory for all MRV In-Reach
            -- systems that implement IPX

            ipxRouting OBJECT-TYPE
                SYNTAX INTEGER { disabled(1), enabled(2) }
                ACCESS read-write
                STATUS mandatory
                DESCRIPTION
                    "Control for IPX routing services."
                ::= { xIpxSystem 1 }

            ipxInternalNetwork OBJECT-TYPE
                SYNTAX INTEGER (1..4294967294)
                ACCESS read-write
                STATUS mandatory
                DESCRIPTION
                    "The IPX Internal Network to use on the the IPX Router."
		DEFVAL { 1 }
                ::= { xIpxSystem 2 }

            -- the Interface group

            -- Implementation of this group is mandatory for all MRV In-Reach
            -- systems that implement IPX

            ipxIfTable OBJECT-TYPE
                SYNTAX SEQUENCE OF IpxIfEntry
                ACCESS not-accessible
                STATUS mandatory
                DESCRIPTION
                    "A list of IPX interface entries."
                ::= { xIpxIf 1 }

            ipxIfEntry OBJECT-TYPE
                SYNTAX IpxIfEntry
                ACCESS not-accessible
                STATUS mandatory
                DESCRIPTION
                    "IPX interface parameters and counters."
                INDEX { ipxIfIndex }
                ::= { ipxIfTable 1 }

            IpxIfEntry ::=
                SEQUENCE {
                    ipxIfIndex
                        INTEGER,
                    ipxIfState
                        INTEGER,
                    ipxIfNetwork
                        INTEGER,
                    ipxIfFrameStyle
                        INTEGER,
                    ipxIfFramesIn
                        Counter,
                    ipxIfFramesOut
                        Counter,
                    ipxIfErrors
                        Counter,
                    ipxIfTransitDelay
                        INTEGER,
                    ipxIfTransitDelayActual
                        INTEGER,
                    ipxIfProtocolPriority
                        INTEGER,
                    ipxIfWatchdogSpoof
                        INTEGER,
                    ipxIfStatusNetwork
                        INTEGER
                }

            ipxIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxIfEntry 1 }

            ipxIfState OBJECT-TYPE
                SYNTAX INTEGER { disabled(1), enabled(2) }
                ACCESS read-write
                STATUS mandatory
                DESCRIPTION
                    "Control for IPX routing services for this 
                    interface."
                DEFVAL { enabled }
                ::= { ipxIfEntry 2 }

            ipxIfNetwork OBJECT-TYPE
                SYNTAX INTEGER
                ACCESS read-write
                STATUS mandatory
                DESCRIPTION
                    "The IPX network number of the network to which this 
                    interface is attached."
                DEFVAL { 0 }
                ::= { ipxIfEntry 3 }

            ipxIfFrameStyle OBJECT-TYPE
                SYNTAX INTEGER { ethernet(1), ieee8023(2), ieee8022(3), ieee802Snap(4) }
                ACCESS read-write
                STATUS mandatory
                DESCRIPTION
                    "Control for the CSMA/CD frame style to use on this 
                    interface."
                DEFVAL { ieee8023 }
                ::= { ipxIfEntry 4 }

            ipxIfFramesIn OBJECT-TYPE
                SYNTAX Counter
                ACCESS read-only
                STATUS mandatory
                DESCRIPTION
                    "The number of IPX frames received on this 
                    interface."
                ::= { ipxIfEntry 5 }

            ipxIfFramesOut OBJECT-TYPE
                SYNTAX Counter
                ACCESS read-only
                STATUS mandatory
                DESCRIPTION
                    "The number of IPX frames sent on this interface."
                ::= { ipxIfEntry 6 }

            ipxIfErrors OBJECT-TYPE
                SYNTAX Counter
                ACCESS read-only
                STATUS mandatory
                DESCRIPTION
                    "The number of IPX errors seen on this interface."
                ::= { ipxIfEntry 7 }

            ipxIfTransitDelay OBJECT-TYPE
                SYNTAX INTEGER
                ACCESS read-write
                STATUS mandatory
                DESCRIPTION
                    "The number of 55 millisecond ticks it takes for a 
                    packet to  travel from one destination to another on 
                    the interface.  A value of 0 means that the system 
                    will calculate this value based on the measured 
                    speed of the interface."
                ::= { ipxIfEntry 8 }

            ipxIfTransitDelayActual OBJECT-TYPE
                SYNTAX INTEGER     
                ACCESS read-only
                STATUS mandatory
                DESCRIPTION
                    "The number of 55 millisecond ticks it takes for a 
                    packet to travel from one destination to another on 
                    the interface."
                ::= { ipxIfEntry 9 }

            ipxIfProtocolPriority OBJECT-TYPE
                SYNTAX INTEGER { low(1), medium(3), high(5) }
                ACCESS read-write
                STATUS mandatory
                DESCRIPTION
                    "This value defines the priority at which all 
                    Internet Routed packets will be placed on the WAN 
                    output queue."
                DEFVAL { medium }
                ::= { ipxIfEntry 10 }

            ipxIfWatchdogSpoof OBJECT-TYPE
                SYNTAX INTEGER { disabled(1), enabled(2) }
                ACCESS read-write
                STATUS mandatory
                DESCRIPTION
                    "Control for whether or not this router
                    responds to IPX watchog requests on this
                    interface."
                DEFVAL { disabled }
                ::= { ipxIfEntry 11 }

            ipxIfStatusNetwork OBJECT-TYPE
               SYNTAX INTEGER
                ACCESS read-only
                STATUS mandatory
                DESCRIPTION
                    "The IPX network number that is actually in use on the 
                    attached interface.  This value may have been learned 
		     via listening to the attached network."
                DEFVAL { 0 }
                ::= { ipxIfEntry 12 }


            -- the Netbios group

            -- Implementation of this group is mandatory for all MRV In-Reach
            -- systems that implement IPX Netbios

            ipxNetbiosHopLimit OBJECT-TYPE
                SYNTAX INTEGER (0..255)
                ACCESS read-write
                STATUS mandatory
                DESCRIPTION
                    "Maximum number of hops that an IPX Netbios packet 
                    may make."
                ::= { xIpxNetbios 1 }

            ipxNetbiosIfTable OBJECT-TYPE
                SYNTAX SEQUENCE OF IpxNetbiosIfEntry
                ACCESS not-accessible
                STATUS mandatory
                DESCRIPTION
                    "A list of IPX interface entries."
                ::= { xIpxNetbios 2 }

            ipxNetbiosIfEntry OBJECT-TYPE
                SYNTAX IpxNetbiosIfEntry
                ACCESS not-accessible
                STATUS mandatory
                DESCRIPTION
                    "IPX interface parameters and counters."
                INDEX { ipxNetbiosIfIndex }
                ::= { ipxNetbiosIfTable 1 }

            IpxNetbiosIfEntry ::=
                SEQUENCE {
                    ipxNetbiosIfIndex
                        INTEGER,
                    ipxIfNetbiosForwarding
                        INTEGER,
                    ipxIfNetbiosIn
                        Counter,
                    ipxIfNetbiosOut
                        Counter
                }

            ipxNetbiosIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxNetbiosIfEntry 1 }

            ipxIfNetbiosForwarding OBJECT-TYPE
                SYNTAX INTEGER { disabled(1), enabled(2) }
                ACCESS read-write
                STATUS mandatory
                DESCRIPTION
                    "Control whether Netbios packet will be forwarded in 
                    or out on this interface."
                DEFVAL { enabled }
                ::= { ipxNetbiosIfEntry 2 }

            ipxIfNetbiosIn OBJECT-TYPE
                SYNTAX Counter
                ACCESS read-only
                STATUS mandatory
                DESCRIPTION
                    "The number of IPX Netbios frames received on this 
                    interface."
                ::= { ipxNetbiosIfEntry 3 }

            ipxIfNetbiosOut OBJECT-TYPE
                SYNTAX Counter
                ACCESS read-only
                STATUS mandatory
                DESCRIPTION
                    "The number of IPX Netbios frames sent on this 
                    interface."
                ::= { ipxNetbiosIfEntry 4 }


            -- the RIP group

            -- Implementation of this group is mandatory for all MRV In-Reach
            -- systems that implement IPX RIP

            ipxRipIfTable OBJECT-TYPE
                SYNTAX SEQUENCE OF IpxRipIfEntry
                ACCESS not-accessible
                STATUS mandatory
                DESCRIPTION
                    "A list of IPX interface entries."
                ::= { xIpxRip 1 }

            ipxRipIfEntry OBJECT-TYPE
                SYNTAX IpxRipIfEntry
                ACCESS not-accessible
                STATUS mandatory
                DESCRIPTION
                    "IPX interface parameters and counters."
                INDEX { ipxRipIfIndex }
                ::= { ipxRipIfTable 1 }

            IpxRipIfEntry ::=
                SEQUENCE {
                    ipxRipIfIndex
                        INTEGER,
                    ipxIfRipBcst
                        INTEGER,
                    ipxIfRipBcstDiscardTimeout
                        INTEGER,
                    ipxIfRipBcstTimer
                        INTEGER,
                    ipxIfRipIn
                        Counter,
                    ipxIfRipOut
                        Counter,
                    ipxIfRipAgedOut
                        Counter
                }

            ipxRipIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxRipIfEntry 1 }

            ipxIfRipBcst OBJECT-TYPE
                SYNTAX INTEGER { disabled(1), enabled(2), propUpdateOnly(3), demandCircuit(4) }
                ACCESS read-write
                STATUS mandatory
                DESCRIPTION
                    "Control whether RIP packets will be broadcasted out 
                    this interface."
                DEFVAL { enabled }
                ::= { ipxRipIfEntry 2 }

            ipxIfRipBcstDiscardTimeout OBJECT-TYPE
                SYNTAX INTEGER
                ACCESS read-write
                STATUS mandatory
                DESCRIPTION
                    "The number of seconds to wait before discarding 
                    information learned from a RIP broadcast."
                DEFVAL { 180 }
                ::= { ipxRipIfEntry 3 }

            ipxIfRipBcstTimer OBJECT-TYPE
                SYNTAX INTEGER
                ACCESS read-write
                STATUS mandatory
                DESCRIPTION
                    "The number of seconds to wait between sending out 
                    RIP broadcasts."
                DEFVAL { 60 }
                ::= { ipxRipIfEntry 4 }

            ipxIfRipIn OBJECT-TYPE
                SYNTAX Counter
                ACCESS read-only
                STATUS mandatory
                DESCRIPTION
                    "The number of RIP broadcasts received on this 
                    interface."
                ::= { ipxRipIfEntry 5 }

            ipxIfRipOut OBJECT-TYPE
                SYNTAX Counter
                ACCESS read-only
                STATUS mandatory
                DESCRIPTION
                    "The number of RIP broadcasts sent on this 
                    interface."
                ::= { ipxRipIfEntry 6 }

            ipxIfRipAgedOut OBJECT-TYPE
                SYNTAX Counter
                ACCESS read-only
                STATUS mandatory
                DESCRIPTION
                    "The number of entries timed out and discarded on 
                    this interface."
                ::= { ipxRipIfEntry 7 }

            ipxRipTable OBJECT-TYPE
                SYNTAX SEQUENCE OF IpxRipEntry
                ACCESS not-accessible
                STATUS mandatory
                DESCRIPTION
                    "A list of RIP entries."
                ::= { xIpxRip 2 }

            ipxRipEntry OBJECT-TYPE
                SYNTAX IpxRipEntry
                ACCESS not-accessible
                STATUS mandatory
                DESCRIPTION
                    "IPX interface parameters and counters."
                INDEX { ipxRipNetwork }
                ::= { ipxRipTable 1 }

            IpxRipEntry ::=
                SEQUENCE {
                    ipxRipNetwork
                        INTEGER,
                    ipxRipRouter
                        OCTET STRING,
                    ipxRipInterface
                        INTEGER,
                    ipxRipHops
                        INTEGER,
                    ipxRipTransTime
                        INTEGER,
                    ipxRipAge
                        INTEGER
                }

            ipxRipNetwork OBJECT-TYPE
                SYNTAX INTEGER
                ACCESS read-only
                STATUS mandatory
                DESCRIPTION
                    "An IPX network number to which this router knows a 
                    path."
                ::= { ipxRipEntry 1 }

            ipxRipRouter OBJECT-TYPE
                SYNTAX OCTET STRING ( SIZE(6) )
                ACCESS read-only
                STATUS mandatory
                DESCRIPTION
                    "The Ethernet address of an IPX router on this 
                    network."
                ::= { ipxRipEntry 2 }

            ipxRipInterface OBJECT-TYPE
                SYNTAX INTEGER
                ACCESS read-only
                STATUS mandatory
                DESCRIPTION
                    "The interface to reach the router.  A value of 
                    ifIndex."
                ::= { ipxRipEntry 3 }

            ipxRipHops OBJECT-TYPE
                SYNTAX INTEGER
                ACCESS read-only
                STATUS mandatory
                DESCRIPTION
                    "The number of hops to reach the router."
                ::= { ipxRipEntry 4 }

            ipxRipTransTime OBJECT-TYPE
                SYNTAX INTEGER
                ACCESS read-only
                STATUS mandatory
                DESCRIPTION
                    "The number of 55 millisecond ticks it takes for a 
                    packet to travel to the router."
                ::= { ipxRipEntry 5 }

            ipxRipAge OBJECT-TYPE
                SYNTAX INTEGER
                ACCESS read-only
                STATUS mandatory
                DESCRIPTION
                    "The age of the RIP entry in seconds."
                ::= { ipxRipEntry 6 }

            ipxRipRtTable OBJECT-TYPE
                SYNTAX SEQUENCE OF IpxRipRtEntry
                ACCESS not-accessible
                STATUS mandatory
                DESCRIPTION
                    "A list of RIP Routing entries."
                ::= { xIpxRip 3 }

            ipxRipRtEntry OBJECT-TYPE
                SYNTAX IpxRipRtEntry
                ACCESS not-accessible
                STATUS mandatory
                DESCRIPTION
                    "IPX Routing Entry information"
                INDEX { ipxRipRtNetwork, ipxRipRtInterface, ipxRipRtOrigin,
                         ipxRipRtRouter  }
                ::= { ipxRipRtTable 1 }

            IpxRipRtEntry ::=
                SEQUENCE {
                    ipxRipRtNetwork
                        INTEGER,
                    ipxRipRtRouter
                        OCTET STRING,
                    ipxRipRtInterface
                        INTEGER,
                    ipxRipRtHops
                        INTEGER,
                    ipxRipRtTransTime
                        INTEGER,
		     ipxRipRtOrigin
			INTEGER,
		     ipxRipRtRowStatus
			INTEGER
                }

            ipxRipRtNetwork OBJECT-TYPE
                SYNTAX INTEGER
                ACCESS read-only
                STATUS mandatory
                DESCRIPTION
                    "An IPX network number to which this router knows a 
                    path."
                ::= { ipxRipRtEntry 1 }

            ipxRipRtRouter OBJECT-TYPE
                SYNTAX OCTET STRING ( SIZE(6) )
                ACCESS read-only
                STATUS mandatory
                DESCRIPTION
                    "The Ethernet address of an IPX router on this 
                    network."
                ::= { ipxRipRtEntry 2 }

            ipxRipRtInterface OBJECT-TYPE
                SYNTAX INTEGER
                ACCESS read-only
                STATUS mandatory
                DESCRIPTION
                    "The interface to reach the router.  A value of 
                    ifIndex."
                ::= { ipxRipRtEntry 3 }

            ipxRipRtHops OBJECT-TYPE
                SYNTAX INTEGER (0..16)
                ACCESS read-write
                STATUS mandatory
                DESCRIPTION
                    "The number of hops to reach the router."
                ::= { ipxRipRtEntry 4 }

            ipxRipRtTransTime OBJECT-TYPE
                SYNTAX INTEGER (0..65535)
                ACCESS read-write
                STATUS mandatory
                DESCRIPTION
                    "The number of 55 millisecond ticks it takes for a 
                    packet to travel to the router."
                ::= { ipxRipRtEntry 5 }

            ipxRipRtOrigin OBJECT-TYPE
                SYNTAX INTEGER { ripLearned(1), static(2), nlspLearned(3) }
                ACCESS read-only
                STATUS mandatory
                DESCRIPTION
                    "The source of the RIP entry, either Learned via RIP or Static."
                ::= { ipxRipRtEntry 6 }


            ipxRipRtRowStatus OBJECT-TYPE
                SYNTAX INTEGER { invalid(1), valid(2) }
                ACCESS read-write
                STATUS mandatory
                DESCRIPTION
                    "Create or Delete RIP routing table entries."
                DEFVAL { valid }
                ::= { ipxRipRtEntry 7}


            -- the SAP group

            -- Implementation of this group is mandatory for all MRV In-Reach
            -- systems that implement IPX SAP

            ipxSapIfTable OBJECT-TYPE
                SYNTAX SEQUENCE OF IpxSapIfEntry
                ACCESS not-accessible
                STATUS mandatory
                DESCRIPTION
                    "A list of IPX interface entries."
                ::= { xIpxSap 1 }

            ipxSapIfEntry OBJECT-TYPE
                SYNTAX IpxSapIfEntry
                ACCESS not-accessible
                STATUS mandatory
                DESCRIPTION
                    "IPX interface parameters and counters."
                INDEX { ipxSapIfIndex }
                ::= { ipxSapIfTable 1 }

            IpxSapIfEntry ::=
                SEQUENCE {
                    ipxSapIfIndex
                        INTEGER,
                    ipxIfSapBcst
                        INTEGER,
                    ipxIfSapBcstDiscardTimeout
                        INTEGER,
                    ipxIfSapBcstTimer
                        INTEGER,
                    ipxIfSapIn
                        Counter,
                    ipxIfSapOut
                        Counter,
                    ipxIfSapAgedOut
                        Counter
                }

            ipxSapIfIndex OBJECT-TYPE
                SYNTAX INTEGER
                ACCESS read-only
                STATUS mandatory
                DESCRIPTION
                    "An index value that uniquely identifies an IPX 
                    interface.  The interface identified by a particular 
                    value of this index is the same interface as 
                    identified by the same value of ifIndex."
                ::= { ipxSapIfEntry 1 }

            ipxIfSapBcst OBJECT-TYPE
                SYNTAX INTEGER { disabled(1), enabled(2), propUpdateOnly(3), demandCircuit(4) }
                ACCESS read-write
                STATUS mandatory
                DESCRIPTION
                    "Control whether SAP packets will be broadcasted out 
                    this interface."
                DEFVAL { enabled }
                ::= { ipxSapIfEntry 2 }

            ipxIfSapBcstDiscardTimeout OBJECT-TYPE
                SYNTAX INTEGER
                ACCESS read-write
                STATUS mandatory
                DESCRIPTION
                    "The number of seconds to wait before discarding 
                    information learned from a SAP broadcast."
                DEFVAL { 180 }
                ::= { ipxSapIfEntry 3 }

            ipxIfSapBcstTimer OBJECT-TYPE
                SYNTAX INTEGER
                ACCESS read-write
                STATUS mandatory
                DESCRIPTION
                    "The number of seconds to wait between sending out 
                    SAP broadcasts."
                DEFVAL { 60 }
                ::= { ipxSapIfEntry 4 }

            ipxIfSapIn OBJECT-TYPE
                SYNTAX Counter
                ACCESS read-only
                STATUS mandatory
                DESCRIPTION
                    "The number SAP broadcasts received on this 
                    interface."
                ::= { ipxSapIfEntry 5 }

            ipxIfSapOut OBJECT-TYPE
                SYNTAX Counter
                ACCESS read-only
                STATUS mandatory
                DESCRIPTION
                    "The number SAP broadcasts sent on this interface."
                ::= { ipxSapIfEntry 6 }

            ipxIfSapAgedOut OBJECT-TYPE
                SYNTAX Counter
                ACCESS read-only
                STATUS mandatory
                DESCRIPTION
                    "The number entries for this interface discarded due 
                    to aging timeout."
                ::= { ipxSapIfEntry 7 }

            ipxSapTable OBJECT-TYPE
                SYNTAX SEQUENCE OF IpxSapEntry
                ACCESS not-accessible
                STATUS mandatory
                DESCRIPTION
                    "A list of SAP entries."
                ::= { xIpxSap 2 }

            ipxSapEntry OBJECT-TYPE
                SYNTAX IpxSapEntry
                ACCESS not-accessible
                STATUS mandatory
                DESCRIPTION
                    "IPX interface parameters and counters."
                INDEX { ipxSapName, ipxSapType }
                ::= { ipxSapTable 1 }

            IpxSapEntry ::=
                SEQUENCE {
                    ipxSapName
                        DisplayString,
                    ipxSapNetwork
                        INTEGER,
                    ipxSapHost
                        OCTET STRING,
                    ipxSapSocket
                        INTEGER,
                    ipxSapInterface
                        INTEGER,
                    ipxSapType
                        INTEGER,
                    ipxSapAge
                        INTEGER
                }

            ipxSapName OBJECT-TYPE
                SYNTAX DisplayString (SIZE (48))
                ACCESS read-only
                STATUS mandatory
                DESCRIPTION
                    "The name of the service, null filled."
                ::= { ipxSapEntry 1 }

            ipxSapNetwork OBJECT-TYPE
                SYNTAX INTEGER
                ACCESS read-only
                STATUS mandatory
                DESCRIPTION
                    "The IPX network number on which the service's host 
                    resides."
                ::= { ipxSapEntry 2 }

            ipxSapHost OBJECT-TYPE
                SYNTAX OCTET STRING ( SIZE(6))
                ACCESS read-only
                STATUS mandatory
                DESCRIPTION
                    "The Ethernet address of the IPX host of the 
                    service."
                ::= { ipxSapEntry 3 }

            ipxSapSocket OBJECT-TYPE
                SYNTAX INTEGER
                ACCESS read-only
                STATUS mandatory
                DESCRIPTION
                    "The socket number of the service on the host."
                ::= { ipxSapEntry 4 }

            ipxSapInterface OBJECT-TYPE
                SYNTAX INTEGER
                ACCESS read-only
                STATUS mandatory
                DESCRIPTION
                    "The interface of the router in the direction of the 
                    service.  A value of ifIndex."
                ::= { ipxSapEntry 5 }

            ipxSapType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service.  The enumeration is an 
					incomplete set of all possible values."
                ::= { ipxSapEntry 6 }

            ipxSapAge OBJECT-TYPE
                SYNTAX INTEGER
                ACCESS read-only
                STATUS mandatory
                DESCRIPTION
                    "The age of the Sap entry in seconds."
                ::= { ipxSapEntry 7 }

            ipxSapSvTable OBJECT-TYPE
                SYNTAX SEQUENCE OF IpxSapSvEntry
                ACCESS not-accessible
                STATUS mandatory
                DESCRIPTION
                    "A list of SAP entries."
                ::= { xIpxSap 3 }

            ipxSapSvEntry OBJECT-TYPE
                SYNTAX IpxSapSvEntry
                ACCESS not-accessible
                STATUS mandatory
                DESCRIPTION
                    "IPX interface parameters and counters."
                INDEX { ipxSapSvName, ipxSapSvType, ipxSapSvOrigin,
	                ipxSapSvNetwork, ipxSapSvSocket, ipxSapSvHost  }
                ::= { ipxSapSvTable 1 }

            IpxSapSvEntry ::=
                SEQUENCE {
                    ipxSapSvName
                        DisplayString,
                    ipxSapSvNetwork
                        INTEGER,
                    ipxSapSvHost
                        OCTET STRING,
                    ipxSapSvSocket
                        INTEGER,
                    ipxSapSvInterface
                        INTEGER,
                    ipxSapSvOrigin
                        INTEGER,
                    ipxSapSvType
                        INTEGER,
		     ipxSapSvHops
			INTEGER,
		     ipxSapSvRowStatus
			INTEGER,
		     ipxSapSvAge
			INTEGER
                }

            ipxSapSvName OBJECT-TYPE
                SYNTAX DisplayString (SIZE (0..48))
                ACCESS read-only
                STATUS mandatory
                DESCRIPTION
                    "The name of the service."
                ::= { ipxSapSvEntry 1 }

            ipxSapSvNetwork OBJECT-TYPE
                SYNTAX INTEGER
                ACCESS read-only
                STATUS mandatory
                DESCRIPTION
                    "The IPX network number on which the service's host 
                    resides."
                ::= { ipxSapSvEntry 2 }

            ipxSapSvHost OBJECT-TYPE
                SYNTAX OCTET STRING ( SIZE(6))
                ACCESS read-only
                STATUS mandatory
                DESCRIPTION
                    "The Ethernet address of the IPX host of the 
                    service."
                ::= { ipxSapSvEntry 3 }

            ipxSapSvSocket OBJECT-TYPE
                SYNTAX INTEGER (0..65535)
                ACCESS read-only
                STATUS mandatory
                DESCRIPTION
                    "The socket number of the service on the host."
                ::= { ipxSapSvEntry 4 }

            ipxSapSvInterface OBJECT-TYPE
                SYNTAX INTEGER
                ACCESS read-only
                STATUS mandatory
                DESCRIPTION
                    "The interface of the router in the direction of the 
                    service.  A value of ifIndex."
                ::= { ipxSapSvEntry 5 }

            ipxSapSvOrigin OBJECT-TYPE
                SYNTAX INTEGER {
                            ipxSapLearned(1),
                            ipxStatic(2)
                       }
                ACCESS read-only
                STATUS mandatory
                DESCRIPTION
                    "The source of the RIP entry, either Learned via RIP or Static."
                ::= { ipxSapSvEntry 6 }

            ipxSapSvType OBJECT-TYPE
                SYNTAX INTEGER {
                            user(1),
                            userGroup(2),
                            printQueue(3),
                            novellFileServer(4),
                            jobServer(5),
                            gateway1(6),
                            printServer(7),
                            archiveQueue(8),
                            archiveServer(9),
                            jobQueue(10),
                            administration(11)
                        }
                ACCESS read-only
                STATUS mandatory
                DESCRIPTION
                    "The type of the service.  The enumeration is an 
					incomplete set of all possible values."
                ::= { ipxSapSvEntry 7 }

            ipxSapSvHops OBJECT-TYPE
                SYNTAX INTEGER (0..16)
                ACCESS read-write
                STATUS mandatory
                DESCRIPTION
                    "The number of hops to the Service."
                ::= { ipxSapSvEntry 8 }

            ipxSapSvRowStatus OBJECT-TYPE
                SYNTAX INTEGER { disabled(1), enabled(2) }
                ACCESS read-write
                STATUS mandatory
                DESCRIPTION
                    "Create or Delete SAP Service table entries."
                DEFVAL { enabled }
                ::= { ipxSapSvEntry 9}

            ipxSapSvAge OBJECT-TYPE
                SYNTAX INTEGER
                ACCESS read-only
                STATUS mandatory
                DESCRIPTION
                    "The age of the Sap entry in seconds."
                ::= { ipxSapSvEntry 10 }

            -- the IPX Filter group

            -- Implementation of this group is mandatory for all MRV In-Reach
            -- systems that implement IPX Filtering

            ipxIfFilterTable OBJECT-TYPE
                SYNTAX SEQUENCE OF IpxIfFilterEntry
                ACCESS not-accessible
                STATUS mandatory
                DESCRIPTION
                    "A list of IPX interface Source and Destination
                     address Filter entries."
                ::= { xIpxFilter 1 }

            ipxIfFilterEntry OBJECT-TYPE
                SYNTAX IpxIfFilterEntry
                ACCESS not-accessible
                STATUS mandatory
                DESCRIPTION
                    "IPX Source and Destination interface Filters."
                INDEX { ipxIfIndex, ipxIfFilterDestNetwork, ipxIfFilterDestNode,
                        ipxIfFilterSourceNetwork, ipxIfFilterSourceNode, 
                        ipxIfFilterPacketType, ipxIfFilterStatusDestNetworkAll,
			ipxIfFilterStatusDestNodeAll,ipxIfFilterStatusSourceNetworkAll,
			ipxIfFilterStatusSourceNodeAll,ipxIfFilterStatusPacketTypeAll  }
                ::= { ipxIfFilterTable 1 }

            IpxIfFilterEntry ::=
                SEQUENCE {
                    ipxIfFilterIndex
                        INTEGER,
                    ipxIfFilterDestNetwork
                        INTEGER,
                    ipxIfFilterDestNode
                        OCTET STRING,
                    ipxIfFilterSourceNetwork
                        INTEGER,
                    ipxIfFilterSourceNode
                        OCTET STRING,
                    ipxIfFilterPacketType
                        INTEGER,
                    ipxIfFilterAction
                        INTEGER,
                    ipxIfFilterRowStatus
                        INTEGER,
                    ipxIfFilterStatusDestNetworkAll
                        INTEGER,
                    ipxIfFilterStatusDestNodeAll
                        INTEGER,
                    ipxIfFilterStatusSourceNetworkAll
                        INTEGER,
                    ipxIfFilterStatusSourceNodeAll
                        INTEGER,
                    ipxIfFilterStatusPacketTypeAll
                        INTEGER
                }

            ipxIfFilterIndex OBJECT-TYPE
                SYNTAX INTEGER
                ACCESS read-only
                STATUS mandatory
                DESCRIPTION
                    "The interface to which this IPX Address filter applies.
                     A value of ifIndex."
                ::= { ipxIfFilterEntry 1 }

            ipxIfFilterDestNetwork OBJECT-TYPE
                SYNTAX INTEGER
                ACCESS read-only
                STATUS mandatory
                DESCRIPTION
                    "The destination IPX network to be filtered."
                ::= { ipxIfFilterEntry 2 }

            ipxIfFilterDestNode OBJECT-TYPE
                SYNTAX OCTET STRING ( SIZE(6))
                ACCESS read-only
                STATUS mandatory
                DESCRIPTION
                    "The destination IPX node to be filtered."
                ::= { ipxIfFilterEntry 3 }

            ipxIfFilterSourceNetwork OBJECT-TYPE
                SYNTAX INTEGER
                ACCESS read-only
                STATUS mandatory
                DESCRIPTION
                    "The destination IPX network to be filtered."
                ::= { ipxIfFilterEntry 4 }

            ipxIfFilterSourceNode OBJECT-TYPE
                SYNTAX OCTET STRING ( SIZE(6))
                ACCESS read-only
                STATUS mandatory
                DESCRIPTION
                    "The destination IPX node to be filtered."
                ::= { ipxIfFilterEntry 5 }

            ipxIfFilterPacketType OBJECT-TYPE
                SYNTAX INTEGER (0..255) 
                ACCESS read-only
                STATUS mandatory
                DESCRIPTION
                    "The IPX packet type to be filtered."
                ::= { ipxIfFilterEntry 6 }

            ipxIfFilterAction OBJECT-TYPE
                SYNTAX INTEGER {
                           forward(1),
                           discard(2)
                       }
                ACCESS read-write
                STATUS mandatory
                DESCRIPTION
                    "The IPX filter action to be taken, either Forward or Discard."
                ::= { ipxIfFilterEntry 7 }

            ipxIfFilterRowStatus OBJECT-TYPE
                SYNTAX INTEGER {
                           invalid(1),
                           valid(2)
                       }
                ACCESS read-write
                STATUS mandatory
                DESCRIPTION
                    "The IPX Filter create or delete function."
                ::= { ipxIfFilterEntry 8 }

            ipxIfFilterStatusDestNetworkAll OBJECT-TYPE
                SYNTAX INTEGER {
                           disabled(1),
                           enabled(2)
                       }
                ACCESS read-only
                STATUS mandatory
                DESCRIPTION
                    "The IPX Filter flag meaning ALL destination networks."
                ::= { ipxIfFilterEntry 9 }

            ipxIfFilterStatusDestNodeAll OBJECT-TYPE
                SYNTAX INTEGER {
                           disabled(1),
                           enabled(2)
                       }
                ACCESS read-only
                STATUS mandatory
                DESCRIPTION
                    "The IPX Filter flag meaning ALL destination nodes."
                ::= { ipxIfFilterEntry 10 }

            ipxIfFilterStatusSourceNetworkAll OBJECT-TYPE
                SYNTAX INTEGER {
                           disabled(1),
                           enabled(2)
                       }
                ACCESS read-only
                STATUS mandatory
                DESCRIPTION
                    "The IPX Filter flag meaning ALL source networks."
                ::= { ipxIfFilterEntry 11 }

            ipxIfFilterStatusSourceNodeAll OBJECT-TYPE
                SYNTAX INTEGER {
                           disabled(1),
                           enabled(2)
                       }
                ACCESS read-only
                STATUS mandatory
                DESCRIPTION
                    "The IPX Filter flag meaning ALL source nodes."
                ::= { ipxIfFilterEntry 12 }

            ipxIfFilterStatusPacketTypeAll OBJECT-TYPE
                SYNTAX INTEGER {
                           disabled(1),
                           enabled(2)
                       }
                ACCESS read-only
                STATUS mandatory
                DESCRIPTION
                    "The IPX Filter flag meaning ALL packet types."
                ::= { ipxIfFilterEntry 13 }


            ipxIfRipFilterTable OBJECT-TYPE
                SYNTAX SEQUENCE OF IpxIfRipFilterEntry
                ACCESS not-accessible
                STATUS mandatory
                DESCRIPTION
                    "A list of IPX interface RIP Filter entries."
                ::= { xIpxFilter 2 }

            ipxIfRipFilterEntry OBJECT-TYPE
                SYNTAX IpxIfRipFilterEntry
                ACCESS not-accessible
                STATUS mandatory
                DESCRIPTION
                    "IPX RIP interface Filters."
                INDEX { ipxIfIndex, ipxIfRipFilterType, ipxIfRipFilterNetwork, ipxIfRipFilterNetworkAll, 
			ipxIfRipFilterHost }
                ::= { ipxIfRipFilterTable 1 }

            IpxIfRipFilterEntry ::=
                SEQUENCE {
                    ipxIfRipFilterNetwork
                        INTEGER,
                    ipxIfRipFilterType
                        INTEGER,
                    ipxIfRipFilterAction
                        INTEGER,
                    ipxIfRipFilterRowStatus
                        INTEGER,
                    ipxIfRipFilterNetworkAll
                        INTEGER,
                    ipxIfRipFilterHost
			OCTET STRING
                }

            ipxIfRipFilterNetwork OBJECT-TYPE
                SYNTAX INTEGER
                ACCESS read-only
                STATUS mandatory
                DESCRIPTION
                    "The IPX RIP network to be filtered."
                ::= { ipxIfRipFilterEntry 1 }

            ipxIfRipFilterType OBJECT-TYPE
                SYNTAX INTEGER {
                           import(1),
                           export(2)
                       }
                ACCESS read-only
                STATUS mandatory
                DESCRIPTION
                    "The IPX RIP filter type, either IMPORT or EXPORT."
                ::= { ipxIfRipFilterEntry 2 }

            ipxIfRipFilterAction OBJECT-TYPE	
                SYNTAX INTEGER {
                           allow(1),
                           deny(2)
                       }
                ACCESS read-write	
                STATUS mandatory	
                DESCRIPTION	
                    "The IPX RIP filter action to be taken, either ALLOW or DENY."
                ::= { ipxIfRipFilterEntry 3 }

            ipxIfRipFilterRowStatus OBJECT-TYPE
                SYNTAX INTEGER {
                           invalid(1),
                           valid(2)
                       }
                ACCESS read-write
                STATUS mandatory
                DESCRIPTION
                    "The IPX RIP Filter create or delete function."
                ::= { ipxIfRipFilterEntry 4 }

            ipxIfRipFilterNetworkAll OBJECT-TYPE
                SYNTAX INTEGER {
                           disabled(1),
                           enabled(2)
                       }
                ACCESS read-only
                STATUS mandatory
                DESCRIPTION
                    "The IPX RIP Filter flag meaning filter ALL networks."
                ::= { ipxIfRipFilterEntry 5 }


            ipxIfRipFilterHost OBJECT-TYPE
                SYNTAX OCTET STRING (SIZE (6))
                ACCESS read-only
                STATUS mandatory
                DESCRIPTION
                    "The RIP Filter IPX Host Address from which RIP will ALLOW/DENY IMPORT of routes."
                ::= { ipxIfRipFilterEntry 6 }


            ipxIfSapFilterTable OBJECT-TYPE
                SYNTAX SEQUENCE OF IpxIfSapFilterEntry
                ACCESS not-accessible
                STATUS mandatory
                DESCRIPTION
                    "A list of IPX interface SAP Filter entries."
                ::= { xIpxFilter 3 }

            ipxIfSapFilterEntry OBJECT-TYPE
                SYNTAX IpxIfSapFilterEntry
                ACCESS not-accessible
                STATUS mandatory
                DESCRIPTION
                    "IPX SAP interface Filters."
                INDEX { ipxIfIndex, ipxIfSapFilterType, ipxIfSapFilterName, ipxIfSapFilterServiceType, 
                        ipxIfSapFilterServiceTypeAll, ipxIfSapFilterNetwork, ipxIfSapFilterNetworkAll, 
			ipxIfSapFilterHost }
                ::= { ipxIfSapFilterTable 1 }

            IpxIfSapFilterEntry ::=
                SEQUENCE {
                    ipxIfSapFilterNetwork
                        INTEGER,
                    ipxIfSapFilterType
                        INTEGER,
                    ipxIfSapFilterServiceType
                        INTEGER,
                    ipxIfSapFilterAction
                        INTEGER,
                    ipxIfSapFilterRowStatus
                        INTEGER,
                    ipxIfSapFilterNetworkAll
                        INTEGER,
                    ipxIfSapFilterServiceTypeAll
                        INTEGER,
                    ipxIfSapFilterName
                        DisplayString,
                    ipxIfSapFilterHost
                        OCTET STRING
                }

            ipxIfSapFilterNetwork OBJECT-TYPE
                SYNTAX INTEGER
                ACCESS read-only
                STATUS mandatory
                DESCRIPTION
                    "The IPX SAP network to be filtered."
                ::= { ipxIfSapFilterEntry 1 }

            ipxIfSapFilterType OBJECT-TYPE
                SYNTAX INTEGER {
                           import(1),
                           export(2)
                       }
                ACCESS read-only
                STATUS mandatory
                DESCRIPTION
                    "The IPX SAP filter type, either IMPORT or EXPORT."
                ::= { ipxIfSapFilterEntry 2 }

            ipxIfSapFilterServiceType OBJECT-TYPE
                SYNTAX INTEGER (0..65535)
                ACCESS read-only
                STATUS mandatory
                DESCRIPTION
                    "The IPX SAP service type to which this filter applies."
                ::= { ipxIfSapFilterEntry 3 }

            ipxIfSapFilterAction OBJECT-TYPE	
                SYNTAX INTEGER {
                           allow(1),
                           deny(2)
                       }
                ACCESS read-write	
                STATUS mandatory	
                DESCRIPTION	
                    "The IPX SAP filter action to be taken, either ALLOW or DENY."
                ::= { ipxIfSapFilterEntry 4 }

            ipxIfSapFilterRowStatus OBJECT-TYPE
                SYNTAX INTEGER {
                           invalid(1),
                           valid(2)
                       }
                ACCESS read-write
                STATUS mandatory
                DESCRIPTION
                    "The IPX SAP Filter create or delete function."
                ::= { ipxIfSapFilterEntry 5 }

            ipxIfSapFilterNetworkAll OBJECT-TYPE
                SYNTAX INTEGER {
                           disabled(1),
                           enabled(2)
                       }
                ACCESS read-only
                STATUS mandatory
                DESCRIPTION
                    "The IPX SAP Filter flag meaning filter ALL networks."
                ::= { ipxIfSapFilterEntry 6 }

            ipxIfSapFilterServiceTypeAll OBJECT-TYPE
                SYNTAX INTEGER {
                           disabled(1),
                           enabled(2)
                       }
                ACCESS read-only
                STATUS mandatory
                DESCRIPTION
                    "The IPX SAP Filter flag meaning filter ALL service types."
                ::= { ipxIfSapFilterEntry 7 }

            ipxIfSapFilterName OBJECT-TYPE
                SYNTAX DisplayString (SIZE (0..48))
                ACCESS read-only
                STATUS mandatory
                DESCRIPTION
                    "The name of the service to be filtered."
                ::= { ipxIfSapFilterEntry 8 }

            ipxIfSapFilterHost OBJECT-TYPE
                SYNTAX OCTET STRING (SIZE (6))
                ACCESS read-only
                STATUS mandatory
                DESCRIPTION
                    "The IPX Host address from which SAP will ALLOW/DENY IMPORT of services ."
                ::= { ipxIfSapFilterEntry 9 }

            -- the Printer group

            -- Implementation of this group is mandatory for all MRV In-Reach
            -- systems that implement IPX printers

            -- Additional single-instance values follow the Port table

            -- the Printer Port table

            ipxPrinterPortTable OBJECT-TYPE
                SYNTAX SEQUENCE OF IpxPrinterPortEntry
                ACCESS not-accessible
                STATUS mandatory
                DESCRIPTION
                    "A list of IPX printer character port entries."
                ::= { xIpxPrinter 1 }

            ipxPrinterPortEntry OBJECT-TYPE
                SYNTAX IpxPrinterPortEntry
                ACCESS not-accessible
                STATUS mandatory
                DESCRIPTION
                    "IPX printer parameter values for a character 
                    port."
                INDEX { ipxPrinterPortIndex }
                ::= { ipxPrinterPortTable 1 }

            IpxPrinterPortEntry ::=
                SEQUENCE {
                    ipxPrinterPortIndex
                        INTEGER,
                    ipxPrinterPortStatus
                        INTEGER,
                    ipxPrinterPortServer
                        DisplayString,
                    ipxPrinterPortPrinter
                        INTEGER,
                    ipxTimeout
                        INTEGER
                }

            ipxPrinterPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { ipxPrinterPortEntry 1 }

            ipxPrinterPortStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { ipxPrinterPortEntry 2 }

            ipxPrinterPortServer OBJECT-TYPE
                SYNTAX DisplayString (SIZE (0..48))
                ACCESS read-write
                STATUS mandatory
                DESCRIPTION
                    "The name of an active print server on the 
                    network."
                ::= { ipxPrinterPortEntry 3 }

            ipxPrinterPortPrinter OBJECT-TYPE
                SYNTAX INTEGER (0..255)
                ACCESS read-write
                STATUS mandatory
                DESCRIPTION
                    "An available remote printer on 
                    ixpPrinterPortServer."
                ::= { ipxPrinterPortEntry 4 }

             ipxTimeout OBJECT-TYPE
                SYNTAX INTEGER (15..300)
                ACCESS read-write
                STATUS mandatory
                DESCRIPTION
                    "A control to set the the time at which a print job from a
                     print server will be timed out and the port freed."
                DEFVAL { 15 }
                ::= { ipxPrinterPortEntry 5 }

            -- The following are additional single-instance values, 
            -- not part of the Port table.

            ipxPrinterEthernet OBJECT-TYPE
                SYNTAX INTEGER { disabled(1), enabled(2) }
                ACCESS read-write
                STATUS mandatory
                DESCRIPTION
                    "Control for use of Ethernet-style message framing, 
                    with the IPX protocol type.  Mutually exclusive with 
                    ipxPrinterMac, ipxPrinterMac802_2_Snap, and ipxPrinterMac802_2."
                ::= { xIpxPrinter 2 }

            ipxPrinterMac OBJECT-TYPE
                SYNTAX INTEGER { disabled(1), enabled(2) }
                ACCESS read-write
                STATUS mandatory
                DESCRIPTION
                    "Control for use of MAC-only message framing, with 
                    no protocol type.  Mutually exclusive with 
                    ipxPrinterEthernet, ipxPrinterMac802_2_Snap, and ipxPrinterMac802_2."
                ::= { xIpxPrinter 3 }

            ipxPrinterMac802-2 OBJECT-TYPE
                SYNTAX INTEGER { disabled(1), enabled(2) }
                ACCESS read-write
                STATUS mandatory
                DESCRIPTION
                    "Control for use of MAC message framing with 
                    802.2 framing.  Mutually exclusive with 
                    ipxPrinterEthernet, ipxPrinterMac, and ipxPrinterMac802_2_Snap."
                ::= { xIpxPrinter 4 }

            ipxPrinterMac802-2-Snap OBJECT-TYPE
                SYNTAX INTEGER { disabled(1), enabled(2) }
                ACCESS read-write
                STATUS mandatory
                DESCRIPTION
                    "Control for use of MAC-only message framing with 
                    802 Snap framing.  Mutually exclusive with 
                    ipxPrinterEthernet, ipxPrinterMac, and ipxPrinterMac802_2."
                ::= { xIpxPrinter 5 }

--
-- FILE: /users/sse/mibs/src/inReach/ir-lat-mib.mib
--

-- $Id: ir-lat-mib.mib,v 1.1 2002/06/27 15:34:42 sse Exp $


            xLat            OBJECT IDENTIFIER ::= { mrvInReachProductDivision 3 }



            -- This is a MIB module for all MRV Communications systems that
            -- implement LAT.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the LAT group

            -- Implementation of this group is mandatory for all in-Reach
            -- systems that implement LAT

            latAnnounceServices OBJECT-TYPE
                SYNTAX INTEGER { disabled(1), enabled(2) }
                ACCESS read-write
                STATUS mandatory
                DESCRIPTION
                    "Control for automatic, periodic announcement of 
                    local services to the network.  Corresponds directly 
                    to SERVER ANNOUNCEMENTS and the presence of the 
                    label 'Announcements' following the label 'Enabled 
                    Characteristics:' in the SERVER CHARACTERISTICS 
                    display."
                ::= { xLat 1 }

            latCircuitTimer OBJECT-TYPE
                SYNTAX INTEGER (30..200)
                ACCESS read-write
                STATUS mandatory
                DESCRIPTION
                    "Number of milleseconds to collect port input data 
                    before sending it to the host.  Corresponds directly 
                    to SERVER CIRCUIT TIMER and the value labeled 
                    'Circuit Timer:' in the SERVER CHARACTERISTICS 
                    display."
                ::= { xLat 2 }

            latIdentificationLengthLimit OBJECT-TYPE
                SYNTAX INTEGER (0..63)
                ACCESS read-write
                STATUS mandatory
                DESCRIPTION
                    "Maximum number of characters to store in the 
                    instances of latVisibleServiceIdentification.  
                    Corresponds directly to SERVER IDENTIFICATION SIZE 
                    and the value labeled 'Identification Size:' in the 
                    SERVER CHARACTERISTICS display."
                ::= { xLat 3 }

            latKeepaliveTimer OBJECT-TYPE
                SYNTAX INTEGER (10..180)
                ACCESS read-write
                STATUS mandatory
                DESCRIPTION
                    "Number of seconds of inactivity before sending a 
                    null message to the host.  Corresponds directly to 
                    SERVER KEEPALIVE TIMER and the value labeled 
                    'Keepalive Timer:' in the SERVER CHARACTERISTICS 
                    display."
                ::= { xLat 4 }

            latMulticastTimer OBJECT-TYPE
                SYNTAX INTEGER (10..180)
                ACCESS read-write
                STATUS mandatory
                DESCRIPTION
                    "Number of seconds between transmission of local 
                    service announcements.  Corresponds directly to 
                    SERVER MULTICAST TIMER and the value labeled 
                    'Multicast Timer:' in the SERVER CHARACTERISTICS 
                    display."
                ::= { xLat 5 }

            latNodeLimit OBJECT-TYPE
                SYNTAX INTEGER (1..1000)
                ACCESS read-write
                STATUS mandatory
                DESCRIPTION
                    "Maximum number of service nodes to keep in the node 
                    table.  Corresponds directly to SERVER NODE LIMIT 
                    and the value labeled 'Node Limit:' in the SERVER 
                    CHARACTERISTICS display."
                ::= { xLat 6 }

            latNumber OBJECT-TYPE
                SYNTAX INTEGER (0..32767)
                ACCESS read-write
                STATUS mandatory
                DESCRIPTION
                    "An arbitrary number assigned and used for 
                    administrative purposes.  Corresponds directly to 
                    SERVER NUMBER and the value labeled 'Number:' in the 
                    SERVER CHARACTERISTICS display."
                ::= { xLat 7 }

            latRetransmitLimit OBJECT-TYPE
                SYNTAX INTEGER (4..120)
                ACCESS read-write
                STATUS mandatory
                DESCRIPTION
                    "Maximum number of times to retransmit an 
                    unacknowledged message.  Corresponds directly to 
                    SERVER RETRANSMIT LIMIT and the value labeled 
                    'Retransmit Limit:' in the SERVER CHARACTERISTICS 
                    display."
                ::= { xLat 8 }

            latLocalServiceGroups OBJECT-TYPE
                SYNTAX OCTET STRING (SIZE (32))
                ACCESS read-write
                STATUS mandatory
                DESCRIPTION
                    "The list of group numbers allowed to use local 
                    services, where a group number is in the range 
                    0-255.  The OCTET STRING contains a bitmap, with one 
                    bit for each group.  Corresponding bit numbers start 
                    with 0 as the high-order bit of the first octet.  
                    Corresponds directly to SERVER SERVICE GROUPS and 
                    the value labeled 'Service Groups:' in the SERVER 
                    CHARACTERISTICS display."
                ::= { xLat 9 }

            latGroupPurge OBJECT-TYPE
                SYNTAX INTEGER { disabled(1), enabled(2) }
                ACCESS read-write
                STATUS mandatory
                DESCRIPTION
                    "Control for automatic deletion of all node table 
                    entries when latServiceGroups or 
                    latPortCurrentGroups is changed.  Corresponds 
                    directly to SERVER PURGE GROUP and the presence of 
                    the label 'Purge Group' following the label 'Enabled 
                    Characteristics:' in the SERVER CHARACTERISTICS 
                    display."
                ::= { xLat 10 }

            latNodePurge OBJECT-TYPE
                SYNTAX INTEGER { disabled(1), enabled(2) }
                ACCESS read-write
                STATUS mandatory
                DESCRIPTION
                    "Control for automatic deletion of all node table 
                    entries with status 'reachable' when the number of 
                    entries exceeds latNodeLimit.  Corresponds directly 
                    to SERVER PURGE NODE and the presence of the label 
                    'Purge Node' following the label 'Enabled 
                    Characteristics:' in the SERVER CHARACTERISTICS 
                    display."
                ::= { xLat 11 }

            latNodesRejected OBJECT-TYPE
                SYNTAX Counter
                ACCESS read-only
                STATUS mandatory
                DESCRIPTION
                    "Number of nodes not added to the node table because 
                    there was no room.  Corresponds directly to the 
                    value labeled 'Discarded Nodes:' in the SERVER 
                    STATUS display."
                ::= { xLat 12 }

            latInMessages OBJECT-TYPE
                SYNTAX Counter
                ACCESS read-only
                STATUS mandatory
                DESCRIPTION
                    "Number of LAT messages received.  Corresponds 
                    directly to the value labeled 'Messages Received:' 
                    in the SERVER COUNTERS display."
                ::= { xLat 13 }

            latOutMessages OBJECT-TYPE
                SYNTAX Counter
                ACCESS read-only
                STATUS mandatory
                DESCRIPTION
                    "Number of LAT messages sent.  Corresponds directly 
                    to the value labeled 'Messages Transmitted:' in the 
                    SERVER COUNTERS display."
                ::= { xLat 14 }

            latInSessionsAccepted OBJECT-TYPE
                SYNTAX Counter
                ACCESS read-only
                STATUS mandatory
                DESCRIPTION
                    "Number of incoming LAT session connection attempts 
                    accepted.  Corresponds directly to the value labeled 
                    'Solicitations Accepted:' in the SERVER COUNTERS 
                    display."
                ::= { xLat 15 }

            latInSessionsRejected OBJECT-TYPE
                SYNTAX Counter
                ACCESS read-only
                STATUS mandatory
                DESCRIPTION
                    "Number of incoming LAT session connection attempts 
                    rejected.  Corresponds directly to the value labeled 
                    'Solicitations Rejected:' in the SERVER COUNTERS 
                    display."
                ::= { xLat 16 }

            latAddressChange OBJECT-TYPE
                SYNTAX Counter
                ACCESS read-only
                STATUS mandatory
                DESCRIPTION
                    "Number of times a service announcement contained a 
                    node name already in the visible service table but 
                    with a different address.  Corresponds directly to 
                    the value labeled 'Multiple Node Addresses:' in the 
                    SERVER COUNTERS display."
                ::= { xLat 17 }

            latInDuplicates OBJECT-TYPE
                SYNTAX Counter
                ACCESS read-only
                STATUS mandatory
                DESCRIPTION
                    "Number of duplicate LAT messages received.  
                    Corresponds directly to the value labeled 
                    'Duplicates Received:' in the SERVER COUNTERS 
                    display."
                ::= { xLat 18 }

            latOutRetransmits OBJECT-TYPE
                SYNTAX Counter
                ACCESS read-only
                STATUS mandatory
                DESCRIPTION
                    "Number of LAT messages retransmitted due to no 
                    acknowledgement.  Corresponds directly to the value 
                    labeled 'Messages Re-transmitted:' in the SERVER 
                    COUNTERS display."
                ::= { xLat 19 }

            latInBadMessages OBJECT-TYPE
                SYNTAX Counter
                ACCESS read-only
                STATUS mandatory
                DESCRIPTION
                    "Number of LAT messages received with invalid 
                    format.  Corresponds directly to the value labeled 
                    'Illegal Messages Rcv'd:' in the SERVER COUNTERS 
                    display."
                ::= { xLat 20 }

            latInBadSlots OBJECT-TYPE
                SYNTAX Counter
                ACCESS read-only
                STATUS mandatory
                DESCRIPTION
                    "Number of LAT messages received with invalid slot 
                    format.  Corresponds directly to the value labeled 
                    'Illegal Slots Rcv'd:' in the SERVER COUNTERS 
                    display."
                ::= { xLat 21 }

            latInBadMulticasts OBJECT-TYPE
                SYNTAX Counter
                ACCESS read-only
                STATUS mandatory
                DESCRIPTION
                    "Number of multicast LAT messages received with 
                    invalid format.  Corresponds directly to the value 
                    labeled 'Illegal Multicasts Rcv'd:' in the SERVER 
                    COUNTERS display."
                ::= { xLat 22 }

            -- additional individual objects follow Node table


            -- the LAT Port table

            latPortTable OBJECT-TYPE
                SYNTAX SEQUENCE OF LatPortEntry
                ACCESS not-accessible
                STATUS mandatory
                DESCRIPTION
                    "A list of LAT character port entries."
                ::= { xLat 23 }

            latPortEntry OBJECT-TYPE
                SYNTAX LatPortEntry
                ACCESS not-accessible
                STATUS mandatory
                DESCRIPTION
                    "LAT parameter values for a port."
                INDEX { latPortIndex }
                ::= { latPortTable 1 }

            LatPortEntry ::=
                SEQUENCE {
                    latPortIndex
                        INTEGER,
                    latPortAuthorizedGroups
                        OCTET STRING,
                    latPortAutoPrompt
                        INTEGER,
                    latPortCurrentGroups
                        OCTET STRING,
                    latPortRemoteModification
                        INTEGER
                }

            latPortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { latPortEntry 1 }

            latPortAuthorizedGroups OBJECT-TYPE
                SYNTAX OCTET STRING (SIZE (32))
                ACCESS read-write
                STATUS mandatory
                DESCRIPTION
                    "The list of group numbers to which the port is 
                    allowed to set access, where a group number is in 
                    the range 0-255.  The OCTET STRING contains a 
                    bitmap, with one bit for each group.  Corresponding 
                    bit numbers start with 0 as the high-order bit of 
                    the first octet.  Corresponds directly to PORT 
                    AUTHORIZED GROUPS and the value labeled 'Authorized 
                    Groups:' in the PORT CHARACTERISTICS display."
                ::= { latPortEntry 2 }

            latPortAutoPrompt OBJECT-TYPE
                SYNTAX INTEGER { disabled(1), enabled(2) }
                ACCESS read-write
                STATUS mandatory
                DESCRIPTION
                    "Control for automatic stimulation of a host prompt 
                    upon forming a new session.  Corresponds directly to 
                    PORT AUTOPROMPT and the presence of the label 
                    'Autoprompt' following the label 'Enabled 
                    Characteristics:' in the PORT CHARACTERISTICS 
                    display."
                ::= { latPortEntry 3 }

            latPortCurrentGroups OBJECT-TYPE
                SYNTAX OCTET STRING (SIZE (32))
                ACCESS read-write
                STATUS mandatory
                DESCRIPTION
                    "The list of group numbers to which the port 
                    currently has set access, where a group number is in 
                    the range 0-255.  The OCTET STRING contains a 
                    bitmap, with one bit for each group.  Corresponding 
                    bit numbers start with 0 as the high-order bit of 
                    the first octet.  Corresponds directly to PORT 
                    GROUPS and the value labeled 'Groups:' in the PORT 
                    CHARACTERISTICS display."
                ::= { latPortEntry 4 }

            latPortRemoteModification OBJECT-TYPE
                SYNTAX INTEGER { disabled(1), enabled(2) }
                ACCESS read-write
                STATUS mandatory
                DESCRIPTION
                    "Control to allow the remote system to modify 
                    certain physical port characteristics.  Corresponds 
                    directly to PORT REMOTE MODIFICATION and the 
                    presence of the label 'Remote Modification' 
                    following the label 'Enabled Characteristics:' in 
                    the PORT CHARACTERISTICS display."
                ::= { latPortEntry 5 }


            -- The LAT Offered Service table

            latOfferedServiceTable OBJECT-TYPE
                SYNTAX SEQUENCE OF LatOfferedServiceEntry
                ACCESS not-accessible
                STATUS mandatory
                DESCRIPTION
                    "A list of offered service entries."
                ::= { xLat 24 }

            latOfferedServiceEntry OBJECT-TYPE
                SYNTAX LatOfferedServiceEntry
                ACCESS not-accessible
                STATUS mandatory
                DESCRIPTION
                    "Parameter values for an offered service entry."
                INDEX { latOfferedServiceName }
                ::= { latOfferedServiceTable 1 }

            LatOfferedServiceEntry ::=
                SEQUENCE {
                    latOfferedServiceName
                        DisplayString,
                    latOfferedServiceStatus
                        INTEGER,
                    latOfferedServiceAllowConnections
                        INTEGER,
                    latOfferedServiceIdentification
                        DisplayString,
                    latOfferedServicePassword
                        DisplayString,
                    latOfferedServicePortMap
                        OCTET STRING,
                    latOfferedServiceQueuing
                        INTEGER,
                    latOfferedServiceEnvironmentalManager					
                        INTEGER
                }

            latOfferedServiceName OBJECT-TYPE
                SYNTAX DisplayString (SIZE (1..16))
                ACCESS read-only
                STATUS mandatory
                DESCRIPTION
                    "The name of an offered service.  Corresponds 
                    directly to the name in a SERVICE command and the 
                    value labeled 'Service:' in the SERVICE 
                    CHARACTERISTICS display."
                ::= { latOfferedServiceEntry 1 }

            latOfferedServiceStatus OBJECT-TYPE
                SYNTAX INTEGER { invalid(1), valid(2) }
                ACCESS read-write
                STATUS mandatory
                DESCRIPTION
                    "The status of the entry.  Set to 'invalid' to 
                    remove the entry, which corresponds directly to the 
                    CLEAR SERVICE command.  Actual removal of the entry 
                    is implementation specific."
                DEFVAL { valid }
                ::= { latOfferedServiceEntry 2 }

            latOfferedServiceAllowConnections OBJECT-TYPE
                SYNTAX INTEGER { disabled(1), enabled(2) }
                ACCESS read-write
                STATUS mandatory
                DESCRIPTION
                    "Control for allowing incoming connections to the 
                    service.  Corresponds directly to SERVICE 
                    CONNECTIONS and the presence of the label 
                    'Connections' following the label 'Enabled 
                    Characteristics:' in the SERVICE CHARACTERISTICS 
                    display."
                ::= { latOfferedServiceEntry 3 }

            latOfferedServiceIdentification OBJECT-TYPE
                SYNTAX DisplayString (SIZE (0..63))
                ACCESS read-write
                STATUS mandatory
                DESCRIPTION
                    "Text to identify a service.  Corresponds directly 
                    to SERVICE IDENTIFICATION and the value labeled 
                    'Identification:' in the SERVICE CHARACTERISTICS 
                    display."
                ::= { latOfferedServiceEntry 4 }

            latOfferedServicePassword OBJECT-TYPE
                SYNTAX DisplayString (SIZE (0..16))
                ACCESS read-write
                STATUS mandatory
                DESCRIPTION
                    "The password a user must supply to use the service.  
                    Corresponds directly to SERVICE PASSWORD and the 
                    presence of the label 'Password' following the label 
                    'Enabled Characteristics:' in the SERVICE 
                    CHARACTERISTICS display.

                    When setting this value, the management system must 
                    supply eight octets, filling with zeros from the 
                    first octet.  That is, the value '1ab42' would be 
                    expressed as '0.0.0.0.0.1.ab.42'.  Setting the value 
                    to zero disables the password check.

                    When returning this value, the agent always returns 
                    a zero length OCTET STRING."
                ::= { latOfferedServiceEntry 5 }

            latOfferedServicePortMap OBJECT-TYPE
                SYNTAX OCTET STRING
                ACCESS read-write
                STATUS mandatory
                DESCRIPTION
                    "The list of character ports offer the service.  The 
                    OCTET STRING contains a bitmap, with one bit for 
                    each port, and enough octets for all the ports on 
                    the system.  Port numbers are as defined for 
                    charPortIndex in the Character MIB [11].  
                    Corresponding bit numbers start with 1 as the 
                    high-order bit of the first octet.  Corresponds 
                    directly to port-list portion of SERVICE PORTS and 
                    the value labeled 'Ports:' in the SERVICE 
                    CHARACTERISTICS display."
                ::= { latOfferedServiceEntry 6 }

            latOfferedServiceQueuing OBJECT-TYPE
                SYNTAX INTEGER { disabled(1), enabled(2) }
                ACCESS read-write
                STATUS mandatory
                DESCRIPTION
                    "Control for allowing queuing of incoming 
                    connections to the service when the service is busy.  
                    Corresponds directly to SERVICE QUEUE and the 
                    presence of the label 'Queuing' following the label 
                    'Enabled Characteristics:' in the SERVICE 
                    CHARACTERISTICS display."
                ::= { latOfferedServiceEntry 7 }

          latOfferedServiceEnvironmentalManager OBJECT-TYPE
           SYNTAX INTEGER { enabled(1), disabled(2) }
           ACCESS read-write   
           STATUS mandatory  
           DESCRIPTION
                "Control indicating whether Environmental Management services
                 are offered."
           ::= { latOfferedServiceEntry 8 }
           
       

            -- The LAT Visible Service table

            latVisibleServiceTable OBJECT-TYPE
                SYNTAX SEQUENCE OF LatVisibleServiceEntry
                ACCESS not-accessible
                STATUS mandatory
                DESCRIPTION
                    "A list of visible service entries."
                ::= { xLat 25 }

            latVisibleServiceEntry OBJECT-TYPE
                SYNTAX LatVisibleServiceEntry
                ACCESS not-accessible
                STATUS mandatory
                DESCRIPTION
                    "Parameter values for a visible service entry."
                INDEX { latVisibleServiceName }
                ::= { latVisibleServiceTable 1 }

            LatVisibleServiceEntry ::=
                SEQUENCE {
                    latVisibleServiceName
                        DisplayString,
                    latVisibleServiceStatus
                        INTEGER,
                    latVisibleServiceNode
                        DisplayString,
                    latVisibleServiceConnectedSessions
                        Gauge,
                    latVisibleServiceIdentification
                        DisplayString,
                    latVisibleServiceRating
                        Gauge
                }

            latVisibleServiceName OBJECT-TYPE
                SYNTAX DisplayString (SIZE (1..16))
                ACCESS read-only
                STATUS mandatory
                DESCRIPTION
                    "The name of a visible service.  Corresponds 
                    directly to the name in a SERVICE command and the 
                    value labeled 'Service Name' in the SERVICE SUMMARY 
                    display."
                ::= { latVisibleServiceEntry 1 }

            latVisibleServiceStatus OBJECT-TYPE
                SYNTAX INTEGER { available(1), unavailable(2), 
                                 unknown(3), unreachable(4), 
                                 reachable(5), connected(6) }
                ACCESS read-only
                STATUS mandatory
                DESCRIPTION
                    "Status of communication with the service.  
                    Corresponds directly to the value labeled 'Status' 
                    in the SERVICE SUMMARY display."
                ::= { latVisibleServiceEntry 2 }

            latVisibleServiceNode OBJECT-TYPE
                SYNTAX DisplayString (SIZE (1..16))
                ACCESS read-only
                STATUS mandatory
                DESCRIPTION
                    "Name of a node offering the service.  Corresponds 
                    directly to the value labeled Node Name in the 
                    SERVICE STATUS display."
                ::= { latVisibleServiceEntry 3 }

            latVisibleServiceConnectedSessions OBJECT-TYPE
                SYNTAX Gauge
                ACCESS read-only
                STATUS mandatory
                DESCRIPTION
                    "Number of connected sessions to the service.  
                    Corresponds directly to the number with the value 
                    'Connected', labeled 'Status' in the SERVICE SUMMARY 
                    display."
                ::= { latVisibleServiceEntry 4 }

            latVisibleServiceIdentification OBJECT-TYPE
                SYNTAX DisplayString (SIZE (0..63))
                ACCESS read-only
                STATUS mandatory
                DESCRIPTION
                    "Text to identify a service.  The length is subject 
                    to limitation by latIdentificationLengthLimit.    
                    Corresponds directly to the value labeled 
                    'Identification:' in the SERVICE SUMMARY display."
                ::= { latVisibleServiceEntry 5 }

            latVisibleServiceRating OBJECT-TYPE
                SYNTAX Gauge
                ACCESS read-only
                STATUS mandatory
                DESCRIPTION
                    "Relative capacity of the service to accept 
                    additional sessions.  Corresponds directly to value 
                    labeled Rating in the SERVICE STATUS display."
                ::= { latVisibleServiceEntry 6 }


            -- The LAT Node table

            latNodeTable OBJECT-TYPE
                SYNTAX SEQUENCE OF LatNodeEntry
                ACCESS not-accessible
                STATUS mandatory
                DESCRIPTION
                    "A list of node entries."
                ::= { xLat 26 }

            latNodeEntry OBJECT-TYPE
                SYNTAX LatNodeEntry
                ACCESS not-accessible
                STATUS mandatory
                DESCRIPTION
                    "Parameter values for a node entry."
                INDEX { latNodeName }
                ::= { latNodeTable 1 }

            LatNodeEntry ::=
                SEQUENCE {
                    latNodeName
                        DisplayString,
                    latNodeStatus
                        INTEGER,
                    latNodeConnectedSessions
                        Gauge,
                    latNodeAddress
                        OCTET STRING,
                    latNodeDataLinkFrame
                        INTEGER,
                    latNodeIdentification
                        DisplayString,
                    latNodeGroups
                        OCTET STRING,
                    latNodeServiceNumber
                        Gauge,
                    latNodeZero
                        INTEGER,
                    latNodeZeroTime
                        TimeTicks,
                    latNodeInMessages
                        Counter,
                    latNodeOutMessages
                        Counter,
                    latNodeInSlots
                        Counter,
                    latNodeOutSlots
                        Counter,
                    latNodeInBytes
                        Counter,
                    latNodeOutBytes
                        Counter,
                    latNodeAddressChange
                        Counter,
                    latNodeInDuplicates
                        Counter,
                    latNodeOutRetransmits
                        Counter,
                    latNodeInBadMessages
                        Counter,
                    latNodeInBadSlots
                        Counter,
                    latNodeInSessionsAccepted
                        Counter,
                    latNodeInSessionsRejected
                        Counter
                }

            latNodeName OBJECT-TYPE
                SYNTAX DisplayString (SIZE (1..16))
                ACCESS read-only
                STATUS mandatory
                DESCRIPTION
                    "The name of a node.  Corresponds directly to the 
                    value labeled 'Node:' in the NODE STATUS display."
                ::= { latNodeEntry 1 }

            latNodeStatus OBJECT-TYPE
                SYNTAX INTEGER { available(1), unavailable(2), 
                                 unknown(3), unreachable(4), 
                                 reachable(5), connected(6) }
                ACCESS read-only
                STATUS mandatory
                DESCRIPTION
                    "Status of communication with the node.  Corresponds 
                    directly to the value labeled 'Status' in the NODE 
                    STATUS display."
                ::= { latNodeEntry 2 }

            latNodeConnectedSessions OBJECT-TYPE
                SYNTAX Gauge
                ACCESS read-only
                STATUS mandatory
                DESCRIPTION
                    "Number of connected sessions to the node.  
                    Corresponds directly to the number with the value 
                    'Connected', labeled 'Status' in the NODE STATUS 
                    display."
                ::= { latNodeEntry 3 }

            latNodeAddress OBJECT-TYPE
                SYNTAX OCTET STRING (SIZE (6))
                ACCESS read-only
                STATUS mandatory
                DESCRIPTION
                    "Ethernet address of the node.  Corresponds directly 
                    to the value labeled 'Address:' in the NODE STATUS 
                    display."
                ::= { latNodeEntry 4 }

            latNodeDataLinkFrame OBJECT-TYPE
                SYNTAX INTEGER
                ACCESS read-only
                STATUS mandatory
                DESCRIPTION
                    "Maximum Ethernet frame used by the node.  
                    Corresponds directly to the value labeled 'Data Link 
                    Frame Size:' in the NODE STATUS display."
                ::= { latNodeEntry 5 }

            latNodeIdentification OBJECT-TYPE
                SYNTAX DisplayString (SIZE (0..63))
                ACCESS read-only
                STATUS mandatory
                DESCRIPTION
                    "Text that identifies the node.  The size is subject 
                    to limitation by latIdentificationLengtLimit.  
                    Corresponds directly to the value labeled 
                    'Identification' in the NODE STATUS display."
                ::= { latNodeEntry 6 }

            latNodeGroups OBJECT-TYPE
                SYNTAX OCTET STRING (SIZE (32))
                ACCESS read-only
                STATUS mandatory
                DESCRIPTION
                    "The list of group numbers to which the node 
                    belongs, where a group number is in the range 0-255.  
                    The OCTET STRING contains a bitmap, with one bit for 
                    each group.  Corresponding bit numbers start with 0 
                    as the high-order bit of the first octet.  
                    Corresponds directly to the value labeled 'Node 
                    Groups:' in the NODE STATUS display."
                ::= { latNodeEntry 7 }

            latNodeServiceNumber OBJECT-TYPE
                SYNTAX Gauge
                ACCESS read-only
                STATUS mandatory
                DESCRIPTION
                    "Number of entries for the node in the node service 
                    table.  Corresponds indirectly to the list of 
                    services in the NODE STATUS display."
                ::= { latNodeEntry 8 }

            latNodeZero OBJECT-TYPE
                SYNTAX INTEGER { ready(1), execute(2) }
                ACCESS read-write
                STATUS mandatory
                DESCRIPTION
                    "Control to zero counters kept for the node.  In 
                    response to a get-request or get-next-request, the 
                    agent always returns 'ready' for this value.  
                    Setting the value to 'ready' has no effect.  Setting 
                    it to 'execute' causes all the system's counters to 
                    be zeroed.  Corresponds to the ZERO NODE command."
                ::= { latNodeEntry 9 }

            latNodeZeroTime OBJECT-TYPE
                SYNTAX TimeTicks
                ACCESS read-only
                STATUS mandatory
                DESCRIPTION
                    "The number of hundredths of a second since the most 
                    recent zeroing of the counters kept for the node, 
                    such as through execution of sysZeroAll or 
                    latNodeZero.  Corresponds directly to the value 
                    labeled 'Seconds Since Zeroed:' in the NODE COUNTERS 
                    display."
                ::= { latNodeEntry 10 }

            latNodeInMessages OBJECT-TYPE
                SYNTAX Counter
                ACCESS read-only
                STATUS mandatory
                DESCRIPTION
                    "The number of LAT messages received from the node.  
                    Corresponds directly to the value labeled 'Messages 
                    Received:' in the NODE COUNTERS display."
                ::= { latNodeEntry 11 }

            latNodeOutMessages OBJECT-TYPE
                SYNTAX Counter
                ACCESS read-only
                STATUS mandatory
                DESCRIPTION
                    "The number of LAT messages sent to the node.  
                    Corresponds directly to the value labeled 'Messages 
                    Transmitted:' in the NODE COUNTERS display."
                ::= { latNodeEntry 12 }

            latNodeInSlots OBJECT-TYPE
                SYNTAX Counter
                ACCESS read-only
                STATUS mandatory
                DESCRIPTION
                    "The number of LAT slots received from the node.  
                    Corresponds directly to the value labeled 'Slots 
                    Received:' in the NODE COUNTERS display."
                ::= { latNodeEntry 13 }

            latNodeOutSlots OBJECT-TYPE
                SYNTAX Counter
                ACCESS read-only
                STATUS mandatory
                DESCRIPTION
                    "The number of LAT slots sent to the node.  
                    Corresponds directly to the value labeled 'Slots 
                    Transmitted:' in the NODE COUNTERS display."
                ::= { latNodeEntry 14 }

            latNodeInBytes OBJECT-TYPE
                SYNTAX Counter
                ACCESS read-only
                STATUS mandatory
                DESCRIPTION
                    "The total number of bytes received from the node, 
                    including Ethernet overhead.  Corresponds directly 
                    to the value labeled 'Bytes Received:' in the NODE 
                    COUNTERS display."
                ::= { latNodeEntry 15 }

            latNodeOutBytes OBJECT-TYPE
                SYNTAX Counter
                ACCESS read-only
                STATUS mandatory
                DESCRIPTION
                    "The total number of bytes sent to the node, 
                    including Ethernet overhead.  Corresponds directly 
                    to the value labeled 'Bytes Transmitted:' in the 
                    NODE COUNTERS display."
                ::= { latNodeEntry 16 }

            latNodeAddressChange OBJECT-TYPE
                SYNTAX Counter
                ACCESS read-only
                STATUS mandatory
                DESCRIPTION
                    "The number of times a LAT message multicast by the 
                    node had a different Ethernet address from the 
                    previous time.  Corresponds directly to the value 
                    labeled 'Multiple Node Addresses:' in the NODE 
                    COUNTERS display."
                ::= { latNodeEntry 17 }

            latNodeInDuplicates OBJECT-TYPE
                SYNTAX Counter
                ACCESS read-only
                STATUS mandatory
                DESCRIPTION
                    "The number of duplicate LAT message received from 
                    the node.  Corresponds directly to the value labeled 
                    'Duplicates Received:' in the NODE COUNTERS 
                    display."
                ::= { latNodeEntry 18 }

            latNodeOutRetransmits OBJECT-TYPE
                SYNTAX Counter
                ACCESS read-only
                STATUS mandatory
                DESCRIPTION
                    "The number of LAT message retransmitted to the node 
                    due to lack of acknowledgement.  Corresponds 
                    directly to the value labeled 'Messages 
                    Re-transmitted:' in the NODE COUNTERS display."
                ::= { latNodeEntry 19 }

            latNodeInBadMessages OBJECT-TYPE
                SYNTAX Counter
                ACCESS read-only
                STATUS mandatory
                DESCRIPTION
                    "The number of LAT message received from the node 
                    with invalid format.  Corresponds directly to the 
                    value labeled 'Illegal Messages Received:' in the 
                    NODE COUNTERS display."
                ::= { latNodeEntry 20 }

            latNodeInBadSlots OBJECT-TYPE
                SYNTAX Counter
                ACCESS read-only
                STATUS mandatory
                DESCRIPTION
                    "The number of LAT slots received from the node with 
                    invalid format.  Corresponds directly to the value 
                    labeled 'Illegal Slots Received:' in the NODE 
                    COUNTERS display."
                ::= { latNodeEntry 21 }

            latNodeInSessionsAccepted OBJECT-TYPE
                SYNTAX Counter
                ACCESS read-only
                STATUS mandatory
                DESCRIPTION
                    "The number of LAT session connection attempts 
                    received from the node and accepted.  Corresponds 
                    directly to the value labeled 'Solicitations 
                    Accepted:' in the NODE COUNTERS display."
                ::= { latNodeEntry 22 }

            latNodeInSessionsRejected OBJECT-TYPE
                SYNTAX Counter
                ACCESS read-only
                STATUS mandatory
                DESCRIPTION
                    "The number of LAT session connection attempts 
                    received from the node and rejected.  Corresponds 
                    directly to the value labeled 'Solicitations 
                    Rejected:' in the NODE COUNTERS display."
                ::= { latNodeEntry 23 }


            -- Additional individual objects

            latSolicits OBJECT-TYPE
                SYNTAX INTEGER { disabled(1), enabled(2) }
                ACCESS read-write
                STATUS mandatory
                DESCRIPTION
                    "Control for multicast solicitation of LAT services. 
                    Corresponds directly to SERVER LAT SOLICITAIONS and 
                    the presence of the label 'LAT SOLICITATIONS' 
                    following the label 'Enabled Characteristics:' in 
                    the SERVER CHARACTERISTICS display."
                ::= { xLat 27 }

            latImmediateAck OBJECT-TYPE
                SYNTAX INTEGER { disabled(1), enabled(2) }
                ACCESS read-write
                STATUS mandatory
                DESCRIPTION 
                    "Control for LAT to provide an immediate ACK,
                     and not to wait for the timer to expire.
                    Corresponds directly to SERVER LAT IMMEDIATE ACK
                    and the presence of the label 'LAT Immediate Ack
                    following the label 'Enabled Characteristics:' in
                    the SERVER CHARACTERISTICS display."
                ::= { xLat 28 } 

--
-- FILE: /users/sse/mibs/src/inReach/ir-param-client-mib.mib
--

-- $Id: ir-param-client-mib.mib,v 1.1 2002/06/27 15:48:48 sse Exp $



            xParamClient    OBJECT IDENTIFIER ::= { mrvInReachProductDivision 7 }

            --  This is the MIB module for clients of MRV In-Reach parameter
            --  service.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the Parameter Client group

            -- Implementation of this group is mandatory for all MRV In-Reach
            -- systems that use the MRV In-Reach parameter service

            paramClientLoaderName OBJECT-TYPE
                SYNTAX DisplayString
                ACCESS read-only
                STATUS mandatory
                DESCRIPTION
                    "The name of the system that most recently provided 
                    this system's stored parameters.  Corresponds 
                    directly to the name value labeled 'Loaded From:' in 
                    the PARAMETER SERVER display."
                ::= { xParamClient 1 }

            paramClientLoaderAddressType OBJECT-TYPE
                SYNTAX AddressType
                ACCESS read-only
                STATUS mandatory
                DESCRIPTION
                    "The type of network address contained in 
                    paramClientLoaderAddress.  'unknown' means no 
                    address has been defined.  'other' means no other 
                    type value applies.  'local' means there is no 
                    address and parameters were loaded from local 
                    storage.  'ip' is an Internet IP address.  
                    'ethernet' is an 802.3 MAC address.  Corresponds 
                    indirectly to the address value labeled 'Loaded 
                    From:' in the PARAMETER SERVER display."
                ::= { xParamClient 2 }

            paramClientLoaderAddress OBJECT-TYPE
                SYNTAX OCTET STRING
                ACCESS read-only
                STATUS mandatory
                DESCRIPTION
                    "The network address of the system that most 
                    recently provided this system's stored parameters.  
                    Corresponds directly to the address value labeled 
                    'Loaded From:' in the PARAMETER SERVER display."
                ::= { xParamClient 3 }

            paramClientParameterVersion OBJECT-TYPE
                SYNTAX INTEGER
                ACCESS read-write
                STATUS mandatory
                DESCRIPTION
                    "The version number of the parameters as stored in 
                    this system's local memory.  Corresponds directly to 
                    SERVER PARAMETER VERSION and the value labeled 'Last 
                    Update Version:' in the PARAMETER SERVER display."
                ::= { xParamClient 4 }

            paramClientUpdateTime OBJECT-TYPE
                SYNTAX DateTime
                ACCESS read-only
                STATUS mandatory
                DESCRIPTION
                    "This system's local date and time when it last 
                    attempted to store parameters with a parameter 
                    server.  Corresponds directly to the values labeled 
                    'Last Update Date:' and 'Last Update Time:' in the 
                    PARAMETER SERVER display."
                ::= { xParamClient 5 }

            paramClientServerCheck OBJECT-TYPE
                SYNTAX INTEGER { disabled(1), enabled(2) }
                ACCESS read-write
                STATUS mandatory
                DESCRIPTION
                    "Control over whether or not this system is allowed 
                    to check for additional parameter servers.  
                    'enabled' allows checking.  Corresponds directly to 
                    PARAMETER SERVER CHECK and the presence of PARAMETER 
                    POLLING under the label 'Enabled Characteristics' in 
                    the SERVER CHARACTERISTICS display."
                ::= { xParamClient 6 }

            paramClientCheckInterval OBJECT-TYPE
                SYNTAX INTEGER (1..120)
                ACCESS read-write
                STATUS mandatory
                DESCRIPTION
                    "The number of minutes between checks for additional 
                    parameter servers.  Corresponds directly to 
                    PARAMETER SERVER CHECK TIMER and the value labeled 
                    'Check Timer:' in the PARAMETER SERVER display."
                ::= { xParamClient 7 }

            paramClientCheckNow OBJECT-TYPE
                SYNTAX INTEGER { ready(1), execute(2) }
                ACCESS read-write
                STATUS mandatory
                DESCRIPTION
                    "Control to cause this system to immediately check 
                    for additional parameter servers.  The agent always 
                    returns 'ready' for this value.  Setting the value 
                    to 'ready' has no effect.  Setting it to 'execute' 
                    causes a check to be started.  Corresponds to the 
                    CHECK PARAMETER SERVER command."
                ::= { xParamClient 8 }

            paramClientServerLimit OBJECT-TYPE
                SYNTAX INTEGER (1..8)
                ACCESS read-write
                STATUS mandatory
                DESCRIPTION
                    "The maximum number of parameter servers this system 
                    is allowed to remember at the same time.  
                    Corresponds directly to PARAMETER SERVER LIMIT and 
                    the value labeled 'Parameter Server Limit:' in the 
                    PARAMETER SERVER display."
                ::= { xParamClient 9 }

            paramClientRetransmitInterval OBJECT-TYPE
                SYNTAX INTEGER (1..30)
                ACCESS read-write
                STATUS mandatory
                DESCRIPTION
                    "The number of minutes between this system's 
                    attempts to store new parameters with a server that 
                    has not acknowledged previous attempts.  Corresponds 
                    directly to PARAMETER SERVER RETRANSMIT TIMER and 
                    the value labeled 'Retransmit Timer: in the 
                    PARAMETER SERVER display."
                ::= { xParamClient 10 }

            paramClientRetransmitLimit OBJECT-TYPE
                SYNTAX INTEGER (1..100)
                ACCESS read-write
                STATUS mandatory
                DESCRIPTION
                    "The maximum number of attempts by this system to 
                    store new parameters with a server that has not 
                    acknowledged previous attempts.  Corresponds 
                    directly to PARAMETER SERVER RETRANSMIT LIMIT and 
                    the value labeled 'Retransmit Limit:' in the 
                    PARAMETER SERVER display."
                ::= { xParamClient 11 }

            paramClientState OBJECT-TYPE
                SYNTAX INTEGER { other(1), idle(2), internal1(3),
                                 internal2(4), internal3(5),
                                 internal4(6), internal5(7),
                                 internal6(8), internal7(9),
                                 internal8(10), hold(11),  retry(12)}
                ACCESS read-only
                STATUS mandatory
                DESCRIPTION
                    "This system's state with regard to update attempts.  
                    The value meanings are:

                    other       none of the following
                    idle        no update in progress
                    internal    internal state of no meaning to manager
                    hold        holding to keep from updating too often
                    retry       waiting to retry after failure

                    Corresponds directly to the value labeled 'Storage 
                    State:' in the PARAMETER SERVER display."
                ::= { xParamClient 12 }

            paramClientProtocolErrors OBJECT-TYPE
                SYNTAX Counter
                ACCESS read-only
                STATUS mandatory
                DESCRIPTION
                    "The number of invalid parameter service protocol 
                    messages received by this system.  Corresponds 
                    directly to the value labeled 'Bad Parameter 
                    Messages:' in the PARAMETER SERVER display."
                ::= { xParamClient 13 }

            paramClientServerRejects OBJECT-TYPE
                SYNTAX Counter
                ACCESS read-only
                STATUS mandatory
                DESCRIPTION
                    "The number of parameter servers this system 
                    rejected due to exceeding paramClientServerLimit.  
                    Corresponds directly to the value labeled 'Rejected 
                    Servers:' in the PARAMETER SERVER display."
                ::= { xParamClient 14 }

            paramClientServerNumber OBJECT-TYPE
                SYNTAX INTEGER
                ACCESS read-only
                STATUS mandatory
                DESCRIPTION
                    "The number of parameter servers known to this 
                    system, indicating the number of entries in 
                    serverTable.  Corresponds directly to the value 
                    labeled 'Parameter Servers:' in the PARAMETER SERVER 
                    display."
                ::= { xParamClient 15 }

            -- Further individual parameters follow the Parameter
            -- Server table


            -- the Parameter Server table

            paramServerTable OBJECT-TYPE
                SYNTAX SEQUENCE OF ParamServerEntry
                ACCESS not-accessible
                STATUS mandatory
                DESCRIPTION
                    "A list of parameter server entries.  The number of 
                    entries is given by the value of 
                    paramClientServerNumber."
                ::= { xParamClient 16 }

            paramServerEntry OBJECT-TYPE
                SYNTAX ParamServerEntry
                ACCESS not-accessible
                STATUS mandatory
                DESCRIPTION
                    "Status and parameter values for a parameter 
                    server."
                INDEX { paramServerName }
                ::= { paramServerTable 1 }

            ParamServerEntry ::=
                SEQUENCE {
                    paramServerName
                        DisplayString,
                    paramServerEntryStatus
                        INTEGER,
                    paramServerAddressType
                        AddressType,
                    paramServerAddress
                        OCTET STRING,
                    paramServerStoredVersion
                        INTEGER,
                    paramServerStoredTime
                        DateTime,
                    paramServerStoredStatus
                        INTEGER,
                    paramServerStoredFailure
                        INTEGER
                }

            paramServerName OBJECT-TYPE
                SYNTAX DisplayString (SIZE (16))
                ACCESS read-only
                STATUS mandatory
                DESCRIPTION
                    "The server's name, unique within this system.  
                    Always 16 characters, null padded on the end.  
                    Corresponds directly to the name used to create the 
                    entry and the value labeled 'Name' in the PARAMETER 
                    SERVER display."
                ::= { paramServerEntry 1 }

            paramServerEntryStatus OBJECT-TYPE
                SYNTAX INTEGER { invalid(1), valid(2) }
                ACCESS read-write
                STATUS mandatory
                DESCRIPTION
                    "The status of the entry.  Set to 'invalid' to 
                    remove the entry, which corresponds directly to the 
                    CLEAR/PURGE PARAMETER SERVER command.  Actual 
                    removal of the entry is implementation specific."
                DEFVAL { valid }
                ::= { paramServerEntry 2 }

            paramServerAddressType OBJECT-TYPE
                SYNTAX AddressType
                ACCESS read-write
                STATUS mandatory
                DESCRIPTION
                    "The type of network address contained in 
                    paramServerAddress.  'unknown' means no address has 
                    been defined.  'other' means no other type value 
                    applies.  'local' means there is no address and 
                    parameters were loaded from local storage.  'ip' is 
                    an Internet IP address.  'ethernet' is an 802.3 MAC 
                    address.  Corresponds indirectly to the value 
                    labeled 'Address' in the PARAMETER SERVER display."
                DEFVAL { unknown }
                ::= { paramServerEntry 3 }

            paramServerAddress OBJECT-TYPE
                SYNTAX OCTET STRING
                ACCESS read-write
                STATUS mandatory
                DESCRIPTION
                    "The server's network address.  Corresponds directly 
                    to the value labeled 'Address' in the PARAMETER 
                    SERVER display."
                DEFVAL { "" }  -- zero length
                ::= { paramServerEntry 4 }

            paramServerStoredVersion OBJECT-TYPE
                SYNTAX INTEGER
                ACCESS read-only
                STATUS mandatory
                DESCRIPTION
                    "Parameter version number currently stored at the 
                    server.  Corresponds directly to the value labeled 
                    'Version' in the PARAMETER SERVER display."
                DEFVAL { 0 }
                ::= { paramServerEntry 5 }

            paramServerStoredTime OBJECT-TYPE
                SYNTAX DateTime
                ACCESS read-only
                STATUS mandatory
                DESCRIPTION
                    "The server's date and time when it stored the 
                    parameters of version paramServerStoredVersion.  
                    Corresponds directly to the value labeled 'Date' in 
                    the PARAMETER SERVER display."
                DEFVAL { '00'h }
                ::= { paramServerEntry 6 }

            paramServerStoredStatus OBJECT-TYPE
                SYNTAX INTEGER { unknown(1), current(2), ahead(3),
                                 behind(4), failing(5), failed(6),
                                 query(7), noMemCard(8) }
                ACCESS read-only
                STATUS mandatory
                DESCRIPTION
                    "Status of this system's parameters with respect to 
                    the server.  Corresponds directly to the value 
                    labeled 'Status' in the PARAMETER SERVER display.  
                    The value meanings are:

                    ahead     server version newer than system's
                    behind    server version older than system's
                    current   up to date
                    failed    system no longer attempting update
                    failing   system trying to update but failing
                    query     attempting to determine version
                    noMemCard no memory card in card drive
                    unknown   version not known
                    "
                DEFVAL { unknown }
                ::= { paramServerEntry 7 }

            paramServerStoredFailure OBJECT-TYPE
                SYNTAX INTEGER { other(1), none(2), protocolOut(3),
                                 open(4), read(5), write(6), 
            resource(7),
                                 protocolIn(8), response(9),
                                 close(10), delete(11), rename(12),
                                 fileData(13) }
                ACCESS read-only
                STATUS mandatory
                DESCRIPTION
                    "When paramServerStoredStatus is 'failed' or 
                    'failing', the reason for the most recent failure.  
                    Corresponds directly to the value labeled 'Reason' 
                    in the PARAMETER SERVER display.  The value meanings 
                    are:

                    other        none of the following
                    none         no failure
                    protocolOut  invalid protocol message to server
                    open         file open error at server
                    read         file read error at server
                    write        file write error at server
                    resource     resource lack at server (e.g. disk)
                    protocolIn   invalid protocol message from server
                    response     no response from server
                    close        file close error at server
                    delete       file delete error at server
                    rename       file rename error at server
                    fileData     bad parameter data stored at server
                    "
                DEFVAL { none }
                ::= { paramServerEntry 8 }


            -- Additional individual parameters

            paramClientPath OBJECT-TYPE
                SYNTAX DisplayString (SIZE (0..40))
                ACCESS read-write
                STATUS mandatory
                DESCRIPTION
                    "The directory path to the parameter file on all 
                    servers.  Corresponds directly to PARAMETER SERVER 
                    PATH and the value labeled 'Path:' in the PARAMETER 
                    SERVER display."
                ::= { xParamClient 17 }

            paramClientChassisStorageState OBJECT-TYPE
                SYNTAX INTEGER { notApplicable(1), unknown(2),
                                 current(3), verifying(4),
                                 busBusy(5), retrying(6),
                                 failing(7), behind(8) }
                ACCESS read-only
                STATUS mandatory
                DESCRIPTION
                    "The status of the current attempt to update 
                    parameters in local chassis storage.  Corresponds 
                    directly to the value labeled 'Chassis 
                    Configuration:'."
                ::= { xParamClient 18 }

            paramClientTftpBroadcast OBJECT-TYPE
                SYNTAX INTEGER { disabled(1), enabled(2) }
                ACCESS read-write
                STATUS mandatory
                DESCRIPTION
                    "Control over whether or not this system is allowed 
                    to send out a TFTP read broadcast after sending
                    a BOOTP broadcast during the Parameter Check Function.
                    'enabled' allows TFTP broadcast.  Corresponds directly to 
                    the presence of PARAMETER TFTP BROADCAST
                    under the label 'Enabled Characteristics' in 
                    the SERVER CHARACTERISTICS display."
                DEFVAL { enabled }
                ::= { xParamClient 20 }

            paramClientWriteNow OBJECT-TYPE
                SYNTAX INTEGER { ready(1), execute(2) }
                ACCESS read-write
                STATUS mandatory
                DESCRIPTION
                   "Control to start saving parameters immediately in
                    response to an execute. Corresponds directly to the WRITE
                    PARAMETERS command. In response to a get-request or
                    get-next-request, the agent always returns 'ready' for
                    this value."
                ::= { xParamClient 21 }   



--
-- FILE: /users/sse/mibs/src/inReach/ir-ppp-mib.mib
--

-- $Id: ir-ppp-mib.mib,v 1.1 2002/06/27 15:38:44 sse Exp $



       xPpp            OBJECT IDENTIFIER ::= { mrvInReachProductDivision 22 }

       -- The individual Groups within the PPP MIB

       xPppBasic       OBJECT IDENTIFIER ::= { xPpp 1 }
       xPppLcp         OBJECT IDENTIFIER ::= { xPpp 2 }
       xPppIpcp        OBJECT IDENTIFIER ::= { xPpp 3 }
       xPppAuth        OBJECT IDENTIFIER ::= { xPpp 4 }
       xPppIpxcp       OBJECT IDENTIFIER ::= { xPpp 5 }

 


            -- This is a MIB module for all MRV In-Reach systems that
            -- implement PPP.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


       -- the PPP basic group

       -- Implementation of this group is mandatory for all MRV In-Reach
       -- systems that implement PPP

       xPppConfigTable OBJECT-TYPE
           SYNTAX SEQUENCE OF XPppConfigEntry
           ACCESS not-accessible
           STATUS mandatory
           DESCRIPTION
               "A table containing PPP specific variables for this 
               PPP implementation."
           ::= { xPppBasic 1 }

       xPppConfigEntry OBJECT-TYPE
           SYNTAX XPppConfigEntry
           ACCESS not-accessible
           STATUS mandatory
           DESCRIPTION
               "Management information about a particular PPP."
           INDEX { ifIndex }
           ::= { xPppConfigTable 1 }

       XPppConfigEntry ::=
           SEQUENCE {
               xPppConfigOpen
                   INTEGER,
               xPppConfigActive
                   INTEGER,
               xPppConfigDefaults
                   INTEGER,
               xPppConfigRestartTimer
                   INTEGER,
               xPppConfigConfLimit
                   INTEGER,
               xPppConfigFailLimit
                   INTEGER,
               xPppConfigPacketLogging
                   INTEGER,
               xPppConfigKATimer
                   INTEGER,
               xPppConfigKATimeout
                   INTEGER
           }

       xPppConfigOpen OBJECT-TYPE
           SYNTAX INTEGER { disabled(1), enabled(2)}
           ACCESS read-write
           STATUS mandatory
           DESCRIPTION
               "Determines if PPP is configured on this port."
           ::= { xPppConfigEntry 1 }

       xPppConfigActive OBJECT-TYPE
           SYNTAX INTEGER { active(1), passive(2)}
           ACCESS read-write
           STATUS mandatory
           DESCRIPTION
               "Determines if LCP will actively open or wait 
               passively."
           ::= { xPppConfigEntry 2 }

       xPppConfigDefaults OBJECT-TYPE
           SYNTAX INTEGER { ready(1), execute(2)}
           ACCESS read-write
           STATUS mandatory
           DESCRIPTION
               "Revert to factory default PPP parameters.  In 
               response to a get-request or get-next-request, the 
               agent always returns 'ready' for this value.  
               Setting the value to 'ready' has no effect.  Setting 
               it to 'execute' sets PPP parameters to factory 
               defaults."
           ::= { xPppConfigEntry 3 }

       xPppConfigRestartTimer OBJECT-TYPE
           SYNTAX INTEGER (1..10)
           ACCESS read-write
           STATUS mandatory
           DESCRIPTION
               "The number of seconds waited before retransmitting 
               during option negotiation."
           ::= { xPppConfigEntry 4 }

       xPppConfigConfLimit OBJECT-TYPE
           SYNTAX INTEGER (2..10)
           ACCESS read-write
           STATUS mandatory
           DESCRIPTION
               "Maximum number of times a configuration request 
               will be sent to the peer without receiving a 
               response."
           ::= { xPppConfigEntry 5 }

       xPppConfigFailLimit OBJECT-TYPE
           SYNTAX INTEGER (2..10)
           ACCESS read-write
           STATUS mandatory
           DESCRIPTION
               "Maximum number of times a peer's proposed option 
               will be NAKed before REJECTing the option."
           ::= { xPppConfigEntry 6 }

       xPppConfigPacketLogging OBJECT-TYPE
           SYNTAX INTEGER { none(1), raw(2), interpreted(3) }
           ACCESS read-write
           STATUS mandatory
           DESCRIPTION
               "Determines the level of packet logging to accounting on this port."
           ::= { xPppConfigEntry 7 }

       xPppConfigKATimer OBJECT-TYPE
           SYNTAX INTEGER ( 0..255 )
           ACCESS read-write
           STATUS mandatory
           DESCRIPTION
               "Determines the number of seconds between transmission of LCP Echo
		Keepalive packets."
           ::= { xPppConfigEntry 8 }

       xPppConfigKATimeout OBJECT-TYPE
           SYNTAX INTEGER
           ACCESS read-write
           STATUS mandatory
           DESCRIPTION
               "Determines the number of seconds to wait to hear LCP Echo Replies
		to our Echo Request Keepalive packets before giving up and shutting
		down the link."
           ::= { xPppConfigEntry 9 }

--     xPppConfigEntries 10 to 19 reserved for Internetworking products.

       xPppStatusTable OBJECT-TYPE
           SYNTAX SEQUENCE OF XPppStatusEntry
           ACCESS not-accessible
           STATUS mandatory
           DESCRIPTION
               "A table containing basic PPP status info."
           ::= { xPppBasic 2 }

       xPppStatusEntry OBJECT-TYPE
           SYNTAX XPppStatusEntry
           ACCESS not-accessible
           STATUS mandatory
           DESCRIPTION
               "Status information about a particular PPP."
           INDEX { ifIndex }
           ::= { xPppStatusTable 1 }

       XPppStatusEntry ::=
           SEQUENCE {
               xPppStatusState
                   INTEGER,
               xPppLinkOpen
                   INTEGER,
               xPppHdlcRxTotalPkts
                   Counter,
               xPppHdlcTxTotalPkts
                   Counter,
               xPppHdlcRxFrameErrs
                   Counter,
               xPppHdlcRxNoBuffer
                   Counter,
               xPppHdlcTxNoBuffer
                   Counter,
               xPppHdlcRxBadFcs
                   Counter,
               xPppHdlcVJDiscards
                   Counter
           }

       xPppStatusState OBJECT-TYPE
           SYNTAX INTEGER { disabled(1), enabled(2) }
           ACCESS read-only
           STATUS mandatory
           DESCRIPTION
               "Displays whether PPP is enabled or disabled on this 
               port."
           ::= { xPppStatusEntry 1 }

       xPppLinkOpen OBJECT-TYPE
           SYNTAX INTEGER { notOpen(1), open(2)}
           ACCESS read-only
           STATUS mandatory
           DESCRIPTION
               "Displays open status of the link."
           ::= { xPppStatusEntry 2 }

       xPppHdlcRxTotalPkts OBJECT-TYPE
           SYNTAX Counter
           ACCESS read-only
           STATUS mandatory
           DESCRIPTION
               "Total of all packets received on PPP link."
           ::= { xPppStatusEntry 3 }

       xPppHdlcTxTotalPkts OBJECT-TYPE
           SYNTAX Counter
           ACCESS read-only
           STATUS mandatory
           DESCRIPTION
               "Total of all packets transmitted on PPP link."
           ::= { xPppStatusEntry 4 }

       xPppHdlcRxFrameErrs OBJECT-TYPE
           SYNTAX Counter
           ACCESS read-only
           STATUS mandatory
           DESCRIPTION
               "Number of framing errors received on PPP link."
           ::= { xPppStatusEntry 5 }

       xPppHdlcRxNoBuffer OBJECT-TYPE
           SYNTAX Counter
           ACCESS read-only
           STATUS mandatory
           DESCRIPTION
               "Number of times a buffer was not available to  
               receive packet into."
           ::= { xPppStatusEntry 6 }

       xPppHdlcTxNoBuffer OBJECT-TYPE
           SYNTAX Counter
           ACCESS read-only
           STATUS mandatory
           DESCRIPTION
               "Number of times a buffer was not available to 
               transmit a packet from."
           ::= { xPppStatusEntry 7 }

       xPppHdlcRxBadFcs OBJECT-TYPE
           SYNTAX Counter
           ACCESS read-only
           STATUS mandatory
           DESCRIPTION
               "Number of packets received with a bad checksum."
           ::= { xPppStatusEntry 8 }

       xPppHdlcVJDiscards OBJECT-TYPE
           SYNTAX Counter
           ACCESS read-only
           STATUS mandatory
           DESCRIPTION
               "Number of packets received that failed VJ 
               decompression."
           ::= { xPppStatusEntry 9 }

       xPppLcpConfigTable OBJECT-TYPE
           SYNTAX SEQUENCE OF XPppLcpConfigEntry
           ACCESS not-accessible
           STATUS mandatory
           DESCRIPTION
               "A table containing PPP LCP specific variables for 
               this PPP implementation."
           ::= { xPppLcp 1 }

       xPppLcpConfigEntry OBJECT-TYPE
           SYNTAX XPppLcpConfigEntry
           ACCESS not-accessible
            STATUS mandatory
           DESCRIPTION
               "Management information about a particular PPP LCP 
               session."
           INDEX { ifIndex }
           ::= { xPppLcpConfigTable 1 }

       XPppLcpConfigEntry ::=
           SEQUENCE {
               xPppLcpConfigAuth
                   INTEGER,
               xPppLcpConfigChapAuth
                   INTEGER
           }

       xPppLcpConfigAuth OBJECT-TYPE
           SYNTAX INTEGER { none(1), pap(2)}
           ACCESS read-write
           STATUS mandatory
           DESCRIPTION
               "Authentication protocol used for authenticating 
               peers."
           ::= { xPppLcpConfigEntry 1 }

       xPppLcpConfigChapAuth OBJECT-TYPE
           SYNTAX INTEGER { none(1), chap(2)}
           ACCESS read-write
           STATUS mandatory
           DESCRIPTION
               "Authentication CHAP protocol used for authenticating 
               peers."
           ::= { xPppLcpConfigEntry 2 }

       xPppLcpStatusTable OBJECT-TYPE
           SYNTAX SEQUENCE OF XPppLcpStatusEntry
           ACCESS not-accessible
           STATUS mandatory
           DESCRIPTION
               "A table containing PPP LCP status info."
           ::= { xPppLcp 2 }

       xPppLcpStatusEntry OBJECT-TYPE
           SYNTAX XPppLcpStatusEntry
           ACCESS not-accessible
           STATUS mandatory
           DESCRIPTION
               "Status information about a particular PPP LCP 
               session."
           INDEX { ifIndex }
           ::= { xPppLcpStatusTable 1 }

       XPppLcpStatusEntry ::=
           SEQUENCE {
               xPppLcpStatusState
                   INTEGER,
               xPppLcpStatusRxAuth
                   INTEGER,
               xPppLcpStatusTxAuth
                   INTEGER,
               xPppLcpStatusRxConReq
                   Counter,
               xPppLcpStatusTxConReq
                   Counter,
               xPppLcpStatusRxConNak
                   Counter,
               xPppLcpStatusTxConNak
                   Counter,
               xPppLcpStatusRxConAck
                   Counter,
               xPppLcpStatusTxConAck
                   Counter,
               xPppLcpStatusRxConRej
                   Counter,
               xPppLcpStatusTxConRej
                   Counter,
               xPppLcpStatusRxTrmReq
                   Counter,
               xPppLcpStatusTxTrmReq
                   Counter,
               xPppLcpStatusRxTrmAck
                   Counter,
               xPppLcpStatusTxTrmAck
                   Counter,
               xPppLcpStatusRxEcoReq
                   Counter,
               xPppLcpStatusTxEcoReq
                   Counter,
               xPppLcpStatusRxEcoRep
                   Counter,
               xPppLcpStatusTxEcoRep
                   Counter,
               xPppLcpStatusRxCodRej
                   Counter,
               xPppLcpStatusTxCodRej
                   Counter,
               xPppLcpStatusRxProRej
                   Counter,
               xPppLcpStatusTxProRej
                   Counter,
               xPppLcpStatusState2
                   INTEGER
           }

       xPppLcpStatusState OBJECT-TYPE
           SYNTAX INTEGER { closed(1), listen(2), requestSent(3),
                            ackReceived(4), ackSent(5), open(6),
                            closing(7) }
           ACCESS read-only
           STATUS deprecated
           DESCRIPTION
               "The current state of LCP."
           ::= { xPppLcpStatusEntry 1 }

       xPppLcpStatusRxAuth OBJECT-TYPE
           SYNTAX INTEGER { none(1), pap(2)}
           ACCESS read-only
           STATUS mandatory
           DESCRIPTION
               "The authentication protocol currently in use from 
               the peer to us."
           ::= { xPppLcpStatusEntry 2 }

       xPppLcpStatusTxAuth OBJECT-TYPE
           SYNTAX INTEGER { none(1), pap(2)}
           ACCESS read-only
           STATUS mandatory
           DESCRIPTION
               "The authentication protocol currently in use from 
               us to the peer."
           ::= { xPppLcpStatusEntry 3 }

       xPppLcpStatusRxConReq OBJECT-TYPE
           SYNTAX Counter 
           ACCESS read-only
           STATUS mandatory
           DESCRIPTION
               "The count of LCP Configure Requests received from 
               the peer."
           ::= { xPppLcpStatusEntry 4 }

       xPppLcpStatusTxConReq OBJECT-TYPE
           SYNTAX Counter 
           ACCESS read-only
           STATUS mandatory
           DESCRIPTION
               "The count of LCP Configure Requests transmitted to 
               the peer."
           ::= { xPppLcpStatusEntry 5 }

       xPppLcpStatusRxConNak OBJECT-TYPE
           SYNTAX Counter 
           ACCESS read-only
           STATUS mandatory
           DESCRIPTION
               "The count of LCP Configure Naks received from the 
               peer."
           ::= { xPppLcpStatusEntry 6 }

       xPppLcpStatusTxConNak OBJECT-TYPE
           SYNTAX Counter 
           ACCESS read-only
           STATUS mandatory
           DESCRIPTION
               "The count of LCP Configure Naks transmitted to the 
               peer."
           ::= { xPppLcpStatusEntry 7 }

       xPppLcpStatusRxConAck OBJECT-TYPE
           SYNTAX Counter 
           ACCESS read-only
           STATUS mandatory
           DESCRIPTION
               "The count of LCP Configure Acks received from the 
               peer."
           ::= { xPppLcpStatusEntry 8 }

       xPppLcpStatusTxConAck OBJECT-TYPE
           SYNTAX Counter 
           ACCESS read-only
           STATUS mandatory
           DESCRIPTION
               "The count of LCP Configure Acks transmitted to the 
               peer."
           ::= { xPppLcpStatusEntry 9 }

       xPppLcpStatusRxConRej OBJECT-TYPE
           SYNTAX Counter 
           ACCESS read-only
           STATUS mandatory
           DESCRIPTION
               "The count of LCP Configure Rejects received from 
               the peer."
           ::= { xPppLcpStatusEntry 10 }

       xPppLcpStatusTxConRej OBJECT-TYPE
           SYNTAX Counter 
           ACCESS read-only
           STATUS mandatory
           DESCRIPTION
               "The count of LCP Configure Rejects transmitted to 
               the peer."
           ::= { xPppLcpStatusEntry 11 }

       xPppLcpStatusRxTrmReq OBJECT-TYPE
           SYNTAX Counter 
           ACCESS read-only
           STATUS mandatory
           DESCRIPTION
               "The count of LCP Terminate Requests received from 
               the peer."
           ::= { xPppLcpStatusEntry 12 }

       xPppLcpStatusTxTrmReq OBJECT-TYPE
           SYNTAX Counter 
           ACCESS read-only
           STATUS mandatory
           DESCRIPTION
               "The count of LCP Terminate Requests transmitted to 
               the peer."
           ::= { xPppLcpStatusEntry 13 }

       xPppLcpStatusRxTrmAck OBJECT-TYPE
           SYNTAX Counter 
           ACCESS read-only
           STATUS mandatory
           DESCRIPTION
               "The count of LCP Terminate Acks received from the 
               peer."
           ::= { xPppLcpStatusEntry 14 }

       xPppLcpStatusTxTrmAck OBJECT-TYPE
           SYNTAX Counter 
           ACCESS read-only
           STATUS mandatory
           DESCRIPTION
               "The count of LCP Terminate Acks transmitted to the 
               peer."
           ::= { xPppLcpStatusEntry 15 }

       xPppLcpStatusRxEcoReq OBJECT-TYPE
           SYNTAX Counter 
           ACCESS read-only
           STATUS mandatory
           DESCRIPTION
               "The count of LCP Echo Requests received from the 
               peer."
           ::= { xPppLcpStatusEntry 16 }

       xPppLcpStatusTxEcoReq OBJECT-TYPE
           SYNTAX Counter 
           ACCESS read-only
           STATUS mandatory
           DESCRIPTION
               "The count of LCP Echo Requests transmitted to the 
               peer."
           ::= { xPppLcpStatusEntry 17 }

       xPppLcpStatusRxEcoRep OBJECT-TYPE
           SYNTAX Counter 
           ACCESS read-only
           STATUS mandatory
           DESCRIPTION
               "The count of LCP Echo Reply received from the 
               peer."
           ::= { xPppLcpStatusEntry 18 }

       xPppLcpStatusTxEcoRep OBJECT-TYPE
           SYNTAX Counter 
           ACCESS read-only
           STATUS mandatory
           DESCRIPTION
               "The count of LCP Echo Reply transmitted to the 
               peer."
           ::= { xPppLcpStatusEntry 19 }

       xPppLcpStatusRxCodRej OBJECT-TYPE
           SYNTAX Counter 
           ACCESS read-only
           STATUS mandatory
           DESCRIPTION
               "The count of LCP Code Rejects received from the 
               peer."
           ::= { xPppLcpStatusEntry 20 }

       xPppLcpStatusTxCodRej OBJECT-TYPE
           SYNTAX Counter 
           ACCESS read-only
           STATUS mandatory
           DESCRIPTION
               "The count of LCP Code Rejects transmitted to the 
               peer."
           ::= { xPppLcpStatusEntry 21 }

       xPppLcpStatusRxProRej OBJECT-TYPE
           SYNTAX Counter 
           ACCESS read-only
           STATUS mandatory
           DESCRIPTION
               "The count of LCP Protocol Rejects received from the 
               peer."
           ::= { xPppLcpStatusEntry 22 }

       xPppLcpStatusTxProRej OBJECT-TYPE
           SYNTAX Counter 
           ACCESS read-only
           STATUS mandatory
           DESCRIPTION
               "The count of LCP Protocol Rejects transmitted to 
               the peer."
           ::= { xPppLcpStatusEntry 23 }

       xPppLcpStatusState2 OBJECT-TYPE
            SYNTAX INTEGER { initial(1), starting(2), closed(3), stopped(4),
                             closing(5), stopping(6), reqSent(7), ackRcvd(8),
                             ackSent(9), opened(10) }
           ACCESS read-only
           STATUS mandatory
           DESCRIPTION
               "The current state of LCP."
           ::= { xPppLcpStatusEntry 24 }

       xPppIpcpConfigTable OBJECT-TYPE
           SYNTAX SEQUENCE OF XPppIpcpConfigEntry
           ACCESS not-accessible
           STATUS mandatory
           DESCRIPTION
               "A table containing PPP IPCPspecific variables for 
               this PPP implementation."
           ::= { xPppIpcp 1 }

       xPppIpcpConfigEntry OBJECT-TYPE
           SYNTAX XPppIpcpConfigEntry
           ACCESS not-accessible
           STATUS mandatory
           DESCRIPTION
               "Management information about a particular PPP IPCP 
               session."
           INDEX { ifIndex }
           ::= { xPppIpcpConfigTable 1 }

       XPppIpcpConfigEntry ::=
           SEQUENCE {
               xPppIpcpConfigLocalAddress
                   IpAddress,
               xPppIpcpConfigRemoteAddress
                   IpAddress,
               xPppIpcpConfigVJCompSlots
                   INTEGER,
               xPppIpcpConfigRangeStart
                   IpAddress,
               xPppIpcpConfigRangeEnd
                   IpAddress,
               xPppIpcpConfigState
                   INTEGER,
               xPppIpcpConfigLocalRangeStart
                   IpAddress,
               xPppIpcpConfigLocalRangeEnd
                   IpAddress,
               xPppIpcpConfigPppIpMask
                   IpAddress


           }

       xPppIpcpConfigLocalAddress OBJECT-TYPE
           SYNTAX IpAddress
           ACCESS read-write
           STATUS mandatory
           DESCRIPTION
               "IP Address of the local PPP interface."
           ::= { xPppIpcpConfigEntry 1 }

       xPppIpcpConfigRemoteAddress OBJECT-TYPE
           SYNTAX IpAddress
           ACCESS read-write
           STATUS mandatory
           DESCRIPTION
               "IP Address of the peer PPP interface."
           ::= { xPppIpcpConfigEntry 2 }

       xPppIpcpConfigVJCompSlots OBJECT-TYPE
           SYNTAX INTEGER (3..15)
           ACCESS read-write
           STATUS mandatory
           DESCRIPTION
               "Number of slots to be used by VJ compression."
           ::= { xPppIpcpConfigEntry 3 }

       xPppIpcpConfigRangeStart OBJECT-TYPE
           SYNTAX IpAddress
           ACCESS read-write
           STATUS mandatory
           DESCRIPTION
               "Start of acceptable address range in which the negotiated 
		remote IP address must fall."
           ::= { xPppIpcpConfigEntry 4 }

       xPppIpcpConfigRangeEnd OBJECT-TYPE
           SYNTAX IpAddress
           ACCESS read-write
           STATUS mandatory
           DESCRIPTION
               "End of acceptable address range in which the negotiated 
		remote IP address must fall."
           ::= { xPppIpcpConfigEntry 5 }
 
       xPppIpcpConfigState OBJECT-TYPE
           SYNTAX INTEGER { disabled(1), enabled(2) }
           ACCESS read-write
           STATUS mandatory
           DESCRIPTION
               "Controls whether IPCP is allowed to run on this port."
           ::= { xPppIpcpConfigEntry 6 }

       xPppIpcpConfigLocalRangeStart OBJECT-TYPE
           SYNTAX IpAddress
           ACCESS read-write
           STATUS mandatory
           DESCRIPTION
               "Start of acceptable address range in which the negotiated 
		local IP address must fall."
           ::= { xPppIpcpConfigEntry 7 }

       xPppIpcpConfigLocalRangeEnd OBJECT-TYPE
           SYNTAX IpAddress
           ACCESS read-write
           STATUS mandatory
           DESCRIPTION
               "End of acceptable address range in which the negotiated 
		local IP address must fall."
           ::= { xPppIpcpConfigEntry 8 }

       xPppIpcpConfigPppIpMask OBJECT-TYPE
           SYNTAX IpAddress
           ACCESS read-write
           STATUS mandatory
           DESCRIPTION
               "The subnet mask to use for a PPP operation on the port. 
                Corresponds directly to the value labeled 'IP Mask:' in the 
                PPP PORT IP CHARACTERISTICS display."
           DEFVAL { 'ffffffff'h }    -- 255.255.255.255
           ::= { xPppIpcpConfigEntry 9 }




       xPppIpcpAsyncConfigTable OBJECT-TYPE
           SYNTAX SEQUENCE OF XPppIpcpAsyncConfigEntry
           ACCESS not-accessible
           STATUS mandatory
           DESCRIPTION
               "A table containing PPP specific variables for this 
               PPP implementation."
           ::= { xPppIpcp 2 }

       xPppIpcpAsyncConfigEntry OBJECT-TYPE
           SYNTAX XPppIpcpAsyncConfigEntry
           ACCESS not-accessible
           STATUS mandatory
           DESCRIPTION
               "Management information about a particular PPP 
               Asynchronous LCP."
           INDEX { ifIndex }
           ::= { xPppIpcpAsyncConfigTable 1 }

       XPppIpcpAsyncConfigEntry ::=
           SEQUENCE {
               xPppIpcpAsyncConfigBrdcast
                   INTEGER
            }

       xPppIpcpAsyncConfigBrdcast OBJECT-TYPE
           SYNTAX INTEGER { disabled(1), enabled(2)}
           ACCESS read-write
           STATUS mandatory
           DESCRIPTION
               "Determines whether to forward an IP Broadcast or 
               not."
           ::= { xPppIpcpAsyncConfigEntry 1 }





       xPppIpcpStatusTable OBJECT-TYPE
           SYNTAX SEQUENCE OF XPppIpcpStatusEntry
           ACCESS not-accessible
           STATUS mandatory
           DESCRIPTION
               "A table containing basic PPP IPCP status info."
           ::= { xPppIpcp 3 }

       xPppIpcpStatusEntry OBJECT-TYPE
           SYNTAX XPppIpcpStatusEntry
           ACCESS not-accessible
           STATUS mandatory
           DESCRIPTION
               "Status information about a particular PPP IPCP 
               session."
           INDEX { ifIndex }
           ::= { xPppIpcpStatusTable 1 }

       XPppIpcpStatusEntry ::=
           SEQUENCE {
               xPppIpcpStatusState
                   INTEGER,
               xPppIpcpStatusLocalAddress
                   IpAddress,
               xPppIpcpStatusRemoteAddress
                   IpAddress,
               xPppIpcpRxConReq
                   Counter,
               xPppIpcpTxConReq
                   Counter,
               xPppIpcpRxConNak 
                   Counter,
               xPppIpcpTxConNak
                   Counter,
               xPppIpcpRxConAck
                   Counter,
               xPppIpcpTxConAck
                   Counter,
               xPppIpcpRxConRej
                   Counter,
               xPppIpcpTxConRej
                   Counter,
               xPppIpcpRxTrmReq
                   Counter,
               xPppIpcpTxTrmReq
                   Counter,
               xPppIpcpRxTrmAck
                   Counter,
               xPppIpcpTxTrmAck
                   Counter,
               xPppIpcpRxPkts
                   Counter,
               xPppIpcpTxPkts
                   Counter,
               xPppIpcpStatusState2
                   INTEGER
           }

       xPppIpcpStatusState OBJECT-TYPE
           SYNTAX INTEGER { closed(1), listen(2), requestSent(3),
                            ackReceived(4), ackSent(5), open(6),
                            closing(7) }
           ACCESS read-only
           STATUS deprecated
           DESCRIPTION
               "The current state of IPCP."
           ::= { xPppIpcpStatusEntry 1 }

       xPppIpcpStatusLocalAddress OBJECT-TYPE
           SYNTAX IpAddress
           ACCESS read-only
           STATUS mandatory
           DESCRIPTION
               "The IP Address currently being used by the local 
               IPCP."
           ::= { xPppIpcpStatusEntry 2 }

       xPppIpcpStatusRemoteAddress OBJECT-TYPE
           SYNTAX IpAddress
           ACCESS read-only
           STATUS mandatory
           DESCRIPTION
               "The IP Address currently being used by the Remote 
               IPCP."
           ::= { xPppIpcpStatusEntry 3 }

       xPppIpcpRxPkts OBJECT-TYPE
           SYNTAX Counter
           ACCESS read-only
           STATUS mandatory
           DESCRIPTION
               "Total number of IP packets received."
           ::= { xPppIpcpStatusEntry 4 }

       xPppIpcpTxPkts OBJECT-TYPE
           SYNTAX Counter
           ACCESS read-only
           STATUS mandatory
           DESCRIPTION
               "Total number of IP packets transmitted."
           ::= { xPppIpcpStatusEntry 5 }

       xPppIpcpRxConReq OBJECT-TYPE
           SYNTAX Counter
           ACCESS read-only
           STATUS mandatory
           DESCRIPTION
               "The count of IPCP Configure Requests received from 
               the peer."
           ::= { xPppIpcpStatusEntry 6 }

       xPppIpcpTxConReq OBJECT-TYPE
           SYNTAX Counter
           ACCESS read-only
           STATUS mandatory
           DESCRIPTION
               "The count of IPCP Configure Requests transmitted to 
               the peer."
           ::= { xPppIpcpStatusEntry 7 }

       xPppIpcpRxConNak OBJECT-TYPE
           SYNTAX Counter
           ACCESS read-only
           STATUS mandatory
           DESCRIPTION
               "The count of IPCP Configure Naks received from the 
               peer."
           ::= { xPppIpcpStatusEntry 8 }

       xPppIpcpTxConNak OBJECT-TYPE
           SYNTAX Counter
           ACCESS read-only
           STATUS mandatory
           DESCRIPTION
               "The count of IPCP Configure Naks transmitted to the 
               peer."
           ::= { xPppIpcpStatusEntry 9 }

       xPppIpcpRxConAck OBJECT-TYPE
           SYNTAX Counter
           ACCESS read-only
           STATUS mandatory
           DESCRIPTION
               "The count of IPCP Configure Acks received from the 
               peer."
           ::= { xPppIpcpStatusEntry 10 }

       xPppIpcpTxConAck OBJECT-TYPE
           SYNTAX Counter
           ACCESS read-only
           STATUS mandatory
           DESCRIPTION
               "The count of IPCP Configure Acks transmitted to the 
               peer."
           ::= { xPppIpcpStatusEntry 11 }

       xPppIpcpRxConRej OBJECT-TYPE
           SYNTAX Counter
           ACCESS read-only
           STATUS mandatory
           DESCRIPTION
               "The count of IPCP Configure Rejects received from 
               the peer."
           ::= { xPppIpcpStatusEntry 12 }

       xPppIpcpTxConRej OBJECT-TYPE
           SYNTAX Counter
           ACCESS read-only
           STATUS mandatory
           DESCRIPTION
               "The count of IPCP Configure Rejects transmitted to 
               the peer."
           ::= { xPppIpcpStatusEntry 13 }

       xPppIpcpRxTrmReq OBJECT-TYPE
           SYNTAX Counter
           ACCESS read-only
           STATUS mandatory
           DESCRIPTION
               "The count of IPCP Terminate Requests received from 
               the peer."
           ::= { xPppIpcpStatusEntry 14 }

       xPppIpcpTxTrmReq OBJECT-TYPE
           SYNTAX Counter
           ACCESS read-only
           STATUS mandatory
           DESCRIPTION
               "The count of IPCP Terminate Requests transmitted to 
               the peer."
           ::= { xPppIpcpStatusEntry 15 }

       xPppIpcpRxTrmAck OBJECT-TYPE
           SYNTAX Counter
           ACCESS read-only
           STATUS mandatory
           DESCRIPTION
               "The count of IPCP Terminate Acks received from the 
               peer."
           ::= { xPppIpcpStatusEntry 16 }

       xPppIpcpTxTrmAck OBJECT-TYPE
           SYNTAX Counter
           ACCESS read-only
           STATUS mandatory
           DESCRIPTION
               "The count of IPCP Terminate Acks transmitted to the 
               peer."
           ::= { xPppIpcpStatusEntry 17 }

       xPppIpcpStatusState2 OBJECT-TYPE
           SYNTAX INTEGER { initial(1), starting(2), closed(3), stopped(4),
                            closing(5), stopping(6), reqSent(7), ackRcvd(8),
                            ackSent(9), opened(10) }
           ACCESS read-only
           STATUS mandatory
           DESCRIPTION
               "The current state of IPCP."
           ::= { xPppIpcpStatusEntry 18 }

       -- The PPP Authentication group is mandatory for systems that
       -- implement PAP or CHAP

       xPppPapPassword OBJECT-TYPE
           SYNTAX OCTET STRING (SIZE (0..16))
           ACCESS read-write
           STATUS mandatory
           DESCRIPTION
               "The password to use for PAP authentication."
           ::= { xPppAuth 1 }


       xPppAuthConfigTable OBJECT-TYPE
           SYNTAX SEQUENCE OF XPppAuthConfigEntry
           ACCESS not-accessible
           STATUS mandatory
           DESCRIPTION
               "A table containing PPP specific variables for this 
               PPP implementation."
           ::= { xPppAuth 2 }

       xPppAuthConfigEntry OBJECT-TYPE
           SYNTAX XPppAuthConfigEntry
           ACCESS not-accessible
           STATUS mandatory
           DESCRIPTION
               "Management information about a particular PPP."
           INDEX { ifIndex }
           ::= { xPppAuthConfigTable 1 }

       XPppAuthConfigEntry ::=
           SEQUENCE {
               xPppAuthChapChallengeTimer
                   INTEGER,
               xPppAuthPapConfigState
                   INTEGER,
               xPppAuthChapConfigState
                   INTEGER
           }

--     xPppAuthTransfer(1),  xPppAuthPapState(2),  xPppAuthChapState(3)
--     reserved for Internetworking products.

       xPppAuthChapChallengeTimer OBJECT-TYPE
           SYNTAX INTEGER (0..120)
           ACCESS read-write
           STATUS mandatory
           DESCRIPTION
               "Length of time in minutes between CHAP reauthentication challenges.
                A value of zero disables the timer."
           DEFVAL { 0 } 
           ::= { xPppAuthConfigEntry 4 }

       xPppAuthPapConfigState OBJECT-TYPE
           SYNTAX INTEGER { disabled(1), enabled(2), kerberos(3), radius(4) }
           ACCESS read-write
           STATUS mandatory
           DESCRIPTION
               "Controls the type of Pap authentication required for this port,
		and whether it is combined with another authentication
		mechanism such as Radius."
           DEFVAL { disabled } 
           ::= { xPppAuthConfigEntry 5 }

       xPppAuthChapConfigState OBJECT-TYPE
           SYNTAX INTEGER { disabled(1), enabled(2), radius(4) }
           ACCESS read-write
           STATUS mandatory
           DESCRIPTION
               "Controls the type of Chap authentication required for this port,
		and whether it is combined with another authentication
		mechanism such as Radius."
           DEFVAL { disabled } 
           ::= { xPppAuthConfigEntry 6 }
			
       xPppAuthStatusTable OBJECT-TYPE
           SYNTAX SEQUENCE OF XPppAuthStatusEntry
           ACCESS not-accessible
           STATUS mandatory
           DESCRIPTION
               "A table containing PPP specific variables for this 
               PPP implementation."
           ::= { xPppAuth 3 }

       xPppAuthStatusEntry OBJECT-TYPE
           SYNTAX XPppAuthStatusEntry
           ACCESS not-accessible
           STATUS mandatory
           DESCRIPTION
               "Management information about a particular PPP."
           INDEX { ifIndex }
           ::= { xPppAuthStatusTable 1 }

       XPppAuthStatusEntry ::=
           SEQUENCE {
               xPppPapStatusState
                   INTEGER,
               xPppChapStatusState
                   INTEGER
           }

       -- xPppAuthStatusState(1), xPppChapInStatus(2) and xPppChapOutStatus(3)
       -- are reserved for Internetworking products.

       xPppPapStatusState OBJECT-TYPE
           SYNTAX INTEGER { initial(1), closed(2), stopped(3), closing(4),
                            reqSent(5), ackRecv(6), ackSent(7), opened(8),
                            kerberosReqSent(9), kerberosStopped(10), 
                            kerberosAckRecv(11), kerberosAckSent(12),
                            papKerberosOpened(13) }
           ACCESS read-only
           STATUS mandatory
           DESCRIPTION
               "The current state of PAP."
           ::= { xPppAuthStatusEntry 4 }

       xPppChapStatusState OBJECT-TYPE
           SYNTAX INTEGER { idle(1), challengeWait(2), challengeSent(3),
                            responseSent(4), challengeSentResponseSent(5),
                            challengeSentAckRecv(6), open(7) }
           ACCESS read-only
           STATUS mandatory
           DESCRIPTION
               "The current state of CHAP."
           ::= { xPppAuthStatusEntry 5 }


       xPppChapPassword OBJECT-TYPE
           SYNTAX OCTET STRING (SIZE (0..16))
           ACCESS read-write
           STATUS mandatory
           DESCRIPTION
               "The password to use for CHAP authentication."
           ::= { xPppAuth 4 }


       -- The PPP IPXCP group for the ipx protocol

       xPppIpxcpConfigTable OBJECT-TYPE
           SYNTAX SEQUENCE OF XPppIpxcpConfigEntry
           ACCESS not-accessible
           STATUS mandatory
           DESCRIPTION
               "A table containing PPP specific variables for this 
               PPP implementation."
           ::= { xPppIpxcp 1 }

       xPppIpxcpConfigEntry OBJECT-TYPE
           SYNTAX XPppIpxcpConfigEntry
           ACCESS not-accessible
           STATUS mandatory
           DESCRIPTION
               "Management information about a particular PPP."
           INDEX { ifIndex }
           ::= { xPppIpxcpConfigTable 1 }

       XPppIpxcpConfigEntry ::=
           SEQUENCE {
               xPppIpxcpCipxCompression
                   INTEGER,
               xPppIpxcpConfigRemoteNode
                   OCTET STRING
           }

       xPppIpxcpCipxCompression OBJECT-TYPE
           SYNTAX INTEGER { disabled(1), enabled(2) }
           ACCESS read-write
           STATUS mandatory
           DESCRIPTION
               "Controls whether CIPX compression will be negotiated on the
               interface."
           DEFVAL { disabled }
           ::= { xPppIpxcpConfigEntry 1 }

       xPppIpxcpConfigRemoteNode OBJECT-TYPE
           SYNTAX OCTET STRING ( SIZE(6) )
           ACCESS read-write
           STATUS mandatory
           DESCRIPTION
               "The IPX Node address which can be offered to the peer if
		it does not know a Node number but requires one."
           ::= { xPppIpxcpConfigEntry 2 }

       xPppIpxcpStatusTable OBJECT-TYPE
           SYNTAX SEQUENCE OF XPppIpxcpStatusEntry
           ACCESS not-accessible
           STATUS mandatory
           DESCRIPTION
               "A table containing PPP specific variables for this 
               PPP implementation."
           ::= { xPppIpxcp 2 }

       xPppIpxcpStatusEntry OBJECT-TYPE
           SYNTAX XPppIpxcpStatusEntry
           ACCESS not-accessible
           STATUS mandatory
           DESCRIPTION
               "Management information about a particular PPP."
           INDEX { ifIndex }
           ::= { xPppIpxcpStatusTable 1 }

       XPppIpxcpStatusEntry ::=
           SEQUENCE {
               xPppIpxcpStatusState
                   INTEGER,
               xPppIpxcpCipxInCompression
                   INTEGER,
               xPppIpxcpCipxOutCompression
                   INTEGER,
               xPppIpxcpCipxInSlots
                   INTEGER,
               xPppIpxcpCipxOutSlots
                   INTEGER,
               xPppIpxcpStatusRemoteNode
                   OCTET STRING
           }

       xPppIpxcpStatusState OBJECT-TYPE
           SYNTAX INTEGER { initial(1), starting(2), closed(3), stopped(4),
                            closing(5), stopping(6), reqSent(7), ackRcvd(8),
                            ackSent(9), opened(10) }
           ACCESS read-only
           STATUS mandatory
           DESCRIPTION
               "The current state of IPXCP."
           ::= { xPppIpxcpStatusEntry 1 }

       xPppIpxcpCipxInCompression OBJECT-TYPE
           SYNTAX INTEGER { open(1), closed(2) }
           ACCESS read-only
           STATUS mandatory
           DESCRIPTION
               "The current state of CIPX compression inbound."
           ::= { xPppIpxcpStatusEntry 2 }

       xPppIpxcpCipxOutCompression OBJECT-TYPE
           SYNTAX INTEGER { open(1), closed(2) }
           ACCESS read-only
           STATUS mandatory
           DESCRIPTION
               "The current state of CIPX compression outbound."
           ::= { xPppIpxcpStatusEntry 3 }

       xPppIpxcpCipxInSlots OBJECT-TYPE
           SYNTAX INTEGER
           ACCESS read-only
           STATUS mandatory
           DESCRIPTION
               "The current number of CIPX compression inbound slots."
           ::= { xPppIpxcpStatusEntry 4 }

       xPppIpxcpCipxOutSlots OBJECT-TYPE
           SYNTAX INTEGER
           ACCESS read-only
           STATUS mandatory
           DESCRIPTION
               "The current number of CIPX compression outbound slots."
           ::= { xPppIpxcpStatusEntry 5 }


       xPppIpxcpStatusRemoteNode OBJECT-TYPE
           SYNTAX OCTET STRING ( SIZE(6) )
           ACCESS read-only
           STATUS mandatory
           DESCRIPTION
               "The IPX Node address currently being used by the Remote 
               IPX peer."
           ::= { xPppIpxcpStatusEntry 6 }

       xPppIpxcpCountersTable OBJECT-TYPE
           SYNTAX SEQUENCE OF XPppIpxcpCountersEntry
           ACCESS not-accessible
           STATUS mandatory
           DESCRIPTION
               "A table containing basic PPP IPXCP status info."
           ::= { xPppIpxcp 3 }

       xPppIpxcpCountersEntry OBJECT-TYPE
           SYNTAX XPppIpxcpCountersEntry
           ACCESS not-accessible
           STATUS mandatory
           DESCRIPTION
               "Counter information about a particular PPP IPXCP 
               session."
           INDEX { ifIndex }
           ::= { xPppIpxcpCountersTable 1 }

       XPppIpxcpCountersEntry ::=
           SEQUENCE {
               xPppIpxcpRxConReq
                   Counter,
               xPppIpxcpTxConReq
                   Counter,
               xPppIpxcpRxConNak 
                   Counter,
               xPppIpxcpTxConNak
                   Counter,
               xPppIpxcpRxConAck
                   Counter,
               xPppIpxcpTxConAck
                   Counter,
               xPppIpxcpRxConRej
                   Counter,
               xPppIpxcpTxConRej
                   Counter,
               xPppIpxcpRxTrmReq
                   Counter,
               xPppIpxcpTxTrmReq
                   Counter,
               xPppIpxcpRxTrmAck
                   Counter,
               xPppIpxcpTxTrmAck
                   Counter
           }

       xPppIpxcpRxConReq OBJECT-TYPE
           SYNTAX Counter
           ACCESS read-only
           STATUS mandatory
           DESCRIPTION
               "The count of IPXCP Configure Requests received from 
               the peer."
           ::= { xPppIpxcpCountersEntry 1 }

       xPppIpxcpTxConReq OBJECT-TYPE
           SYNTAX Counter
           ACCESS read-only
           STATUS mandatory
           DESCRIPTION
               "The count of IPXCP Configure Requests transmitted to 
               the peer."
           ::= { xPppIpxcpCountersEntry 2 }

       xPppIpxcpRxConNak OBJECT-TYPE
           SYNTAX Counter
           ACCESS read-only
           STATUS mandatory
           DESCRIPTION
               "The count of IPXCP Configure Naks received from the 
               peer."
           ::= { xPppIpxcpCountersEntry 3 }

       xPppIpxcpTxConNak OBJECT-TYPE
           SYNTAX Counter
           ACCESS read-only
           STATUS mandatory
           DESCRIPTION
               "The count of IPXCP Configure Naks transmitted to the 
               peer."
           ::= { xPppIpxcpCountersEntry 4 }

       xPppIpxcpRxConAck OBJECT-TYPE
           SYNTAX Counter
           ACCESS read-only
           STATUS mandatory
           DESCRIPTION
               "The count of IPXCP Configure Acks received from the 
               peer."
           ::= { xPppIpxcpCountersEntry 5 }

       xPppIpxcpTxConAck OBJECT-TYPE
           SYNTAX Counter
           ACCESS read-only
           STATUS mandatory
           DESCRIPTION
               "The count of IPXCP Configure Acks transmitted to the 
               peer."
           ::= { xPppIpxcpCountersEntry 6 }

       xPppIpxcpRxConRej OBJECT-TYPE
           SYNTAX Counter
           ACCESS read-only
           STATUS mandatory
           DESCRIPTION
               "The count of IPXCP Configure Rejects received from 
               the peer."
           ::= { xPppIpxcpCountersEntry 7 }

       xPppIpxcpTxConRej OBJECT-TYPE
           SYNTAX Counter
           ACCESS read-only
           STATUS mandatory
           DESCRIPTION
               "The count of IPXCP Configure Rejects transmitted to 
               the peer."
           ::= { xPppIpxcpCountersEntry 8 }

       xPppIpxcpRxTrmReq OBJECT-TYPE
           SYNTAX Counter
           ACCESS read-only
           STATUS mandatory
           DESCRIPTION
               "The count of IPXCP Terminate Requests received from 
               the peer."
           ::= { xPppIpxcpCountersEntry 9 }

       xPppIpxcpTxTrmReq OBJECT-TYPE
           SYNTAX Counter
           ACCESS read-only
           STATUS mandatory
           DESCRIPTION
               "The count of IPXCP Terminate Requests transmitted to 
               the peer."
           ::= { xPppIpxcpCountersEntry 10 }

       xPppIpxcpRxTrmAck OBJECT-TYPE
           SYNTAX Counter
           ACCESS read-only
           STATUS mandatory
           DESCRIPTION
               "The count of IPXCP Terminate Acks received from the 
               peer."
           ::= { xPppIpxcpCountersEntry 11 }

       xPppIpxcpTxTrmAck OBJECT-TYPE
           SYNTAX Counter
           ACCESS read-only
           STATUS mandatory
           DESCRIPTION
               "The count of IPXCP Terminate Acks transmitted to the 
               peer."
           ::= { xPppIpxcpCountersEntry 12 }



--
-- FILE: /users/sse/mibs/src/inReach/ir-radius-mib.mib
--

-- $Id: ir-radius-mib.mib,v 1.1 2002/06/27 15:39:03 sse Exp $


            xRadius          OBJECT IDENTIFIER ::= { mrvInReachProductDivision 35 }

            -- MRV In-Reach Radius subgroups

            xRadiusPort             OBJECT IDENTIFIER ::= { xRadius 1 }
            xRadiusCircuit          OBJECT IDENTIFIER ::= { xRadius 2 }
            xRadiusConfig           OBJECT IDENTIFIER ::= { xRadius 3 }
            xRadiusServers          OBJECT IDENTIFIER ::= { xRadius 4 }
            xRadiusCounters         OBJECT IDENTIFIER ::= { xRadius 5 }
	        


            -- This is a MIB module for all MRV In-Reach systems that
            -- implement Radius.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


        -- the Radius  Port group

            xRadiusPortTable OBJECT-TYPE
                SYNTAX SEQUENCE OF XRadiusPortEntry
                ACCESS not-accessible
                STATUS mandatory
                DESCRIPTION
                    "Table of fields indexed by port."
                ::= { xRadiusPort 1 }

            xRadiusPortEntry OBJECT-TYPE
                SYNTAX XRadiusPortEntry
                ACCESS not-accessible
                STATUS mandatory
                DESCRIPTION
                    "A particular entry."
                INDEX { xRadiusPortIndex }
                ::= { xRadiusPortTable 1 }

            XRadiusPortEntry ::=
                SEQUENCE {
                        xRadiusPortIndex
                            INTEGER,
                        xRadiusPortStatus
                            INTEGER,
                        xRadiusPortSolicitStatus
                            INTEGER,
                        xRadiusAcctPortStatus
                            INTEGER
                         }

            xRadiusPortIndex OBJECT-TYPE
                SYNTAX INTEGER
                ACCESS read-only
                STATUS mandatory
                DESCRIPTION
                    "The index of the port."
                ::= { xRadiusPortEntry 1 }

            xRadiusPortStatus OBJECT-TYPE
                SYNTAX INTEGER { disabled(1), enabled(2) }
                ACCESS read-only
                STATUS mandatory
                DESCRIPTION
                    "Indicates the state of Radius Authentication on 
                     the port."
                DEFVAL { disabled }
                ::= { xRadiusPortEntry 2 }

            xRadiusPortSolicitStatus OBJECT-TYPE
                SYNTAX INTEGER { disabled(1), enabled(2) }
                ACCESS read-write
                STATUS mandatory
                DESCRIPTION
                    "Indicates the state of Radius solicitation mode 
                     on the port."
                DEFVAL { disabled }
                ::= { xRadiusPortEntry 3 }

            xRadiusAcctPortStatus OBJECT-TYPE
                SYNTAX INTEGER { disabled(1), enabled(2), limited(3) }
                ACCESS read-only
                STATUS mandatory
                DESCRIPTION
                    "Indicates the state of Radius Accounting on the port."
                DEFVAL { disabled }
                ::= { xRadiusPortEntry 4 }


        -- the Radius Circuit group







        -- the Radius Configuration group

            xRadiusAuthServerPort OBJECT-TYPE
                SYNTAX INTEGER (0..65535)
                ACCESS read-write
                STATUS mandatory
                DESCRIPTION
                    "The UDP port on which the Radius authentication request
                     will be made."
                DEFVAL { 1645 }
                ::= { xRadiusConfig 1 }

            xRadiusAcctServerPort OBJECT-TYPE
                SYNTAX INTEGER (0..65535)
                ACCESS read-write
                STATUS mandatory
                DESCRIPTION
                    "The UDP port on which the Radius accounting request
                     will be made."
                DEFVAL { 1646 }
                ::= { xRadiusConfig 2 }

            xRadiusTimeout OBJECT-TYPE
                SYNTAX INTEGER (1..255)
                ACCESS read-write
                STATUS mandatory
                DESCRIPTION
                    "The period of time that the Radius client will wait
                     for a reply from the server."
                DEFVAL { 5 }
                ::= { xRadiusConfig 3 }

            xRadiusServerRetries OBJECT-TYPE
                SYNTAX INTEGER (1..10)
                ACCESS read-write
                STATUS mandatory
                DESCRIPTION
                    "The number of times a Radius server will be tried."
                DEFVAL { 3 }
                ::= { xRadiusConfig 4 }

            xRadiusAcctLogAttempts OBJECT-TYPE
                SYNTAX INTEGER (1..50000)
                ACCESS read-write
                STATUS mandatory
                DESCRIPTION
                    "The number of times the client will attempt to log
                     the accounting record to either the primary or 
                     secondary Radius server before giving up and failing."
                DEFVAL { 5 }
                ::= { xRadiusConfig 5 }

            xRadiusChapChallengeSize OBJECT-TYPE
                SYNTAX INTEGER (4..128)
                ACCESS read-write
                STATUS mandatory
                DESCRIPTION
                    "The size of the CHAP challenge that is sent to the 
                     peer and the Radius server."
                DEFVAL { 16 }
                ::= { xRadiusConfig 6 }

            xRadiusLogging OBJECT-TYPE
                SYNTAX INTEGER { disabled(1), enabled(2) }
                ACCESS read-write
                STATUS mandatory
                DESCRIPTION
                    "Indicates the state of Radius logging for packet 
                     tracing and troubleshooting. Messages are logged
                     to the MRV In-Reach event log."
                DEFVAL { disabled }
                ::= { xRadiusConfig 7 }

            xRadiusMessage OBJECT-TYPE
                SYNTAX DisplayString ( SIZE(40) )
                ACCESS read-write
                STATUS mandatory
                DESCRIPTION
                    "The authentication prompting message for Radius
                     logins."
                DEFVAL { "" }
                ::= { xRadiusConfig 8 }


        -- the Radius Server group

            xRadServer1SubGrp       OBJECT IDENTIFIER ::= { xRadiusServers 1 }
            xRadServer2SubGrp       OBJECT IDENTIFIER ::= { xRadiusServers 2 }

            -- the Radius Primary Server entries

            xRadiusServerName1 OBJECT-TYPE
                SYNTAX OCTET STRING ( SIZE(51) )
                ACCESS read-write
                STATUS mandatory
                DESCRIPTION
                    "The primary Radius server queried for authentication."
                DEFVAL { "" }
                ::= { xRadServer1SubGrp 1 }

                        -- Secrets shouldn't be accessed via SNMP
            xRadiusSecret1 OBJECT-TYPE
                SYNTAX OCTET STRING ( SIZE(32) )
                ACCESS read-only
                STATUS obsolete
                DESCRIPTION
                    "The secret value used to communicate with the primary
                     Radius server."
                DEFVAL { "Default_Secret" }
                ::= { xRadServer1SubGrp 2 }

            xRadiusServerAccess1 OBJECT-TYPE
                SYNTAX Counter
                ACCESS read-only
                STATUS mandatory
                DESCRIPTION
                    "The number of successful accesses of primary Radius 
                     server."
                ::= { xRadServer1SubGrp 3 }

            xRadiusServerAccessFailed1 OBJECT-TYPE
                SYNTAX Counter
                ACCESS read-only
                STATUS mandatory
                DESCRIPTION
                    "The number of failed accesses of primary Radius server."
                ::= { xRadServer1SubGrp 4 }

            -- the Radius Secondary Server entries

            xRadiusServerName2 OBJECT-TYPE
                SYNTAX OCTET STRING ( SIZE(51) )
                ACCESS read-write
                STATUS mandatory
                DESCRIPTION
                    "The secondary Radius server queried for authentication, 
                     if the primary one fails."
                DEFVAL { "" }
                ::= { xRadServer2SubGrp 1 }

                        -- Secrets shouldn't be accessed via SNMP
            xRadiusSecret2 OBJECT-TYPE
                SYNTAX OCTET STRING ( SIZE(32) )
                ACCESS read-only
                STATUS obsolete
                DESCRIPTION
                    "The secret value used to communicate with the 
                     secondary Radius server."
                DEFVAL { "Default_Secret" }
                ::= { xRadServer2SubGrp 2 }

            xRadiusServerAccess2 OBJECT-TYPE
                SYNTAX Counter
                ACCESS read-only
                STATUS mandatory
                DESCRIPTION
                    "The number of successful accesses of secondary Radius 
                     server."
                ::= { xRadServer2SubGrp 3}

            xRadiusServerAccessFailed2 OBJECT-TYPE
                SYNTAX Counter
                ACCESS read-only
                STATUS mandatory
                DESCRIPTION
                    "The number of failed accesses of secondary Radius 
                     server."
                ::= { xRadServer2SubGrp 4}


        -- the Radius Counters group

            xRadAuthCtsSubGrp   OBJECT IDENTIFIER ::= { xRadiusCounters 1 }
            xRadAcctCtsSubGrp   OBJECT IDENTIFIER ::= { xRadiusCounters 2 }

            -- the Radius Authentication Counters entries

            xRadiusLogins OBJECT-TYPE
                SYNTAX Counter
                ACCESS read-only
                STATUS mandatory
                DESCRIPTION
                    "The number of successful logins using Radius."
                ::= { xRadAuthCtsSubGrp 1 }

            xRadiusLoginsFailed OBJECT-TYPE
                SYNTAX Counter
                ACCESS read-only
                STATUS mandatory
                DESCRIPTION
                    "The number of failed logins resulting from being 
                     rejected by the Radius server."
                ::= { xRadAuthCtsSubGrp 2 }

            xRadiusConfigFailed OBJECT-TYPE
                SYNTAX Counter
                ACCESS read-only
                STATUS mandatory
                DESCRIPTION
                    "The number of failed logins resulting from unsupported
                     attribute values."
                ::= { xRadAuthCtsSubGrp 3 }

            xRadiusPolicyFailed OBJECT-TYPE
                SYNTAX Counter
                ACCESS read-only
                STATUS mandatory
                DESCRIPTION
                    "The number of failed logins resulting from failing
                     specific Radius policies on the MRV In-Reach unit."
                ::= { xRadAuthCtsSubGrp 4 }

            -- the Radius Accounting Counters entries

            xRadiusAcctSuccess OBJECT-TYPE
                SYNTAX Counter
                ACCESS read-only
                STATUS mandatory
                DESCRIPTION
                    "The number of successfully recorded Radius accounting
                     log records."
                ::= { xRadAcctCtsSubGrp 1}

            xRadiusAcctFailed OBJECT-TYPE
                SYNTAX Counter
                ACCESS read-only
                STATUS mandatory
                DESCRIPTION
                    "The number of failed (not logged) Radius accounting
                     log records."
                ::= { xRadAcctCtsSubGrp 2}

            xRadiusAcctReqWait OBJECT-TYPE
                SYNTAX Counter
                ACCESS read-only
                STATUS mandatory
                DESCRIPTION
                    "The number of log requests waiting for a reply from 
                     the Radius server."
                ::= { xRadAcctCtsSubGrp 3 }

      

--
-- FILE: /users/sse/mibs/src/inReach/ir-system-mib.mib
--

-- $Id: ir-system-mib.mib,v 1.1 2002/06/27 15:39:29 sse Exp $



            xSystem         OBJECT IDENTIFIER ::= { mrvInReachProductDivision 1 }

            -- This is a MIB module for all MRV In-Reach systems.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


            -- the System group

            -- Implementation of this group is mandatory for all MRV In-Reach
            -- systems.

            sysIdent OBJECT-TYPE
                SYNTAX DisplayString (SIZE (0..50))
                ACCESS read-write
                STATUS mandatory
                DESCRIPTION
                    "An identification string for local and remote 
                    displays.  Corresponds directly to SERVER 
                    IDENTIFICATION and the value labeled 
                    'Identification:' on the SERVER CHARACTERISTICS 
                    display."
                ::= { xSystem 1 }

            sysDefineMode OBJECT-TYPE
                SYNTAX INTEGER { permOnly(1), operAndPerm(2) }
                ACCESS read-write
                STATUS mandatory
                DESCRIPTION
                    "The system's operation with regard to DEFINE 
                    commands.  'permOnly' indicates that DEFINE commands 
                    modify only the permanent data base.  'operAndPerm' 
                    indicates that DEFINE commands modify both 
                    operational and permanent data bases, unless 
                    specifically documented to the contrary.  
                    Corresponds to SERVER CHANGE and the presence of the 
                    label CHANGE in the SERVER CHARACTERISTICS 
                    display."
                ::= { xSystem 2 }

            sysDateTime OBJECT-TYPE
                SYNTAX DateTime
                ACCESS read-write
                STATUS mandatory
                DESCRIPTION
                    "The system's current local date and time.  
                    Corresponds directly to SERVER DATE and SERVER TIME 
                    and the value in various displays."
                ::= { xSystem 3 }

            sysTimeZone OBJECT-TYPE
                SYNTAX OCTET STRING (SIZE (2))
                ACCESS read-write
                STATUS mandatory
                DESCRIPTION
                    "The adjustment to apply to a universal (Greenwich) 
                    time received when down-line loaded, comprising two 
                    octets.  The first octet is the number of hours west 
                    of universal, the second is the number of minutes.  
                    Corresponds directly to SERVER TIMEZONE and the 
                    value labeled 'Timezone:' in the SERVER 
                    CHARACTERISTICS display."
                ::= { xSystem 4 }

            sysLoadSoftware OBJECT-TYPE
                SYNTAX DisplayString (SIZE (0..16))
                ACCESS read-write
                STATUS mandatory
                DESCRIPTION
                    "The software file name to request for down-line 
                    load of the server.  Corresponds directly to SERVER 
                    SOFTWARE, and the value labeled 'Software:' in the 
                    SERVER CHARACTERISTICS display."
                ::= { xSystem 5 }

            sysDump OBJECT-TYPE
                SYNTAX INTEGER { disabled(1), enabled(2) }
                ACCESS read-write
                STATUS mandatory
                DESCRIPTION
                    "Control for dumping the system's memory when the 
                    system crashes.  Corresponds directly to SERVER DUMP 
                    and the presence of 'Dump' under the label 'Enabled 
                    Characteristics' in the SERVER CHARACTERISTICS 
                    display."
                ::= { xSystem 6 }

            sysMaintenancePassword OBJECT-TYPE
                SYNTAX OCTET STRING (SIZE (0..8))
                ACCESS read-write
                STATUS mandatory
                DESCRIPTION
                    "The password a management system must supply to 
                    force the system to reboot or use the system's 
                    remote console via the Maintenance Operation 
                    Protocol (MOP).  Corresponds directly to SERVER 
                    MAINTENANCE PASSWORD.

                    When setting this value, the management system must 
                    supply eight octets, filling with zeros from the 
                    first octet.  That is, the value '1ab42' would be 
                    expressed as '0.0.0.0.0.1.ab.42'.  Setting the value 
                    to zero disables the password check.

                    When returning this value, the agent always returns 
                    a zero length OCTET STRING."
                ::= { xSystem 7 }

            sysLocalName OBJECT-TYPE
                SYNTAX DisplayString (SIZE (1..16))
                ACCESS read-write
                STATUS mandatory
                DESCRIPTION
                    "The system's local name.  Corresponds directly to 
                    SERVER NAME and the value labeled 'Name:' in the 
                    SERVER CHARACTERISTICS display."
                ::= { xSystem 8 }

            sysSoftwareVersionType OBJECT-TYPE
                SYNTAX INTEGER { alpha(1), beta(2),
                                 production(3), special(4) }
                ACCESS read-only
                STATUS mandatory
                DESCRIPTION
                    "The software version variant running in the system.  
                    Corresponds to the letter in the software version in 
                    the SERVER CHARACTERISTICS display.

                    alpha         'A':   alpha test
                    beta          'B':   beta test
                    production    null:  normal, production software
                    special       'S':   special, custom software
                    "
                ::= { xSystem 9 }

            sysSoftwareVersion OBJECT-TYPE
                SYNTAX OCTET STRING (SIZE (4))
                ACCESS read-only
                STATUS mandatory
                DESCRIPTION
                    "The software version running in the system.  In 
                    order, the octets contain major version, minor 
                    version, ECO, and pre-release number.  Corresponds 
                    to the numbers in the software version in the SERVER 
                    CHARACTERISTICS display.

                    For example, the version display for 
                    sysSoftwareVersionType 'production' and 
                    sysSoftwareVersion '2.2.0.0' is 'V2.2'.

                    The version display for sysSoftwareVersionType 
                    'beta' and sysSoftwareVersion '3.1.0.4' is 
                    'V3.1B4'."
                ::= { xSystem 10 }

            sysRomVersion OBJECT-TYPE
                SYNTAX INTEGER
                ACCESS read-only
                STATUS mandatory
                DESCRIPTION
                    "The firmware version of the bootstrap ROM installed 
                    in the system.  Corresponds directly to the value 
                    labeled 'Rom' in the SERVER CHARACTERISTICS 
                    display."
                ::= { xSystem 11 }

            sysHardwareType OBJECT-TYPE
                SYNTAX HardwareType
                ACCESS read-only
                STATUS mandatory
                DESCRIPTION
                    "The type of hardware on which the system is 
                    running.  Corresponds directly to the value labeled 
                    'Hardware Type:' in the UNIT display."
                ::= { xSystem 12 }

            sysHardwareVersion OBJECT-TYPE
                SYNTAX INTEGER
                ACCESS read-only
                STATUS mandatory
                DESCRIPTION
                    "This version of hardware on which the system is 
                    running.  Corresponds directly to part of the value 
                    labeled 'HW' in the SERVER CHARACTERISTICS 
                    display."
                ::= { xSystem 13 }

            sysChassisType OBJECT-TYPE
                SYNTAX ChassisType
                ACCESS read-only
                STATUS mandatory
                DESCRIPTION
                    "The type of chassis in which the system is running.  
                    Corresponds directly to part of the value labeled 
                    'HW' in the SERVER CHARACTERISTICS display."
                ::= { xSystem 14 }

            sysChassisVersion OBJECT-TYPE
                SYNTAX INTEGER
                ACCESS read-only
                STATUS mandatory
                DESCRIPTION
                    "This version of chassis in which the system is 
                    running.  Corresponds directly to part of the value 
                    labeled 'HW' in the SERVER CHARACTERISTICS 
                    display."
                ::= { xSystem 15 }

            sysCrash OBJECT-TYPE
                SYNTAX INTEGER { ready(1), execute(2) }
                ACCESS read-write
                STATUS mandatory
                DESCRIPTION
                    "Control to cause this system to crash.  In response 
                    to a get-request or get-next-request, the agent 
                    always returns 'ready' for this value.  Setting the 
                    value to 'ready' has no effect.  Setting it to 
                    'execute' causes an immediate crash.  Corresponds to 
                    the CRASH command."
            ::= { xSystem 16 }

            sysInitialize OBJECT-TYPE
                SYNTAX INTEGER { ready(1), conditionalExecute(2),
                                 unconditionalExecute(3), cancel(4) }
                ACCESS read-write
                STATUS mandatory
                DESCRIPTION
                    "Control to cause this system to reset its software 
                    to initial load values, typically by reloading.  
                    When executing an initialize command, the system 
                    observes the value of sysInitializeDelay as supplied 
                    anywhere in the same set request with sysInitialize. 
                     If this value is not included in the set request, 
                    the system uses its default value.

                    In response to a get-request or get-next-request, 
                    the agent always returns 'ready' for this value.  

                    Setting the value to 'ready' has no effect.  Setting 
                    it to 'conditionalExecute' causes initialization if 
                    the overall system state is acceptible (such as not 
                    needing to store permanent parameters).  Setting it 
                    to 'unconditionalExecute' causes initialization 
                    regardless of the overall system state.  Setting it 
                    to 'cancel' aborts an initialization that has not 
                    yet started.  According to standard SNMP operation, 
                    if the system is not in a proper state to accept a 
                    given set request for this value, it returns the 
                    standard SNMP error 'badValue'.

                    Corresponds to the INITIALIZE command."
                ::= { xSystem 17 }

            sysInitializeDelay OBJECT-TYPE
                SYNTAX INTEGER (0..32767)
                ACCESS read-write
                STATUS mandatory
                DESCRIPTION
                    "The number of minutes to delay before beginning the 
                    system initialization process as executed with 
                    sysInitialize.

                    This value cannot be set outside a set-request that 
                    contains the value 'execute' for sysInitialize.  If 
                    not included in such a set, the default value is 1.

                    Corresponds to the INITIALIZE command's DELAY 
                    parameter and to the value labeled 'Minutes to 
                    shutdown:' in the SYSTEM STATUS display."
                ::= { xSystem 18 }

            sysZeroAll OBJECT-TYPE
                SYNTAX INTEGER { ready(1), execute(2) }
                ACCESS read-write
                STATUS mandatory
                DESCRIPTION
                    "Control to zero all counters.  In response to a 
                    get-request or get-next-request, the agent always 
                    returns 'ready' for this value.  Setting the value 
                    to 'ready' has no effect.  Setting it to 'execute' 
                    causes all the system's counters to be zeroed.  
                    Corresponds to the ZERO ALL command."
                ::= { xSystem 19 }

            sysZeroBase OBJECT-TYPE
                SYNTAX INTEGER { ready(1), execute(2) }
                ACCESS read-write
                STATUS mandatory
                DESCRIPTION
                    "Control to zero all base counters.  In response to 
                    a get-request or get-next-request, the agent always 
                    returns 'ready' for this value.  Setting the value 
                    to 'ready' has no effect.  Setting it to 'execute' 
                    causes all the system's base counters to be zeroed.  
                    Examples of counters that are zeroed are the SNMP 
                    counters or the counters from the SYSTEM COUNTERS 
                    display.  Examples of counters that are not zeroed 
                    are Ethernet interface counters or port counters.  
                    Corresponds to the ZERO SYSTEM command."
                ::= { xSystem 20 }

            sysZeroBaseTime OBJECT-TYPE
                SYNTAX TimeTicks
                ACCESS read-only
                STATUS mandatory
                DESCRIPTION
                    "The number hundredths of a second since the most 
                    recent zeroing of the base counters, such as through 
                    execution of sysZeroAll or sysZeroBase.  Corresponds 
                    directly to the value labeled 'Seconds Since 
                    Zeroed:' in the SERVER COUNTERS display."
                ::= { xSystem 21 }

            sysLoaderName OBJECT-TYPE
                SYNTAX DisplayString (SIZE (0..40))
                ACCESS read-only
                STATUS mandatory
                DESCRIPTION
                    "The name of the system that provided this system's 
                    running software.  Corresponds directly to the value 
                    labeled 'Primary Host:' in the SERVER STATUS 
                    display."
                ::= { xSystem 22 }

            sysLoaderAddressType OBJECT-TYPE
                SYNTAX AddressType
                ACCESS read-only
                STATUS mandatory
                DESCRIPTION
                    "The type of network address contained in 
                    sysLoaderAddress.  'unknown' means no address has 
                    been defined.  'other' means no other type value 
                    applies.  'local' means there is no address and this 
                    system's software was loaded from local storage.  
                    'ip' is an Internet IP address.  'ethernet' is an 
                    802.3 MAC address.  Corresponds indirectly to the 
                    value labeled 'Load Address:' in the SERVER STATUS 
                    display."
                ::= { xSystem 23 }

            sysLoaderAddress OBJECT-TYPE
                SYNTAX OCTET STRING
                ACCESS read-only
                STATUS mandatory
                DESCRIPTION
                    "The network address of the system that provided 
                    this system's running software.  Corresponds 
                    directly to the value labeled 'Load Address:' in the 
                    SERVER STATUS display."
                ::= { xSystem 24 }

            sysDumperAddressType OBJECT-TYPE
                SYNTAX AddressType
                ACCESS read-only
                STATUS mandatory
                DESCRIPTION
                    "The type of network address contained in 
                    sysDumperAddress.  'unknown' means no address has 
                    been defined.  'other' means no other type value 
                    applies.  'local' means there is no address and this 
                    system's was dumped to local storage.  'ip' is an 
                    Internet IP address.  'ethernet' is an 802.3 MAC 
                    address.  Corresponds indirectly to the value 
                    labeled 'Dump Address:' in the SERVER STATUS 
                    display."
                ::= { xSystem 25 }

            sysDumperAddress OBJECT-TYPE
                SYNTAX OCTET STRING
                ACCESS read-only
                STATUS mandatory
                DESCRIPTION
                    "The network address of the system that most 
                    recently accepted a crash dump from this system.  
                    Corresponds directly to the value labeled 'Dump 
                    Address:' in the SERVER STATUS display."
                ::= { xSystem 26 }

            sysResourceLacks OBJECT-TYPE
                SYNTAX Counter
                ACCESS read-only
                STATUS mandatory
                DESCRIPTION
                    "The number of times a local resource allocation 
                    failed, for example due to lack of dynamic memory.  
                    Corresponds directly to the value labeled 'Resource 
                    Errors:' in the SERVER STATUS display."
                ::= { xSystem 27 }

            sysChassisState OBJECT-TYPE
                SYNTAX INTEGER { notApplicable(1), noFault(2), fault(3),
                                 loop(4) }
                ACCESS read-only
                STATUS mandatory
                DESCRIPTION
                    "For chassis-based systems, the state of the overall 
                    chassis.  'notApplicable' indicates the system is 
                    not chassis based.  'noFault' indicates no current 
                    chassis problem.  'fault' indicates a current 
                    chassis problem such as a card or power supply 
                    failure.  Corresponds directly to the value labeled 
                    'Crate Current State: in the SERVER ALTERNATE STATUS 
                    display."
                ::= { xSystem 28 }

            sysChassisFaultTransitions OBJECT-TYPE
                SYNTAX Counter
                ACCESS read-only
                STATUS mandatory
                DESCRIPTION
                    "The number of times this system has seen 
                    sysChassisState switch from 'noFault' to 'fault' or 
                    from 'fault' to 'noFault'.  Corresponds directly to 
                    the value labeled 'Crate Transition Count: in the 
                    SERVER ALTERNATE STATUS display."
                ::= { xSystem 29 }

            sysResourceNumber OBJECT-TYPE
                SYNTAX INTEGER
                ACCESS read-only
                STATUS mandatory
                DESCRIPTION
                    "The number of resource entries in the Resource 
                    table."
                ::= { xSystem 30 }

            sysFeatureNumber OBJECT-TYPE
                SYNTAX INTEGER
                ACCESS read-only
                STATUS mandatory
                DESCRIPTION
                    "The number of feature entries in the Feature 
                    table."
                ::= { xSystem 31 }

            -- more base objects following tables


            -- the Resource table

            resTable OBJECT-TYPE
                SYNTAX SEQUENCE OF ResEntry
                ACCESS not-accessible
                STATUS mandatory
                DESCRIPTION
                    "A list of resource entries.  The number of entries 
                    is given by the value of sysResourceNumber."
                ::= { xSystem 32 }

            resEntry OBJECT-TYPE
                SYNTAX ResEntry
                ACCESS not-accessible
                STATUS mandatory
                DESCRIPTION
                    "Status values for a system resource."
                INDEX { resType }
                ::= { resTable 1 }

            ResEntry ::=
                SEQUENCE {
                    resType
                        INTEGER,
                    resCurrent
                        Gauge,
                    resWorst
                        Gauge,
                    resAdminMaximum
                        INTEGER,
                    resLacks
                        Counter,
                    resLackTime
                        DateTime,
                    resOperMaximum
                        INTEGER
                }

            resType OBJECT-TYPE
                SYNTAX INTEGER { cpuPercent(1), memoryPercent(2),
                                 process(3), timer(4), packetBuffer(5),
                                 ipcMessage(6), textPool(7),
                                 freeMemory(8), globalMemoryPercent(9),
                                 phivDecnetRouteCache(10),
                                 ipFilterCache(11), ipRouteCache(12),
                                 ipxRouteCache(13), ipPolicyTable(14),
                                 ipFilterTable(15),
                                 phivDecnetPolicyTable(16),
                                 phivDecnetFilterTable(17),
                                 appleRouteCache(18),
                                 appleFilterTable(19),
                                 repeaterPortAccessTable(20),
                                 repeaterPortNameTable(21),
                                 ipxRipTable(22), ipxSapTable(23),
                                 repeaterPortSecurityTable(24),
                                 bridgeFilterTable(25),
                                 bridgeStaticFilters(26),
                                 bridgeSourceFilters(27),
                                 bridgeLearnedFilters(28),
                                 bridgeInactiveFilters(29),
                                 bridgeProtocolFilters(30),
                                 latAnnouncementCompressionTable(31),
                                 packetCompressionTable(32),
                                 ipFragmentTable(33),
                                 repeaterRedundancyTable(34),
                                 repeaterGlobalSecurityTable(35),
				 packetHeaders(36), interfaces(37),
				 circuits(38), ipIgmpTable(39),
				 ipMulticastTable(40), ipRouteTable(41),
				 ipxRipFilterTable(42), ipxSapFilterTable(43)
                               }
                ACCESS read-only
                STATUS mandatory
                DESCRIPTION
                    "Identification of a resource type.  Typically 
                    corresponds directly to a label such as 'Processes:' 
                    in the SERVER ALTERNATE STATUS display."
                ::= { resEntry 1 }

            resCurrent OBJECT-TYPE
                SYNTAX Gauge
                ACCESS read-only
                STATUS mandatory
                DESCRIPTION
                    "The number of resources currently in use on the 
                    system.  Typically corresponds directly to a value 
                    labeled 'Cur' in the SERVER ALTERNATE STATUS 
                    display."
                ::= { resEntry 2 }

            resWorst OBJECT-TYPE
                SYNTAX Gauge
                ACCESS read-only
                STATUS mandatory
                DESCRIPTION
                    "The highest or lowest value of resCurrent since 
                    system initialization.  Typically corresponds 
                    directly to a value labeled 'High' or 'Low' in the 
                    SERVER ALTERNATE STATUS display."
                ::= { resEntry 3 }

            resAdminMaximum OBJECT-TYPE
                SYNTAX INTEGER
                ACCESS read-write
                STATUS mandatory
                DESCRIPTION
                    "The desired maximum possible number of resources in 
                    the system.  In many cases, ACCESS to this object 
                    for a particular resType is read-only.  Typically 
                    corresponds directly to a value labeled 'Max' in the 
                    SERVER ALTERNATE STATUS display for desired, 
                    administrative values.  When the desired change 
                    takes effect is implementation specific, ranging 
                    from immediately to the next system initialization."
                ::= { resEntry 4 }

            resLacks OBJECT-TYPE
                SYNTAX Counter
                ACCESS read-only
                STATUS mandatory
                DESCRIPTION
                    "The number of times since system initialization 
                    that the system could not obtain the resource 
                    because none were available.  Typically corresponds 
                    directly to a value labeled 'Failure' in the SERVER 
                    ALTERNATE STATUS display.

                    If such failures do not apply to the particular 
                    resource, such as 'cpuPercent', the agent returns 
                    zero for this object."
                ::= { resEntry 5 }

            resLackTime OBJECT-TYPE
                SYNTAX DateTime
                ACCESS read-only
                STATUS mandatory
                DESCRIPTION
                    "The local system date and time when resLack last 
                    increased.  Typically corresponds directly to a 
                    value labeled 'Last Occurred' in the SERVER 
                    ALTERNATE STATUS display.

                    If such failures do not apply to the particular 
                    resource, such as 'cpuPercent', the agent returns 
                    all zeroes (unknown) for this object."
            ::= { resEntry 6 }

            resOperMaximum OBJECT-TYPE
                SYNTAX INTEGER
                ACCESS read-only
                STATUS mandatory
                DESCRIPTION
                    "The current maximum possible number of resources in 
                    the system.  Typically corresponds directly to a 
                    value labeled 'Max' in the SERVER ALTERNATE STATUS 
                    display for current operational values.  This value 
                    is based on current or previous value of 
                    resAdminMaximum."
                ::= { resEntry 7 }


            -- the Feature table

            featTable OBJECT-TYPE
                SYNTAX SEQUENCE OF FeatEntry
                ACCESS not-accessible
                STATUS mandatory
                DESCRIPTION
                    "A list of feature entries.  The number of entries 
                    is given by the value of sysFeatureNumber."
                ::= { xSystem 33 }

            featEntry OBJECT-TYPE
                SYNTAX FeatEntry
                ACCESS not-accessible
                STATUS mandatory
                DESCRIPTION
                    "Status values for a system feature."
                INDEX { featType }
                ::= { featTable 1 }

            FeatEntry ::=
                SEQUENCE {
                    featType
                        INTEGER,
                    featStatus
                        INTEGER,
                    featKey
                        DisplayString
                }

            featType OBJECT-TYPE
                SYNTAX INTEGER { help(1), snmp(2), xremote(3),
                                 tn3270(4), menu(5), multisessions(6),
                                 lat(7), eventLog(8),
                                 internetSecurity(9), slip(10),
                                 scriptServer(11), kerberos(12),
                                 telnet(13), rlogin(14), allPorts(15),
                                 xprinter(16), x25(17),
                                 frameRelay(18),
                                 ipMulticastSpecial(19),
                                 changeEthernetAddress(20),
                                 expanded800(21), lpDaemon(22),
                                 ppp(23), unixCommands(24),
                                 arap(25), fingerDaemon(26),
                                 routeDaemon(27), rwhoDaemon(28),
                                 securID(29), apd(30), ipxRouting(31),
                		 ipxFiltering(32), ipFiltering(33), 
                                 kerberos5(34), radius(35), 
                                 enviromentalManager(36), terminalServer(37),
                                 ssh(38), tl1(39) }
                ACCESS read-only
                STATUS mandatory
                DESCRIPTION
                    "Identification of a feature type.  Corresponds to a 
                    SERVER feature keyword."
                ::= { featEntry 1 }

            featStatus OBJECT-TYPE
                SYNTAX INTEGER { disabled(1), enabled(2), locked(3) }
                ACCESS read-write
                STATUS mandatory
                DESCRIPTION
                    "The status of the feature as of the next system 
                    initialization.  Corresponds to the presence of the 
                    feature's lable following the label 'Enabled 
                    Feature(s): in the UNIT display."
                ::= { featEntry 2 }

            featKey OBJECT-TYPE
                SYNTAX DisplayString (SIZE (8))
                ACCESS read-write
                STATUS mandatory
                DESCRIPTION
                    "The key a management system must supply to make a 
                    locked feature available.  When unlocking a feature 
                    and the management system does not supply a value 
                    for featStatus, that object's value is 
                    implementation dependent.

                    When returning this value, the agent always returns 
                    a zero length DisplayString."
                ::= { featEntry 3 }


            -- the Boot Control group

            -- The Boot Control group contains parameters to control
            -- how a system loads and dumps its runtime software and
            -- parameters.  Typically these parameters are kept for
            -- and used by system initialization firmware.

            -- This group is deprecated in favor of the Boot Control
            -- Record table, found later in this MIB.

            xBootControl OBJECT IDENTIFIER ::= { xSystem 34 }

            bootControlLoadInternetFile OBJECT-TYPE
                SYNTAX DisplayString (SIZE (0..64))
                ACCESS read-write
                STATUS deprecated
                DESCRIPTION
                    "The filename to request when loading an image via 
                    TFTP.  Corresponds directly to SERVER INTERNET LOAD 
                    FILE and the value labeled 'Internet Load File:' in 
                    the SERVER BOOT CHARACTERISTICS display."
                ::= { xBootControl 1 }

            bootControlLoadInternetServer OBJECT-TYPE
                SYNTAX IpAddress
                ACCESS read-write
                STATUS deprecated
                DESCRIPTION
                    "The internet address of the server to use when 
                    loading an image via TFTP.  Corresponds directly to 
                    SERVER INTERNET LOAD HOST and the value labeled 
                    'Internet Load Host:' in the SERVER BOOT 
                    CHARACTERISTICS display."
                ::= { xBootControl 2 }

            bootControlLoadInternetGateway OBJECT-TYPE
                SYNTAX IpAddress
                ACCESS read-write
                STATUS deprecated
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { xBootControl 3 }

            bootControlLoadBootpTftp OBJECT-TYPE
                SYNTAX INTEGER { disabled(1), enabled(2) }
                ACCESS read-write
                STATUS deprecated
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { xBootControl 4 }

            bootControlLoadTftpDirect OBJECT-TYPE
                SYNTAX INTEGER { disabled(1), enabled(2) }
                ACCESS read-write
                STATUS deprecated
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { xBootControl 5 }

            bootControlLoadLocal OBJECT-TYPE
                SYNTAX INTEGER { disabled(1), enabled(2) }
                ACCESS read-write
                STATUS deprecated
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { xBootControl 6 }

            bootControlLoadMop OBJECT-TYPE
                SYNTAX INTEGER { disabled(1), enabled(2) }
                ACCESS read-write
                STATUS deprecated
                DESCRIPTION
                    "Control for loading via DEC MOP.  Corresponds to 
                    SERVER LOAD PROTOCOL MOP and the presence of 'MOP' 
                    following the label 'Load Protocols Enabled:' in the 
                    SERVER BOOT CHARACTERISTICS display."
                ::= { xBootControl 7 }

            bootControlLoadProprietary OBJECT-TYPE
                SYNTAX INTEGER { disabled(1), enabled(2) }
                ACCESS read-write
                STATUS deprecated
                DESCRIPTION
                    "Control for loading via MRV In-Reach-proprietary extended 
                    MOP.  Corresponds to SERVER LOAD PROTOCOL 
                    PROPRIETARY and the presence of 'Proprietary' 
                    following the label 'Load Protocols Enabled:' in the 
                    SERVER BOOT CHARACTERISTICS display."
                ::= { xBootControl 8 }

            bootControlLoadRarpTftp OBJECT-TYPE
                SYNTAX INTEGER { disabled(1), enabled(2) }
                ACCESS read-write
                STATUS deprecated
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { xBootControl 9 }

            bootControlDumpBootpTftp OBJECT-TYPE
                SYNTAX INTEGER { disabled(1), enabled(2) }
                ACCESS read-write
                STATUS deprecated
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { xBootControl 10 }

            bootControlDumpLocal OBJECT-TYPE
                SYNTAX INTEGER { disabled(1), enabled(2) }
                ACCESS read-write
                STATUS deprecated
                DESCRIPTION
                    "Control for dumping to a local medium.  Corresponds 
                    to SERVER DUMP PROTOCOL LOCAL and the presence of 
                    'Local' following the label 'Dump Protocols 
                    Enabled:' in the SERVER BOOT CHARACTERISTICS 
                    display."
                ::= { xBootControl 11 }

            bootControlDumpMop OBJECT-TYPE
                SYNTAX INTEGER { disabled(1), enabled(2) }
                ACCESS read-write
                STATUS deprecated
                DESCRIPTION
                    "Control for dumping via DEC MOP.  Corresponds to 
                    SERVER DUMP PROTOCOL MOP and the presence of 'MOP' 
                    following the label 'Dump Protocols Enabled:' in the 
                    SERVER BOOT CHARACTERISTICS display."
                ::= { xBootControl 12 }

            bootControlDumpProprietary OBJECT-TYPE
                SYNTAX INTEGER { disabled(1), enabled(2) }
                ACCESS read-write
                STATUS deprecated
                DESCRIPTION
                    "Control for dumping via MRV In-Reach-proprietary extended 
                    MOP.  Corresponds to SERVER DUMP PROTOCOL 
                    PROPRIETARY and the presence of 'Proprietary' 
                    following the label 'Dump Protocols Enabled:' in the 
                    SERVER BOOT CHARACTERISTICS display."
                ::= { xBootControl 13 }

            bootControlDumpRarpTftp OBJECT-TYPE
                SYNTAX INTEGER { disabled(1), enabled(2) }
                ACCESS read-write
                STATUS deprecated
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { xBootControl 14 }

            bootControlParamBootpTftp OBJECT-TYPE
                SYNTAX INTEGER { disabled(1), enabled(2) }
                ACCESS read-write
                STATUS deprecated
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { xBootControl 15 }

            bootControlParamLocal OBJECT-TYPE
                SYNTAX INTEGER { disabled(1), enabled(2) }
                ACCESS read-write
                STATUS deprecated
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { xBootControl 16 }

            bootControlParamMop OBJECT-TYPE
                SYNTAX INTEGER { disabled(1), enabled(2) }
                ACCESS read-write
                STATUS deprecated
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { xBootControl 17 }

            bootControlParamProprietary OBJECT-TYPE
                SYNTAX INTEGER { disabled(1), enabled(2) }
                ACCESS read-write
                STATUS deprecated
                DESCRIPTION
                    "Control for loading parameters via 
                    MRV In-Reach-proprietary extended MOP.  Corresponds to 
                    SERVER PARAMETER PROTOCOL PROPRIETARY and the 
                    presence of 'Proprietary' following the label 
                    'Parameter Protocols Enabled:' in the SERVER BOOT 
                    CHARACTERISTICS display."
                ::= { xBootControl 18 }

            bootControlParamRarpTftp OBJECT-TYPE
                SYNTAX INTEGER { disabled(1), enabled(2) }
                ACCESS read-write
                STATUS deprecated
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { xBootControl 19 }


            -- the System group, basic parameters continued

            sysInstalledMemory OBJECT-TYPE
                SYNTAX Gauge
                ACCESS read-only
                STATUS mandatory
                DESCRIPTION
                    "The total number of bytes of main memory installed 
                    in the system.  Corresponds directly to the value 
                    labeled 'Installed' on the SERVER ALTERNATE STATUS 
                    display.  A value of 0 indicates standard memory for 
                    the particular hardware."
                ::= { xSystem 35 }

            sysTemperatureLevel OBJECT-TYPE
                SYNTAX INTEGER { unknown(1), normal(2), high(3) }
                ACCESS read-only
                STATUS mandatory
                DESCRIPTION
                    "The temperature level of the system.  'unknown' 
                    indicates the system does not support a temperature 
                    sensor.  'normal' indicates a normal temperature 
                    level.  'high' indicates an excessive temperature 
                    level.  Corresponds directly to the value labeled 
                    'Temperature Level:' in the SERVER ALTERNATE STATUS 
                    display."
                ::= { xSystem 36 }

            -- basic parameters continue after boot record table


            -- the Boot Control Record table

            -- The Boot Control Record table contains parameters to
            -- control how a system loads and dumps its runtime
            -- software and parameters.  Typically these parameters
            -- are kept for and used by system initialization firmware.

            -- This table is mandatory for systems that offer runtime
            -- control of these parameters, and empty in systems
            -- that do not.

            bootRecordTable OBJECT-TYPE
                SYNTAX SEQUENCE OF BootRecordEntry
                ACCESS not-accessible
                STATUS mandatory
                DESCRIPTION
                    "A list of boot control records."
                ::= { xSystem 37 }

            bootRecordEntry OBJECT-TYPE
                SYNTAX BootRecordEntry
                ACCESS not-accessible
                 STATUS mandatory
                DESCRIPTION
                    "Values for a boot record."
                INDEX { bootRecordIndex }
                ::= { bootRecordTable 1 }

            BootRecordEntry ::=
                SEQUENCE {
                    bootRecordIndex
                        INTEGER,
                    bootRecordLoadInternetFile
                        DisplayString,
                    bootRecordLoadInternetServer
                        IpAddress,
                    bootRecordLoadInternetGateway
                        IpAddress,
                    bootRecordLoadBootpTftp
                        INTEGER,
                    bootRecordLoadTftpDirect
                        INTEGER,
                    bootRecordLoadLocal
                        INTEGER,
                    bootRecordLoadMop
                        INTEGER,
                    bootRecordLoadProprietary
                        INTEGER,
                    bootRecordLoadRarpTftp
                        INTEGER,
                    bootRecordDumpBootpTftp
                        INTEGER,
                    bootRecordDumpLocal
                        INTEGER,
                    bootRecordDumpMop
                        INTEGER,
                    bootRecordDumpProprietary
                        INTEGER,
                    bootRecordDumpRarpTftp
                        INTEGER,
                    bootRecordParamBootpTftp
                        INTEGER,
                    bootRecordParamLocal
                        INTEGER,
                    bootRecordParamMop
                        INTEGER,
                    bootRecordParamProprietary
                        INTEGER,
                    bootRecordParamRarpTftp
                        INTEGER,
                    bootRecordStatus
                        INTEGER,
                    bootRecordMopFile
                        DisplayString,
                    bootRecordInternetAddress
                        IpAddress,
                    bootRecordParamTftpDirect
                        INTEGER,
                    bootRecordInternetDelimiter 
                        DisplayString 
                }

            bootRecordIndex OBJECT-TYPE
                SYNTAX INTEGER
                ACCESS read-only
                STATUS mandatory
                DESCRIPTION
                    "An index value that uniquely identifies a boot 
                    control record entry, from 1 to the number of 
                    entries for the system."
                ::= { bootRecordEntry 1 }

            bootRecordLoadInternetFile OBJECT-TYPE
                SYNTAX DisplayString (SIZE (0..64))
                ACCESS read-write
                STATUS mandatory
                DESCRIPTION
                    "The filename to request when loading an image via 
                    TFTP.  Corresponds directly to SERVER INTERNET LOAD 
                    FILE and the value labeled 'Internet Load File:' in 
                    the SERVER BOOT CHARACTERISTICS display."
                ::= { bootRecordEntry 2 }

            bootRecordLoadInternetServer OBJECT-TYPE
                SYNTAX IpAddress
                ACCESS read-write
                STATUS mandatory
                DESCRIPTION
                    "The internet address of the server to use when 
                    loading an image via TFTP.  Corresponds directly to 
                    SERVER INTERNET LOAD HOST and the value labeled 
                    'Internet Load Host:' in the SERVER BOOT 
                    CHARACTERISTICS display."
                ::= { bootRecordEntry 3 }

            bootRecordLoadInternetGateway OBJECT-TYPE
                SYNTAX IpAddress
                ACCESS read-write
                STATUS mandatory
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { bootRecordEntry 4 }

            bootRecordLoadBootpTftp OBJECT-TYPE
                SYNTAX INTEGER { disabled(1), enabled(2) }
                ACCESS read-write
                STATUS mandatory
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { bootRecordEntry 5 }

            bootRecordLoadTftpDirect OBJECT-TYPE
                SYNTAX INTEGER { disabled(1), enabled(2) }
                ACCESS read-write
                STATUS mandatory
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { bootRecordEntry 6 }

            bootRecordLoadLocal OBJECT-TYPE
                SYNTAX INTEGER { disabled(1), enabled(2) }
                ACCESS read-write
                STATUS mandatory
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { bootRecordEntry 7 }

            bootRecordLoadMop OBJECT-TYPE
                SYNTAX INTEGER { disabled(1), enabled(2) }
                ACCESS read-write
                STATUS mandatory
                DESCRIPTION
                    "Control for loading via DEC MOP.  Corresponds to 
                    SERVER LOAD PROTOCOL MOP and the presence of 'MOP' 
                    following the label 'Load Protocols Enabled:' in the 
                    SERVER BOOT CHARACTERISTICS display."
                ::= { bootRecordEntry 8 }

            bootRecordLoadProprietary OBJECT-TYPE
                SYNTAX INTEGER { disabled(1), enabled(2) }
                ACCESS read-write
                STATUS mandatory
                DESCRIPTION
                    "Control for loading via MRV In-Reach-proprietary extended 
                    MOP.  Corresponds to SERVER LOAD PROTOCOL 
                    PROPRIETARY and the presence of 'Proprietary' 
                    following the label 'Load Protocols Enabled:' in the 
                    SERVER BOOT CHARACTERISTICS display."
                ::= { bootRecordEntry 9 }

            bootRecordLoadRarpTftp OBJECT-TYPE
                SYNTAX INTEGER { disabled(1), enabled(2) }
                ACCESS read-write
                STATUS mandatory
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { bootRecordEntry 10 }

            bootRecordDumpBootpTftp OBJECT-TYPE
                SYNTAX INTEGER { disabled(1), enabled(2) }
                ACCESS read-write
                STATUS mandatory
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { bootRecordEntry 11 }

            bootRecordDumpLocal OBJECT-TYPE
                SYNTAX INTEGER { disabled(1), enabled(2) }
                ACCESS read-write
                STATUS mandatory
                DESCRIPTION
                    "Control for dumping to a local medium.  Corresponds 
                    to SERVER DUMP PROTOCOL LOCAL and the presence of 
                    'Local' following the label 'Dump Protocols 
                    Enabled:' in the SERVER BOOT CHARACTERISTICS 
                    display."
                ::= { bootRecordEntry 12 }

            bootRecordDumpMop OBJECT-TYPE
                SYNTAX INTEGER { disabled(1), enabled(2) }
                ACCESS read-write
                STATUS mandatory
                DESCRIPTION
                    "Control for dumping via DEC MOP.  Corresponds to 
                    SERVER DUMP PROTOCOL MOP and the presence of 'MOP' 
                    following the label 'Dump Protocols Enabled:' in the 
                    SERVER BOOT CHARACTERISTICS display."
                ::= { bootRecordEntry 13 }

            bootRecordDumpProprietary OBJECT-TYPE
                SYNTAX INTEGER { disabled(1), enabled(2) }
                ACCESS read-write
                STATUS mandatory
                DESCRIPTION
                    "Control for dumping via MRV In-Reach-proprietary extended 
                    MOP.  Corresponds to SERVER DUMP PROTOCOL 
                    PROPRIETARY and the presence of 'Proprietary' 
                    following the label 'Dump Protocols Enabled:' in the 
                    SERVER BOOT CHARACTERISTICS display."
                ::= { bootRecordEntry 14 }

            bootRecordDumpRarpTftp OBJECT-TYPE
                SYNTAX INTEGER { disabled(1), enabled(2) }
                ACCESS read-write
                STATUS mandatory
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { bootRecordEntry 15 }

            bootRecordParamBootpTftp OBJECT-TYPE
                SYNTAX INTEGER { disabled(1), enabled(2) }
                ACCESS read-write
                STATUS mandatory
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { bootRecordEntry 16 }

            bootRecordParamLocal OBJECT-TYPE
                SYNTAX INTEGER { disabled(1), enabled(2) }
                ACCESS read-write
                STATUS mandatory
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { bootRecordEntry 17 }

            bootRecordParamMop OBJECT-TYPE
                SYNTAX INTEGER { disabled(1), enabled(2) }
                ACCESS read-write
                STATUS mandatory
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { bootRecordEntry 18 }

            bootRecordParamProprietary OBJECT-TYPE
                SYNTAX INTEGER { disabled(1), enabled(2) }
                ACCESS read-write
                STATUS mandatory
                DESCRIPTION
                    "Control for loading parameters via 
                    MRV In-Reach proprietary extended MOP.  Corresponds to 
                    SERVER PARAMETER PROTOCOL PROPRIETARY and the 
                    presence of 'Proprietary' following the label 
                    'Parameter Protocols Enabled:' in the SERVER BOOT 
                    CHARACTERISTICS display."
                ::= { bootRecordEntry 19 }

            bootRecordParamRarpTftp OBJECT-TYPE
                SYNTAX INTEGER { disabled(1), enabled(2) }
                ACCESS read-write
                STATUS mandatory
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { bootRecordEntry 20 }

            bootRecordStatus OBJECT-TYPE
                SYNTAX INTEGER { disabled(1), enabled(2) }
                ACCESS read-write
                STATUS mandatory
                DESCRIPTION
               "The status of the entry.  Set to 'disabled' to
               disable the entry."
                ::= { bootRecordEntry 21 }

            bootRecordMopFile OBJECT-TYPE
                SYNTAX DisplayString (SIZE (0..15))
                ACCESS read-write
                STATUS mandatory
                DESCRIPTION
                    "The software file name to request for down-line 
                    load of the server via MOP or XMOP."
                ::= { bootRecordEntry 22 }

            bootRecordInternetAddress OBJECT-TYPE
                SYNTAX IpAddress
                ACCESS read-write
                STATUS mandatory
                DESCRIPTION
                    "The internet address of the system is to use for 
                    itself when loading via TFTP.  The value 0.0.0.0 
                    indicates default action."
                ::= { bootRecordEntry 23 }

            bootRecordParamTftpDirect OBJECT-TYPE
                SYNTAX INTEGER { disabled(1), enabled(2) }
                ACCESS read-write
                STATUS mandatory
                DESCRIPTION
                    "Control for loading parameters via the protocol
                    DTFTP.  Corresponds to SERVER PARAMETER 
                    PROTOCOL DTFTP and the presence of 'DTFTP' 
                    following the label 'Parameter Protocols Enabled:' 
                    in the SERVER BOOT CHARACTERISTICS display."
                ::= { bootRecordEntry 24 }

            bootRecordInternetDelimiter OBJECT-TYPE 
                SYNTAX DisplayString (SIZE (0..1)) 
                ACCESS read-write 
                STATUS mandatory
                DESCRIPTION 
                    "The character separating the load file directory name
                    from the file name." 
                DEFVAL { '00'h }  -- the null string
                ::= { bootRecordEntry 25 }



            -- the System group, basic parameters continued

            sysLastAgentError OBJECT-TYPE
                SYNTAX INTEGER { noError(1), tooBig(2), noSuchName(3),
                                 badValue(4), readOnly(5), genErr(6),
                                 badCommunity(7), badVersion(8), badType(9),
                                 badClient(10) }
                ACCESS read-only
                STATUS mandatory
                DESCRIPTION
                    "The most recent error the agent encountered in 
                    attempting to satisfy an SNMP request.  Reading this 
                    value has the side effect of resetting it to 
                    'noError'."
                ::= { xSystem 38 }

             sysRcpMulticast OBJECT-TYPE
                SYNTAX INTEGER { disabled(1), enabled(2) }
                ACCESS read-write
                STATUS mandatory
                DESCRIPTION
                    "Control for sending of the MOP RCP system identifier
                    message.  Corresponds directly to the presence of 'RCP
                    Multicast' under the label 'Enabled Characteristics'
                    in the SERVER CHARACTERISTICS display."
                ::= { xSystem 40 }

            sysTimeServerAddress OBJECT-TYPE
                SYNTAX TypedAddress
                ACCESS read-only 
                STATUS mandatory 
                DESCRIPTION 
                    "The address of the time server, either an
                     IpAddr or an ethernet address."
                ::= { xSystem 41 }

            sysTimeServerConfiguredAddress OBJECT-TYPE
                SYNTAX TypedAddress
                ACCESS read-write
                STATUS mandatory
                DESCRIPTION
                      "The address of a configured time server (, either an
                          IpAddr or an ethernet address)."
                ::= { xSystem 46 }

            sysTimeServerConfiguredStatus OBJECT-TYPE
                SYNTAX INTEGER { disabled(1), enabled(2), required(3) }
                ACCESS read-write
                STATUS mandatory
                DESCRIPTION
                   "Control whether the sysTimeServerConfiguredAddress is
                    the only time server used to obtain the time (REQUIRED),
                    the first time server used to obtain the time (ENABLED),
                    or not used to obtain the time (DISABLED)."
                DEFVAL { disabled }
                ::= { xSystem 47 }
                 
            sysBootRecordOverrideDefinedAddress OBJECT-TYPE
                SYNTAX INTEGER { enabled(1), disabled(2) }
                ACCESS read-write
                STATUS mandatory
                DESCRIPTION
                   "Control to override the internally defined Internet address
                    with that obtained from the bootp loading protocol."
                DEFVAL { disabled  }
                ::= { xSystem 48 }

            sysBootRecordMessageEnable OBJECT-TYPE
                SYNTAX INTEGER { enabled(1), disabled(2) }
                ACCESS read-write
                STATUS mandatory
                DESCRIPTION
                    "Control to display load status messages during reboot.
                     Corresponds directly to the value labeled 'Status Message:'
                     in the SERVER LOADDUMP display."
                DEFVAL { enabled }
                ::= { xSystem 49 }
 
            sysBootRecordParamDefaults OBJECT-TYPE
                SYNTAX INTEGER { enabled(1), disabled(2) }
                ACCESS read-write
                STATUS mandatory
                DESCRIPTION
                    "Control to use default parameters upon the next reboot
                     after which time this control reverts to disabled. This
                     control only applies to stand-alone devices. Corresponds 
                     directly to the value labeled 'Default Parameters:'
                     in the SERVER LOADDUMP display."
                DEFVAL { disabled  }
                ::= { xSystem 50 }
 
            sysLoginAuthFailureTrapType OBJECT-TYPE
                SYNTAX INTEGER { none(1), loginPassword(2), pap(3),
                                 chap(4), kerberos(5), securId(6),
                                 radius(7), privilegedPassword(8),
                                 limitedPrivilegedPassword(9) }
                ACCESS read-only
                STATUS mandatory
                DESCRIPTION 
                    "Indicates the type of authentication failure which last
                     occurred."   
                
                ::= { xSystem 78 }

             sysLoginAuthTrapIdentity OBJECT-TYPE
                SYNTAX DisplayString (SIZE (0..16))
                ACCESS read-only
                STATUS mandatory
                DESCRIPTION
                    "An identification string for the circuit or port where an
                     authentication failure last occurred."
                ::= { xSystem 81 }

            sysLocalScriptServer OBJECT-TYPE
                SYNTAX INTEGER { disabled(1), enabled(2) }
                ACCESS read-write
                STATUS mandatory
                DESCRIPTION
                    "Control to allow script serving for this system
                     from a script residing in a local flash card."
                DEFVAL { enabled }
                ::= { xSystem 82 }

            sysInReachManagementSecurityStatus OBJECT-TYPE
                SYNTAX INTEGER { disabled(1), enabled(2) }
                ACCESS read-only
                STATUS mandatory
                DESCRIPTION
                    "Indicates whether per port authentication is in use. This
                     includes username, password, privilege level, and list of
                     power outlets controlled by that user, or console
                     connections allowed from that port."
                DEFVAL { disabled }
                ::= { xSystem 83 }

            sysProductName OBJECT-TYPE
                SYNTAX DisplayString
                ACCESS read-only
                STATUS mandatory
                DESCRIPTION
                    "Displays the product name of this system."
                ::= { xSystem 84 }

            sysModemPresent OBJECT-TYPE
                SYNTAX INTEGER { noModem(1), modem(2) }
                ACCESS read-only
                STATUS mandatory
                DESCRIPTION
                    "Indicates whether this system has a built-in 
                     modem."
                ::= { xSystem 85 }

            sysCauseAction  OBJECT-TYPE
                SYNTAX INTEGER { disabled(1), enabled(2) }
                ACCESS read-write
                STATUS mandatory
                DESCRIPTION
                    "A control for toggling the cause action feature.
                     Corresponds directly to the presence of 'Trigger/Action' 
                     under the label 'Enabled Characteristics:' in the SERVER
                     CHARACTERISTICS display. The desired change will not take
                     effect until the next system initialization."
                DEFVAL { disabled }
                ::= { xSystem 86 }                

            sysWebServerConfigAdminStatus  OBJECT-TYPE
                SYNTAX INTEGER { disabled(1), enabled(2) }
                ACCESS read-write
                STATUS mandatory
                DESCRIPTION
                    "A control for bring the web server up or down.
                     Corresponds directly to the presence of 'Web Server'
                     under the label 'Enabled Characteristics:' in the SERVER
                     CHARACTERISTICS display."
                DEFVAL { enabled }
                ::= { xSystem 87 }                

 	sysTl1SourceIdentifier OBJECT-TYPE
		SYNTAX DisplayString (SIZE (0..20))
		ACCESS read-write
		STATUS mandatory
		DESCRIPTION
		    "The source identifier (SID) is the server name used by
                     TL1 to identify the server."
		::= { xSystem 88 }

        sysInitializeDelayParameter OBJECT-TYPE
                SYNTAX INTEGER { ready(1), execute(2) }
                ACCESS read-write
                STATUS mandatory
                DESCRIPTION
                    "Control to begin the system initialization process
                    providing that at least one parameter server is
                    current. Corresponds directly to the INITIALIZE DELAY 
                    PARAMETER command. In response to a get-request or
                    get-next-request, the agent always returns 'ready' for
                    this value."
                ::= { xSystem 89 }

 	sysTimeProtocol OBJECT-TYPE
                SYNTAX INTEGER { disabled(1), enabled(2) }
		ACCESS read-write
		STATUS mandatory
		DESCRIPTION
		    "Indicates whether the SNTP protocol is used to obtain
                     the time at startup. If disabled, the older TIMED
                     protocol is used. Both protocols run over UDP."
                DEFVAL { disabled }
		::= { xSystem 90 }

 	sysTimeBroadcast OBJECT-TYPE
                SYNTAX INTEGER { disabled(1), enabled(2) }
		ACCESS read-write
		STATUS mandatory
		DESCRIPTION
		    "Indicates whether the unit will broadcast for the 
                     time at startup."
                DEFVAL { enabled }
		::= { xSystem 91 }

            -- System Traps
            -- resourceLack is deprecated, and replaced by resourceFailure.

            resourceLack TRAP-TYPE
                ENTERPRISE xSystem
                VARIABLES { 
                    resType
                    }
                DESCRIPTION
                    "Indication that the system incremented the 
                    corresponding value of resLacks."
                ::= 1

            resourceFailure TRAP-TYPE
                ENTERPRISE mrvInReachProductDivision
                VARIABLES { 
                    resType,
		    sysLocation
                    }
                DESCRIPTION
                    "Indication that a system resource lack occurred of
                     the type resType."
                ::= 9

            sysLoginAuthenticationFailure TRAP-TYPE
                ENTERPRISE mrvInReachProductDivision
                VARIABLES {  sysLoginAuthFailureTrapType,
                        sysLoginAuthTrapIdentity }
                DESCRIPTION
                    "Indicates when and where a user attempted and failed to
                     access the system."
                ::= 28


END
