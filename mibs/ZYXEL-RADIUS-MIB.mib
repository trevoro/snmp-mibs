-- ZyXEL Communications Corporation
-- Private Enterprise MIB definition 
  
-- This file describes the ZyXEL Communications Corporation Enterprise MIB.
-- It contains ZyXEL products OIDs, and common managed objects.

-- $Log: ZYXEL-RADIUS-MIB.mib $ 
-- Revision 1.5  2013/06/25 10:00:43  Mandy 
-- Support notified trap for error recovered 
-- Revision 1.4  2012/09/19 07:45:36  Kevin 
-- if it's leaf node, revise the vender name from zyxel to zy 
-- Revision 1.3  2012/08/22 09:48:43  Kevin 
-- clean warning for SNMPc 
-- Revision 1.2  2012/07/05 06:24:30  Kevin 
-- 1. upgrade from SNMP to SNMPv2  
-- 2. clean warning 
-- Revision 1.1  2012/05/30 07:50:29  Kevin 
-- Initial revision 

ZYXEL-RADIUS-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelRadius MODULE-IDENTITY
		LAST-UPDATED	"201207010000Z"    
		ORGANIZATION "Enterprise Solution ZyXEL"     
		CONTACT-INFO
			""	   
		DESCRIPTION
			"The subtree for radius"
		::= { esMgmt 71 }

	zyxelRadiusServerSetup     		OBJECT IDENTIFIER ::= { zyxelRadius 1 }
	zyxelRadiusServerNotifications  OBJECT IDENTIFIER ::= { zyxelRadius 2 }
	
	  
-- *******************************************************************
-- *
-- * zyxelRadiusServerSetup
-- *
-- *******************************************************************

--* zyxelRadiusAuthenticationServerSetup
        zyxelRadiusAuthenticationServerSetup OBJECT IDENTIFIER ::= { zyxelRadiusServerSetup 1 }

-- zyxelRadiusAuthenticationServerMode       
        zyRadiusAuthenticationServerMode OBJECT-TYPE
        SYNTAX  INTEGER{
        		index-priority(1),
				round-robin(2)
        }
        MAX-ACCESS  read-write
        STATUS  current
        DESCRIPTION
        	"This field is valid only if you configure multiple RADIUS servers.  Select index-priority and the 
        	switch tries to authenticate with the first configured RADIU server, if the RADIUS server does not 
        	respond then this switch tries to authenticate with the second RADIUS server. Select round-robin to 
        	alternate between the RADIUS servers that it sends authentication requests to."
        ::= { zyxelRadiusAuthenticationServerSetup 1 }

-- zyxelRadiusAuthenticationServerTimeout
        zyRadiusAuthenticationServerTimeout OBJECT-TYPE
        SYNTAX  INTEGER
        MAX-ACCESS  read-write
        STATUS  current
        DESCRIPTION
			"Specify the amount of time in seconds that the switch waits for an authentication request response 
			from the RADIUS server. If you are using index-priority for your authentication and you are using two 
			RADIUS servers then the timeout value is divided between the two RADIUS servers. For example, if you 
			set the timeout value to 30 seconds, then the Switch waits for a response from the first RADIUS server 
			for 15 seconds and then tries the second RADIUS server. "
        ::= { zyxelRadiusAuthenticationServerSetup 2 }

-- zyxelRadiusAuthenticationServerTable
        zyxelRadiusAuthenticationServerTable OBJECT-TYPE
        SYNTAX	SEQUENCE OF ZyxelRadiusAuthenticationServerEntry
        MAX-ACCESS  not-accessible
        STATUS  current
        DESCRIPTION
                 	"The table contains RADIUS authentication server configuration."
        ::= { zyxelRadiusAuthenticationServerSetup 3 }
        
		zyxelRadiusAuthenticationServerEntry OBJECT-TYPE
        SYNTAX	ZyxelRadiusAuthenticationServerEntry
        MAX-ACCESS	not-accessible
        STATUS	current
        DESCRIPTION    	
			"An entry contains RADIUS authentication server configuration."
        INDEX          	{ zyRadiusAuthenticationServerIndex }
        ::= { zyxelRadiusAuthenticationServerTable 1 }

        ZyxelRadiusAuthenticationServerEntry ::=
           SEQUENCE {
        	zyRadiusAuthenticationServerIndex			INTEGER,
        	zyRadiusAuthenticationServerIpAddr			IpAddress,
        	zyRadiusAuthenticationServerUdpPort			INTEGER,
        	zyRadiusAuthenticationServerSharedSecret	DisplayString
           }

        zyRadiusAuthenticationServerIndex OBJECT-TYPE
        SYNTAX  INTEGER
        MAX-ACCESS  not-accessible
        STATUS  current
        DESCRIPTION
			"An index that uniquely identifies a RADIUS authentication entry."
        ::= { zyxelRadiusAuthenticationServerEntry 1 }

        zyRadiusAuthenticationServerIpAddr OBJECT-TYPE
        SYNTAX  IpAddress
        MAX-ACCESS  read-write
        STATUS  current
        DESCRIPTION
			"Enter IP address of an external RADIUS authentication server."
        ::= { zyxelRadiusAuthenticationServerEntry 2 }

        zyRadiusAuthenticationServerUdpPort OBJECT-TYPE
        SYNTAX  INTEGER
        MAX-ACCESS  read-write
        STATUS  current
        DESCRIPTION
			"The default port of a RADIUS server for authentication is 1812. You need not change this value unless 
			your netwrok administrator instructs you to do so."
        ::= { zyxelRadiusAuthenticationServerEntry 3 }

        zyRadiusAuthenticationServerSharedSecret OBJECT-TYPE
        SYNTAX  DisplayString
        MAX-ACCESS  read-write
        STATUS  current
        DESCRIPTION
			"Specify a password as the key to be shared between the external RADIUS authentication server and the 
			switch. This key is not sent over the network. This key must be the same on the external RADIUS 
			authentication server and the switch."
        ::= { zyxelRadiusAuthenticationServerEntry 4 }

--* zyxelRadiusAccountingServerSetup
	    zyxelRadiusAccountingServerSetup OBJECT IDENTIFIER ::= { zyxelRadiusServerSetup 2 }

-- zyxelRadiusAccountingServerTimeout
        zyRadiusAccountingServerTimeout OBJECT-TYPE
        SYNTAX  INTEGER
        MAX-ACCESS  read-write
        STATUS  current
        DESCRIPTION
			"Specify the amount of time in seconds that the switch waits for an accounting request response from 
			the RADIUS accounting server."
        ::= { zyxelRadiusAccountingServerSetup 1 }

-- zyxelRadiusAccountingServerTable
        zyxelRadiusAccountingServerTable OBJECT-TYPE
        SYNTAX	SEQUENCE OF ZyxelRadiusAccountingServerEntry
        MAX-ACCESS  not-accessible
        STATUS  current
        DESCRIPTION
 			"The table contains RADIUS accounting server configuration."
        ::= { zyxelRadiusAccountingServerSetup 2 }
        
		zyxelRadiusAccountingServerEntry OBJECT-TYPE
        SYNTAX	ZyxelRadiusAccountingServerEntry
        MAX-ACCESS	not-accessible
        STATUS	current
        DESCRIPTION    	
			"An entry contains RADIUS accounting server configuration."
        INDEX          	{ zyRadiusAccountingServerIndex }
        ::= { zyxelRadiusAccountingServerTable 1 }

        ZyxelRadiusAccountingServerEntry ::=
           SEQUENCE {
        	zyRadiusAccountingServerIndex			INTEGER,
        	zyRadiusAccountingServerIpAddr			IpAddress,
        	zyRadiusAccountingServerUdpPort			INTEGER,
        	zyRadiusAccountingServerSharedSecret	DisplayString
           }

        zyRadiusAccountingServerIndex OBJECT-TYPE
        SYNTAX  INTEGER
        MAX-ACCESS  not-accessible
        STATUS  current
        DESCRIPTION
			"An index that uniquely identifies a RADIUS accounting entry."
        ::= { zyxelRadiusAccountingServerEntry 1 }

        zyRadiusAccountingServerIpAddr OBJECT-TYPE
        SYNTAX  IpAddress
        MAX-ACCESS  read-write
        STATUS  current
        DESCRIPTION
			"Enter IP address of an external RADIUS accounting server."
        ::= { zyxelRadiusAccountingServerEntry 2 }

        zyRadiusAccountingServerUdpPort OBJECT-TYPE
        SYNTAX  INTEGER
        MAX-ACCESS  read-write
        STATUS  current
        DESCRIPTION
			"The default port of a RADIUS accounting server for accounting is 1813. You need not change this 
			value unless your network administator instructs you to do so."
        ::= { zyxelRadiusAccountingServerEntry 3 }

        zyRadiusAccountingServerSharedSecret OBJECT-TYPE
        SYNTAX  DisplayString
        MAX-ACCESS  read-write
        STATUS  current
        DESCRIPTION
			"Specify a password as the key to be shared between the external RADIUS accounting server and the 
			switch.	This key is not sent over the network. This key must be the same on the external RADIUS 
			accounting server and the switch"
        ::= { zyxelRadiusAccountingServerEntry 4 }
		
	   	zyRadiusServerAuthenticationServerNotReachable NOTIFICATION-TYPE
       	OBJECTS {
			zyRadiusAuthenticationServerIndex
        }       
	   	STATUS  current
       	DESCRIPTION
        	"RADIUS authentication server is not reachable. Network element does not receive replies from RADIUS 
        	authentication server."
       	::= { zyxelRadiusServerNotifications 1 }   

	   	zyRadiusServerAccountingServerNotReachable NOTIFICATION-TYPE
       	OBJECTS {
			zyRadiusAccountingServerIndex
        }       
	   	STATUS  current
       	DESCRIPTION
        	"RADIUS accounting server is not reachable. Network element does not receive replies from RADIUS 
        	accounting server."
       	::= { zyxelRadiusServerNotifications 2 }
       	
	   	zyRadiusServerAuthenticationServerNotReachableRecovered NOTIFICATION-TYPE
       	OBJECTS {
			zyRadiusAuthenticationServerIndex
        }       
	   	STATUS  current
       	DESCRIPTION
        	"RADIUS authentication server is recovered to rechable."
       	::= { zyxelRadiusServerNotifications 3 }   

	   	zyRadiusServerAccountingServerNotReachableRecovered NOTIFICATION-TYPE
       	OBJECTS {
			zyRadiusAccountingServerIndex
        }       
	   	STATUS  current
       	DESCRIPTION
        	"RADIUS accounting server is recovered to rechable."
       	::= { zyxelRadiusServerNotifications 4 }
		
		
		
END
