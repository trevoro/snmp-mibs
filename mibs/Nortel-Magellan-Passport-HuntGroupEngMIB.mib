Nortel-Magellan-Passport-HuntGroupEngMIB
DEFINITIONS ::= BEGIN



IMPORTS

      OBJECT-TYPE
   FROM RFC-1212

      passportMIBs
   FROM Nortel-Magellan-Passport-UsefulDefinitionsMIB

      Counter32,
      DisplayString,
      StorageType,
      RowStatus,
      Unsigned32
   FROM Nortel-Magellan-Passport-StandardTextualConventionsMIB

      NonReplicated
   FROM Nortel-Magellan-Passport-TextualConventionsMIB

      lpIndex,
      lpEngIndex,
      lpEng
   FROM Nortel-Magellan-Passport-LogicalProcessorMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     HuntGroupEng Enterprise MIB."

huntGroupEngMIB OBJECT IDENTIFIER ::= { passportMIBs 131 }










-- Lp Eng HuntGroupService
-- The HuntGroupService component contains engineering statistics 
-- for all hunt groups on the FP.

lpEngHgs OBJECT IDENTIFIER ::= { lpEng 4 }



lpEngHgsRowStatusTable OBJECT-TYPE
   SYNTAX     SEQUENCE OF LpEngHgsRowStatusEntry
   ACCESS     not-accessible
   STATUS     mandatory
   DESCRIPTION
     "This entry controls the addition and deletion of 
      lpEngHgs components."
::= { lpEngHgs 1 }

lpEngHgsRowStatusEntry OBJECT-TYPE
   SYNTAX     LpEngHgsRowStatusEntry
   ACCESS     not-accessible
   STATUS     mandatory
   DESCRIPTION
     "A single entry in the table represents a single 
      lpEngHgs component."
   INDEX {
      lpIndex,
      lpEngIndex,
      lpEngHgsIndex }
::= { lpEngHgsRowStatusTable 1 }

LpEngHgsRowStatusEntry ::= SEQUENCE {
   lpEngHgsRowStatus
      RowStatus,
   lpEngHgsComponentName
      DisplayString,
   lpEngHgsStorageType
      StorageType,
   lpEngHgsIndex
      NonReplicated }

lpEngHgsRowStatus OBJECT-TYPE
   SYNTAX     RowStatus 
   ACCESS     read-write
   STATUS     mandatory
   DESCRIPTION
     "This variable is used as the basis for SNMP naming of
      lpEngHgs components.
      These components can be added and deleted."
::= { lpEngHgsRowStatusEntry 1 }

lpEngHgsComponentName OBJECT-TYPE
   SYNTAX     DisplayString 
   ACCESS     read-only
   STATUS     mandatory
   DESCRIPTION
     "This variable provides the component's string name for
      use with the ASCII Console Interface"
::= { lpEngHgsRowStatusEntry 2 }

lpEngHgsStorageType OBJECT-TYPE
   SYNTAX     StorageType 
   ACCESS     read-only
   STATUS     mandatory
   DESCRIPTION
     "This variable represents the storage type value for the
      lpEngHgs tables."
::= { lpEngHgsRowStatusEntry 4 }

lpEngHgsIndex OBJECT-TYPE
   SYNTAX     NonReplicated 
   ACCESS     not-accessible
   STATUS     mandatory
   DESCRIPTION
     "This variable represents the index for the lpEngHgs tables."
::= { lpEngHgsRowStatusEntry 10 }

lpEngHgsOperationalTable OBJECT-TYPE
   SYNTAX     SEQUENCE OF LpEngHgsOperationalEntry
   ACCESS     not-accessible
   STATUS     mandatory
   DESCRIPTION
     "The Operational group contains attributes for all hunt groups on the 
      LP."
::= { lpEngHgs 10 }

lpEngHgsOperationalEntry OBJECT-TYPE
   SYNTAX     LpEngHgsOperationalEntry
   ACCESS     not-accessible
   STATUS     mandatory
   DESCRIPTION
     "An entry in the lpEngHgsOperationalTable."
   INDEX {
      lpIndex,
      lpEngIndex,
      lpEngHgsIndex }
::= { lpEngHgsOperationalTable 1 }

LpEngHgsOperationalEntry ::= SEQUENCE {
   lpEngHgsHuntGroups
      Unsigned32,
   lpEngHgsHuntAttempts
      Counter32 }

lpEngHgsHuntGroups OBJECT-TYPE
   SYNTAX     Unsigned32 (0..65535)
   ACCESS     read-only
   STATUS     mandatory
   DESCRIPTION
     "This attribute indicates the number of hunt groups provisioned on 
      the LP."
   DEFVAL     { 0 }
::= { lpEngHgsOperationalEntry 1 }

lpEngHgsHuntAttempts OBJECT-TYPE
   SYNTAX     Counter32 
   ACCESS     read-only
   STATUS     mandatory
   DESCRIPTION
     "This attribute counts the total number of hunt attempts made by all 
      hunt groups. The count includes both initial and subsequent hunt 
      attempts. Individual hunt groups maintain this counter within the 
      huntAttempts attribute of the Hg/n component. This counter wraps 
      to 0 when it exceeds its maximum value."
::= { lpEngHgsOperationalEntry 2 }




-- 
-- Version and Compliance statements
-- 



-- Object-Group Statement:
-- A list of all current accessible leaf objects.

-- OBJECTS { lpEngHgsStorageType,
--           lpEngHgsRowStatus,
--           lpEngHgsHuntGroups,
--           lpEngHgsHuntAttempts,
--           lpEngHgsComponentName }
-- STATUS  mandatory
-- DESCRIPTION
--   "A list of all current accessible leaf objects."

huntGroupEngGroup OBJECT IDENTIFIER ::= { huntGroupEngMIB 1 }
huntGroupEngGroupBE OBJECT IDENTIFIER ::= { huntGroupEngGroup 5 }
huntGroupEngGroupBE01 OBJECT IDENTIFIER ::= { huntGroupEngGroupBE 2 }
huntGroupEngGroupBE01A OBJECT IDENTIFIER ::= { huntGroupEngGroupBE01 2 }



-- Agent-Capabilities Statement:

-- PRODUCT-RELEASE "Passport Release 7.0 HuntGroupEng."
-- STATUS          mandatory
-- DESCRIPTION     "HuntGroupEng MIB: MIB Version BE01A,
--                  Software Version BG00S4C."
-- SUPPORTS        Nortel-Magellan-Passport-HuntGroupEngMIB
--    INCLUDES     { huntGroupEngGroupBE01A }

huntGroupEngCapabilities OBJECT IDENTIFIER ::= { huntGroupEngMIB 3 }
huntGroupEngCapabilitiesBE OBJECT IDENTIFIER ::= { huntGroupEngCapabilities 5 }
huntGroupEngCapabilitiesBE01 OBJECT IDENTIFIER ::= { huntGroupEngCapabilitiesBE 2 }
huntGroupEngCapabilitiesBE01A OBJECT IDENTIFIER ::= { huntGroupEngCapabilitiesBE01 2 }





END
