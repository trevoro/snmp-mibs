Nortel-Magellan-Passport-VncsCallServerMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      AsciiString,
      DigitString,
      FixedPoint1,
      Link,
      WildcardedDigitString
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     VncsCallServer Enterprise MIB."

vncsCallServerMIB OBJECT IDENTIFIER ::= { passportMIBs 66 }










-- Vncs/n		
-- The Vncs component provides the information to the Path Oriented 
-- Routing System (PORS) required during switched voice call 
-- establishment. It translates the directory number prefix into the 
-- routing information and the voice service profile parameters. Each 
-- instance of this component represents one numbering plan.

vncs OBJECT IDENTIFIER ::= { components 44 }



vncsRowStatusTable OBJECT-TYPE
   SYNTAX     SEQUENCE OF VncsRowStatusEntry
   ACCESS     not-accessible
   STATUS     mandatory
   DESCRIPTION
     "This entry controls the addition and deletion of 
      vncs components."
::= { vncs 1 }

vncsRowStatusEntry OBJECT-TYPE
   SYNTAX     VncsRowStatusEntry
   ACCESS     not-accessible
   STATUS     mandatory
   DESCRIPTION
     "A single entry in the table represents a single 
      vncs component."
   INDEX {
      vncsIndex }
::= { vncsRowStatusTable 1 }

VncsRowStatusEntry ::= SEQUENCE {
   vncsRowStatus
      RowStatus,
   vncsComponentName
      DisplayString,
   vncsStorageType
      StorageType,
   vncsIndex
      Integer32 }

vncsRowStatus OBJECT-TYPE
   SYNTAX     RowStatus 
   ACCESS     read-write
   STATUS     mandatory
   DESCRIPTION
     "This variable is used as the basis for SNMP naming of
      vncs components.
      These components can be added and deleted."
::= { vncsRowStatusEntry 1 }

vncsComponentName OBJECT-TYPE
   SYNTAX     DisplayString 
   ACCESS     read-only
   STATUS     mandatory
   DESCRIPTION
     "This variable provides the component's string name for
      use with the ASCII Console Interface"
::= { vncsRowStatusEntry 2 }

vncsStorageType OBJECT-TYPE
   SYNTAX     StorageType 
   ACCESS     read-only
   STATUS     mandatory
   DESCRIPTION
     "This variable represents the storage type value for the
      vncs tables."
::= { vncsRowStatusEntry 4 }

vncsIndex OBJECT-TYPE
   SYNTAX     Integer32 (1..16)
   ACCESS     not-accessible
   STATUS     mandatory
   DESCRIPTION
     "This variable represents the index for the vncs tables."
::= { vncsRowStatusEntry 10 }

vncsProvTable OBJECT-TYPE
   SYNTAX     SEQUENCE OF VncsProvEntry
   ACCESS     not-accessible
   STATUS     mandatory
   DESCRIPTION
     "This group represents the provisionable attributes of the VNCS 
      server."
::= { vncs 10 }

vncsProvEntry OBJECT-TYPE
   SYNTAX     VncsProvEntry
   ACCESS     not-accessible
   STATUS     mandatory
   DESCRIPTION
     "An entry in the vncsProvTable."
   INDEX {
      vncsIndex }
::= { vncsProvTable 1 }

VncsProvEntry ::= SEQUENCE {
   vncsCommentText
      AsciiString }

vncsCommentText OBJECT-TYPE
   SYNTAX     AsciiString (SIZE (0..40))
   ACCESS     read-write
   STATUS     mandatory
   DESCRIPTION
     "This attribute specifies the name of the customer that is using this 
      VNCS server. Typical use of this attribute is to store customer 
      name."
::= { vncsProvEntry 1 }

vncsStatsTable OBJECT-TYPE
   SYNTAX     SEQUENCE OF VncsStatsEntry
   ACCESS     not-accessible
   STATUS     mandatory
   DESCRIPTION
     "This group provides data for the Vncs component."
::= { vncs 11 }

vncsStatsEntry OBJECT-TYPE
   SYNTAX     VncsStatsEntry
   ACCESS     not-accessible
   STATUS     mandatory
   DESCRIPTION
     "An entry in the vncsStatsTable."
   INDEX {
      vncsIndex }
::= { vncsStatsTable 1 }

VncsStatsEntry ::= SEQUENCE {
   vncsTotalTranslations
      Counter32 }

vncsTotalTranslations OBJECT-TYPE
   SYNTAX     Counter32 
   ACCESS     read-only
   STATUS     mandatory
   DESCRIPTION
     "This attribute counts the total number of translation requests 
      received by VNCS. This counter wraps to zero when it reaches its 
      maximum value."
::= { vncsStatsEntry 1 }

vncsVRoutesTable OBJECT-TYPE
   SYNTAX     SEQUENCE OF VncsVRoutesEntry
   ACCESS     not-accessible
   STATUS     mandatory
   DESCRIPTION
     "This attribute indicates which VoiceRoute components are using 
      this Vncs."
::= { vncs 305 }

vncsVRoutesEntry OBJECT-TYPE
   SYNTAX     VncsVRoutesEntry
   ACCESS     not-accessible
   STATUS     mandatory
   DESCRIPTION
     "An entry in the vncsVRoutesTable."
   INDEX {
      vncsIndex,
      vncsVRoutesValue }
::= { vncsVRoutesTable 1 }

VncsVRoutesEntry ::= SEQUENCE {
   vncsVRoutesValue
      Link }

vncsVRoutesValue OBJECT-TYPE
   SYNTAX     Link 
   ACCESS     read-only
   STATUS     mandatory
   DESCRIPTION
     "This variable represents both the value and the index for the
      vncsVRoutesTable."
::= { vncsVRoutesEntry 1 }


-- Vncs/n diallingPlan/x		
-- The DiallingPlan subcomponent contains part of the Voice 
-- Networking Call Server database that belongs under one dialling 
-- plan. There are three dialling plans supported, dialling plan 0, 
-- dialling plan 1 and dialling plan 2.

vncsDP OBJECT IDENTIFIER ::= { vncs 2 }



vncsDPRowStatusTable OBJECT-TYPE
   SYNTAX     SEQUENCE OF VncsDPRowStatusEntry
   ACCESS     not-accessible
   STATUS     mandatory
   DESCRIPTION
     "This entry controls the addition and deletion of 
      vncsDP components."
::= { vncsDP 1 }

vncsDPRowStatusEntry OBJECT-TYPE
   SYNTAX     VncsDPRowStatusEntry
   ACCESS     not-accessible
   STATUS     mandatory
   DESCRIPTION
     "A single entry in the table represents a single 
      vncsDP component."
   INDEX {
      vncsIndex,
      vncsDPIndex }
::= { vncsDPRowStatusTable 1 }

VncsDPRowStatusEntry ::= SEQUENCE {
   vncsDPRowStatus
      RowStatus,
   vncsDPComponentName
      DisplayString,
   vncsDPStorageType
      StorageType,
   vncsDPIndex
      Integer32 }

vncsDPRowStatus OBJECT-TYPE
   SYNTAX     RowStatus 
   ACCESS     read-write
   STATUS     mandatory
   DESCRIPTION
     "This variable is used as the basis for SNMP naming of
      vncsDP components.
      These components can be added."
::= { vncsDPRowStatusEntry 1 }

vncsDPComponentName OBJECT-TYPE
   SYNTAX     DisplayString 
   ACCESS     read-only
   STATUS     mandatory
   DESCRIPTION
     "This variable provides the component's string name for
      use with the ASCII Console Interface"
::= { vncsDPRowStatusEntry 2 }

vncsDPStorageType OBJECT-TYPE
   SYNTAX     StorageType 
   ACCESS     read-only
   STATUS     mandatory
   DESCRIPTION
     "This variable represents the storage type value for the
      vncsDP tables."
::= { vncsDPRowStatusEntry 4 }

vncsDPIndex OBJECT-TYPE
   SYNTAX     Integer32 (0..2)
   ACCESS     not-accessible
   STATUS     mandatory
   DESCRIPTION
     "This variable represents the index for the vncsDP tables."
::= { vncsDPRowStatusEntry 10 }

vncsDPStatsTable OBJECT-TYPE
   SYNTAX     SEQUENCE OF VncsDPStatsEntry
   ACCESS     not-accessible
   STATUS     mandatory
   DESCRIPTION
     "This group provides the operational components for the AccessCode 
      component. It displays total DirectoryNumber components under 
      this access code, total translation requests received and total 
      requests failed under this access code."
::= { vncsDP 10 }

vncsDPStatsEntry OBJECT-TYPE
   SYNTAX     VncsDPStatsEntry
   ACCESS     not-accessible
   STATUS     mandatory
   DESCRIPTION
     "An entry in the vncsDPStatsTable."
   INDEX {
      vncsIndex,
      vncsDPIndex }
::= { vncsDPStatsTable 1 }

VncsDPStatsEntry ::= SEQUENCE {
   vncsDPCompleteTranslations
      Counter32,
   vncsDPIncompleteTranslations
      Counter32,
   vncsDPFailedTranslations
      Counter32 }

vncsDPCompleteTranslations OBJECT-TYPE
   SYNTAX     Counter32 
   ACCESS     read-only
   STATUS     mandatory
   DESCRIPTION
     "This attribute counts the total number of complete translations 
      handled under this AccessCode component. The complete 
      translations are the one that resulted in the return by VNCS server 
      of the reply message with the routing information and voice profile 
      parameters associated with the directory number prefix supplied in 
      the translation request message. This counter wraps to zero when it 
      reaches its maximum value."
::= { vncsDPStatsEntry 1 }

vncsDPIncompleteTranslations OBJECT-TYPE
   SYNTAX     Counter32 
   ACCESS     read-only
   STATUS     mandatory
   DESCRIPTION
     "This attribute counts the total number of incomplete translations 
      handled under this AccessCode component. The incomplete 
      translations are the one that require more digits in the directory 
      number prefix to uniquely identify routing attributes. This counter 
      wraps to zero when it reaches its maximum value."
::= { vncsDPStatsEntry 2 }

vncsDPFailedTranslations OBJECT-TYPE
   SYNTAX     Counter32 
   ACCESS     read-only
   STATUS     mandatory
   DESCRIPTION
     "This attribute counts the total number of failed translations handled 
      under this AccessCode component. The failed translations are the 
      one for which the directory number prefix could not be found in the 
      database. the value wraps up when it reaches maximum."
::= { vncsDPStatsEntry 3 }


-- Vncs/n DP/x 	DirectoryNumber/x
-- The DirectoryNumber subcomponent represents a prefix directory 
-- number excluding the access code. The instance value must be 1 to 
-- 40 digits each of value 0 through 9 or wildcard digit. The wildcard 
-- digit is represented by "?". It is used to indicate to VNCS that the 
-- digit in that position should be ignored for routing purposes. 
-- Wildcard inconsistencies must not exist. If a prefix directory 
-- number already exists with a digit in a particular position, a new 
-- prefix may not be added with a wild card in that position and if the 
-- prefix already exists with a wild card in the particular position, a 
-- new prefix may not be added with a specific digit in the same 
-- position.

vncsDPDn OBJECT IDENTIFIER ::= { vncsDP 2 }



vncsDPDnRowStatusTable OBJECT-TYPE
   SYNTAX     SEQUENCE OF VncsDPDnRowStatusEntry
   ACCESS     not-accessible
   STATUS     mandatory
   DESCRIPTION
     "This entry controls the addition and deletion of 
      vncsDPDn components."
::= { vncsDPDn 1 }

vncsDPDnRowStatusEntry OBJECT-TYPE
   SYNTAX     VncsDPDnRowStatusEntry
   ACCESS     not-accessible
   STATUS     mandatory
   DESCRIPTION
     "A single entry in the table represents a single 
      vncsDPDn component."
   INDEX {
      vncsIndex,
      vncsDPIndex,
      vncsDPDnIndex }
::= { vncsDPDnRowStatusTable 1 }

VncsDPDnRowStatusEntry ::= SEQUENCE {
   vncsDPDnRowStatus
      RowStatus,
   vncsDPDnComponentName
      DisplayString,
   vncsDPDnStorageType
      StorageType,
   vncsDPDnIndex
      WildcardedDigitString }

vncsDPDnRowStatus OBJECT-TYPE
   SYNTAX     RowStatus 
   ACCESS     read-write
   STATUS     mandatory
   DESCRIPTION
     "This variable is used as the basis for SNMP naming of
      vncsDPDn components.
      These components can be added and deleted."
::= { vncsDPDnRowStatusEntry 1 }

vncsDPDnComponentName OBJECT-TYPE
   SYNTAX     DisplayString 
   ACCESS     read-only
   STATUS     mandatory
   DESCRIPTION
     "This variable provides the component's string name for
      use with the ASCII Console Interface"
::= { vncsDPDnRowStatusEntry 2 }

vncsDPDnStorageType OBJECT-TYPE
   SYNTAX     StorageType 
   ACCESS     read-only
   STATUS     mandatory
   DESCRIPTION
     "This variable represents the storage type value for the
      vncsDPDn tables."
::= { vncsDPDnRowStatusEntry 4 }

vncsDPDnIndex OBJECT-TYPE
   SYNTAX     WildcardedDigitString (SIZE (1..40))
   ACCESS     not-accessible
   STATUS     mandatory
   DESCRIPTION
     "This variable represents the index for the vncsDPDn tables."
::= { vncsDPDnRowStatusEntry 10 }

vncsDPDnProvTable OBJECT-TYPE
   SYNTAX     SEQUENCE OF VncsDPDnProvEntry
   ACCESS     not-accessible
   STATUS     mandatory
   DESCRIPTION
     "This group represents attributes that the prefix directory number 
      maps to."
::= { vncsDPDn 10 }

vncsDPDnProvEntry OBJECT-TYPE
   SYNTAX     VncsDPDnProvEntry
   ACCESS     not-accessible
   STATUS     mandatory
   DESCRIPTION
     "An entry in the vncsDPDnProvTable."
   INDEX {
      vncsIndex,
      vncsDPIndex,
      vncsDPDnIndex }
::= { vncsDPDnProvTable 1 }

VncsDPDnProvEntry ::= SEQUENCE {
   vncsDPDnDestinationNodeId
      Unsigned32,
   vncsDPDnDestinationComponentId
      RowPointer,
   vncsDPDnVoiceProfileNumber
      Unsigned32,
   vncsDPDnNumberingPlanIndicator
      INTEGER,
   vncsDPDnDataNetworkAddress
      DigitString }

vncsDPDnDestinationNodeId OBJECT-TYPE
   SYNTAX     Unsigned32 (0..4095)
   ACCESS     read-write
   STATUS     mandatory
   DESCRIPTION
     "This attribute in conjunction with the destinationComponentId 
      attribute identifies the destination of a voice connection. 
      The destinationNodeId and the destinationComponentId attributes 
      are being replaced by the DataNetworkAddress (Dna) attribute.
      For the migration procedure consult NTP 241-7001-410 'Passport 
      Voice Networking User Guide'.
      If the destinationComponentId, the destinationNodeId and the Dna 
      attributes are all set, the call routing is based on the 
      destinationNodeId and the destinationComponentId, unless the call 
      is initiated from the Magellan Passport Access (MPA) module, 
      which will use the Dna attribute.
      The valid destination call identifier settings are:
      1. destinationNodeId and destinationNodeId attributes set
      2. destinationNodeId, destinationNodeId and Dna attributes set
      3. Dna attribute set
      For calls initiated from the MPA, only options 2 and 3 are valid."
   DEFVAL     { 0 }
::= { vncsDPDnProvEntry 1 }

vncsDPDnDestinationComponentId OBJECT-TYPE
   SYNTAX     RowPointer 
   ACCESS     read-write
   STATUS     mandatory
   DESCRIPTION
     "This attribute in conjunction with the destinationNodeId attribute 
      identifies the destination of a voice connection. The only valid 
      component name for this attribute value is vroute.
      The destinationNodeId and the destinationComponentId attributes 
      are being replaced by the DataNetworkAddress (Dna) attribute.
      For the migration procedure consult NTP 241-7001-410 'Passport 
      Voice Networking User Guide'.
      If the destinationComponentId, the destinationNodeId and the Dna 
      attributes are all set, the call routing is based on the 
      destinationNodeId and the destinationComponentId, unless the call 
      is initiated from the Magellan Passport Access (MPA) module, 
      which will use the Dna attribute.
      The valid destination call identifier settings are:
      1. destinationNodeId and destinationNodeId attributes set
      2. destinationNodeId, destinationNodeId and Dna attributes set
      3. Dna attribute set
      For calls initiated from the MPA, only options 2 and 3 are valid."
::= { vncsDPDnProvEntry 2 }

vncsDPDnVoiceProfileNumber OBJECT-TYPE
   SYNTAX     Unsigned32 (1..16)
   ACCESS     read-write
   STATUS     mandatory
   DESCRIPTION
     "This attribute identifies the voice profile number."
   DEFVAL     { 1 }
::= { vncsDPDnProvEntry 3 }

vncsDPDnNumberingPlanIndicator OBJECT-TYPE
   SYNTAX     INTEGER  {
                 x121(0),
                 e164(1) }
   ACCESS     read-write
   STATUS     mandatory
   DESCRIPTION
     "This attribute indicates the Numbering Plan Indicator (NPI) of the 
      Dna of the destination component. An address may belong to the 
      X.121 or E.164 numbering plans. X.121 is used in packet switched 
      data networks."
   DEFVAL     { e164 }
::= { vncsDPDnProvEntry 4 }

vncsDPDnDataNetworkAddress OBJECT-TYPE
   SYNTAX     DigitString (SIZE (0..15))
   ACCESS     read-write
   STATUS     mandatory
   DESCRIPTION
     "The Dna attribute contains digits which form a unique identifier of 
      the destination of a voice connection.
      This attribute is used instead of the destinationNodeId and 
      destinationComponentId attributes to identify the destination of the 
      voice connection.
      This attribute is only used if the destinationNodeId and the 
      destinationComponentId attributes are not set or if the call is 
      initiated from the Magellan Passport Access (MPA) module."
::= { vncsDPDnProvEntry 5 }


-- Vncs/n VoiceProfile/n
-- A VoiceProfile component contains all provisionable logical 
-- connection attributes and framer attributes used to set up a virtual 
-- circuit. Directory-number prefixes are mapped to VoiceProfile 
-- instances by the Vncs Dp Dn component. Many directory-number 
-- prefixes use the same profile.

vncsVp OBJECT IDENTIFIER ::= { vncs 3 }



vncsVpRowStatusTable OBJECT-TYPE
   SYNTAX     SEQUENCE OF VncsVpRowStatusEntry
   ACCESS     not-accessible
   STATUS     mandatory
   DESCRIPTION
     "This entry controls the addition and deletion of 
      vncsVp components."
::= { vncsVp 1 }

vncsVpRowStatusEntry OBJECT-TYPE
   SYNTAX     VncsVpRowStatusEntry
   ACCESS     not-accessible
   STATUS     mandatory
   DESCRIPTION
     "A single entry in the table represents a single 
      vncsVp component."
   INDEX {
      vncsIndex,
      vncsVpIndex }
::= { vncsVpRowStatusTable 1 }

VncsVpRowStatusEntry ::= SEQUENCE {
   vncsVpRowStatus
      RowStatus,
   vncsVpComponentName
      DisplayString,
   vncsVpStorageType
      StorageType,
   vncsVpIndex
      Integer32 }

vncsVpRowStatus OBJECT-TYPE
   SYNTAX     RowStatus 
   ACCESS     read-write
   STATUS     mandatory
   DESCRIPTION
     "This variable is used as the basis for SNMP naming of
      vncsVp components.
      These components can be added and deleted."
::= { vncsVpRowStatusEntry 1 }

vncsVpComponentName OBJECT-TYPE
   SYNTAX     DisplayString 
   ACCESS     read-only
   STATUS     mandatory
   DESCRIPTION
     "This variable provides the component's string name for
      use with the ASCII Console Interface"
::= { vncsVpRowStatusEntry 2 }

vncsVpStorageType OBJECT-TYPE
   SYNTAX     StorageType 
   ACCESS     read-only
   STATUS     mandatory
   DESCRIPTION
     "This variable represents the storage type value for the
      vncsVp tables."
::= { vncsVpRowStatusEntry 4 }

vncsVpIndex OBJECT-TYPE
   SYNTAX     Integer32 (1..16)
   ACCESS     not-accessible
   STATUS     mandatory
   DESCRIPTION
     "This variable represents the index for the vncsVp tables."
::= { vncsVpRowStatusEntry 10 }

vncsVpLCOpsTable OBJECT-TYPE
   SYNTAX     SEQUENCE OF VncsVpLCOpsEntry
   ACCESS     not-accessible
   STATUS     mandatory
   DESCRIPTION
     "The attributes of this group collectively form part of a template used 
      to describe and set up a switched logical connection. The attributes 
      of a switched logical connection are similar to the attributes of a 
      permanent logical connection."
::= { vncsVp 2 }

vncsVpLCOpsEntry OBJECT-TYPE
   SYNTAX     VncsVpLCOpsEntry
   ACCESS     not-accessible
   STATUS     mandatory
   DESCRIPTION
     "An entry in the vncsVpLCOpsTable."
   INDEX {
      vncsIndex,
      vncsVpIndex }
::= { vncsVpLCOpsTable 1 }

VncsVpLCOpsEntry ::= SEQUENCE {
   vncsVpSetupPriority
      Unsigned32,
   vncsVpHoldingPriority
      Unsigned32,
   vncsVpBumpPreference
      INTEGER,
   vncsVpRequiredTrafficType
      INTEGER,
   vncsVpPermittedTrunkTypes
      OCTET STRING,
   vncsVpRequiredSecurity
      Unsigned32,
   vncsVpRequiredCustomerParm
      Unsigned32,
   vncsVpPathAttributeToMinimize
      INTEGER,
   vncsVpMaximumAcceptableCost
      Unsigned32,
   vncsVpMaximumAcceptableDelay
      Unsigned32,
   vncsVpEmissionPriority
      Unsigned32,
   vncsVpDiscardPriority
      Unsigned32,
   vncsVpPathFailureAction
      INTEGER,
   vncsVpOptimization
      INTEGER }

vncsVpSetupPriority OBJECT-TYPE
   SYNTAX     Unsigned32 (0..4)
   ACCESS     read-write
   STATUS     mandatory
   DESCRIPTION
     "This attribute specifies the priority at which a path is established. 
      Zero is the highest priority and four is the lowest. When PORS 
      establishes a path through the network, it uses the setupPriority 
      attribute to determine its potential for bumping established paths to 
      acquire their bandwidth. The holdingPriority, a complementary 
      attribute of this attribute, indicates the priority a path maintains 
      once it is established. A new path can bump an existing path if the 
      new path's setupPriority is higher (numerically less) than the 
      existing path's holdingPriority."
   DEFVAL     { 2 }
::= { vncsVpLCOpsEntry 1 }

vncsVpHoldingPriority OBJECT-TYPE
   SYNTAX     Unsigned32 (0..4)
   ACCESS     read-write
   STATUS     mandatory
   DESCRIPTION
     "This attribute specifies the priority that a path holds once it is 
      established. Zero is the highest priority and four is the lowest. A 
      path's holdingPriority determines its likelihood of being bumped by 
      a new path to acquire its bandwidth. The setupPriority, a 
      complementary attribute, indicates the priority of a path at 
      establishment time. A new path can bump an existing path if the 
      new path's setupPriority is higher (numerically less) than the 
      existing path's holdingPriority."
   DEFVAL     { 2 }
::= { vncsVpLCOpsEntry 2 }

vncsVpBumpPreference OBJECT-TYPE
   SYNTAX     INTEGER  {
                 bumpWhenNecessary(0),
                 bumpToObtainBestRoute(1) }
   ACCESS     read-write
   STATUS     mandatory
   DESCRIPTION
     "This attribute specifies when bumping occurs in the route selection 
      process. A connection with higher (numerically less) setupPriority 
      may bump a connection with lower (numerically higher) 
      setupPriority in order to acquire its bandwidth and be established. 
      By default, bumping occurs only when it is necessary. That is, a 
      connection will bump another connection only if there is no other 
      way for the connection to be established. A connection may be set 
      to bump in order to use the best available route it may have."
   DEFVAL     { bumpWhenNecessary }
::= { vncsVpLCOpsEntry 3 }

vncsVpRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute specifies the type of traffic transmitted over the path. 
      There are eight possible traffic types, and the path can transmit only 
      one of them. The originating end of the connection determines the 
      type. These are arbitrary designations for traffic type. The voice, 
      data and video traffic types are defined, and five other arbitrary 
      traffic types can be defined by the network administration. This 
      attribute is used in the route selection process to restrict the route to 
      trunks that support this traffic type. The supportedTrafficType trunk 
      attribute lists all the types of traffic allowed on the trunk. For 
      example, if requiredTrafficType is specified as trafficType1, then 
      only trunks that include trafficType1 in supportedTrafficType will 
      be candidates for this connection."
   DEFVAL     { voice }
::= { vncsVpLCOpsEntry 6 }

vncsVpPermittedTrunkTypes OBJECT-TYPE
   SYNTAX     OCTET STRING (SIZE (1))
   ACCESS     read-write
   STATUS     mandatory
   DESCRIPTION
     "This attribute specifies up to eight types of trunks that can be used 
      on the route. The terrestrial and satellite trunk types have been 
      defined, leaving six remaining arbitrary types that can be defined by 
      the network administration. The trunk's type is indicated in the 
      trunkType attribute of the Trunk component. When selecting a 
      route, PORS chooses only trunks whose trunkTypes are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { vncsVpLCOpsEntry 7 }

vncsVpRequiredSecurity OBJECT-TYPE
   SYNTAX     Unsigned32 (0..7)
   ACCESS     read-write
   STATUS     mandatory
   DESCRIPTION
     "This attribute specifies the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
   DEFVAL     { 4 }
::= { vncsVpLCOpsEntry 8 }

vncsVpRequiredCustomerParm OBJECT-TYPE
   SYNTAX     Unsigned32 (0..7)
   ACCESS     read-write
   STATUS     mandatory
   DESCRIPTION
     "This attribute specifies the allowed customer defined parameter of 
      the trunks on the route. Its value, a number from zero to seven, is 
      chosen by network administration to have a meaning specific to 
      their network, thus allowing them to customize the use of their 
      trunks. A complementary trunk attribute, customerParameter, also 
      has a value from zero to seven. The route selection process does not 
      consider trunks whose customerParameter is greater than the 
      requiredCustomerParameter of the path."
   DEFVAL     { 4 }
::= { vncsVpLCOpsEntry 9 }

vncsVpPathAttributeToMinimize OBJECT-TYPE
   SYNTAX     INTEGER  {
                 cost(0),
                 delay(1) }
   ACCESS     read-write
   STATUS     mandatory
   DESCRIPTION
     "This attribute specifies whether a route is selected on the basis of 
      minimizing the cost or the delay. Each trunk has a cost and a delay 
      metric associated with it. The cost of a selected route is the sum of 
      the trunk cost metrics for all trunks included in the route. The delay 
      of a selected route is the sum of the trunk delay metric for all trunks 
      included in the route."
   DEFVAL     { cost }
::= { vncsVpLCOpsEntry 10 }

vncsVpMaximumAcceptableCost OBJECT-TYPE
   SYNTAX     Unsigned32 (0..65535)
   ACCESS     read-write
   STATUS     mandatory
   DESCRIPTION
     "This attribute specifies an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done for any 
      minimization criterion. No route is selected if the cost metric of the 
      shortest route is larger than the maximumAcceptableCost."
   DEFVAL     { 1280 }
::= { vncsVpLCOpsEntry 11 }

vncsVpMaximumAcceptableDelay OBJECT-TYPE
   SYNTAX     Unsigned32 (0..100000)
   ACCESS     read-write
   STATUS     mandatory
   DESCRIPTION
     "This attribute specifies an upper bound on the delay of a route, 
      which is the sum of the delays of all trunks on the route. It should 
      be provisioned with a reasonable maximum acceptable delay for the 
      end to end one way delay of a 512-byte packet. Remember, that the 
      trunk during its staging measures a measuredRoundTripDelay. This 
      delay is divided by two and truncated to an integer number of 
      milliseconds to provide a one way delay which is used to populate 
      the delay in this trunk object in the topological database. The value 
      includes emission, propagation, and queuing delays. A 512-byte 
      packet is used to perform the measurement. 
      If for any trunk the half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { vncsVpLCOpsEntry 12 }

vncsVpEmissionPriority OBJECT-TYPE
   SYNTAX     Unsigned32 (0..2)
   ACCESS     read-write
   STATUS     mandatory
   DESCRIPTION
     "This attribute specifies the urgency with which packets on the path 
      are emitted by the trunks on the route. EmissionPriority of zero 
      indicates the highest emission priority, while two indicates the 
      lowest emission priority. Packets with a higher emissionPriority (or 
      numerically less) are serviced and sent out before the packets of 
      lower emissionPriority (or numerically higher)."
   DEFVAL     { 0 }
::= { vncsVpLCOpsEntry 13 }

vncsVpDiscardPriority OBJECT-TYPE
   SYNTAX     Unsigned32 (1..3)
   ACCESS     read-write
   STATUS     mandatory
   DESCRIPTION
     "This attribute specifies the importance of the packets on the path. 
      One is used for paths carrying the most important traffic, and three 
      is used for paths carrying the least important traffic. Packets with 
      lower discardPriority(numerically lower) are discarded after 
      packets with a higher discardPriority(numerically higher)."
   DEFVAL     { 1 }
::= { vncsVpLCOpsEntry 14 }

vncsVpPathFailureAction OBJECT-TYPE
   SYNTAX     INTEGER  {
                 disconnectConnection(0),
                 reRoutePath(1) }
   ACCESS     read-write
   STATUS     mandatory
   DESCRIPTION
     "This attribute specifies whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails, the 
      application is informed of the failure. 
      With this option set to reRoutePath, the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option will have the desired effect that the path is 
      rerouted without complete disconnection at both ends."
   DEFVAL     { reRoutePath }
::= { vncsVpLCOpsEntry 15 }

vncsVpOptimization OBJECT-TYPE
   SYNTAX     INTEGER  {
                 disabled(0),
                 enabled(1) }
   ACCESS     read-write
   STATUS     mandatory
   DESCRIPTION
     "This attribute specifies whether this connection should attempt to 
      optimize its path when requested by the Rtg Pors component. Every 
      path is optimal when it is established, but as network traffic patterns 
      and configurations change this path may no longer be optimal. The 
      PORS connection manager on a module requests circuits to 
      optimize at the optimizationInterval."
   DEFVAL     { enabled }
::= { vncsVpLCOpsEntry 16 }

vncsVpFrOpsTable OBJECT-TYPE
   SYNTAX     SEQUENCE OF VncsVpFrOpsEntry
   ACCESS     not-accessible
   STATUS     mandatory
   DESCRIPTION
     "This group contains attributes which define how audio data is 
      carried across the Passport network."
::= { vncsVp 3 }

vncsVpFrOpsEntry OBJECT-TYPE
   SYNTAX     VncsVpFrOpsEntry
   ACCESS     not-accessible
   STATUS     mandatory
   DESCRIPTION
     "An entry in the vncsVpFrOpsTable."
   INDEX {
      vncsIndex,
      vncsVpIndex }
::= { vncsVpFrOpsTable 1 }

VncsVpFrOpsEntry ::= SEQUENCE {
   vncsVpMaxVoiceBitRate
      INTEGER,
   vncsVpMinVoiceBitRate
      INTEGER,
   vncsVpMaxModemBitRate
      INTEGER,
   vncsVpMinModemBitRate
      INTEGER,
   vncsVpAudioGain
      INTEGER,
   vncsVpSilenceSuppression
      INTEGER,
   vncsVpEchoCancellation
      INTEGER,
   vncsVpSilenceSuppressionFactor
      Unsigned32,
   vncsVpDataCallsAccepted
      INTEGER,
   vncsVpFaxIdleSuppressionG711G726
      INTEGER,
   vncsVpInsertedOutputDelay
      INTEGER,
   vncsVpVoiceTrafficOptimization
      INTEGER,
   vncsVpDtmfRegeneration
      INTEGER,
   vncsVpV17EncodedAsG711G726
      INTEGER }

vncsVpMaxVoiceBitRate OBJECT-TYPE
   SYNTAX     INTEGER  {
                 n64(0),
                 n32(1),
                 n24(2),
                 n16(3) }
   ACCESS     read-write
   STATUS     obsolete
   DESCRIPTION
     "This attribute specifies the maximum encoding bit rate (minimum 
      compression rate) that will be used for voice data.
      
      This attribute was migrated to the max element of the g711G726 
      row of the voiceRates attribute."
   DEFVAL     { n64 }
::= { vncsVpFrOpsEntry 1 }

vncsVpMinVoiceBitRate OBJECT-TYPE
   SYNTAX     INTEGER  {
                 n64(0),
                 n32(1),
                 n24(2),
                 n16(3) }
   ACCESS     read-write
   STATUS     obsolete
   DESCRIPTION
     "This attribute specifies the minimum encoding bit rate (maximum 
      compression rate) that will be used for voice data.
      
      Migration information:
      
      If minVoiceBitRate is 64 kbit/s, it means that the user did not accept 
      any compression. To get the same effect with the 	current 
      provisioning, we set Vncs/m Vp/n voiceEncodingChoice 	first = 
      g711Only, second = none and third = none.
      
      If minVoiceBitRate is 16, 24 or 32 kbit/s, it means that the user 	did 
      accept compression. To get the same effect with the current	
      provisioning, we set the minimum g711G726 rate in Vncs/m 
      VoiceProfile/n 	voiceRates to minVoiceBitRate and leave 
      voiceEncodingChoice with 	its default values."
   DEFVAL     { n16 }
::= { vncsVpFrOpsEntry 2 }

vncsVpMaxModemBitRate OBJECT-TYPE
   SYNTAX     INTEGER  {
                 n64(0),
                 n32(1),
                 n24(2),
                 n16(3) }
   ACCESS     read-write
   STATUS     obsolete
   DESCRIPTION
     "This attribute was migrated to the max element of the g711G726 
      row of the modemFaxRates attribute.
      DESCRIPTION"
   DEFVAL     { n64 }
::= { vncsVpFrOpsEntry 3 }

vncsVpMinModemBitRate OBJECT-TYPE
   SYNTAX     INTEGER  {
                 n64(0),
                 n32(1),
                 n24(2),
                 n16(3) }
   ACCESS     read-write
   STATUS     obsolete
   DESCRIPTION
     "This attribute has been obsoleted. Migration information is as 
      follows:
      
      If minModemBitRate is 64 kbit/s, it means that the user did not 
      accept any compression. To get the same effect with the current 
      provisioning, we set Vncs/m Vp/n modemFaxEncodingChoice first 
      = g711Only, second = none and third = none.
      
      If minModemBitRate is 16, 24 or 32 kbit/s, it means that the user 
      did accept compression. To get the same effect with the current 
      provisioning, we set the minimum g711G726 rate in Vncs/m 
      VoiceProfile/n modemFaxRates to minModemBitRate and leave 
      modemFaxEncodingChoice with its default values.
      DESCRIPTION"
   DEFVAL     { n32 }
::= { vncsVpFrOpsEntry 4 }

vncsVpAudioGain OBJECT-TYPE
   SYNTAX     INTEGER  {
                 minus6(0),
                 minus4(1),
                 minus2(2),
                 n0(3),
                 n2(4),
                 n4(5),
                 n6(6) }
   ACCESS     read-write
   STATUS     obsolete
   DESCRIPTION
     "This attribute has been migrated to VRoute Interface 
      egressAudioGain."
   DEFVAL     { n0 }
::= { vncsVpFrOpsEntry 5 }

vncsVpSilenceSuppression OBJECT-TYPE
   SYNTAX     INTEGER  {
                 off(0),
                 on(1),
                 congested(2),
                 slow(3),
                 slowAndCongested(4) }
   ACCESS     read-write
   STATUS     mandatory
   DESCRIPTION
     "This attribute specifies when silence suppression is desired during 
      voice traffic on an audio call.
      
      If silenceSuppression is off, silence suppression is never desired.
      If silenceSuppression is on, silence suppression is always desired.
      If silenceSuppression is congested, silence suppression is desired 
      only when the network is congested. 
      If silenceSuppression is slow, silence suppression is desired only 
      after 20 seconds without audio.
      If silenceSuppression is slowAndCongested, both the slow and 
      congested options are desired.
      
      The negotiated silence suppression is available in Vsr Svs Framer 
      negotiatedSilenceSuppression."
   DEFVAL     { on }
::= { vncsVpFrOpsEntry 6 }

vncsVpEchoCancellation OBJECT-TYPE
   SYNTAX     INTEGER  {
                 off(0),
                 on(1) }
   ACCESS     read-write
   STATUS     obsolete
   DESCRIPTION
     "This attribute has been migrated to VRoute Interface 
      echoCancellation."
   DEFVAL     { on }
::= { vncsVpFrOpsEntry 7 }

vncsVpSilenceSuppressionFactor OBJECT-TYPE
   SYNTAX     Unsigned32 (0..60)
   ACCESS     read-write
   STATUS     mandatory
   DESCRIPTION
     "This attribute specifies the expected savings (percent reduction) in 
      required bandwidth if silence suppression is used. If silence 
      suppression is used, the bandwidth required for the connection will 
      be lower than if silence suppression is not used. However, the 
      routing system will not be aware of the unused bandwidth unless 
      that bandwidth is specified by this attribute. 
      If the value specified for the expected savings is too low, then some 
      bandwidth made available by the use of silence suppression will be 
      wasted. If the value specified for the expected savings is too high, 
      then some connections may fail to set up because the routing system 
      will over-calculate the amount of bandwidth available.
      The effectiveness of silence suppression can be influenced by 
      language related speech patterns."
   DEFVAL     { 40 }
::= { vncsVpFrOpsEntry 8 }

vncsVpDataCallsAccepted OBJECT-TYPE
   SYNTAX     INTEGER  {
                 no(0),
                 yes(1) }
   ACCESS     read-write
   STATUS     mandatory
   DESCRIPTION
     "This attribute specifies whether data calls are allowed if this profile 
      is used."
   DEFVAL     { yes }
::= { vncsVpFrOpsEntry 9 }

vncsVpFaxIdleSuppressionG711G726 OBJECT-TYPE
   SYNTAX     INTEGER  {
                 off(0),
                 on(1) }
   ACCESS     read-write
   STATUS     mandatory
   DESCRIPTION
     "This attribute specifies the fax idle suppression parameter used 
      during negotiation with the remote end across the subnet. It applies 
      only to fax traffic, not voice or modem traffic.
      
      The negotiated G.711/G.726 fax idle suppression is available in Vsr 
      Svs Framer negotiatedFisG711G726."
   DEFVAL     { on }
::= { vncsVpFrOpsEntry 15 }

vncsVpInsertedOutputDelay OBJECT-TYPE
   SYNTAX     INTEGER  {
                 n5(5),
                 n15(15),
                 n22(22),
                 n30(30),
                 n35(35),
                 n40(40),
                 n45(45),
                 n50(50),
                 n75(75),
                 n100(100),
                 n125(125),
                 n150(150) }
   ACCESS     read-write
   STATUS     mandatory
   DESCRIPTION
     "This attribute specifies the amount of added output delay used to 
      compensate for cross network delay variations. It applies to voice, 
      modem and fax traffic. It is required to add output delay so that the 
      statistical variation in the transit time of cells crossing the network 
      does not cause gaps in speech. Backbone networks where high 
      priority traffic consumes a high percentage of trunk bandwidth will 
      require a higher insertedOutputDelay to compensate for the greater 
      cell delay variation (CDV).
      
      This attribute is ignored if this call runs on a 1pDS1V or 1pE1V 
      card."
   DEFVAL     { n22 }
::= { vncsVpFrOpsEntry 17 }

vncsVpVoiceTrafficOptimization OBJECT-TYPE
   SYNTAX     INTEGER  {
                 bandwidth(0),
                 delay(1) }
   ACCESS     read-write
   STATUS     obsolete
   DESCRIPTION
     "This attribute is not supported now.
      This attribute specifies how to optimize voice traffic. Setting 
      voiceTrafficOptimization to bandwidth specifies that voice traffic 
      should be optimized to preserve bandwidth. Setting 
      voiceTrafficOptimization to delay specifies that voice traffic should 
      be optimized to minimize delay."
   DEFVAL     { bandwidth }
::= { vncsVpFrOpsEntry 18 }

vncsVpDtmfRegeneration OBJECT-TYPE
   SYNTAX     INTEGER  {
                 off(0),
                 on(1) }
   ACCESS     read-write
   STATUS     mandatory
   DESCRIPTION
     "This attribute specifies the DTMF regeneration parameter used 
      during negotiation with the remote end across the subnet. 
      
      If dtmfRegeneration is on, it is desired that DTMF tones received 
      from the link are first converted to digits before being sent to the 
      subnet. When a digit is received from the subnet, its respective 
      DTMF tone is desired to be generated before being sent to the link.
      
      If dtmfRegeneration is off, it is desired that DTMF tones are 
      transported transparently as audio.
      
      DTMF regeneration is not supported on 1pDS1V, 1pE1V, and 
      J2MV cards. On these cards, the value of dtmfRegeneration is 
      ignored.
      
      The negotiated DTMF regeneration is available in Vsr Svs Framer 
      negotiatedDtmfRegeneration."
   DEFVAL     { off }
::= { vncsVpFrOpsEntry 19 }

vncsVpV17EncodedAsG711G726 OBJECT-TYPE
   SYNTAX     INTEGER  {
                 no(0),
                 yes(1) }
   ACCESS     read-write
   STATUS     mandatory
   DESCRIPTION
     "This attribute specifies how services using this VoiceProfile 
      negotiate with V.17 fax machines. This attribute is not used unless 
      the negotiated fax encoding, available in Vsr Svs Framer 
      negotiatedEncoding, is v29V27Relay and the negotiated 
      modemFax encoding, available in Vsr Svs Framer 
      negotiatedEncoding, is g711, g726 or g711G726.
      
      If v17EncodedAsG711G726 is no, it is desired that V.17 fax 
      machines be instructed to use V.29 so that V.29 fax traffic sent by 
      fax machines can be demodulated and encoded using fax relay.
      
      If v17EncodedAsG711G726 is yes, it is desired that V.17 fax 
      machines be permitted to use V.17 so that V.17 fax traffic sent by 
      fax machines can be encoded using G.711 or G.726. The actual 
      encoding performed depends on the negotiated minimum and 
      maximum modemFax rates, available in Vsr Svs Framer 
      negotiatedRates.
      
      The actual negotiation between services using this VoiceProfile and 
      V.17 fax machines is available in Vsr Svs Framer 
      negotiatedV17AsG711G726."
   DEFVAL     { no }
::= { vncsVpFrOpsEntry 20 }

vncsVpStatsTable OBJECT-TYPE
   SYNTAX     SEQUENCE OF VncsVpStatsEntry
   ACCESS     not-accessible
   STATUS     mandatory
   DESCRIPTION
     "This group contains the operational statistics data for a Voice 
      Networking profile component."
::= { vncsVp 4 }

vncsVpStatsEntry OBJECT-TYPE
   SYNTAX     VncsVpStatsEntry
   ACCESS     not-accessible
   STATUS     mandatory
   DESCRIPTION
     "An entry in the vncsVpStatsTable."
   INDEX {
      vncsIndex,
      vncsVpIndex }
::= { vncsVpStatsTable 1 }

VncsVpStatsEntry ::= SEQUENCE {
   vncsVpUsageCount
      Unsigned32 }

vncsVpUsageCount OBJECT-TYPE
   SYNTAX     Unsigned32 (0..4294967295)
   ACCESS     read-only
   STATUS     mandatory
   DESCRIPTION
     "This attribute counts the number of times this VoiceProfile is 
      accessed to set up a connection. This counter wraps to 0 when it 
      reaches its maximum value."
::= { vncsVpStatsEntry 1 }

vncsVpVoiceRatesTable OBJECT-TYPE
   SYNTAX     SEQUENCE OF VncsVpVoiceRatesEntry
   ACCESS     not-accessible
   STATUS     obsolete
   DESCRIPTION
     "This attribute has been migrated to voiceRates."
::= { vncsVp 322 }

vncsVpVoiceRatesEntry OBJECT-TYPE
   SYNTAX     VncsVpVoiceRatesEntry
   ACCESS     not-accessible
   STATUS     obsolete
   DESCRIPTION
     "An entry in the vncsVpVoiceRatesTable."
   INDEX {
      vncsIndex,
      vncsVpIndex,
      vncsVpVoiceRatesEncodingIndex,
      vncsVpVoiceRatesRateIndex }
::= { vncsVpVoiceRatesTable 1 }

VncsVpVoiceRatesEntry ::= SEQUENCE {
   vncsVpVoiceRatesEncodingIndex
      INTEGER,
   vncsVpVoiceRatesRateIndex
      INTEGER,
   vncsVpVoiceRatesValue
      FixedPoint1 }

vncsVpVoiceRatesEncodingIndex OBJECT-TYPE
   SYNTAX     INTEGER  {
                 g711Only(0),
                 g711G726(1),
                 g728Only(2),
                 g729Only(3) }
   ACCESS     not-accessible
   STATUS     obsolete
   DESCRIPTION
     "This variable represents the next to last index for the 
      vncsVpVoiceRatesTable."
::= { vncsVpVoiceRatesEntry 1 }

vncsVpVoiceRatesRateIndex OBJECT-TYPE
   SYNTAX     INTEGER  {
                 min(0),
                 max(1) }
   ACCESS     not-accessible
   STATUS     obsolete
   DESCRIPTION
     "This variable represents the final index for the 
      vncsVpVoiceRatesTable."
::= { vncsVpVoiceRatesEntry 2 }

vncsVpVoiceRatesValue OBJECT-TYPE
   SYNTAX     FixedPoint1 (80 | 160 | 240 | 320 | 640)
   ACCESS     read-write
   STATUS     obsolete
   DESCRIPTION
     "This variable represents an individual value for the
      vncsVpVoiceRatesTable."
::= { vncsVpVoiceRatesEntry 3 }

vncsVpVoiceEncodingChoiceTable OBJECT-TYPE
   SYNTAX     SEQUENCE OF VncsVpVoiceEncodingChoiceEntry
   ACCESS     not-accessible
   STATUS     obsolete
   DESCRIPTION
     "This attribute has been migrated to voiceEncodingChoice."
::= { vncsVp 323 }

vncsVpVoiceEncodingChoiceEntry OBJECT-TYPE
   SYNTAX     VncsVpVoiceEncodingChoiceEntry
   ACCESS     not-accessible
   STATUS     obsolete
   DESCRIPTION
     "An entry in the vncsVpVoiceEncodingChoiceTable."
   INDEX {
      vncsIndex,
      vncsVpIndex,
      vncsVpVoiceEncodingChoiceIndex }
::= { vncsVpVoiceEncodingChoiceTable 1 }

VncsVpVoiceEncodingChoiceEntry ::= SEQUENCE {
   vncsVpVoiceEncodingChoiceIndex
      INTEGER,
   vncsVpVoiceEncodingChoiceValue
      INTEGER }

vncsVpVoiceEncodingChoiceIndex OBJECT-TYPE
   SYNTAX     INTEGER  {
                 first(0),
                 second(1),
                 third(2) }
   ACCESS     not-accessible
   STATUS     obsolete
   DESCRIPTION
     "This variable represents the vncsVpVoiceEncodingChoiceTable
      specific index for the vncsVpVoiceEncodingChoiceTable."
::= { vncsVpVoiceEncodingChoiceEntry 1 }

vncsVpVoiceEncodingChoiceValue OBJECT-TYPE
   SYNTAX     INTEGER  {
                 g711Only(0),
                 g711G726(1),
                 g728Only(2),
                 g729Only(3),
                 none(4) }
   ACCESS     read-write
   STATUS     obsolete
   DESCRIPTION
     "This variable represents an individual value for the
      vncsVpVoiceEncodingChoiceTable."
::= { vncsVpVoiceEncodingChoiceEntry 2 }

vncsVpModemFaxRatesTable OBJECT-TYPE
   SYNTAX     SEQUENCE OF VncsVpModemFaxRatesEntry
   ACCESS     not-accessible
   STATUS     obsolete
   DESCRIPTION
     "This attribute has been migrated to modemFaxRates."
::= { vncsVp 324 }

vncsVpModemFaxRatesEntry OBJECT-TYPE
   SYNTAX     VncsVpModemFaxRatesEntry
   ACCESS     not-accessible
   STATUS     obsolete
   DESCRIPTION
     "An entry in the vncsVpModemFaxRatesTable."
   INDEX {
      vncsIndex,
      vncsVpIndex,
      vncsVpModemFaxRatesEncodingIndex,
      vncsVpModemFaxRatesRateIndex }
::= { vncsVpModemFaxRatesTable 1 }

VncsVpModemFaxRatesEntry ::= SEQUENCE {
   vncsVpModemFaxRatesEncodingIndex
      INTEGER,
   vncsVpModemFaxRatesRateIndex
      INTEGER,
   vncsVpModemFaxRatesValue
      FixedPoint1 }

vncsVpModemFaxRatesEncodingIndex OBJECT-TYPE
   SYNTAX     INTEGER  {
                 g711Only(0),
                 g711G726(1),
                 relay(2) }
   ACCESS     not-accessible
   STATUS     obsolete
   DESCRIPTION
     "This variable represents the next to last index for the 
      vncsVpModemFaxRatesTable."
::= { vncsVpModemFaxRatesEntry 1 }

vncsVpModemFaxRatesRateIndex OBJECT-TYPE
   SYNTAX     INTEGER  {
                 min(0),
                 max(1) }
   ACCESS     not-accessible
   STATUS     obsolete
   DESCRIPTION
     "This variable represents the final index for the 
      vncsVpModemFaxRatesTable."
::= { vncsVpModemFaxRatesEntry 2 }

vncsVpModemFaxRatesValue OBJECT-TYPE
   SYNTAX     FixedPoint1 (3 | 12 | 24 | 48 | 72 | 96 | 120 | 144 | 160 | 240 | 320 | 640)
   ACCESS     read-write
   STATUS     obsolete
   DESCRIPTION
     "This variable represents an individual value for the
      vncsVpModemFaxRatesTable."
::= { vncsVpModemFaxRatesEntry 3 }

vncsVpModemFaxEncodingChoiceTable OBJECT-TYPE
   SYNTAX     SEQUENCE OF VncsVpModemFaxEncodingChoiceEntry
   ACCESS     not-accessible
   STATUS     obsolete
   DESCRIPTION
     "This attribute has been migrated to modemFaxEncodingChoice.
      
      The faxRelay feature must be present to include a setting of relay."
::= { vncsVp 325 }

vncsVpModemFaxEncodingChoiceEntry OBJECT-TYPE
   SYNTAX     VncsVpModemFaxEncodingChoiceEntry
   ACCESS     not-accessible
   STATUS     obsolete
   DESCRIPTION
     "An entry in the vncsVpModemFaxEncodingChoiceTable."
   INDEX {
      vncsIndex,
      vncsVpIndex,
      vncsVpModemFaxEncodingChoiceIndex }
::= { vncsVpModemFaxEncodingChoiceTable 1 }

VncsVpModemFaxEncodingChoiceEntry ::= SEQUENCE {
   vncsVpModemFaxEncodingChoiceIndex
      INTEGER,
   vncsVpModemFaxEncodingChoiceValue
      INTEGER }

vncsVpModemFaxEncodingChoiceIndex OBJECT-TYPE
   SYNTAX     INTEGER  {
                 first(0),
                 second(1),
                 third(2) }
   ACCESS     not-accessible
   STATUS     obsolete
   DESCRIPTION
     "This variable represents the vncsVpModemFaxEncodingChoiceTable
      specific index for the vncsVpModemFaxEncodingChoiceTable."
::= { vncsVpModemFaxEncodingChoiceEntry 1 }

vncsVpModemFaxEncodingChoiceValue OBJECT-TYPE
   SYNTAX     INTEGER  {
                 g711Only(0),
                 g711G726(1),
                 relay(2),
                 none(3) }
   ACCESS     read-write
   STATUS     obsolete
   DESCRIPTION
     "This variable represents an individual value for the
      vncsVpModemFaxEncodingChoiceTable."
::= { vncsVpModemFaxEncodingChoiceEntry 2 }

vncsVpNewVoiceRatesTable OBJECT-TYPE
   SYNTAX     SEQUENCE OF VncsVpNewVoiceRatesEntry
   ACCESS     not-accessible
   STATUS     mandatory
   DESCRIPTION
     "This attribute specifies the minimum and maximum voice rate 
      parameters used during negotiation with the remote end across the 
      subnet. For g711G726 encoding, rates can change during voice 
      traffic due to congestion in the network. Therefore, you can have 
      differing minimum and maximum rates for g711G726 encoding. All 
      other encodings have a fixed rate for the duration of voice traffic 
      and so their minimum and maximum rates can not be modified.
      
      The negotiated minimum and maximum voice rates are available in 
      Vsr Svs Framer negotiatedRates."
::= { vncsVp 381 }

vncsVpNewVoiceRatesEntry OBJECT-TYPE
   SYNTAX     VncsVpNewVoiceRatesEntry
   ACCESS     not-accessible
   STATUS     mandatory
   DESCRIPTION
     "An entry in the vncsVpNewVoiceRatesTable."
   INDEX {
      vncsIndex,
      vncsVpIndex,
      vncsVpNewVoiceRatesEncodingIndex,
      vncsVpNewVoiceRatesRateIndex }
::= { vncsVpNewVoiceRatesTable 1 }

VncsVpNewVoiceRatesEntry ::= SEQUENCE {
   vncsVpNewVoiceRatesEncodingIndex
      INTEGER,
   vncsVpNewVoiceRatesRateIndex
      INTEGER,
   vncsVpNewVoiceRatesValue
      FixedPoint1 }

vncsVpNewVoiceRatesEncodingIndex OBJECT-TYPE
   SYNTAX     INTEGER  {
                 g711Only(0),
                 g711G726(1),
                 g728Only(2),
                 g729Only(3) }
   ACCESS     not-accessible
   STATUS     mandatory
   DESCRIPTION
     "This variable represents the next to last index for the 
      vncsVpNewVoiceRatesTable."
::= { vncsVpNewVoiceRatesEntry 1 }

vncsVpNewVoiceRatesRateIndex OBJECT-TYPE
   SYNTAX     INTEGER  {
                 min(0),
                 max(1) }
   ACCESS     not-accessible
   STATUS     mandatory
   DESCRIPTION
     "This variable represents the final index for the 
      vncsVpNewVoiceRatesTable."
::= { vncsVpNewVoiceRatesEntry 2 }

vncsVpNewVoiceRatesValue OBJECT-TYPE
   SYNTAX     FixedPoint1 (80 | 160 | 240 | 320 | 640)
   ACCESS     read-write
   STATUS     mandatory
   DESCRIPTION
     "This variable represents an individual value for the
      vncsVpNewVoiceRatesTable."
::= { vncsVpNewVoiceRatesEntry 3 }

vncsVpNewVoiceEncodingChoiceTable OBJECT-TYPE
   SYNTAX     SEQUENCE OF VncsVpNewVoiceEncodingChoiceEntry
   ACCESS     not-accessible
   STATUS     mandatory
   DESCRIPTION
     "This attribute specifies preferences regarding the encoding of voice 
      traffic. During the setup of an audio call, the local and remote ends 
      negotiate a common encoding to use. The local end's ordered list of 
      preferred encodings is given by all voiceEncodingChoice elements 
      that are not set to none. Prior to negotiation, the local end removes 
      encodings from its list that it cannot use for a particular call. For 
      example, the card for a particular call may not support certain 
      encodings. After this local check, the local end sends its voice 
      encoding preferences to the remote end. The remote end chooses 
      the most preferred encoding that it can support from the list and this 
      encoding is the one used during voice traffic. If the remote end 
      cannot support any encodings on the local end's list, a call does not 
      proceed and an alarm is issued.
      
      The current encoding and encoding rate are available in Vsr Svs 
      currentEncoding and Vsr Svs currentRate.
      
      The encoding choice g711Only specifies that pulse code modulation 
      (PCM) defined by ITU-T G.711 should be performed to encode 
      voice traffic for calls using this profile. In this case, all voice traffic 
      is carried uncompressed at 64 kbit/s.
      
      The encoding choice g711G726 specifies that either pulse code 
      modulation (PCM) defined by ITU-T G.711 or adaptive differential 
      pulse code modulation (ADPCM) defined by ITU-T G.726 should 
      be performed to encode voice traffic for calls using this profile. The 
      actual encoding performed depends on congestion in the network 
      and the settings of the g711G726 row of the voiceRates attribute.
      
      The encoding choice of g728Only specifies that the Low Delay 
      Coded Excited Linear Predictive Coder (LD-CELP) algorithm 
      defined by ITU-T G.728 should be performed to encode voice 
      traffic for calls using this profile. In this case, all voice traffic is 
      carried at 16 kbit/s.
      
      The encoding choice of g729Only specifies that the Conjugated 
      Structure Algebraic Code Excited Linear Predictive Coder 
      (CS-ACELP) algorithm defined by ITU-T G.729 should be 
      performed to encode voice traffic for calls using this profile. In this 
      case, all voice traffic is carried at 8 kbit/s.
      
      The encoding choice of none specifies the end of the encoding 
      choice list. No other encoding choice can appear after none, and 
      none cannot appear as the first choice. The only encoding choice 
      that can appear more than once in voiceEncodingChoice is none.
      
      G.728 and G.729 encoding cannot be performed on a 1pDS1V, 
      1pE1V or J2MV card. 
      
      The negotiated voice encoding is available in Vsr Svs Framer 
      negotiatedEncoding."
::= { vncsVp 382 }

vncsVpNewVoiceEncodingChoiceEntry OBJECT-TYPE
   SYNTAX     VncsVpNewVoiceEncodingChoiceEntry
   ACCESS     not-accessible
   STATUS     mandatory
   DESCRIPTION
     "An entry in the vncsVpNewVoiceEncodingChoiceTable."
   INDEX {
      vncsIndex,
      vncsVpIndex,
      vncsVpNewVoiceEncodingChoiceIndex }
::= { vncsVpNewVoiceEncodingChoiceTable 1 }

VncsVpNewVoiceEncodingChoiceEntry ::= SEQUENCE {
   vncsVpNewVoiceEncodingChoiceIndex
      INTEGER,
   vncsVpNewVoiceEncodingChoiceValue
      INTEGER }

vncsVpNewVoiceEncodingChoiceIndex OBJECT-TYPE
   SYNTAX     INTEGER  {
                 first(0),
                 second(1),
                 third(2) }
   ACCESS     not-accessible
   STATUS     mandatory
   DESCRIPTION
     "This variable represents the vncsVpNewVoiceEncodingChoiceTable
      specific index for the vncsVpNewVoiceEncodingChoiceTable."
::= { vncsVpNewVoiceEncodingChoiceEntry 1 }

vncsVpNewVoiceEncodingChoiceValue OBJECT-TYPE
   SYNTAX     INTEGER  {
                 g711Only(0),
                 g711G726(1),
                 g728Only(2),
                 g729Only(3),
                 none(4) }
   ACCESS     read-write
   STATUS     mandatory
   DESCRIPTION
     "This variable represents an individual value for the
      vncsVpNewVoiceEncodingChoiceTable."
::= { vncsVpNewVoiceEncodingChoiceEntry 2 }

vncsVpNewModemFaxRatesTable OBJECT-TYPE
   SYNTAX     SEQUENCE OF VncsVpNewModemFaxRatesEntry
   ACCESS     not-accessible
   STATUS     mandatory
   DESCRIPTION
     "This attribute specifies the minimum and maximum modemFax and 
      fax rate parameters used during negotiation with the remote end 
      across the subnet.
      
      For g711Only encoding, all modem/fax traffic is carried 
      uncompressed at 64 kbit/s, so this row of modemFaxRates cannot 
      be changed.
      
      For g711G726 encoding, rates can change during modemFax and 
      fax traffic due to congestion in the network. The minimum and 
      maximum rates that can occur during the modemFax traffic are 
      specified by the g711G726 row of modemFaxRates.
      
      The relay row of modemFaxRates specifies the minimum and 
      maximum rates of sending fax machines that are allowed for fax 
      relay. relay does not apply to modem calls.
      
      The negotiated minimum and maximum modemFax and fax rates 
      are available in Vsr Svs Framer negotiatedRates."
::= { vncsVp 383 }

vncsVpNewModemFaxRatesEntry OBJECT-TYPE
   SYNTAX     VncsVpNewModemFaxRatesEntry
   ACCESS     not-accessible
   STATUS     mandatory
   DESCRIPTION
     "An entry in the vncsVpNewModemFaxRatesTable."
   INDEX {
      vncsIndex,
      vncsVpIndex,
      vncsVpNewModemFaxRatesEncodingIndex,
      vncsVpNewModemFaxRatesRateIndex }
::= { vncsVpNewModemFaxRatesTable 1 }

VncsVpNewModemFaxRatesEntry ::= SEQUENCE {
   vncsVpNewModemFaxRatesEncodingIndex
      INTEGER,
   vncsVpNewModemFaxRatesRateIndex
      INTEGER,
   vncsVpNewModemFaxRatesValue
      FixedPoint1 }

vncsVpNewModemFaxRatesEncodingIndex OBJECT-TYPE
   SYNTAX     INTEGER  {
                 g711Only(0),
                 g711G726(1),
                 relay(2) }
   ACCESS     not-accessible
   STATUS     mandatory
   DESCRIPTION
     "This variable represents the next to last index for the 
      vncsVpNewModemFaxRatesTable."
::= { vncsVpNewModemFaxRatesEntry 1 }

vncsVpNewModemFaxRatesRateIndex OBJECT-TYPE
   SYNTAX     INTEGER  {
                 min(0),
                 max(1) }
   ACCESS     not-accessible
   STATUS     mandatory
   DESCRIPTION
     "This variable represents the final index for the 
      vncsVpNewModemFaxRatesTable."
::= { vncsVpNewModemFaxRatesEntry 2 }

vncsVpNewModemFaxRatesValue OBJECT-TYPE
   SYNTAX     FixedPoint1 (0 | 3 | 12 | 24 | 48 | 72 | 96 | 120 | 144 | 160 | 240 | 320 | 640)
   ACCESS     read-write
   STATUS     mandatory
   DESCRIPTION
     "This variable represents an individual value for the
      vncsVpNewModemFaxRatesTable."
::= { vncsVpNewModemFaxRatesEntry 3 }

vncsVpNewModemFaxEncodingChoiceTable OBJECT-TYPE
   SYNTAX     SEQUENCE OF VncsVpNewModemFaxEncodingChoiceEntry
   ACCESS     not-accessible
   STATUS     mandatory
   DESCRIPTION
     "This attribute specifies preferences regarding the encoding of 
      modemFax and fax traffic. During the setup of an audio call, the 
      local and remote ends negotiate one common encoding to use 
      during modemFax traffic and one common encoding to use during 
      fax traffic. The local end's ordered list of preferred encodings is 
      given by all modemFaxEncodingChoice elements that are not set to 
      none. Prior to negotiation, the local end removes encodings from its 
      list that it cannot use for a particular call. For example, the card for 
      a particular call may not be able to support certain encodings, or in 
      the case of relay, the rate of the sending machine may not be 
      supported. After this local check, the local end sends its modem/fax 
      encoding preferences to the remote end. The remote end uses the 
      two most preferred encodings that it can support from the list to 
      determine the encoding used during modemFax traffic and the 
      encoding used during fax traffic. If the remote end cannot support 
      any encodings on the local end's list, a call does not proceed and an 
      alarm is issued.
      
      The current encoding and encoding rate are available in Vsr Svs 
      currentEncoding and Vsr Svs currentRate.
      
      The encoding choice g711Only specifies that pulse code modulation 
      (PCM) defined by ITU-T G.711 should be performed to encode 
      modem/fax traffic for calls using this profile. In this case, all 
      modem/fax traffic is carried uncompressed at 64 kbit/s.
      
      The encoding choice g711G726 specifies that either pulse code 
      modulation (PCM) defined by ITU-T G.711 or adaptive differential 
      pulse code modulation (ADPCM) defined by ITU-T G.726 should 
      be performed to encode modem/fax traffic for calls using this 
      profile. The actual encoding performed depends on congestion in 
      the network and the settings of the g711G726 row of the 
      modemFaxRates attribute.
      
      The encoding choice of relay specifies that modulated modem/fax 
      traffic is demodulated and sent through the network as Passport 
      cells at the base rate of the sending machine. The types of 
      modulation/demodulation supported are V.29 up to 9.6 kbit/s and 
      V.27 up to 4.8 kbit/s. Only fax traffic can use relay.
      
      If modemFaxEncodingChoice is relay, none, none, modem traffic 
      is not supported. If modemFaxEncodingChoice is none, none, 
      none, all traffic is treated like voice traffic.
      
      Fax relay cannot be performed on 1pDS1V, 1pE1V or J2MV cards.
      
      The negotiated modemFax and fax encodings are available in Vsr 
      Svs Framer negotiatedEncoding."
::= { vncsVp 384 }

vncsVpNewModemFaxEncodingChoiceEntry OBJECT-TYPE
   SYNTAX     VncsVpNewModemFaxEncodingChoiceEntry
   ACCESS     not-accessible
   STATUS     mandatory
   DESCRIPTION
     "An entry in the vncsVpNewModemFaxEncodingChoiceTable."
   INDEX {
      vncsIndex,
      vncsVpIndex,
      vncsVpNewModemFaxEncodingChoiceIndex }
::= { vncsVpNewModemFaxEncodingChoiceTable 1 }

VncsVpNewModemFaxEncodingChoiceEntry ::= SEQUENCE {
   vncsVpNewModemFaxEncodingChoiceIndex
      INTEGER,
   vncsVpNewModemFaxEncodingChoiceValue
      INTEGER }

vncsVpNewModemFaxEncodingChoiceIndex OBJECT-TYPE
   SYNTAX     INTEGER  {
                 first(0),
                 second(1),
                 third(2) }
   ACCESS     not-accessible
   STATUS     mandatory
   DESCRIPTION
     "This variable represents the vncsVpNewModemFaxEncodingChoiceTable
      specific index for the vncsVpNewModemFaxEncodingChoiceTable."
::= { vncsVpNewModemFaxEncodingChoiceEntry 1 }

vncsVpNewModemFaxEncodingChoiceValue OBJECT-TYPE
   SYNTAX     INTEGER  {
                 g711Only(0),
                 g711G726(1),
                 relay(2),
                 none(3) }
   ACCESS     read-write
   STATUS     mandatory
   DESCRIPTION
     "This variable represents an individual value for the
      vncsVpNewModemFaxEncodingChoiceTable."
::= { vncsVpNewModemFaxEncodingChoiceEntry 2 }




-- 
-- Version and Compliance statements
-- 



-- Object-Group Statement:
-- A list of all current accessible leaf objects.

-- OBJECTS { vncsDPStorageType,
--           vncsVpDataCallsAccepted,
--           vncsVRoutesValue,
--           vncsVpNewModemFaxEncodingChoiceValue,
--           vncsVpRequiredSecurity,
--           vncsVpInsertedOutputDelay,
--           vncsVpSilenceSuppressionFactor,
--           vncsVpNewModemFaxRatesValue,
--           vncsDPDnRowStatus,
--           vncsVpPathAttributeToMinimize,
--           vncsVpOptimization,
--           vncsVpRequiredTrafficType,
--           vncsDPComponentName,
--           vncsVpComponentName,
--           vncsVpNewVoiceRatesValue,
--           vncsVpPermittedTrunkTypes,
--           vncsVpEmissionPriority,
--           vncsVpRowStatus,
--           vncsVpHoldingPriority,
--           vncsVpDtmfRegeneration,
--           vncsDPIncompleteTranslations,
--           vncsRowStatus,
--           vncsVpMaximumAcceptableCost,
--           vncsTotalTranslations,
--           vncsVpSilenceSuppression,
--           vncsDPRowStatus,
--           vncsDPDnNumberingPlanIndicator,
--           vncsDPDnComponentName,
--           vncsVpPathFailureAction,
--           vncsVpV17EncodedAsG711G726,
--           vncsDPFailedTranslations,
--           vncsVpUsageCount,
--           vncsDPDnDataNetworkAddress,
--           vncsCommentText,
--           vncsDPDnStorageType,
--           vncsVpDiscardPriority,
--           vncsVpFaxIdleSuppressionG711G726,
--           vncsDPDnVoiceProfileNumber,
--           vncsDPDnDestinationNodeId,
--           vncsDPCompleteTranslations,
--           vncsComponentName,
--           vncsVpBumpPreference,
--           vncsVpStorageType,
--           vncsDPDnDestinationComponentId,
--           vncsVpMaximumAcceptableDelay,
--           vncsVpSetupPriority,
--           vncsStorageType,
--           vncsVpRequiredCustomerParm,
--           vncsVpNewVoiceEncodingChoiceValue }
-- STATUS  mandatory
-- DESCRIPTION
--   "A list of all current accessible leaf objects."

vncsCallServerGroup OBJECT IDENTIFIER ::= { vncsCallServerMIB 1 }
vncsCallServerGroupBE OBJECT IDENTIFIER ::= { vncsCallServerGroup 5 }
vncsCallServerGroupBE01 OBJECT IDENTIFIER ::= { vncsCallServerGroupBE 2 }
vncsCallServerGroupBE01A OBJECT IDENTIFIER ::= { vncsCallServerGroupBE01 2 }



-- Agent-Capabilities Statement:

-- PRODUCT-RELEASE "Passport Release 7.0 VncsCallServer."
-- STATUS          mandatory
-- DESCRIPTION     "VncsCallServer MIB: MIB Version BE01A,
--                  Software Version BG00S4C."
-- SUPPORTS        Nortel-Magellan-Passport-VncsCallServerMIB
--    INCLUDES     { vncsCallServerGroupBE01A }

vncsCallServerCapabilities OBJECT IDENTIFIER ::= { vncsCallServerMIB 3 }
vncsCallServerCapabilitiesBE OBJECT IDENTIFIER ::= { vncsCallServerCapabilities 5 }
vncsCallServerCapabilitiesBE01 OBJECT IDENTIFIER ::= { vncsCallServerCapabilitiesBE 2 }
vncsCallServerCapabilitiesBE01A OBJECT IDENTIFIER ::= { vncsCallServerCapabilitiesBE01 2 }





END
