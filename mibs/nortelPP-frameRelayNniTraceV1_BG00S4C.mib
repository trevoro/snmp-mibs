Nortel-Magellan-Passport-FrameRelayNniTraceMIB
DEFINITIONS ::= BEGIN



IMPORTS

      OBJECT-TYPE
   FROM RFC-1212

      passportMIBs
   FROM Nortel-Magellan-Passport-UsefulDefinitionsMIB

      RowPointer,
      DisplayString,
      StorageType,
      RowStatus,
      Unsigned32
   FROM Nortel-Magellan-Passport-StandardTextualConventionsMIB

      AsciiString,
      NonReplicated
   FROM Nortel-Magellan-Passport-TextualConventionsMIB

      frNniIndex,
      frNni
   FROM Nortel-Magellan-Passport-FrameRelayNniMIB;




-- LAST-UPDATED   "9706300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayNniTrace Enterprise MIB."

frameRelayNniTraceMIB OBJECT IDENTIFIER ::= { passportMIBs 106 }










-- FrUni/n Trace
-- FrNni/n Trace
-- The Trace component of the Frame Relay service determines if the 
-- trace capability is allowed on this interface. If it is not provisioned, 
-- then a trace session cannot be started on this service.

frNniTrace OBJECT IDENTIFIER ::= { frNni 7 }



frNniTraceRowStatusTable OBJECT-TYPE
   SYNTAX     SEQUENCE OF FrNniTraceRowStatusEntry
   ACCESS     not-accessible
   STATUS     mandatory
   DESCRIPTION
     "This entry controls the addition and deletion of 
      frNniTrace components."
::= { frNniTrace 1 }

frNniTraceRowStatusEntry OBJECT-TYPE
   SYNTAX     FrNniTraceRowStatusEntry
   ACCESS     not-accessible
   STATUS     mandatory
   DESCRIPTION
     "A single entry in the table represents a single 
      frNniTrace component."
   INDEX {
      frNniIndex,
      frNniTraceIndex }
::= { frNniTraceRowStatusTable 1 }

FrNniTraceRowStatusEntry ::= SEQUENCE {
   frNniTraceRowStatus
      RowStatus,
   frNniTraceComponentName
      DisplayString,
   frNniTraceStorageType
      StorageType,
   frNniTraceIndex
      NonReplicated }

frNniTraceRowStatus OBJECT-TYPE
   SYNTAX     RowStatus 
   ACCESS     read-write
   STATUS     mandatory
   DESCRIPTION
     "This variable is used as the basis for SNMP naming of
      frNniTrace components.
      These components can be added and deleted."
::= { frNniTraceRowStatusEntry 1 }

frNniTraceComponentName OBJECT-TYPE
   SYNTAX     DisplayString 
   ACCESS     read-only
   STATUS     mandatory
   DESCRIPTION
     "This variable provides the component's string name for
      use with the ASCII Console Interface"
::= { frNniTraceRowStatusEntry 2 }

frNniTraceStorageType OBJECT-TYPE
   SYNTAX     StorageType 
   ACCESS     read-only
   STATUS     mandatory
   DESCRIPTION
     "This variable represents the storage type value for the
      frNniTrace tables."
::= { frNniTraceRowStatusEntry 4 }

frNniTraceIndex OBJECT-TYPE
   SYNTAX     NonReplicated 
   ACCESS     not-accessible
   STATUS     mandatory
   DESCRIPTION
     "This variable represents the index for the frNniTrace tables."
::= { frNniTraceRowStatusEntry 10 }

frNniTraceOperationalTable OBJECT-TYPE
   SYNTAX     SEQUENCE OF FrNniTraceOperationalEntry
   ACCESS     not-accessible
   STATUS     mandatory
   DESCRIPTION
     "This group provides the operational attributes for the Trace 
      component."
::= { frNniTrace 10 }

frNniTraceOperationalEntry OBJECT-TYPE
   SYNTAX     FrNniTraceOperationalEntry
   ACCESS     not-accessible
   STATUS     mandatory
   DESCRIPTION
     "An entry in the frNniTraceOperationalTable."
   INDEX {
      frNniIndex,
      frNniTraceIndex }
::= { frNniTraceOperationalTable 1 }

FrNniTraceOperationalEntry ::= SEQUENCE {
   frNniTraceReceiverName
      AsciiString,
   frNniTraceDuration
      Unsigned32,
   frNniTraceQueueLimit
      Unsigned32,
   frNniTraceSession
      RowPointer }

frNniTraceReceiverName OBJECT-TYPE
   SYNTAX     AsciiString (SIZE (0..8))
   ACCESS     read-write
   STATUS     mandatory
   DESCRIPTION
     "This attribute should be set to the name of the desired trace receiver 
      before starting a trace session. All available trace receivers are listed 
      under the Trace Rcvr/<string> component. This attribute cannot be 
      set while a trace is active."
::= { frNniTraceOperationalEntry 2 }

frNniTraceDuration OBJECT-TYPE
   SYNTAX     Unsigned32 (0..9999)
   ACCESS     read-write
   STATUS     mandatory
   DESCRIPTION
     "This attribute specifies the duration, in minutes, of a trace session. 
      A value of 0 indicates unlimited duration in which case a trace 
      session remains active until a stop command is issued. The default 
      duration is 60 minutes. This attribute cannot be set while a trace is 
      active."
   DEFVAL     { 60 }
::= { frNniTraceOperationalEntry 3 }

frNniTraceQueueLimit OBJECT-TYPE
   SYNTAX     Unsigned32 (1..100)
   ACCESS     read-write
   STATUS     mandatory
   DESCRIPTION
     "This attribute specifies the total number of bytes of traced data 
      which may be queued for transmission to the trace receiver. When 
      this limit is exceeded, incoming traced frames are discarded. This 
      attribute can be set while a trace is active and takes effect 
      immediately."
   DEFVAL     { 20 }
::= { frNniTraceOperationalEntry 4 }

frNniTraceSession OBJECT-TYPE
   SYNTAX     RowPointer 
   ACCESS     read-only
   STATUS     mandatory
   DESCRIPTION
     "This attribute is set automatically. It identifies the Trace Session 
      component which is forwarding the trace data. This attribute is 
      empty unless a trace is active."
::= { frNniTraceOperationalEntry 5 }


-- FrUni/n Trace Filter 
-- FrNni/n Trace Filter
-- The Filter component defines the type of traced data that is sent to 
-- the receiver. The Filter component provides default values for all its 
-- attributes which are sufficient to start a trace session. Nonetheless, if 
-- needed, these attributes may be changed before or during a trace 
-- session.

frNniTraceFilter OBJECT IDENTIFIER ::= { frNniTrace 2 }



frNniTraceFilterRowStatusTable OBJECT-TYPE
   SYNTAX     SEQUENCE OF FrNniTraceFilterRowStatusEntry
   ACCESS     not-accessible
   STATUS     mandatory
   DESCRIPTION
     "This entry controls the addition and deletion of 
      frNniTraceFilter components."
::= { frNniTraceFilter 1 }

frNniTraceFilterRowStatusEntry OBJECT-TYPE
   SYNTAX     FrNniTraceFilterRowStatusEntry
   ACCESS     not-accessible
   STATUS     mandatory
   DESCRIPTION
     "A single entry in the table represents a single 
      frNniTraceFilter component."
   INDEX {
      frNniIndex,
      frNniTraceIndex,
      frNniTraceFilterIndex }
::= { frNniTraceFilterRowStatusTable 1 }

FrNniTraceFilterRowStatusEntry ::= SEQUENCE {
   frNniTraceFilterRowStatus
      RowStatus,
   frNniTraceFilterComponentName
      DisplayString,
   frNniTraceFilterStorageType
      StorageType,
   frNniTraceFilterIndex
      NonReplicated }

frNniTraceFilterRowStatus OBJECT-TYPE
   SYNTAX     RowStatus 
   ACCESS     read-only
   STATUS     mandatory
   DESCRIPTION
     "This variable is used as the basis for SNMP naming of
      frNniTraceFilter components.
      These components cannot be added nor deleted."
::= { frNniTraceFilterRowStatusEntry 1 }

frNniTraceFilterComponentName OBJECT-TYPE
   SYNTAX     DisplayString 
   ACCESS     read-only
   STATUS     mandatory
   DESCRIPTION
     "This variable provides the component's string name for
      use with the ASCII Console Interface"
::= { frNniTraceFilterRowStatusEntry 2 }

frNniTraceFilterStorageType OBJECT-TYPE
   SYNTAX     StorageType 
   ACCESS     read-only
   STATUS     mandatory
   DESCRIPTION
     "This variable represents the storage type value for the
      frNniTraceFilter tables."
::= { frNniTraceFilterRowStatusEntry 4 }

frNniTraceFilterIndex OBJECT-TYPE
   SYNTAX     NonReplicated 
   ACCESS     not-accessible
   STATUS     mandatory
   DESCRIPTION
     "This variable represents the index for the frNniTraceFilter tables."
::= { frNniTraceFilterRowStatusEntry 10 }

frNniTraceFilterOperationalTable OBJECT-TYPE
   SYNTAX     SEQUENCE OF FrNniTraceFilterOperationalEntry
   ACCESS     not-accessible
   STATUS     mandatory
   DESCRIPTION
     "This group provides the operational attributes for the Frame Relay 
      Trace Filter component."
::= { frNniTraceFilter 10 }

frNniTraceFilterOperationalEntry OBJECT-TYPE
   SYNTAX     FrNniTraceFilterOperationalEntry
   ACCESS     not-accessible
   STATUS     mandatory
   DESCRIPTION
     "An entry in the frNniTraceFilterOperationalTable."
   INDEX {
      frNniIndex,
      frNniTraceIndex,
      frNniTraceFilterIndex }
::= { frNniTraceFilterOperationalTable 1 }

FrNniTraceFilterOperationalEntry ::= SEQUENCE {
   frNniTraceFilterTraceType
      OCTET STRING,
   frNniTraceFilterTracedDlci
      Unsigned32,
   frNniTraceFilterDirection
      OCTET STRING,
   frNniTraceFilterTracedLength
      Unsigned32 }

frNniTraceFilterTraceType OBJECT-TYPE
   SYNTAX     OCTET STRING (SIZE (1))
   ACCESS     read-write
   STATUS     mandatory
   DESCRIPTION
     "This attribute specifies the level of filtering required for this trace 
      session. A value of lmi indicates that Lmi frames are traced. A 
      value of dlci indicates that frames from the Dlci specified by the 
      tracedDlci attribute are traced. A value of badFrames indicates that 
      bad received frames (overruns, CRC errors, aborts) are traced. The 
      default is to trace all frames. This attribute can be set while a trace 
      is active and takes effect immediately.

      Description of bits:
      lmi(0)
      dlci(1)
      badFrames(2)"
   DEFVAL     { 'e0'H }
::= { frNniTraceFilterOperationalEntry 1 }

frNniTraceFilterTracedDlci OBJECT-TYPE
   SYNTAX     Unsigned32 (0..1007)
   ACCESS     read-write
   STATUS     mandatory
   DESCRIPTION
     "This attribute specifies a particular Dlci to trace. A value of zero 
      specifies that all Dlcis are to be traced. This attribute can be set 
      while a trace is active and takes effect immediately."
   DEFVAL     { 0 }
::= { frNniTraceFilterOperationalEntry 2 }

frNniTraceFilterDirection OBJECT-TYPE
   SYNTAX     OCTET STRING (SIZE (1))
   ACCESS     read-write
   STATUS     mandatory
   DESCRIPTION
     "This attribute specifies the direction of the data to be traced as 
      viewed by the service. The values can be egress, and/or ingress. An 
      egress value indicates frames outbound from the service. An 
      ingress value indicates frames inbound to the service. This attribute 
      can be set while a trace is active and takes effect immediately.

      Description of bits:
      egress(0)
      ingress(1)"
   DEFVAL     { 'c0'H }
::= { frNniTraceFilterOperationalEntry 3 }

frNniTraceFilterTracedLength OBJECT-TYPE
   SYNTAX     Unsigned32 (1..2000)
   ACCESS     read-write
   STATUS     mandatory
   DESCRIPTION
     "This attribute specifies the maximum number of bytes to trace per 
      frame starting from the byte following the frame flag. If the frame 
      length is longer than the value specified by this attribute, then the 
      traced frame is truncated. This attribute can be set while a trace is 
      active and takes effect immediately."
   DEFVAL     { 2000 }
::= { frNniTraceFilterOperationalEntry 4 }




-- 
-- Version and Compliance statements
-- 



-- Object-Group Statement:
-- A list of all current accessible leaf objects.

-- OBJECTS { frNniTraceComponentName,
--           frNniTraceFilterTracedDlci,
--           frNniTraceStorageType,
--           frNniTraceRowStatus,
--           frNniTraceDuration,
--           frNniTraceFilterTraceType,
--           frNniTraceFilterComponentName,
--           frNniTraceQueueLimit,
--           frNniTraceSession,
--           frNniTraceFilterStorageType,
--           frNniTraceFilterRowStatus,
--           frNniTraceFilterDirection,
--           frNniTraceReceiverName,
--           frNniTraceFilterTracedLength }
-- STATUS  mandatory
-- DESCRIPTION
--   "A list of all current accessible leaf objects."

frameRelayNniTraceGroup OBJECT IDENTIFIER ::= { frameRelayNniTraceMIB 1 }
frameRelayNniTraceGroupBD OBJECT IDENTIFIER ::= { frameRelayNniTraceGroup 4 }
frameRelayNniTraceGroupBD01 OBJECT IDENTIFIER ::= { frameRelayNniTraceGroupBD 2 }
frameRelayNniTraceGroupBD01A OBJECT IDENTIFIER ::= { frameRelayNniTraceGroupBD01 2 }



-- Agent-Capabilities Statement:

-- PRODUCT-RELEASE "Passport Release 7.0 FrameRelayNniTrace."
-- STATUS          mandatory
-- DESCRIPTION     "FrameRelayNniTrace MIB: MIB Version BD01A,
--                  Software Version BG00S4C."
-- SUPPORTS        Nortel-Magellan-Passport-FrameRelayNniTraceMIB
--    INCLUDES     { frameRelayNniTraceGroupBD01A }

frameRelayNniTraceCapabilities OBJECT IDENTIFIER ::= { frameRelayNniTraceMIB 3 }
frameRelayNniTraceCapabilitiesBD OBJECT IDENTIFIER ::= { frameRelayNniTraceCapabilities 4 }
frameRelayNniTraceCapabilitiesBD01 OBJECT IDENTIFIER ::= { frameRelayNniTraceCapabilitiesBD 2 }
frameRelayNniTraceCapabilitiesBD01A OBJECT IDENTIFIER ::= { frameRelayNniTraceCapabilitiesBD01 2 }





END
