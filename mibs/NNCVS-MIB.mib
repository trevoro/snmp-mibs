-------------------------------------------------------------------------------
-- file: NncVS.mib
--
-- description:
--      This file contains the SNMP definitions for Newbridge ATM
--      Voiceband Services application cards.
--
-- %%history-start%%
-- 1999.05.26 dylans 31A1284: atm.van2 trib merge 
-- 1999.06.23 dylans P.284729: Updated after review 
-- %%history-end%%
--
-- Copyright 1998, 1999 Newbridge Networks Corporation.  All Rights Reserved
-------------------------------------------------------------------------------
NNCVS-MIB DEFINITIONS ::= BEGIN
 
  IMPORTS
    MODULE-IDENTITY, OBJECT-TYPE, Counter32    FROM SNMPv2-SMI
    TEXTUAL-CONVENTION                         FROM SNMPv2-TC
    MODULE-COMPLIANCE, OBJECT-GROUP            FROM SNMPv2-CONF
    ifIndex                                    FROM IF-MIB
    nncExtensions                              FROM NNCGNI0001-SMI;

nncVS MODULE-IDENTITY
  LAST-UPDATED    "9901060924Z"
  ORGANIZATION    "Newbridge Networks Corporation"
  CONTACT-INFO
                  "Newbridge Networks Corporation
                   Postal: 600 March Road
                   Kanata, Ontario
                   Canada K2K 2E6
 
                   Phone:  +1 613 591 3600
                   Fax:    +1 613 591 3680"
 
  DESCRIPTION     "This module contains definitions for monitoring and 
                   configuring Newbridge Voiceband Services cards."
 
  ::= { nncExtensions 72 }
 
 
  nncVSObjects             OBJECT IDENTIFIER ::= { nncVS 1}
  nncVSTraps               OBJECT IDENTIFIER ::= { nncVS 2} 
  nncVSGroups              OBJECT IDENTIFIER ::= { nncVS 3}
  nncVSCompliances         OBJECT IDENTIFIER ::= { nncVS 4}

  nncVSConfiguration       OBJECT IDENTIFIER ::= { nncVSObjects 1 }
  nncVSStatistics          OBJECT IDENTIFIER ::= { nncVSObjects 2 }

 
-------------------------------------------------------------------------------
-- VS Statistics Table
-------------------------------------------------------------------------------
 
nncVSStatisticsTable    OBJECT-TYPE
    SYNTAX        SEQUENCE OF NncVSStatisticsEntry
    MAX-ACCESS    not-accessible
    STATUS        current
    DESCRIPTION
        "The nncVSStatisticsTable contains VS Statistics on a per
         channel basis."
    ::= { nncVSStatistics 1 }
 
nncVSStatisticsEntry    OBJECT-TYPE
    SYNTAX        NncVSStatisticsEntry
    MAX-ACCESS    not-accessible
    STATUS        current
    DESCRIPTION
        "An entry in the nncVSStatisticsTable."
    INDEX  { ifIndex }
    ::= { nncVSStatisticsTable 1 }
 
NncVSStatisticsEntry ::= SEQUENCE  {
    nncVSLOCSeconds                     Counter32,
    nncVSRemoteChanFailureSeconds       Counter32,
    nncVSUnderrunSeconds                Counter32,
    nncVSBufferUnderflows               Counter32,
    nncVSBufferOverflows                Counter32,
    nncVSSequenceDiscontinuities        Counter32,
    nncVSSpeechRx                       Counter32,
    nncVSSpeechTx                       Counter32,
    nncVSFaxRx                          Counter32,
    nncVSFaxTx                          Counter32,
    nncVSBypassRx                       Counter32,
    nncVSBypassTx                       Counter32,
    nncVSCASRx                          Counter32,
    nncVSCASTx                          Counter32,
    nncVSDTMFDigitsRx                   Counter32,
    nncVSDTMFDigitsTx                   Counter32,
    nncVSSilenceRx                      Counter32,
    nncVSSilenceTx                      Counter32
    }

nncVSLOCSeconds              OBJECT-TYPE
    SYNTAX        Counter32
    MAX-ACCESS    read-only
    STATUS        current
    DESCRIPTION
        "This count gives the number seconds for which Loss of Continuity
         was declared."
    ::= { nncVSStatisticsEntry 1 }

nncVSRemoteChanFailureSeconds OBJECT-TYPE
    SYNTAX        Counter32
    MAX-ACCESS    read-only
    STATUS        current
    DESCRIPTION
        "This count gives the number seconds for which the remote channel
         was in a failure state."
    ::= { nncVSStatisticsEntry 2 }

nncVSUnderrunSeconds         OBJECT-TYPE
    SYNTAX        Counter32
    MAX-ACCESS    read-only
    STATUS        current
    DESCRIPTION
        "This count gives the number seconds for which Underrun
         was declared."
    ::= { nncVSStatisticsEntry 3 }

nncVSBufferUnderflows        OBJECT-TYPE
    SYNTAX        Counter32
    MAX-ACCESS    read-only
    STATUS        current
    DESCRIPTION
        "This count gives the number of jitter buffer underflows."
    ::= { nncVSStatisticsEntry 4 }

nncVSBufferOverflows         OBJECT-TYPE
    SYNTAX        Counter32
    MAX-ACCESS    read-only
    STATUS        current
    DESCRIPTION
        "This count gives the number of jitter buffer overflows."
    ::= { nncVSStatisticsEntry 5 }

nncVSSequenceDiscontinuities OBJECT-TYPE
    SYNTAX        Counter32
    MAX-ACCESS    read-only
    STATUS        current
    DESCRIPTION
        "This count gives the number of sequence discontinuities in
         packets received."
    ::= { nncVSStatisticsEntry 6 }

nncVSSpeechRx          OBJECT-TYPE
    SYNTAX        Counter32
    MAX-ACCESS    read-only
    STATUS        current
    DESCRIPTION
        "The number of speech subframes received by the channel."
    ::= { nncVSStatisticsEntry 7 }

nncVSSpeechTx          OBJECT-TYPE
    SYNTAX        Counter32
    MAX-ACCESS    read-only
    STATUS        current
    DESCRIPTION
        "The number of speech subframes transmitted by the channel."
    ::= { nncVSStatisticsEntry 8 }

nncVSFaxRx OBJECT-TYPE
    SYNTAX        Counter32
    MAX-ACCESS    read-only
    STATUS        current
    DESCRIPTION
        "The number of fax subframes received by the channel."
    ::= { nncVSStatisticsEntry 9 }

nncVSFaxTx OBJECT-TYPE
    SYNTAX        Counter32
    MAX-ACCESS    read-only
    STATUS        current
    DESCRIPTION
        "The number of fax subframes transmitted by the channel."
    ::= { nncVSStatisticsEntry 10 }

nncVSBypassRx OBJECT-TYPE
    SYNTAX        Counter32
    MAX-ACCESS    read-only
    STATUS        current
    DESCRIPTION
        "The number of bypass subframes received by the channel."
    ::= { nncVSStatisticsEntry 11 }

nncVSBypassTx OBJECT-TYPE
    SYNTAX        Counter32
    MAX-ACCESS    read-only
    STATUS        current
    DESCRIPTION
        "The number of bypass subframes transmitted by the channel."
    ::= { nncVSStatisticsEntry 12 }

nncVSCASRx OBJECT-TYPE
    SYNTAX        Counter32
    MAX-ACCESS    read-only
    STATUS        current
    DESCRIPTION
        "The number of CAS subframes received by the channel."
    ::= { nncVSStatisticsEntry 13 }

nncVSCASTx OBJECT-TYPE
    SYNTAX        Counter32
    MAX-ACCESS    read-only
    STATUS        current
    DESCRIPTION
        "The number of CAS subframes transmitted by the channel."
    ::= { nncVSStatisticsEntry 14 }

nncVSDTMFDigitsRx OBJECT-TYPE
    SYNTAX        Counter32
    MAX-ACCESS    read-only
    STATUS        current
    DESCRIPTION
        "The number of DTMF subframes received by the channel."
    ::= { nncVSStatisticsEntry 15 }

nncVSDTMFDigitsTx OBJECT-TYPE
    SYNTAX        Counter32
    MAX-ACCESS    read-only
    STATUS        current
    DESCRIPTION
        "The number of DTMF subframes transmitted by the channel."
    ::= { nncVSStatisticsEntry 16 }
 
nncVSSilenceRx OBJECT-TYPE
    SYNTAX        Counter32
    MAX-ACCESS    read-only
    STATUS        current
    DESCRIPTION
        "The number of silence subframes received by the channel."
    ::= { nncVSStatisticsEntry 17 }

nncVSSilenceTx OBJECT-TYPE
    SYNTAX        Counter32
    MAX-ACCESS    read-only
    STATUS        current
    DESCRIPTION
        "The number of silence subframes transmitted by the channel."
    ::= { nncVSStatisticsEntry 18 }
 
-------------------------------------------------------------------------------
-- Conformance Group Definitions
-------------------------------------------------------------------------------
 
nncVSGeneralStatisticsGroup        OBJECT-GROUP
  OBJECTS {
    nncVSLOCSeconds,
    nncVSRemoteChanFailureSeconds,
    nncVSUnderrunSeconds,
    nncVSBufferUnderflows,
    nncVSBufferOverflows,
    nncVSSequenceDiscontinuities
  }
  STATUS          current
  DESCRIPTION     "Collection of objects providing raw general VS stats."
  ::= { nncVSGroups 1 }

nncVSSubframeStatisticsGroup        OBJECT-GROUP
  OBJECTS {
    nncVSSpeechRx,
    nncVSSpeechTx,
    nncVSFaxRx,
    nncVSFaxTx,
    nncVSBypassRx,
    nncVSBypassTx,
    nncVSCASRx,
    nncVSCASTx,
    nncVSDTMFDigitsRx,
    nncVSDTMFDigitsTx,
    nncVSSilenceRx,
    nncVSSilenceTx
  }
  STATUS          current
  DESCRIPTION     "Collection of objects providing raw VS subframe stats."
  ::= { nncVSGroups 2 }


-------------------------------------------------------------------------------
-- Compliance Statements (mandatory)
-------------------------------------------------------------------------------
nncVSCompliance    MODULE-COMPLIANCE
  STATUS          current
  DESCRIPTION     "The compliance statement for Newbridge SNMP."
  MODULE
    MANDATORY-GROUPS {
      nncVSGeneralStatisticsGroup,
      nncVSSubframeStatisticsGroup
    }
  ::= { nncVSCompliances 1}

-------------------------------------------------------------------------------
--      Review Minutes
-------------------------------------------------------------------------------
END -- DEFINITION OF NNCVS-MIB
