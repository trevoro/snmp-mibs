-- SCCS version: "@(#)att_sip.mib	4.1.2.2"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T SIP MIB for Customer Network Management
--


        ATT-CNM-SIP-MIB DEFINITIONS ::= BEGIN

        IMPORTS
                enterprises, Gauge
                        FROM RFC1155-SMI
                DisplayString
                        FROM RFC1213-MIB
                OBJECT-TYPE
                        FROM RFC-1212;

	--
	-- Object Identifiers
	--

        att-2           OBJECT IDENTIFIER ::= { enterprises 74 }
        att-products    OBJECT IDENTIFIER ::= { att-2 1 }
        att-mgmt        OBJECT IDENTIFIER ::= { att-2 2 }
        att-cnmAgent	OBJECT IDENTIFIER ::= { att-products 9 }
        att-cnm		OBJECT IDENTIFIER ::= { att-mgmt 15 }
        att-cnm-sip     OBJECT IDENTIFIER ::= { att-cnm 5 }


	--
	-- NOTE:
	--      All representations of SMDS addresses in this MIB module
	--      use, as a textual convention (i.e.,this convention does
	--      not affect their encoding), the data type:
	--

        SMDSAddress ::= OCTET STRING(SIZE(8))

        --
        -- SMDSAddress is the 60-bit SMDS address, preceded by
        -- 4 bits with the following values:
        --      "1100" when representing an individual address
        --      "1110" when representing a group address
        --


	--
	-- the SIP group of objects (att-cnm-sip) include:
	--
	--	the SIP Configuration table
	--	the SIP Measurements table
	--	the SIP Level 3 Error Log table
	--

	-- the SIP Configuration table

	--
	-- This table provides configuration information
	-- the SIP interfaces supported by this system.
	--

        attCNMsipConfigTable OBJECT-TYPE
                SYNTAX  SEQUENCE OF AttCNMsipConfigEntry
                ACCESS  not-accessible
                STATUS  mandatory
                DESCRIPTION
                        "A list of entries containing configuration
                        information for all SIP interfaces managed by
                        this system."
                ::= { att-cnm-sip 1 }

        attCNMsipConfigEntry OBJECT-TYPE
                SYNTAX  AttCNMsipConfigEntry
                ACCESS  not-accessible
                STATUS  mandatory
                DESCRIPTION
                        "An entry containing configuration information
                        for a particular SIP interface."
                INDEX   { attCNMsipConfigIndex }
                ::= { attCNMsipConfigTable 1 }

        AttCNMsipConfigEntry ::=
                SEQUENCE {
                    attCNMsipConfigIndex
                        INTEGER,
                    attCNMsipMeasMaxIntervals
                        INTEGER,
                    attCNMsipMeasIntervalLen
                        INTEGER
                }

        attCNMsipConfigIndex OBJECT-TYPE
                SYNTAX  INTEGER
                ACCESS  read-only
                STATUS  mandatory
                DESCRIPTION
                        "A unique value for each SIP interface. The interface
                        identified by a particular value of this index is
                        the same interface as identified by the same value
                        of an attCNMifConfigIndex object instance."
                ::= { attCNMsipConfigEntry 1 }

        attCNMsipMeasMaxIntervals OBJECT-TYPE
                SYNTAX  INTEGER
                ACCESS  read-only
                STATUS  mandatory
                DESCRIPTION
                        "This variable identifies the maximum number
			of measurement intervals supported for the
			measurements maintained by this SIP interface
			in the attCNMsipMeasTable."
                ::= { attCNMsipConfigEntry 2 }

        attCNMsipMeasIntervalLen OBJECT-TYPE
                SYNTAX  INTEGER
                ACCESS  read-only
                STATUS  mandatory
                DESCRIPTION
                        "This variable identifies the number of seconds
                        that make up one complete measurement interval for
			the measurements maintained by this SIP interface
                        in the attCNMsipMeasTable."
                ::= { attCNMsipConfigEntry 3 }



	-- the SIP Measurements table

	--
	-- This table provides counts on the various traffic
	-- measurements maintained by a SIP interface during
	-- the specified measurement interval.
	--

	attCNMsipMeasTable OBJECT-TYPE
		SYNTAX	SEQUENCE OF AttCNMsipMeasEntry
		ACCESS  not-accessible
		STATUS  mandatory
		DESCRIPTION
			"A list of entries containing traffic measurements,
			maintained during the specified measurement interval,
			for all SIP interfaces managed by this system."
		::= { att-cnm-sip 2 }

	attCNMsipMeasEntry OBJECT-TYPE
		SYNTAX  AttCNMsipMeasEntry
		ACCESS  not-accessible
		STATUS  mandatory
		DESCRIPTION
			"An entry containing traffic measurements,
			maintained during the specified measurement interval,
			for a particular SIP interface."
		INDEX	{ attCNMsipMeasIndex,
				attCNMsipMeasInterval }
		::= { attCNMsipMeasTable 1 }

	AttCNMsipMeasEntry ::=
		SEQUENCE {
		    attCNMsipMeasIndex
			INTEGER,
		    attCNMsipMeasInterval
			INTEGER,
		    attCNMsipMeasTimeStamp
			INTEGER,
		    attCNMsipMeasLocalTime
			DisplayString,
		    attCNMsipReceivedL3PDUs
			Gauge,
		    attCNMsipSentL3PDUs
			Gauge,
		    attCNMsipReceivedGroupL3PDUs
			Gauge,
		    attCNMsipSentGroupL3PDUs
			Gauge,
		    attCNMsipReceivedL2PDUs
			Gauge,
		    attCNMsipSentL2PDUs
			Gauge
		}

	attCNMsipMeasIndex OBJECT-TYPE
		SYNTAX	INTEGER
		ACCESS	read-only
		STATUS	mandatory
		DESCRIPTION
			"A unique value for each SIP interface. The interface
			identified by a particular value of this index is
			the same interface as identified by the same value
			of an attCNMifConfigIndex object instance."
		::= { attCNMsipMeasEntry 1 }

	attCNMsipMeasInterval OBJECT-TYPE
		SYNTAX  INTEGER
		ACCESS  read-only
		STATUS  mandatory
		DESCRIPTION
			"This variable identifies the measurement interval
			number for which measurement is provided. It is a
			number between 1 and XX, where 1 identifies the most
			recently completed measurement interval and XX is
			the least recently completed measurement interval.

                        The value of XX is specified by the
			attCNMsipMeasMaxIntervals object given in the
			attCNMsipConfigTable.

                        The maximum length of each measurement interval is
                        specified by the attCNMsipMeasIntervalLen object given
			in the attCNMsipConfigTable."
		::= { attCNMsipMeasEntry 2 }

	attCNMsipMeasTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMsipMeasEntry 3 }

	attCNMsipMeasLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMsipMeasEntry 4 }

	attCNMsipReceivedL3PDUs OBJECT-TYPE
		SYNTAX	Gauge
		ACCESS	read-only
		STATUS	mandatory
		DESCRIPTION
			"The counter associated with the number of
			individual-addressed and group-addressed L3 PDUs
			received by a SIP interface during the specified
			measurement interval."
		::= { attCNMsipMeasEntry 5 }

	attCNMsipSentL3PDUs OBJECT-TYPE
		SYNTAX	Gauge
		ACCESS	read-only
		STATUS	mandatory
		DESCRIPTION
			"The counter associated with the number of
			individual-addressed and group-addressed L3 PDUs
			sent by a SIP interface during the specified
			measurement interval."
		::= { attCNMsipMeasEntry 6 }

	attCNMsipReceivedGroupL3PDUs OBJECT-TYPE
		SYNTAX	Gauge
		ACCESS	read-only
		STATUS	mandatory
		DESCRIPTION
			"The counter associated with the number of
			group-addressed L3 PDUs received by a SIP interface
			during the specified measurement interval."
		::= { attCNMsipMeasEntry 7 }

	attCNMsipSentGroupL3PDUs OBJECT-TYPE
		SYNTAX	Gauge
		ACCESS	read-only
		STATUS	mandatory
		DESCRIPTION
			"The counter associated with the number of
			group-addressed L3 PDUs sent by a SIP interface
			during the specified measurement interval."
		::= { attCNMsipMeasEntry 8 }

	attCNMsipReceivedL2PDUs OBJECT-TYPE
		SYNTAX	Gauge
		ACCESS	read-only
		STATUS	mandatory
		DESCRIPTION
			"The counter associated with the number of
			L2 PDUs received by a SIP interface during the
			specified measurement interval."
		::= { attCNMsipMeasEntry 9 }

	attCNMsipSentL2PDUs OBJECT-TYPE
		SYNTAX	Gauge
		ACCESS	read-only
		STATUS	mandatory
		DESCRIPTION
			"The counter associated with the number of
			L2 PDUs sent by a SIP interface during the
			specified measurement interval."
		::= { attCNMsipMeasEntry 10 }


	-- the SIP Level 3 Error Log table

        --
        -- This table provides a log of the latest occurrences
	-- of the various protocol errors encountered at the
	-- Level 3 layer of all SIP interfaces supported by this
	-- system.
        --

	attCNMsipL3ErrorLogTable OBJECT-TYPE
		SYNTAX	SEQUENCE OF AttCNMsipL3ErrorLogEntry
		ACCESS  not-accessible
		STATUS  mandatory
		DESCRIPTION
			"A list of entries identifying the latest occurrence
			of protocol errors encountered at the Level 3 layer
			of all SIP interfaces managed by this system."
		::= { att-cnm-sip 3 }

	attCNMsipL3ErrorLogEntry OBJECT-TYPE
		SYNTAX  AttCNMsipL3ErrorLogEntry
		ACCESS  not-accessible
		STATUS  mandatory
		DESCRIPTION
			"An entry identifying the latest occurrence
			of a specific protocol error encountered
			at the Level 3 layer of a particular SIP interface."
		INDEX	{ attCNMsipL3ErrorLogIndex,
				attCNMsipL3ErrorLogType }
		::= { attCNMsipL3ErrorLogTable 1 }

	AttCNMsipL3ErrorLogEntry ::=
		SEQUENCE {
		    attCNMsipL3ErrorLogIndex
			INTEGER,
		    attCNMsipL3ErrorLogType
			INTEGER,
		    attCNMsipL3ErrorLogSA
			SMDSAddress,
		    attCNMsipL3ErrorLogDA
			SMDSAddress,
		    attCNMsipL3ErrorLogTimeStamp
			INTEGER,
		    attCNMsipL3ErrorLogLocalTime
			DisplayString
		}

	attCNMsipL3ErrorLogIndex OBJECT-TYPE
		SYNTAX	INTEGER
		ACCESS	read-only
		STATUS	mandatory
		DESCRIPTION
			"A unique value for each SIP interface. The interface
			identified by a particular value of this index is
			the same interface as identified by the same value
			of an attCNMifConfigIndex object instance."
		::= { attCNMsipL3ErrorLogEntry 1 }

	attCNMsipL3ErrorLogType OBJECT-TYPE
		SYNTAX  INTEGER {
			    daFieldFormatError(1),
			    saFieldFormatError(2),
			    baSizeFieldValueInvalid(3),
			    heLengthInvalid(4),
			    heElementLengthInvalid(5),
			    heVersionElementInvalid(6),
			    heCarrierSelectionElementInvalid(7),
			    hePADInvalid(8),
			    beTagMismatch(9),
			    baSizeFieldNotEqualLengthField(10),
			    incorrectLength(11),
			    mriTimeout(12)
			}
		ACCESS  read-only
		STATUS  mandatory
		DESCRIPTION
			"The type of error. It could be one of:

			- Destination Address Field Format Error,
			- Source Address Field Format Error,
			- Invalid BAsize Field Value,
			- Invalid Header Extension Length,
			- Invalid Header Extension: Element Length,
			- Invalid Header Extension: Carrier Selection Element
			  			    Format,
			- Invalid Header Extension: Carrier Selection Element
						    Length,
			- Invalid Header Extension: Version Element Position,
						    Length or Value,
			- BEtag Mismatch,
			- BAsize Field Not Equal To Length Field,
			- Incorrect Length,
			- MSS Receive Interval Timeout."
		::= { attCNMsipL3ErrorLogEntry 2 }

	attCNMsipL3ErrorLogSA OBJECT-TYPE
		SYNTAX	SMDSAddress
		ACCESS	read-only
		STATUS	mandatory
		DESCRIPTION
			"The SMDS source address in the rejected L3 PDU."
		::= { attCNMsipL3ErrorLogEntry 3 }

	attCNMsipL3ErrorLogDA OBJECT-TYPE
		SYNTAX	SMDSAddress
		ACCESS	read-only
		STATUS	mandatory
		DESCRIPTION
			"The SMDS destination address in the rejected L3 PDU."
		::= { attCNMsipL3ErrorLogEntry 4 }

	attCNMsipL3ErrorLogTimeStamp OBJECT-TYPE
		SYNTAX	INTEGER
		ACCESS	read-only
		STATUS	mandatory
		DESCRIPTION
			"The time stamp for the latest occurrence of the
			specified error, as measured in seconds from
			00:00:00 UTC (Coordinated Universal Time)
			January 1, 1970. Any fraction is rounded up."
		::= { attCNMsipL3ErrorLogEntry 5 }

	attCNMsipL3ErrorLogLocalTime OBJECT-TYPE
		SYNTAX	DisplayString(SIZE(0..255))
		ACCESS	read-only
		STATUS	mandatory
		DESCRIPTION
			"The time stamp for the latest occurrence of the
			specified error. It is given as a printable ASCII
			string showing the local time at the latest
			occurrence of this type of error."
		::= { attCNMsipL3ErrorLogEntry 6 }

	END
