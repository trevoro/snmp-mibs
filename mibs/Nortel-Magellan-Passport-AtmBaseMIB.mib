Nortel-Magellan-Passport-AtmBaseMIB
DEFINITIONS ::= BEGIN



IMPORTS

      OBJECT-TYPE
   FROM RFC-1212

      passportMIBs
   FROM Nortel-Magellan-Passport-UsefulDefinitionsMIB

      DisplayString,
      StorageType,
      RowStatus,
      Gauge32,
      Integer32,
      Unsigned32
   FROM Nortel-Magellan-Passport-StandardTextualConventionsMIB

      NonReplicated,
      FixedPoint1
   FROM Nortel-Magellan-Passport-TextualConventionsMIB

      lpIndex,
      lp,
      lpEngIndex,
      lpEng
   FROM Nortel-Magellan-Passport-LogicalProcessorMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmBase Enterprise MIB."

atmBaseMIB OBJECT IDENTIFIER ::= { passportMIBs 63 }










-- Lp/n AtmResourceControl
-- The AtmResourceControl component is used to configure the usage 
-- of ATM-specific resources on a Logical Processor running ATM 
-- services. (This component is only permitted under Logical 
-- Processors which are linked to ATM card types.)

lpArc OBJECT IDENTIFIER ::= { lp 19 }



lpArcRowStatusTable OBJECT-TYPE
   SYNTAX     SEQUENCE OF LpArcRowStatusEntry
   ACCESS     not-accessible
   STATUS     obsolete
   DESCRIPTION
     "This entry controls the addition and deletion of 
      lpArc components."
::= { lpArc 1 }

lpArcRowStatusEntry OBJECT-TYPE
   SYNTAX     LpArcRowStatusEntry
   ACCESS     not-accessible
   STATUS     obsolete
   DESCRIPTION
     "A single entry in the table represents a single 
      lpArc component."
   INDEX {
      lpIndex,
      lpArcIndex }
::= { lpArcRowStatusTable 1 }

LpArcRowStatusEntry ::= SEQUENCE {
   lpArcRowStatus
      RowStatus,
   lpArcComponentName
      DisplayString,
   lpArcStorageType
      StorageType,
   lpArcIndex
      NonReplicated }

lpArcRowStatus OBJECT-TYPE
   SYNTAX     RowStatus 
   ACCESS     read-write
   STATUS     obsolete
   DESCRIPTION
     "This variable is used as the basis for SNMP naming of
      lpArc components.
      These components can be added and deleted."
::= { lpArcRowStatusEntry 1 }

lpArcComponentName OBJECT-TYPE
   SYNTAX     DisplayString 
   ACCESS     read-only
   STATUS     obsolete
   DESCRIPTION
     "This variable provides the component's string name for
      use with the ASCII Console Interface"
::= { lpArcRowStatusEntry 2 }

lpArcStorageType OBJECT-TYPE
   SYNTAX     StorageType 
   ACCESS     read-only
   STATUS     obsolete
   DESCRIPTION
     "This variable represents the storage type value for the
      lpArc tables."
::= { lpArcRowStatusEntry 4 }

lpArcIndex OBJECT-TYPE
   SYNTAX     NonReplicated 
   ACCESS     not-accessible
   STATUS     obsolete
   DESCRIPTION
     "This variable represents the index for the lpArc tables."
::= { lpArcRowStatusEntry 10 }

lpArcProvTable OBJECT-TYPE
   SYNTAX     SEQUENCE OF LpArcProvEntry
   ACCESS     not-accessible
   STATUS     obsolete
   DESCRIPTION
     "This group specifies the configuration of processor-wide ATM-
      specific resources on a Logical Processor running ATM services. 
      Note that altering any of these parameters results in a card reset."
::= { lpArc 100 }

lpArcProvEntry OBJECT-TYPE
   SYNTAX     LpArcProvEntry
   ACCESS     not-accessible
   STATUS     obsolete
   DESCRIPTION
     "An entry in the lpArcProvTable."
   INDEX {
      lpIndex,
      lpArcIndex }
::= { lpArcProvTable 1 }

LpArcProvEntry ::= SEQUENCE {
   lpArcTotalConnectionPoolCapacity
      Unsigned32,
   lpArcMulticastBranchesCapacity
      Unsigned32,
   lpArcTxFrameMemoryAllocation
      Unsigned32,
   lpArcRxFrameMemoryAllocation
      Unsigned32,
   lpArcPerVcQueueInterfaces
      Unsigned32,
   lpArcShapingStackAllocation
      OCTET STRING,
   lpArcShapingScalingFactor
      FixedPoint1,
   lpArcCdvAttenuation
      INTEGER,
   lpArcPortAggregation
      INTEGER,
   lpArcSubConnectionPoolCapacity
      Unsigned32,
   lpArcLnnConnectionPoolCapacity
      Unsigned32 }

lpArcTotalConnectionPoolCapacity OBJECT-TYPE
   SYNTAX     Unsigned32 (0..10752)
   ACCESS     read-write
   STATUS     obsolete
   DESCRIPTION
     "This attribute is migrated to the Lp/n Eng Arc Ov attribute of the 
      same name.
      
      This attribute specifies the maximum number of connections (both 
      VCC and VPC) that can be enabled on the LogicalProcessor.
      
      If the LogicalProcessor is associated with a card of a cardType 
      other than one of the following: 3pE3Atm, 3pDS3Atm, 
      3pOC3MmAtm, 3pOC3SmAtm, 3pE1Atm, 3pDS1Atm, 
      2pJ6MAtm; the value of the attribute restricts the sum of the 
      (maxVccs + maxVpcs) across all AtmIfs bound to this 
      LogicalProcessor.
      
      If the LogicalProcessor is associated with a card of one of the 
      following cardTypes: 3pE3Atm, 3pDS3Atm, 3pOC3MmAtm, 
      3pOC3SmAtm, 3pE1Atm, 3pDS1Atm, 2pJ6MAtm; the number of 
      available connections are distributed equally across the ports on the 
      FP. The number of connections associated to a particular port will 
      limit the size of the Vcc space defined by the ConnMap of the AtmIf 
      linked to the port. Furthermore, the value of this attribute is 
      restricted based on the number of ports on the card. For one port 
      cards, the minimum is 512, the maximum is 4096 and the value 
      must be divisible by 256. For two port cards, the minimum is 1024, 
      the maximum is 8192 and the value must be divisible by 512. For 
      three port cards, the minimum is 1536, the maximum is 7680 and 
      the value must be divisible by 768.
      
      Increasing the value of this attribute reduces the CQM memory 
      available for cell and frame free list.
      
      This attribute must be set to 0 if the connectionPoolCapacity 
      attribute is set to non-zero values."
   DEFVAL     { 3072 }
::= { lpArcProvEntry 5 }

lpArcMulticastBranchesCapacity OBJECT-TYPE
   SYNTAX     Unsigned32 (0..10752)
   ACCESS     read-write
   STATUS     obsolete
   DESCRIPTION
     "This attribute is migrated to the Lp/n Eng Arc Ov attribute of the 
      same name.
      
      This attribute specifies the number of multicast branches that can be 
      enabled on the Logical Processor.
      
      A multicast branch is used for cell replication on a Vcc connection 
      whose Vcc distributionType is pointToMultipoint. A branch 
      represent one ATM destination for the replicated cells
      
      Increasing the value of this attribute reduces the CQM memory 
      available for the cell and frame free lists."
   DEFVAL     { 0 }
::= { lpArcProvEntry 6 }

lpArcTxFrameMemoryAllocation OBJECT-TYPE
   SYNTAX     Unsigned32 (0..100)
   ACCESS     read-write
   STATUS     obsolete
   DESCRIPTION
     "This attribute is migrated to the Lp/n Eng Arc Ov attribute 
      txCellMemoryAllocation. It is converted from frame percentage to 
      cell percentage by subtracting this value from 100.
      
      This attribute specifies the percentage of the transmit CQM memory 
      which should be allocated to the transmit frame free list on the 
      ATM-FP. The remaining transmit CQM memory is allocated to the 
      transmit cell free list. Frame memory is used for trunks, ATM VCC 
      testing and for inter-card communication. There is an absolute 
      minimum quantity of frame buffers which is required by ATM 
      software on the FP. If the value of this attribute is smaller than the 
      absolute minimum, the ATM software will allocate the minimum 
      required, rather than the actual number requested.
      
      The actual percentage of the transmit CQM memory allocated to the 
      transmit frame free list is indicated by the Aru 
      txFrameMemoryAllocation attribute. A difference between the 
      provisioned and the operational values may exist due to the 
      requirement for a minimum number of frame buffers or rounding 
      during computation within the FP."
   DEFVAL     { 50 }
::= { lpArcProvEntry 10 }

lpArcRxFrameMemoryAllocation OBJECT-TYPE
   SYNTAX     Unsigned32 (0..100)
   ACCESS     read-write
   STATUS     obsolete
   DESCRIPTION
     "This attribute is migrated to the Lp/n Eng Arc Ov attribute 
      rxCellMemoryAllocation. It is converted from frame percentage to 
      cell percentage by subtracting this value from 100.
      
      This attribute specifies the percentage of the receive CQM memory 
      which should be allocated to the receive frame free list on the ATM-
      FP. The remaining receive CQM memory is allocated to the receive 
      cell free list. Frame memory is used for trunks, ATM VCC testing 
      and for inter-card communication. There is an absolute minimum 
      quantity of frame buffers which is required by ATM software on the 
      FP. If the value of this attribute is smaller than the absolute 
      minimum, the ATM software will allocate the minimum required, 
      rather than the actual number requested. 
      
      The actual percentage of the receive CQM memory allocated to the 
      receive frame free list is indicated by the Aru 
      rxFrameMemoryAllocation attribute. A difference between the 
      provisioned and the operational values may exist due to the 
      requirement for a minimum number of frame buffers or rounding 
      during computation within the FP"
   DEFVAL     { 80 }
::= { lpArcProvEntry 20 }

lpArcPerVcQueueInterfaces OBJECT-TYPE
   SYNTAX     Unsigned32 (0..4)
   ACCESS     read-write
   STATUS     obsolete
   DESCRIPTION
     "This attribute is migrated to the Lp/n Eng Arc Cqc Ov attribute of 
      the same name.
      
      This attribute specifies the number of independent ports or IMA 
      components which support shaping and per-VC queueing on the 
      LogicalProcessor. 
      
      When this attribute is not zero, at most 4 independent ports or 4 Ima 
      virtual links are supported, regardless of whether or not traffic 
      shaping is enabled on the associated AtmIf components. In this case 
      only independent port instances 0-3 or Ima instances 0-3 can be 
      supported on an associated AtmIf component.
      
      For 2 ports cards, the valid values for this attribute are 0, 1, or 2.
      For 3 ports cards, the valid values for this attribute are 0, 1, or 3.
      For 8 ports cards, the valid values for this attribute are 0, 1, 2, or 4."
   DEFVAL     { 0 }
::= { lpArcProvEntry 25 }

lpArcShapingStackAllocation OBJECT-TYPE
   SYNTAX     OCTET STRING (SIZE (1))
   ACCESS     read-write
   STATUS     obsolete
   DESCRIPTION
     "This attribute is migrated to the perVcQueueInterfaces attribute of 
      the Lp/n Eng Arc Cqc Ov. Value ~0,~1,~2 is migrated to the value 
      0; value 0,~1,~2 is migrated to value 1; value 0,1,~2 is migrated to 
      the value 2 and value 0,1,2 is migrated to the value 3 (for cardTypes 
      3pE3Atm, 3pDS3Atm, 3pOC3MmAtm, 3pOC3SmAtm, 3pE1Atm, 
      3pDS1Atm) or to the value 4 (for other cardTypes).
      
      This attribute specifies the allocation of shaping stack resources 
      among the ports on this FP. Shaping stacks can currently be 
      allocated on port 0, ports 0 and 1, or ports 0, 1 and 2. Allocating 
      shaping stacks on a port allows the use of traffic shaping and per-
      VC queueing on that port.

      Description of bits:
      n0(0)
      n1(1)
      n2(2)"
   DEFVAL     { '80'H }
::= { lpArcProvEntry 30 }

lpArcShapingScalingFactor OBJECT-TYPE
   SYNTAX     FixedPoint1 (10 | 14 | 20 | 28 | 40 | 56)
   ACCESS     read-write
   STATUS     obsolete
   DESCRIPTION
     "This attribute is migrated to the Lp/n Eng Arc Cqc Ov attribute of 
      the same name.
      
      This attribute specifies the scaling factor which is to be applied to 
      all shaping rates for this ATM-FP. The scaling factor is a 
      multiplicative factor which is applied to the chosen shaping rate to 
      produce an actual shaping rate. For example, if a shaping rate of 25 
      Mbps is used with a scaling factor of 2, the actual shaping rate is 
      12.5 Mbps."
   DEFVAL     { 10 }
::= { lpArcProvEntry 40 }

lpArcCdvAttenuation OBJECT-TYPE
   SYNTAX     INTEGER  {
                 off(0),
                 on(1) }
   ACCESS     read-write
   STATUS     obsolete
   DESCRIPTION
     "This attribute is migrated to the Lp/n Eng Arc Cqc Ov attribute 
      cdvReduction.
      
      This attribute enables the attenuation of the maximum Cell Delay 
      Variation (CDV) of shaped transmit traffic.
      
      When the value of this attribute is set to off, the CDV value can be 
      determined by the following equation:
      CDV <= 2/ASR + 1/LS
      where ASR is the Actual Shaping Rate of the connection and LS is 
      the Link Speed of the interface.
      
      When the value of this attribute is set to on, the CDV relationship 
      changes to the following equation:
      CDV <= 1/ASR + 1/LS
      
      As can be noted from the equations above, setting this attribute to 
      on can reduce the CDV significantly. CDV attenuation may be used 
      to conform to policers which have strict Cell Delay Variance 
      Tolerance (CDVT). However using this function reduces the 
      transmit bandwidth utilization of the following cards: 3pDS3Atm, 
      3pOC3Atm."
   DEFVAL     { off }
::= { lpArcProvEntry 41 }

lpArcPortAggregation OBJECT-TYPE
   SYNTAX     INTEGER  {
                 on(0),
                 off(1) }
   ACCESS     read-write
   STATUS     obsolete
   DESCRIPTION
     "This attribute is migrated to the Lp/n Eng Arc Cqc Ov attribute 
      portCongestionPolicy.
      
      This attribute specifies whether port aggregation is turned on or off 
      for this ATM-FP. It applies only to transmit traffic served on the 
      common queues and does not apply to perVc queues.
      
      When port aggregation is on, the enqueue decision of cells or 
      frames to a common queue is based upon the congestion state of the 
      entire port to which the queue belongs. A port is defined to be as 
      congested as the most congested queue amongst all its queues: the 
      low, medium and high emission priority queues. Thus, for example, 
      if the low priority queue is congested, the high priority queue will 
      also experience discards even though the high priority queue may 
      itself not be congested. Setting port aggregation on assures that the 
      low priority queues are also serviced in the event of congestion.
      
      When the value of this attribute is set to off, the enqueue decision of 
      cells or frames to a common queue is based solely upon the 
      congestion state of that queue, not the port. This setting assures that 
      the absolute priority of the traffic is taken into account, regardless of 
      whether or not the lower priority queues are being served."
   DEFVAL     { on }
::= { lpArcProvEntry 42 }

lpArcSubConnectionPoolCapacity OBJECT-TYPE
   SYNTAX     Unsigned32 (1..8192)
   ACCESS     read-write
   STATUS     obsolete
   DESCRIPTION
     "This attribute is migrated to the Lp/n Eng Fcrc Ov attribute of the 
      same name.
      
      This attribute specifies the maximum number of sub-connections 
      for the LogicalProcessor. 
      
      A sub-connection is used for interworking the ATM services with 
      the frame oriented services such as Frame Relay, and Path Oriented 
      Routing System (PORS). When a frame is received at a sub-
      connection, the frame header is modified to be compatible with the 
      service it is to be forwarded to.
      
      Due to limited resources, not all of the provisioned number of sub-
      connections may be allocated. The actual number of sub-
      connections allocated is indicated by the sum of Aru 
      subConnectionPoolAvailable and Aru SubConnectionPoolUsage 
      attributes. 
      
      This pool is used for connection oriented services only. Each of the 
      following components uses one sub-connection from this pool: 
      FrAtm/x Dlci/y Siwf
      McsMgr Frf5EpG/x Frf5Ep/y Lmi
      McsMgr Frf5EpG/x Frf5Ep/y Dlci/z
      
      When the sub-connection pool is exhausted, no more connections 
      will be accepted from the services which utilize this pool."
   DEFVAL     { 1024 }
::= { lpArcProvEntry 43 }

lpArcLnnConnectionPoolCapacity OBJECT-TYPE
   SYNTAX     Unsigned32 (1..512)
   ACCESS     read-write
   STATUS     obsolete
   DESCRIPTION
     "This attribute is migrated to the Lp/n Eng Fcrc Ov attribute of the 
      same name.
      
      This attribute specifies the maximum number of resource records 
      for the connections which utilize Logical Network Number (LNN) 
      on the LogicalProcessor.
      
      A logical network is a subset of passport modules together with a 
      subset of trunks that interconnect those modules. It carries the 
      traffic for a defined set of network protocols. A LNN is used to 
      identify a logical network. The connectionless services which 
      utilize the logical networks require some processing at the 
      intermediate nodes. This pool is allocated at the intermediate nodes 
      to sustain these connectionless services.
      
      Due to limited resources, not all of the provisioned number of LNN 
      connection resource records may be allocated. The actual number of 
      resource records allocated is indicated by the sum of Aru 
      lnnConnectionPoolAvailable and Aru lnnConnectionPoolUsage 
      attributes.
      
      If the McsMgr DprsMcsEpG/x Ep/y EpD 
      transportConnectionPreference attribute is set to atmOnly, each 
      instance of the McsMgr DprsMcsEpG/x Ep/y component uses one 
      resource record from this pool."
   DEFVAL     { 128 }
::= { lpArcProvEntry 44 }

lpArcConnCapTable OBJECT-TYPE
   SYNTAX     SEQUENCE OF LpArcConnCapEntry
   ACCESS     not-accessible
   STATUS     obsolete
   DESCRIPTION
     "This attribute is migrated to the Lp/n Eng Arc Cqc Ov attribute of 
      the same name.
      
      This attribute is provided for backward compatibility and can only 
      be used if the LogicalProcessor is associated to a card of one of the 
      following cardType: 3pE3Atm, 3pDS3Atm, 3pOC3MmAtm, 
      3pOC3SmAtm, 3pE1Atm, 3pDS1Atm, 2pJ6MAtm. This attribute 
      can be used when the desired distribution of connections across 
      ports cannot be achieved using the totalConnectionPoolCapacity 
      attribute.
      
      This attribute defines the maximum number of connections (both 
      VCC and VPC) that are available on each port. The entries are 
      indexed by port number. This number limits the range of the 
      ConnMap entries. Note that the value of this attribute must be 
      evenly divisible by 256, and that port 2 supports at most 2560 
      connections, not the full 4096."
::= { lpArc 291 }

lpArcConnCapEntry OBJECT-TYPE
   SYNTAX     LpArcConnCapEntry
   ACCESS     not-accessible
   STATUS     obsolete
   DESCRIPTION
     "An entry in the lpArcConnCapTable."
   INDEX {
      lpIndex,
      lpArcIndex,
      lpArcConnCapIndex }
::= { lpArcConnCapTable 1 }

LpArcConnCapEntry ::= SEQUENCE {
   lpArcConnCapIndex
      Integer32,
   lpArcConnCapValue
      Unsigned32 }

lpArcConnCapIndex OBJECT-TYPE
   SYNTAX     Integer32 (0..2)
   ACCESS     not-accessible
   STATUS     obsolete
   DESCRIPTION
     "This variable represents the lpArcConnCapTable
      specific index for the lpArcConnCapTable."
::= { lpArcConnCapEntry 1 }

lpArcConnCapValue OBJECT-TYPE
   SYNTAX     Unsigned32 (0 | 512..4096)
   ACCESS     read-write
   STATUS     obsolete
   DESCRIPTION
     "This variable represents an individual value for the
      lpArcConnCapTable."
::= { lpArcConnCapEntry 2 }


-- Lp/n AtmResourceUsage
-- The AtmResourceUsage component describes the usage of ATM-
-- specific resources on a LogicalProcessor running ATM services. 
-- This component is always dynamically created under the LP which 
-- supports an ATM-FP. 

lpAru OBJECT IDENTIFIER ::= { lp 20 }



lpAruRowStatusTable OBJECT-TYPE
   SYNTAX     SEQUENCE OF LpAruRowStatusEntry
   ACCESS     not-accessible
   STATUS     obsolete
   DESCRIPTION
     "This entry controls the addition and deletion of 
      lpAru components."
::= { lpAru 1 }

lpAruRowStatusEntry OBJECT-TYPE
   SYNTAX     LpAruRowStatusEntry
   ACCESS     not-accessible
   STATUS     obsolete
   DESCRIPTION
     "A single entry in the table represents a single 
      lpAru component."
   INDEX {
      lpIndex,
      lpAruIndex }
::= { lpAruRowStatusTable 1 }

LpAruRowStatusEntry ::= SEQUENCE {
   lpAruRowStatus
      RowStatus,
   lpAruComponentName
      DisplayString,
   lpAruStorageType
      StorageType,
   lpAruIndex
      NonReplicated }

lpAruRowStatus OBJECT-TYPE
   SYNTAX     RowStatus 
   ACCESS     read-only
   STATUS     obsolete
   DESCRIPTION
     "This variable is used as the basis for SNMP naming of
      lpAru components.
      These components cannot be added nor deleted."
::= { lpAruRowStatusEntry 1 }

lpAruComponentName OBJECT-TYPE
   SYNTAX     DisplayString 
   ACCESS     read-only
   STATUS     obsolete
   DESCRIPTION
     "This variable provides the component's string name for
      use with the ASCII Console Interface"
::= { lpAruRowStatusEntry 2 }

lpAruStorageType OBJECT-TYPE
   SYNTAX     StorageType 
   ACCESS     read-only
   STATUS     obsolete
   DESCRIPTION
     "This variable represents the storage type value for the
      lpAru tables."
::= { lpAruRowStatusEntry 4 }

lpAruIndex OBJECT-TYPE
   SYNTAX     NonReplicated 
   ACCESS     not-accessible
   STATUS     obsolete
   DESCRIPTION
     "This variable represents the index for the lpAru tables."
::= { lpAruRowStatusEntry 10 }

lpAruOperTable OBJECT-TYPE
   SYNTAX     SEQUENCE OF LpAruOperEntry
   ACCESS     not-accessible
   STATUS     obsolete
   DESCRIPTION
     "This group describes the usage of ATM-specific resources on a 
      Logical Processor running ATM services."
::= { lpAru 100 }

lpAruOperEntry OBJECT-TYPE
   SYNTAX     LpAruOperEntry
   ACCESS     not-accessible
   STATUS     obsolete
   DESCRIPTION
     "An entry in the lpAruOperTable."
   INDEX {
      lpIndex,
      lpAruIndex }
::= { lpAruOperTable 1 }

LpAruOperEntry ::= SEQUENCE {
   lpAruTotalConnectionPoolUsage
      Unsigned32,
   lpAruMulticastBranchesUsage
      Unsigned32,
   lpAruTxCellBlockCapacity
      Unsigned32,
   lpAruTxCellBlockUsage
      Gauge32,
   lpAruTxCellFreeListSize
      Unsigned32,
   lpAruTxCellFreeListCongestionState
      INTEGER,
   lpAruTxFrameMemoryAllocation
      Unsigned32,
   lpAruTxFrameBlockCapacity
      Unsigned32,
   lpAruTxFrameBlockUsage
      Gauge32,
   lpAruTxFrameFreeListSize
      Unsigned32,
   lpAruTxFrameFreeListCongestionState
      INTEGER,
   lpAruRxCellBlockCapacity
      Unsigned32,
   lpAruRxCellBlockUsage
      Gauge32,
   lpAruRxCellFreeListSize
      Unsigned32,
   lpAruRxCellFreeListCongestionState
      INTEGER,
   lpAruRxFrameMemoryAllocation
      Unsigned32,
   lpAruRxFrameBlockCapacity
      Unsigned32,
   lpAruRxFrameBlockUsage
      Gauge32,
   lpAruRxFrameFreeListSize
      Unsigned32,
   lpAruRxFrameFreeListCongestionState
      INTEGER,
   lpAruSubConnectionPoolAvailable
      Unsigned32,
   lpAruSubConnectionPoolUsage
      Unsigned32,
   lpAruLnnConnectionPoolAvailable
      Unsigned32,
   lpAruLnnConnectionPoolUsage
      Unsigned32 }

lpAruTotalConnectionPoolUsage OBJECT-TYPE
   SYNTAX     Unsigned32 (0..10752)
   ACCESS     read-only
   STATUS     obsolete
   DESCRIPTION
     "If the LogicalProcessor is associated with a card of a cardType 
      other than 4pE1Aal1 or 4pDS1Aal1, this attribute indicates the total 
      number of enabled VCCs and VPCs in AtmIfs associated with this 
      LogicalProcessor. An example of a VCC not in the enabled state is 
      a VCC with a Test subcomponent. This attribute is equal to the sum 
      of the AtmIf Ca connectionPoolUsage attributes of AtmIfs 
      associated with this LogicalProcessor.
      
      If the LogicalProcessor is associated with a card of cardType 
      4pE1Aal1 or 4pDS1Aal1, this attribute indicates the total number 
      of Ces components associated with this LogicalProcessor."
::= { lpAruOperEntry 5 }

lpAruMulticastBranchesUsage OBJECT-TYPE
   SYNTAX     Unsigned32 (0..10752)
   ACCESS     read-only
   STATUS     obsolete
   DESCRIPTION
     "This attribute indicates the total number of multicast branches that 
      are active on the Logical Processor."
::= { lpAruOperEntry 6 }

lpAruTxCellBlockCapacity OBJECT-TYPE
   SYNTAX     Unsigned32 (0..8192)
   ACCESS     read-only
   STATUS     obsolete
   DESCRIPTION
     "This attribute indicates the amount of memory reserved for storing 
      ATM cells to be transmitted by the Lp."
::= { lpAruOperEntry 10 }

lpAruTxCellBlockUsage OBJECT-TYPE
   SYNTAX     Gauge32 (0..8192)
   ACCESS     read-only
   STATUS     obsolete
   DESCRIPTION
     "This attribute indicates the amount of memory currently being used 
      to store ATM cells to be transmitted by the Lp."
::= { lpAruOperEntry 20 }

lpAruTxCellFreeListSize OBJECT-TYPE
   SYNTAX     Unsigned32 (0..16383)
   ACCESS     read-only
   STATUS     obsolete
   DESCRIPTION
     "This attribute indicates the current size of the transmit cell free list. 
      The transmit cell free list is the memory available for storing ATM 
      cells to be transmitted by the Lp."
::= { lpAruOperEntry 23 }

lpAruTxCellFreeListCongestionState OBJECT-TYPE
   SYNTAX     INTEGER (0..3)
   ACCESS     read-only
   STATUS     obsolete
   DESCRIPTION
     "This attribute indicates the congestion state of the transmit cell free 
      list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { lpAruOperEntry 26 }

lpAruTxFrameMemoryAllocation OBJECT-TYPE
   SYNTAX     Unsigned32 (0..100)
   ACCESS     read-only
   STATUS     obsolete
   DESCRIPTION
     "This attribute defines the percentage of the transmit CQM memory 
      which is allocated to the transmit frame free list on the ATM-FP. 
      The remaining transmit CQM memory is allocated to the transmit 
      cell free list. Frame memory is used for trunks, ATM Vcc testing 
      and for inter-card communication."
::= { lpAruOperEntry 30 }

lpAruTxFrameBlockCapacity OBJECT-TYPE
   SYNTAX     Unsigned32 (0..8192)
   ACCESS     read-only
   STATUS     obsolete
   DESCRIPTION
     "This attribute indicates the amount of memory reserved for storing 
      frames to be transmitted by the Lp."
::= { lpAruOperEntry 40 }

lpAruTxFrameBlockUsage OBJECT-TYPE
   SYNTAX     Gauge32 (0..8192)
   ACCESS     read-only
   STATUS     obsolete
   DESCRIPTION
     "This attribute indicates the amount of memory currently being used 
      to store frames to be transmitted by the Lp."
::= { lpAruOperEntry 50 }

lpAruTxFrameFreeListSize OBJECT-TYPE
   SYNTAX     Unsigned32 (0..16383)
   ACCESS     read-only
   STATUS     obsolete
   DESCRIPTION
     "This attribute indicates the current size of the transmit frame free 
      list. The transmit frame free list is the memory (in ATM cells) 
      available for storing frames to be transmitted by the Lp."
::= { lpAruOperEntry 53 }

lpAruTxFrameFreeListCongestionState OBJECT-TYPE
   SYNTAX     INTEGER (0..3)
   ACCESS     read-only
   STATUS     obsolete
   DESCRIPTION
     "This attribute indicates the congestion state of the transmit frame 
      free list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { lpAruOperEntry 56 }

lpAruRxCellBlockCapacity OBJECT-TYPE
   SYNTAX     Unsigned32 (0..8192)
   ACCESS     read-only
   STATUS     obsolete
   DESCRIPTION
     "This attribute indicates the amount of memory reserved for storing 
      ATM cells received by the Lp."
::= { lpAruOperEntry 60 }

lpAruRxCellBlockUsage OBJECT-TYPE
   SYNTAX     Gauge32 (0..8192)
   ACCESS     read-only
   STATUS     obsolete
   DESCRIPTION
     "This attribute indicates the amount of memory currently being used 
      to store ATM cells received by the Lp."
::= { lpAruOperEntry 70 }

lpAruRxCellFreeListSize OBJECT-TYPE
   SYNTAX     Unsigned32 (0..16383)
   ACCESS     read-only
   STATUS     obsolete
   DESCRIPTION
     "This attribute indicates the current size of the receive cell free list. 
      The receive cell free list is the memory available for storing ATM 
      cells received by the Lp."
::= { lpAruOperEntry 73 }

lpAruRxCellFreeListCongestionState OBJECT-TYPE
   SYNTAX     INTEGER (0..3)
   ACCESS     read-only
   STATUS     obsolete
   DESCRIPTION
     "This attribute indicates the congestion state of the receive cell free 
      list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { lpAruOperEntry 76 }

lpAruRxFrameMemoryAllocation OBJECT-TYPE
   SYNTAX     Unsigned32 (0..100)
   ACCESS     read-only
   STATUS     obsolete
   DESCRIPTION
     "This attribute indicates the percentage of the receive CQM memory 
      which is allocated to the receive frame free list on the ATM-FP. The 
      remaining receive CQM memory is allocated to the receive cell free 
      list. Frame memory is used for trunks, ATM Vcc testing and for 
      inter-card communication."
::= { lpAruOperEntry 80 }

lpAruRxFrameBlockCapacity OBJECT-TYPE
   SYNTAX     Unsigned32 (0..8192)
   ACCESS     read-only
   STATUS     obsolete
   DESCRIPTION
     "This attribute indicates the amount of memory reserved for storing 
      frames received by the Lp."
::= { lpAruOperEntry 90 }

lpAruRxFrameBlockUsage OBJECT-TYPE
   SYNTAX     Gauge32 (0..8192)
   ACCESS     read-only
   STATUS     obsolete
   DESCRIPTION
     "This attribute indicates the amount of memory currently being used 
      to store frames received by the Lp."
::= { lpAruOperEntry 100 }

lpAruRxFrameFreeListSize OBJECT-TYPE
   SYNTAX     Unsigned32 (0..16383)
   ACCESS     read-only
   STATUS     obsolete
   DESCRIPTION
     "This attribute indicates the current size of the receive frame free list. 
      The receive frame free list is the memory (in ATM cells) available 
      for storing frames received by the Lp."
::= { lpAruOperEntry 103 }

lpAruRxFrameFreeListCongestionState OBJECT-TYPE
   SYNTAX     INTEGER (0..3)
   ACCESS     read-only
   STATUS     obsolete
   DESCRIPTION
     "This attribute indicates the congestion state of the receive frame free 
      list on this ATM-FP. 
      
      The congestion state of a free list is indicated by a numeric value 
      ranging from 0 to 3. When a free list is in a congested state x, only 
      traffic with discard priority (DP) 0 to x will be stored. Traffic with 
      DP > x will be discarded. 
      
      Therefore, if the congestion state is 3, there is no congestion and all 
      traffic is stored. Likewise, when the congestion state is 0, there is 
      maximum congestion and only traffic with DP=0 will be stored."
::= { lpAruOperEntry 106 }

lpAruSubConnectionPoolAvailable OBJECT-TYPE
   SYNTAX     Unsigned32 (0..8192)
   ACCESS     read-only
   STATUS     obsolete
   DESCRIPTION
     "This attribute indicates the number of sub-connections available for 
      the LogicalProcessor. 
      
      A sub-connection is used for interworking the ATM services with 
      the frame oriented services such as Frame Relay, and Path Oriented 
      Routing System (PORS). When a frame is received at a sub-
      connection, the frame header is modified to be compatible with the 
      service it is to be forwarded to. 
      
      This pool is used for connection oriented services only. Each of the 
      following components uses one sub-connection from this pool: 
      FrAtm/x Dlci/y Siwf
      McsMgr Frf5EpG/x Frf5Ep/y Lmi
      McsMgr Frf5EpG/x Frf5Ep/y Dlci/z
      
      Note when the value of this attribute reaches zero, no more 
      connections will be accepted for any of the services which utilize 
      this pool. To increase the size of this pool, use the Arc 
      subConnectionPoolCapacity attribute."
::= { lpAruOperEntry 107 }

lpAruSubConnectionPoolUsage OBJECT-TYPE
   SYNTAX     Unsigned32 (0..8192)
   ACCESS     read-only
   STATUS     obsolete
   DESCRIPTION
     "This attribute indicates the number of sub-connections being 
      utilized for the LogicalProcessor.
      
      A sub-connection is used for interworking the ATM services with 
      the frame oriented services such as Frame Relay, and Path Oriented 
      Routing System (PORS). When a frame is received at a sub-
      connection, the frame header is modified to be compatible with the 
      service it is to be forwarded to.
      
      This pool is used for connection oriented services only. Each of the 
      following components uses one sub-connection from this pool: 
      FrAtm/x Dlci/y Siwf
      McsMgr Frf5EpG/x Frf5Ep/y Lmi
      McsMgr Frf5EpG/x Frf5Ep/y Dlci/z"
::= { lpAruOperEntry 108 }

lpAruLnnConnectionPoolAvailable OBJECT-TYPE
   SYNTAX     Unsigned32 (0..512)
   ACCESS     read-only
   STATUS     obsolete
   DESCRIPTION
     "This attribute indicates the number of resource records available for 
      the connections which utilize Logical Network Number (LNN) on 
      the LogicalProcessor.
      
      A logical network is a subset of passport modules together with a 
      subset of trunks that interconnect those modules. It carries the 
      traffic for a defined set of network protocols. A LNN is used to 
      identify a logical network. The connectionless services which 
      utilize the logical networks require some processing at the 
      intermediate nodes. This pool is allocated at the intermediate nodes 
      to sustain these connectionless services.
      
      If the McsMgr DprsMcsEpG/x Ep/y EpD 
      transportConnectionPreference attribute is set to atmOnly, each 
      instance of the McsMgr DprsMcsEpG/x Ep/y component uses one 
      resource record from this pool.
      
      Note, when the value of this attribute reaches zero, no more 
      connections will be accepted for any of the services which utilize 
      this pool. To increase the size of this pool, use the Arc 
      lnnConnectionPoolCapacity attribute."
::= { lpAruOperEntry 109 }

lpAruLnnConnectionPoolUsage OBJECT-TYPE
   SYNTAX     Unsigned32 (0..512)
   ACCESS     read-only
   STATUS     obsolete
   DESCRIPTION
     "This attribute indicates the number of resource records being 
      utilized for the connections which use Logical Network Number 
      (LNN) on the LogicalProcessor.
      
      A logical network is a subset of passport modules together with a 
      subset of trunks that interconnect those modules. It carries the 
      traffic for a defined set of network protocols. A LNN is used to 
      identify a logical network. The connectionless services which 
      utilize the logical networks require some processing at the 
      intermediate nodes. This pool is applied at the intermediate nodes to 
      sustain these connectionless services.
      
      If the McsMgr DprsMcsEpG/x Ep/y EpD 
      transportConnectionPreference attribute is set to atmOnly, each 
      instance of the McsMgr DprsMcsEpG/x Ep/y component uses one 
      resource record from this pool."
::= { lpAruOperEntry 110 }

lpAruConnUsageTable OBJECT-TYPE
   SYNTAX     SEQUENCE OF LpAruConnUsageEntry
   ACCESS     not-accessible
   STATUS     obsolete
   DESCRIPTION
     "This attribute has been replaced by the set of AtmIf CA 
      connectionPoolUsage attributes for AtmIf associated to 
      independent links or IMA groups on this LogicalProcessor. The 
      change better encapsulates the information associated with the 
      AtmIf.
      
      This attribute indicates the number of connection identifiers (both 
      VCC and VPC) that are in use on each port. The entries are indexed 
      by port number."
::= { lpAru 292 }

lpAruConnUsageEntry OBJECT-TYPE
   SYNTAX     LpAruConnUsageEntry
   ACCESS     not-accessible
   STATUS     obsolete
   DESCRIPTION
     "An entry in the lpAruConnUsageTable."
   INDEX {
      lpIndex,
      lpAruIndex,
      lpAruConnUsageIndex }
::= { lpAruConnUsageTable 1 }

LpAruConnUsageEntry ::= SEQUENCE {
   lpAruConnUsageIndex
      Integer32,
   lpAruConnUsageValue
      Unsigned32 }

lpAruConnUsageIndex OBJECT-TYPE
   SYNTAX     Integer32 (0..2)
   ACCESS     not-accessible
   STATUS     obsolete
   DESCRIPTION
     "This variable represents the lpAruConnUsageTable
      specific index for the lpAruConnUsageTable."
::= { lpAruConnUsageEntry 1 }

lpAruConnUsageValue OBJECT-TYPE
   SYNTAX     Unsigned32 (0..16000)
   ACCESS     read-only
   STATUS     obsolete
   DESCRIPTION
     "This variable represents an individual value for the
      lpAruConnUsageTable."
::= { lpAruConnUsageEntry 2 }

lpAruTxCflThreshTable OBJECT-TYPE
   SYNTAX     SEQUENCE OF LpAruTxCflThreshEntry
   ACCESS     not-accessible
   STATUS     obsolete
   DESCRIPTION
     "This attribute indicates the maximum value of the 
      txCellFreeListSize and the discard thresholds of the transmit cell 
      free list. The transmit cell free list is the memory used for storing 
      ATM cells to be transmitted by the Lp.
      
      The first value indicates the maximum size of the transmit cell free 
      list. This is derived based upon the connectionPoolCapacity and the 
      txFrameMemoryAllocation under the ARC component.
      
      When the txCellFreeListSize decreases to the second value, the 
      txCellFreeListCongestionState changes from 3 to 2. In congestion 
      state 2, traffic with discard priority (DP) = 3 is discarded. This 
      threshold is set approximately at 25 percent of the first value, the 
      maximum transmit cell free list size.
      
      When the txCellFreeListSize decreases to the third value, the 
      txCellFreeListCongestionState changes from 2 to 1. In congestion 
      state 1, traffic with discard priority (DP) = 2 is discarded. This 
      threshold is set approximately at 20 percent of the first value, the 
      maximum transmit cell free list size.
      
      When the txCellFreeListSize decreases to the fourth value, the 
      txCellFreeListCongestionState changes from 1 to 0. In congestion 
      state 0, traffic with discard priority (DP) = 1 is discarded. This 
      threshold is set approximately at 10 percent of the first value, the 
      maximum transmit cell free list size."
::= { lpAru 353 }

lpAruTxCflThreshEntry OBJECT-TYPE
   SYNTAX     LpAruTxCflThreshEntry
   ACCESS     not-accessible
   STATUS     obsolete
   DESCRIPTION
     "An entry in the lpAruTxCflThreshTable."
   INDEX {
      lpIndex,
      lpAruIndex,
      lpAruTxCflThreshIndex }
::= { lpAruTxCflThreshTable 1 }

LpAruTxCflThreshEntry ::= SEQUENCE {
   lpAruTxCflThreshIndex
      Integer32,
   lpAruTxCflThreshValue
      Unsigned32 }

lpAruTxCflThreshIndex OBJECT-TYPE
   SYNTAX     Integer32 (0..3)
   ACCESS     not-accessible
   STATUS     obsolete
   DESCRIPTION
     "This variable represents the lpAruTxCflThreshTable
      specific index for the lpAruTxCflThreshTable."
::= { lpAruTxCflThreshEntry 1 }

lpAruTxCflThreshValue OBJECT-TYPE
   SYNTAX     Unsigned32 (0..16383)
   ACCESS     read-only
   STATUS     obsolete
   DESCRIPTION
     "This variable represents an individual value for the
      lpAruTxCflThreshTable."
::= { lpAruTxCflThreshEntry 2 }

lpAruTxFflThreshTable OBJECT-TYPE
   SYNTAX     SEQUENCE OF LpAruTxFflThreshEntry
   ACCESS     not-accessible
   STATUS     obsolete
   DESCRIPTION
     "This attribute indicates the maximum txFrameFreeListSize and the 
      discard thresholds of the transmit frame free list. The transmit frame 
      free list is the memory (in units of ATM cells) used for storing 
      frames to be transmitted by the Lp.
      
      The first parameter indicates the total size of the transmit frame free 
      list. This is derived based upon the connectionPoolCapacity and the 
      txFrameMemoryAllocation under the ARC component.
      
      When the txFrameFreeListSize decreases to the second value, the 
      txFrameFreeListCongestionState changes from 3 to 2. In congestion 
      state 2, traffic with discard priority (DP) = 3 is discarded. This 
      threshold is set approximately at 25 percent of the first value, the 
      maximum transmit frame free list size.
      
      When the txFrameFreeListSize decreases to the third value, the 
      txFrameFreeListCongestionState changes from 2 to 1. In congestion 
      state 1, traffic with discard priority (DP) = 2 is discarded. This 
      threshold is set approximately at 20 percent of the first value, the 
      maximum transmit frame free list size.
      
      When the txFameFreeListSize decreases to the fourth value, the 
      txFameFreeListCongestionState changes from 1 to 0. In congestion 
      state 0, traffic with discard priority (DP) = 1 is discarded. This 
      threshold is set approximately at 10 percent of the first value, the 
      maximum transmit frame free list size."
::= { lpAru 354 }

lpAruTxFflThreshEntry OBJECT-TYPE
   SYNTAX     LpAruTxFflThreshEntry
   ACCESS     not-accessible
   STATUS     obsolete
   DESCRIPTION
     "An entry in the lpAruTxFflThreshTable."
   INDEX {
      lpIndex,
      lpAruIndex,
      lpAruTxFflThreshIndex }
::= { lpAruTxFflThreshTable 1 }

LpAruTxFflThreshEntry ::= SEQUENCE {
   lpAruTxFflThreshIndex
      Integer32,
   lpAruTxFflThreshValue
      Unsigned32 }

lpAruTxFflThreshIndex OBJECT-TYPE
   SYNTAX     Integer32 (0..3)
   ACCESS     not-accessible
   STATUS     obsolete
   DESCRIPTION
     "This variable represents the lpAruTxFflThreshTable
      specific index for the lpAruTxFflThreshTable."
::= { lpAruTxFflThreshEntry 1 }

lpAruTxFflThreshValue OBJECT-TYPE
   SYNTAX     Unsigned32 (0..16383)
   ACCESS     read-only
   STATUS     obsolete
   DESCRIPTION
     "This variable represents an individual value for the
      lpAruTxFflThreshTable."
::= { lpAruTxFflThreshEntry 2 }

lpAruRxCflThreshTable OBJECT-TYPE
   SYNTAX     SEQUENCE OF LpAruRxCflThreshEntry
   ACCESS     not-accessible
   STATUS     obsolete
   DESCRIPTION
     "This attribute indicates the maximum value of the 
      rxCellFreeListSize and the discard thresholds of the receive cell free 
      list. The receive cell free list is the memory used for storing ATM 
      cells to be received by the Lp.
      
      The first value indicates the maximum size of the receive cell free 
      list. This is derived based upon the connectionPoolCapacity and the 
      rxFrameMemoryAllocation under the ARC component.
      
      When the rxCellFreeListSize decreases to the second value, the 
      rxCellFreeListCongestionState changes from 3 to 2. In congestion 
      state 2, traffic with discard priority (DP) = 3 is discarded. This 
      threshold is set approximately at 25 percent of the first value, the 
      maximum receive cell free list size.
      
      When the rxCellFreeListSize decreases to the third value, the 
      rxCellFreeListCongestionState changes from 2 to 1. In congestion 
      state 1, traffic with discard priority (DP) = 2 is discarded. This 
      threshold is set approximately at 20 percent of the first value, the 
      maximum receive cell free list size.
      
      When the rxCellFreeListSize decreases to the fourth value, the 
      rxCellFreeListCongestionState changes from 1 to 0. In congestion 
      state 0, traffic with discard priority (DP) = 1 is discarded. This 
      threshold is set approximately at 10 percent of the first value, the 
      maximum receive cell free list size."
::= { lpAru 355 }

lpAruRxCflThreshEntry OBJECT-TYPE
   SYNTAX     LpAruRxCflThreshEntry
   ACCESS     not-accessible
   STATUS     obsolete
   DESCRIPTION
     "An entry in the lpAruRxCflThreshTable."
   INDEX {
      lpIndex,
      lpAruIndex,
      lpAruRxCflThreshIndex }
::= { lpAruRxCflThreshTable 1 }

LpAruRxCflThreshEntry ::= SEQUENCE {
   lpAruRxCflThreshIndex
      Integer32,
   lpAruRxCflThreshValue
      Unsigned32 }

lpAruRxCflThreshIndex OBJECT-TYPE
   SYNTAX     Integer32 (0..3)
   ACCESS     not-accessible
   STATUS     obsolete
   DESCRIPTION
     "This variable represents the lpAruRxCflThreshTable
      specific index for the lpAruRxCflThreshTable."
::= { lpAruRxCflThreshEntry 1 }

lpAruRxCflThreshValue OBJECT-TYPE
   SYNTAX     Unsigned32 (0..16383)
   ACCESS     read-only
   STATUS     obsolete
   DESCRIPTION
     "This variable represents an individual value for the
      lpAruRxCflThreshTable."
::= { lpAruRxCflThreshEntry 2 }

lpAruRxFflThreshTable OBJECT-TYPE
   SYNTAX     SEQUENCE OF LpAruRxFflThreshEntry
   ACCESS     not-accessible
   STATUS     obsolete
   DESCRIPTION
     "This attribute indicates the maximum rxFrameFreeListSize and the 
      discard thresholds of the transmit frame free list. The receive frame 
      free list is the memory (in units of ATM cells) used for storing 
      frames to be received by the Lp.
      
      The first parameter indicates the total size of the receive frame free 
      list. This is derived based upon the connectionPoolCapacity and the 
      rxFrameMemoryAllocation under the ARC component.
      
      When the rxFrameFreeListSize decreases to the second value, the 
      rxFrameFreeListCongestionState changes from 3 to 2. In 
      congestion state 2, traffic with discard priority (DP) = 3 is 
      discarded. This threshold is set approximately at 25 percent of the 
      first value, the maximum receive frame free list size.
      
      When the rxFrameFreeListSize decreases to the third value, the 
      rxFrameFreeListCongestionState changes from 2 to 1. In 
      congestion state 1, traffic with discard priority (DP) = 2 is 
      discarded. This threshold is set approximately at 20 percent of the 
      first value, the maximum receive frame free list size.
      
      When the rxFameFreeListSize decreases to the fourth value, the 
      rxFameFreeListCongestionState changes from 1 to 0. In congestion 
      state 0, traffic with discard priority (DP) = 1 is discarded. This 
      threshold is set approximately at 10 percent of the first value, the 
      maximum receive frame free list size."
::= { lpAru 356 }

lpAruRxFflThreshEntry OBJECT-TYPE
   SYNTAX     LpAruRxFflThreshEntry
   ACCESS     not-accessible
   STATUS     obsolete
   DESCRIPTION
     "An entry in the lpAruRxFflThreshTable."
   INDEX {
      lpIndex,
      lpAruIndex,
      lpAruRxFflThreshIndex }
::= { lpAruRxFflThreshTable 1 }

LpAruRxFflThreshEntry ::= SEQUENCE {
   lpAruRxFflThreshIndex
      Integer32,
   lpAruRxFflThreshValue
      Unsigned32 }

lpAruRxFflThreshIndex OBJECT-TYPE
   SYNTAX     Integer32 (0..3)
   ACCESS     not-accessible
   STATUS     obsolete
   DESCRIPTION
     "This variable represents the lpAruRxFflThreshTable
      specific index for the lpAruRxFflThreshTable."
::= { lpAruRxFflThreshEntry 1 }

lpAruRxFflThreshValue OBJECT-TYPE
   SYNTAX     Unsigned32 (0..16383)
   ACCESS     read-only
   STATUS     obsolete
   DESCRIPTION
     "This variable represents an individual value for the
      lpAruRxFflThreshTable."
::= { lpAruRxFflThreshEntry 2 }


-- Lp/n Eng AtmResourceControl
-- This component describes the usage of ATM-specific resources on 
-- an FP running ATM services. This component is always 
-- dynamically created under any LP Eng which supports an FP. 

lpEngArc OBJECT IDENTIFIER ::= { lpEng 5 }



lpEngArcRowStatusTable OBJECT-TYPE
   SYNTAX     SEQUENCE OF LpEngArcRowStatusEntry
   ACCESS     not-accessible
   STATUS     mandatory
   DESCRIPTION
     "This entry controls the addition and deletion of 
      lpEngArc components."
::= { lpEngArc 1 }

lpEngArcRowStatusEntry OBJECT-TYPE
   SYNTAX     LpEngArcRowStatusEntry
   ACCESS     not-accessible
   STATUS     mandatory
   DESCRIPTION
     "A single entry in the table represents a single 
      lpEngArc component."
   INDEX {
      lpIndex,
      lpEngIndex,
      lpEngArcIndex }
::= { lpEngArcRowStatusTable 1 }

LpEngArcRowStatusEntry ::= SEQUENCE {
   lpEngArcRowStatus
      RowStatus,
   lpEngArcComponentName
      DisplayString,
   lpEngArcStorageType
      StorageType,
   lpEngArcIndex
      NonReplicated }

lpEngArcRowStatus OBJECT-TYPE
   SYNTAX     RowStatus 
   ACCESS     read-write
   STATUS     mandatory
   DESCRIPTION
     "This variable is used as the basis for SNMP naming of
      lpEngArc components.
      These components can be added and deleted."
::= { lpEngArcRowStatusEntry 1 }

lpEngArcComponentName OBJECT-TYPE
   SYNTAX     DisplayString 
   ACCESS     read-only
   STATUS     mandatory
   DESCRIPTION
     "This variable provides the component's string name for
      use with the ASCII Console Interface"
::= { lpEngArcRowStatusEntry 2 }

lpEngArcStorageType OBJECT-TYPE
   SYNTAX     StorageType 
   ACCESS     read-only
   STATUS     mandatory
   DESCRIPTION
     "This variable represents the storage type value for the
      lpEngArc tables."
::= { lpEngArcRowStatusEntry 4 }

lpEngArcIndex OBJECT-TYPE
   SYNTAX     NonReplicated 
   ACCESS     not-accessible
   STATUS     mandatory
   DESCRIPTION
     "This variable represents the index for the lpEngArc tables."
::= { lpEngArcRowStatusEntry 10 }

lpEngArcOperTable OBJECT-TYPE
   SYNTAX     SEQUENCE OF LpEngArcOperEntry
   ACCESS     not-accessible
   STATUS     mandatory
   DESCRIPTION
     "This group describes the usage of ATM-specific resources on a 
      Logical Processor running ATM services.
      The attributes listed represent Queue Controller resource usage for 
      all ATM Cards (CQC for CQC based cards or PQC for SGAF 
      cards)."
::= { lpEngArc 10 }

lpEngArcOperEntry OBJECT-TYPE
   SYNTAX     LpEngArcOperEntry
   ACCESS     not-accessible
   STATUS     mandatory
   DESCRIPTION
     "An entry in the lpEngArcOperTable."
   INDEX {
      lpIndex,
      lpEngIndex,
      lpEngArcIndex }
::= { lpEngArcOperTable 1 }

LpEngArcOperEntry ::= SEQUENCE {
   lpEngArcTotalConnectionPoolAvailable
      Unsigned32,
   lpEngArcTotalConnectionPoolUsage
      Unsigned32,
   lpEngArcMulticastBranchesAvailable
      Unsigned32,
   lpEngArcMulticastBranchesUsage
      Unsigned32,
   lpEngArcTxCellMemoryAllocation
      Unsigned32,
   lpEngArcTxCellMemoryAvailable
      Gauge32,
   lpEngArcTxCellMemoryMinAvailable
      Gauge32,
   lpEngArcTxCellMemoryCongestionState
      Gauge32,
   lpEngArcRxCellMemoryAllocation
      Unsigned32,
   lpEngArcRxCellMemoryAvailable
      Gauge32,
   lpEngArcRxCellMemoryMinAvailable
      Gauge32,
   lpEngArcRxCellMemoryCongestionState
      Gauge32,
   lpEngArcTxCellMemoryMaxUsage
      Gauge32,
   lpEngArcTxCellMemoryUsage
      Gauge32,
   lpEngArcRxCellMemoryMaxUsage
      Gauge32,
   lpEngArcRxCellMemoryUsage
      Gauge32 }

lpEngArcTotalConnectionPoolAvailable OBJECT-TYPE
   SYNTAX     Unsigned32 (0..32768)
   ACCESS     read-only
   STATUS     mandatory
   DESCRIPTION
     "This attribute indicates the number of connection resources 
      available (VCC, VPC, and VPT) that can be used on this FP.
      
      A standard Vpt uses 3 connection resources and a basic Vpt uses 2."
::= { lpEngArcOperEntry 1 }

lpEngArcTotalConnectionPoolUsage OBJECT-TYPE
   SYNTAX     Unsigned32 (0..32768)
   ACCESS     read-only
   STATUS     mandatory
   DESCRIPTION
     "This attribute indicates the number of connection resources (VCC, 
      VPC, and VPT) in use on this FP.
      
      A standard Vpt uses 3 connection resources and a basic Vpt uses 2."
::= { lpEngArcOperEntry 2 }

lpEngArcMulticastBranchesAvailable OBJECT-TYPE
   SYNTAX     Unsigned32 (0..16384)
   ACCESS     read-only
   STATUS     mandatory
   DESCRIPTION
     "This attribute indicates the total number of multicast branches that 
      are available on this FP."
::= { lpEngArcOperEntry 3 }

lpEngArcMulticastBranchesUsage OBJECT-TYPE
   SYNTAX     Unsigned32 (0..16384)
   ACCESS     read-only
   STATUS     mandatory
   DESCRIPTION
     "This attribute indicates the total number of multicast branches that 
      are active on this FP."
::= { lpEngArcOperEntry 4 }

lpEngArcTxCellMemoryAllocation OBJECT-TYPE
   SYNTAX     Unsigned32 (1..99)
   ACCESS     read-only
   STATUS     mandatory
   DESCRIPTION
     "This attribute indicates the fraction of the transmit memory which is 
      allocated for the transmission of cells on the FP. Cell memory is 
      used for Atm Bearer Services, ATM SVCs and ATM PVCs.
      
      The remaining transmit memory is allocated for the transmission of 
      frames. Frame memory is used for trunks, ATM VCC testing and 
      for inter-card communication."
::= { lpEngArcOperEntry 5 }

lpEngArcTxCellMemoryAvailable OBJECT-TYPE
   SYNTAX     Gauge32 (0..163839)
   ACCESS     read-only
   STATUS     obsolete
   DESCRIPTION
     "This attribute indicates the current availability of the transmit  cell 
      memory.
      
      The transmit cell memory is the memory available for storing ATM 
      cells to be transmitted by this FP."
::= { lpEngArcOperEntry 6 }

lpEngArcTxCellMemoryMinAvailable OBJECT-TYPE
   SYNTAX     Gauge32 (0..163839)
   ACCESS     read-only
   STATUS     obsolete
   DESCRIPTION
     "This attribute indicates the lowest availability of the transmit cell 
      memory.
      
      The transmit cell memory is the memory available for storing ATM 
      cells to be transmitted by this FP.
      
      This value is reset to the current availability every 15 minutes and 
      when the card is reset."
::= { lpEngArcOperEntry 7 }

lpEngArcTxCellMemoryCongestionState OBJECT-TYPE
   SYNTAX     Gauge32 (0..3)
   ACCESS     read-only
   STATUS     mandatory
   DESCRIPTION
     "This attribute indicates the congestion state of the transmit cell 
      memory for this FP. 
      
      This attribute indicates which txCellMemoryThresholds corresponds 
      to the current value of txCellMemoryUsage. The congestion state is 
      used to determine if cells of a particular discard priority (DP) are 
      discarded before being queued for transmit. 
      
      The congestion state of transmit cell memory is indicated by a 
      numeric value ranging from 3 to 0. When transmit cell memory is in 
      congestion state 'x', traffic with DP > 'x' is discarded before 
      transmit. Traffic with DP < 'x' may be queued for transmit, 
      depending on the congestion level of the connection transmit queue. 
      Traffic with DP = 'x' may be either queued or discarded depending 
      on how close the value of txCellMemoryUsage is to the next 
      threshold as displayed in txCellMemoryThresholds. For example, 
      CLP1 traffic is queued until the value indicated by 
      txCellMemoryUsage equals the value indicated in 
      txCellMemoryThresholds 3. At that point, CLP1 traffic is discarded."
::= { lpEngArcOperEntry 8 }

lpEngArcRxCellMemoryAllocation OBJECT-TYPE
   SYNTAX     Unsigned32 (1..99)
   ACCESS     read-only
   STATUS     mandatory
   DESCRIPTION
     "This attribute indicates the fraction of the receive  memory which is 
      allocated for the reception of cells on the FP. Cell memory is used 
      for Atm Bearer Services, ATM SVCS and ATM PVCS.
      
      The remaining receive memory is allocated to the reception of 
      frame. Frame memory is used for trunks, ATM VCC testing and for 
      inter-card communication."
::= { lpEngArcOperEntry 9 }

lpEngArcRxCellMemoryAvailable OBJECT-TYPE
   SYNTAX     Gauge32 (0..163839)
   ACCESS     read-only
   STATUS     obsolete
   DESCRIPTION
     "This attribute indicates the current availability of the receive  cell 
      memory. 
      
      The receive cell memory is the memory available for storing ATM 
      cells to be transmitted by this FP."
::= { lpEngArcOperEntry 10 }

lpEngArcRxCellMemoryMinAvailable OBJECT-TYPE
   SYNTAX     Gauge32 (0..16384)
   ACCESS     read-only
   STATUS     obsolete
   DESCRIPTION
     "This attribute indicates the lowest availability of the receive  cell 
      memory. 
      
      The receive cell memory is the memory available for storing ATM 
      cells to be transmitted by this FP.
      
      This value is reset to the current availability every 15 minutes and 
      when the card is reset."
::= { lpEngArcOperEntry 11 }

lpEngArcRxCellMemoryCongestionState OBJECT-TYPE
   SYNTAX     Gauge32 (0..3)
   ACCESS     read-only
   STATUS     mandatory
   DESCRIPTION
     "This attribute indicates the congestion state of the receive cell 
      memory on this FP. 
      
      This attribute indicates which rxCellMemoryThresholds 
      corresponds to the current value of rxCellMemoryUsage. The 
      congestion state is used to determine if cells of a particular discard 
      priority (DP) are discarded before being queued for processing on 
      this FP. 
      
      The congestion state of receive cell memory is indicated by a 
      numeric value ranging from 3 to 0. When receive cell memory is in 
      congestion state 'x', traffic with DP > 'x' is discarded before 
      processing. Traffic with DP < 'x' may be queued for processing, 
      depending on the congestion level of the processor or bus queue. 
      Traffic with DP = 'x' may be either queued or discarded depending 
      on how close the value of rxCellMemoryUsage is to the next 
      threshold as displayed in rxCellMemoryThresholds. For example, 
      CLP1 traffic is queued until the value indicated by 
      rxCellMemoryUsage equals the value indicated in 
      rxCellMemoryThresholds 3. At that point, CLP1 traffic is discarded."
::= { lpEngArcOperEntry 12 }

lpEngArcTxCellMemoryMaxUsage OBJECT-TYPE
   SYNTAX     Gauge32 (0..163839)
   ACCESS     read-only
   STATUS     mandatory
   DESCRIPTION
     "This attribute indicates the maximum number which has recently 
      occurred for the txCellMemoryUsage attribute. 
      
      On CQC-based ATM FPs, this number indicates the maximum 
      usage of transmit cells for all ports on this FP. 
      
      On ATM IP FPs, this number indicates the maximum usage of 
      transmit cells in the Passport Queue Controller (PQC) ASIC. 
      Queuing of ATM cells for transmit normally occurs in the ATM 
      Queue Manager (AQM) ASIC, which is indicated in the Lp Eng Arc 
      Aqm/x txCellMemoryUsage attribute. Transmit cells should only be 
      queued in the PQC under circumstances of extreme transient 
      congestion. 
      
      This value is reset to the current usage every 15 minutes and when 
      the card is reset."
::= { lpEngArcOperEntry 13 }

lpEngArcTxCellMemoryUsage OBJECT-TYPE
   SYNTAX     Gauge32 (0..163839)
   ACCESS     read-only
   STATUS     mandatory
   DESCRIPTION
     "This attribute indicates the current number of transmit cells which 
      are in use for this FP. 
      
      On CQC-based ATM FPs, this number indicates the total transmit 
      cells which are in use for all ports on this FP. 
      
      On ATM IP FPs, this number indicates the number of transmit cells 
      which are in use in the Passport Queue Controller (PQC) ASIC. 
      Queuing of ATM cells for transmit normally occurs in the ATM 
      Queue Manager (AQM) ASIC, which is indicated in the Lp Eng Arc 
      Aqm/x txCellMemoryUsage attribute. Transmit cells should only be 
      queued in the PQC under circumstances of extreme transient 
      congestion."
::= { lpEngArcOperEntry 14 }

lpEngArcRxCellMemoryMaxUsage OBJECT-TYPE
   SYNTAX     Gauge32 (0..163839)
   ACCESS     read-only
   STATUS     mandatory
   DESCRIPTION
     "This attribute indicates the maximum usage of receive cells for all 
      ports on this FP. Receive cell memory is used for storing ATM cells 
      received by this FP which are currently queued either for handling 
      by the processor on this FP or queued for transmitting over the 
      backplane to other FPs.
      
      This value is reset to the current usage every 15 minutes and when 
      the card is reset."
::= { lpEngArcOperEntry 15 }

lpEngArcRxCellMemoryUsage OBJECT-TYPE
   SYNTAX     Gauge32 (0..163839)
   ACCESS     read-only
   STATUS     mandatory
   DESCRIPTION
     "This attribute indicates the current number of receive cells which 
      are in use for all ports on this FP. Receive cell memory is used for 
      storing ATM cells received by this FP which are currently queued 
      either for handling by the processor on this FP or queued for 
      transmitting over the backplane to other FPs on this switch."
::= { lpEngArcOperEntry 16 }

lpEngArcTxCellThreshTable OBJECT-TYPE
   SYNTAX     SEQUENCE OF LpEngArcTxCellThreshEntry
   ACCESS     not-accessible
   STATUS     mandatory
   DESCRIPTION
     "This attribute is a vector which indicates the size and three discard 
      thresholds for transmit cell memory for this FP. The transmit cell 
      memory is used for storing ATM cells to be transmitted by this FP.
      
      The first value indicates the transmit cell memory size. This is 
      derived based on the total transmit memory capacity of this FP, and 
      the value of the connectionPoolCapacity and the 
      txCellMemoryAllocation attributes.
      
      The current value of txCellMemoryUsage together with the vector 
      of values in txCellMemoryThresholds determines the 
      txCellMemoryCongestionState. The congestion state determines 
      whether cells of a given discard priority (DP) are discarded or 
      queued for transmit. 
      
      When the txCellMemoryUsage attribute is between threshold 0 and 
      threshold 1, the txCellMemoryCongestionState indicates the value 
      0. In congestion state 0, traffic with DP > 0 is discarded. Threshold 
      1 is set approximately at 90 percent of threshold 0, the total transmit 
      cell memory size. 
      
      When the txCellMemoryUsage attribute is between threshold 1 and 
      threshold 2, the txCellMemoryCongestionState indicates the value 
      1. In congestion state 1, traffic with DP > 1 is discarded. Threshold 
      2 is set approximately at 85 percent of threshold 0, the total transmit 
      cell memory size. 
      
      When the txCellMemoryUsage attribute is between threshold 2 and 
      threshold 3, the txCellMemoryCongestionState indicates the value 
      2. In congestion state 2, traffic with DP > 2 is discarded. Threshold 
      3 is set approximately at 75 percent of threshold 0, the total transmit 
      cell memory size. 
      
      When the txCellMemoryUsage attribute is below threshold 3, the 
      txCellMemoryCongestionState indicates the value 3. In congestion 
      state 3, traffic with DP=3 is queued."
::= { lpEngArc 440 }

lpEngArcTxCellThreshEntry OBJECT-TYPE
   SYNTAX     LpEngArcTxCellThreshEntry
   ACCESS     not-accessible
   STATUS     mandatory
   DESCRIPTION
     "An entry in the lpEngArcTxCellThreshTable."
   INDEX {
      lpIndex,
      lpEngIndex,
      lpEngArcIndex,
      lpEngArcTxCellThreshIndex }
::= { lpEngArcTxCellThreshTable 1 }

LpEngArcTxCellThreshEntry ::= SEQUENCE {
   lpEngArcTxCellThreshIndex
      Integer32,
   lpEngArcTxCellThreshValue
      Unsigned32 }

lpEngArcTxCellThreshIndex OBJECT-TYPE
   SYNTAX     Integer32 (0..3)
   ACCESS     not-accessible
   STATUS     mandatory
   DESCRIPTION
     "This variable represents the lpEngArcTxCellThreshTable
      specific index for the lpEngArcTxCellThreshTable."
::= { lpEngArcTxCellThreshEntry 1 }

lpEngArcTxCellThreshValue OBJECT-TYPE
   SYNTAX     Unsigned32 (0..163839)
   ACCESS     read-only
   STATUS     mandatory
   DESCRIPTION
     "This variable represents an individual value for the
      lpEngArcTxCellThreshTable."
::= { lpEngArcTxCellThreshEntry 2 }

lpEngArcRxCellThreshTable OBJECT-TYPE
   SYNTAX     SEQUENCE OF LpEngArcRxCellThreshEntry
   ACCESS     not-accessible
   STATUS     mandatory
   DESCRIPTION
     "This attribute is a vector which indicates the size and three discard 
      thresholds for receive cell memory for this FP. Receive cell memory 
      is used for storing ATM cells received by this FP which are queued 
      either for handling by the processor on this FP or queued for 
      transmitting over the backplane to other FPs on this switch. 
      
      The first value indicates the receive cell memory size. This is 
      derived based on the total receive memory capacity of this FP, and 
      the value of the connectionPoolCapacity and the 
      rxCellMemoryAllocation attributes.
      
      The current value of rxCellMemoryUsage together with the vector 
      of values in rxCellMemoryThresholds determines the 
      rxCellMemoryCongestionState. The congestion state determines 
      whether cells of a given discard priority (DP) are discarded or 
      queued. 
      
      When the rxCellMemoryUsage attribute is between threshold 0 and 
      threshold 1, the rxCellMemoryCongestionState indicates the value 
      0. In congestion state 0, traffic with DP > 0 is discarded. Threshold 
      1 is set approximately at 90 percent of threshold 0, the total receive 
      cell memory size. 
      
      When the rxCellMemoryUsage attribute is between threshold 1 and 
      threshold 2, the rxCellMemoryCongestionState indicates the value 
      1. In congestion state 1, traffic with DP > 1 is discarded. Threshold 
      2 is set approximately at 85 percent of threshold 0, the total receive 
      cell memory size. 
      
      When the rxCellMemoryUsage attribute is between threshold 2 and 
      threshold 3, the rxCellMemoryCongestionState indicates the value 
      2. In congestion state 2, traffic with DP > 2 is discarded. Threshold 
      3 is set approximately at 75 percent of threshold 0, the total receive 
      cell memory size. 
      
      When the rxCellMemoryUsage attribute is below threshold 3, the 
      rxCellMemoryCongestionState indicates the value 3. In congestion 
      state 3, traffic with DP=3 is queued."
::= { lpEngArc 444 }

lpEngArcRxCellThreshEntry OBJECT-TYPE
   SYNTAX     LpEngArcRxCellThreshEntry
   ACCESS     not-accessible
   STATUS     mandatory
   DESCRIPTION
     "An entry in the lpEngArcRxCellThreshTable."
   INDEX {
      lpIndex,
      lpEngIndex,
      lpEngArcIndex,
      lpEngArcRxCellThreshIndex }
::= { lpEngArcRxCellThreshTable 1 }

LpEngArcRxCellThreshEntry ::= SEQUENCE {
   lpEngArcRxCellThreshIndex
      Integer32,
   lpEngArcRxCellThreshValue
      Unsigned32 }

lpEngArcRxCellThreshIndex OBJECT-TYPE
   SYNTAX     Integer32 (0..3)
   ACCESS     not-accessible
   STATUS     mandatory
   DESCRIPTION
     "This variable represents the lpEngArcRxCellThreshTable
      specific index for the lpEngArcRxCellThreshTable."
::= { lpEngArcRxCellThreshEntry 1 }

lpEngArcRxCellThreshValue OBJECT-TYPE
   SYNTAX     Unsigned32 (0..163839)
   ACCESS     read-only
   STATUS     mandatory
   DESCRIPTION
     "This variable represents an individual value for the
      lpEngArcRxCellThreshTable."
::= { lpEngArcRxCellThreshEntry 2 }


-- Lp/n Eng Arc Override
-- This component is used to configure the usage of ATM-specific 
-- resources on a Logical Processor running ATM services. The 
-- attributes listed represent Queue Controller resource configuration 
-- for all ATM Cards (CQC for CQC based cards or PQC for SGAF 
-- cards).
-- This component is only permitted under Logical Processors which 
-- are linked to ATM card types.)

lpEngArcOv OBJECT IDENTIFIER ::= { lpEngArc 2 }



lpEngArcOvRowStatusTable OBJECT-TYPE
   SYNTAX     SEQUENCE OF LpEngArcOvRowStatusEntry
   ACCESS     not-accessible
   STATUS     mandatory
   DESCRIPTION
     "This entry controls the addition and deletion of 
      lpEngArcOv components."
::= { lpEngArcOv 1 }

lpEngArcOvRowStatusEntry OBJECT-TYPE
   SYNTAX     LpEngArcOvRowStatusEntry
   ACCESS     not-accessible
   STATUS     mandatory
   DESCRIPTION
     "A single entry in the table represents a single 
      lpEngArcOv component."
   INDEX {
      lpIndex,
      lpEngIndex,
      lpEngArcIndex,
      lpEngArcOvIndex }
::= { lpEngArcOvRowStatusTable 1 }

LpEngArcOvRowStatusEntry ::= SEQUENCE {
   lpEngArcOvRowStatus
      RowStatus,
   lpEngArcOvComponentName
      DisplayString,
   lpEngArcOvStorageType
      StorageType,
   lpEngArcOvIndex
      NonReplicated }

lpEngArcOvRowStatus OBJECT-TYPE
   SYNTAX     RowStatus 
   ACCESS     read-write
   STATUS     mandatory
   DESCRIPTION
     "This variable is used as the basis for SNMP naming of
      lpEngArcOv components.
      These components can be added and deleted."
::= { lpEngArcOvRowStatusEntry 1 }

lpEngArcOvComponentName OBJECT-TYPE
   SYNTAX     DisplayString 
   ACCESS     read-only
   STATUS     mandatory
   DESCRIPTION
     "This variable provides the component's string name for
      use with the ASCII Console Interface"
::= { lpEngArcOvRowStatusEntry 2 }

lpEngArcOvStorageType OBJECT-TYPE
   SYNTAX     StorageType 
   ACCESS     read-only
   STATUS     mandatory
   DESCRIPTION
     "This variable represents the storage type value for the
      lpEngArcOv tables."
::= { lpEngArcOvRowStatusEntry 4 }

lpEngArcOvIndex OBJECT-TYPE
   SYNTAX     NonReplicated 
   ACCESS     not-accessible
   STATUS     mandatory
   DESCRIPTION
     "This variable represents the index for the lpEngArcOv tables."
::= { lpEngArcOvRowStatusEntry 10 }

lpEngArcOvProvTable OBJECT-TYPE
   SYNTAX     SEQUENCE OF LpEngArcOvProvEntry
   ACCESS     not-accessible
   STATUS     mandatory
   DESCRIPTION
     "This group specifies the configuration of processor-wide ATM-
      specific resources on a Logical Processor running ATM services on 
      ATM cards. Note that altering any of these parameters will result in 
      a card reboot."
::= { lpEngArcOv 10 }

lpEngArcOvProvEntry OBJECT-TYPE
   SYNTAX     LpEngArcOvProvEntry
   ACCESS     not-accessible
   STATUS     mandatory
   DESCRIPTION
     "An entry in the lpEngArcOvProvTable."
   INDEX {
      lpIndex,
      lpEngIndex,
      lpEngArcIndex,
      lpEngArcOvIndex }
::= { lpEngArcOvProvTable 1 }

LpEngArcOvProvEntry ::= SEQUENCE {
   lpEngArcOvTotalConnectionPoolCapacity
      Unsigned32,
   lpEngArcOvMulticastBranchesCapacity
      Unsigned32,
   lpEngArcOvTxCellMemoryAllocation
      Unsigned32,
   lpEngArcOvRxCellMemoryAllocation
      Unsigned32 }

lpEngArcOvTotalConnectionPoolCapacity OBJECT-TYPE
   SYNTAX     Unsigned32 (0..32768)
   ACCESS     read-write
   STATUS     mandatory
   DESCRIPTION
     "This attribute specifies the maximum number of connections (VCC, 
      VPC, and VPT) that can be enabled on this FP. A standard Vpt uses 
      3 connections and a basic Vpt uses 2.
      
      If the LogicalProcessor is associated with a card of a cardType 
      other than one of the following: 3pE3Atm, 3pDS3Atm, 
      3pOC3MmAtm, 3pOC3SmAtm, 3pE1Atm, 3pDS1Atm, 
      2pJ6MAtm; the value of the attribute restricts the sum of the 
      (maxVccs + maxVpcs + (maxVpts * 3)) across all AtmIfs bound to 
      this LogicalProcessor.
      
      If the LogicalProcessor is associated with a card of one of the 
      following cardTypes: 3pE3Atm, 3pDS3Atm, 3pOC3MmAtm, 
      3pOC3SmAtm, 3pE1Atm, 3pDS1Atm, 2pJ6MAtm; the number of 
      available connections are distributed equally across the ports on the 
      FP. The number of connections associated to a particular port limits 
      the size of the Vcc space which can be defined by the ConnMap of 
      the AtmIf linked to the port. If the ConnMap component does not 
      exist, its default settings are used for this check. Furthermore, the 
      value of this attribute is restricted based on the number of ports on 
      the card. For one port cards, the minimum is 512, the maximum is 
      4096 and the value must be divisible by 256. For two port cards, the 
      minimum is 1024, the maximum is 8192 and the value must be 
      divisible by 512. For three port cards, the minimum is 1536, the 
      maximum is 7680 and the value must be divisible by 768.
      
      If the LogicalProcessor is associated with a card of one of 
      the following cardTypes: 8pE1Atm, 8pDS1Atm, the 
      maximum value for this attribute is 10752.
      
      For SGAF cards, the Connmap attributes are set to their default 
      values.
      
      Increasing the value of this attribute reduces the memory available 
      for cell and frame memory.
      
      This attribute must be set to 0 if the connectionPoolCapacity 
      attribute of the Arc Ov component is set to non-zero values."
   DEFVAL     { 3072 }
::= { lpEngArcOvProvEntry 1 }

lpEngArcOvMulticastBranchesCapacity OBJECT-TYPE
   SYNTAX     Unsigned32 (0..16384)
   ACCESS     read-write
   STATUS     mandatory
   DESCRIPTION
     "This attribute specifies the number of multicast branches that can be 
      enabled on this FP.
      
      A multicast branch is used for cell replication on a VCC connection 
      whose Vcc distributionType is pointToMultipoint. A branch 
      represents one ATM destination for the replicated cells.
      
      Increasing the value of this attribute reduces the memory 
      available for the cell and frame storage.
      
      For CQC based ATM FPs, the maximum value for this attribute is 
      10752."
   DEFVAL     { 0 }
::= { lpEngArcOvProvEntry 2 }

lpEngArcOvTxCellMemoryAllocation OBJECT-TYPE
   SYNTAX     Unsigned32 (1..99)
   ACCESS     read-write
   STATUS     mandatory
   DESCRIPTION
     "This attribute specifies the fraction of the transmit memory which 
      should be allocated to the transmission of cells on an FP. The 
      remaining memory is allocated for the transmission of frames. 
      Frame memory is used for trunks, ATM VCC testing and for inter-
      card communication. Cell memory is used for Atm Bearer Service, 
      ATM SVCs and ATM PVCs.
      
      There is an absolute minimum quantity of frame buffers which is 
      required by ATM software on the FP. If the value of this attribute is 
      smaller than the absolute minimum, the ATM software allocates the 
      minimum required, rather than the actual number requested.
      
      The actual percentage of the transmit  memory allocated to the 
      transmit cell memory is indicated by the Arc 
      txCellMemoryAllocation attribute. A difference between the 
      provisioned and the operational values may exist due to the 
      requirement for a minimum number of frame buffers or rounding 
      during computation within the FP."
   DEFVAL     { 50 }
::= { lpEngArcOvProvEntry 3 }

lpEngArcOvRxCellMemoryAllocation OBJECT-TYPE
   SYNTAX     Unsigned32 (1..99)
   ACCESS     read-write
   STATUS     mandatory
   DESCRIPTION
     "This attribute specifies the fraction of the receive  memory which 
      should be allocated to the reception of cells on an FP. The 
      remaining receive  memory is allocated for the reception of frames. 
      Frame memory is used for trunks, ATM VCC testing and for inter-
      card communication. Cell memory is used for Atm Bearer Service, 
      ATM SVCs and ATM PVCs. 
      
      There is an absolute minimum quantity of frame buffers which is 
      required by ATM software on the FP. If the value of this attribute is 
      smaller than the absolute minimum, the ATM software allocates the 
      minimum required, rather than the actual number requested. 
      
      The actual percentage of the receive  memory allocated to the 
      receive cell memory is indicated by the Arc 
      rxCellMemoryAllocation attribute. A difference between the 
      provisioned and the operational values may exist due to the 
      requirement for a minimum number of frame buffers or rounding 
      during computation within the FP."
   DEFVAL     { 20 }
::= { lpEngArcOvProvEntry 4 }


-- Lp/n Eng Arc Cqc
-- The Cqc component describes the usage of ATM-specific resources 
-- on a LogicalProcessor running ATM services on CQC based ATM 
-- cards. This component is always dynamically created under the LP 
-- Eng Arc which supports a CQC based FP. 

lpEngArcCqc OBJECT IDENTIFIER ::= { lpEngArc 3 }



lpEngArcCqcRowStatusTable OBJECT-TYPE
   SYNTAX     SEQUENCE OF LpEngArcCqcRowStatusEntry
   ACCESS     not-accessible
   STATUS     mandatory
   DESCRIPTION
     "This entry controls the addition and deletion of 
      lpEngArcCqc components."
::= { lpEngArcCqc 1 }

lpEngArcCqcRowStatusEntry OBJECT-TYPE
   SYNTAX     LpEngArcCqcRowStatusEntry
   ACCESS     not-accessible
   STATUS     mandatory
   DESCRIPTION
     "A single entry in the table represents a single 
      lpEngArcCqc component."
   INDEX {
      lpIndex,
      lpEngIndex,
      lpEngArcIndex,
      lpEngArcCqcIndex }
::= { lpEngArcCqcRowStatusTable 1 }

LpEngArcCqcRowStatusEntry ::= SEQUENCE {
   lpEngArcCqcRowStatus
      RowStatus,
   lpEngArcCqcComponentName
      DisplayString,
   lpEngArcCqcStorageType
      StorageType,
   lpEngArcCqcIndex
      NonReplicated }

lpEngArcCqcRowStatus OBJECT-TYPE
   SYNTAX     RowStatus 
   ACCESS     read-write
   STATUS     mandatory
   DESCRIPTION
     "This variable is used as the basis for SNMP naming of
      lpEngArcCqc components.
      These components can be added and deleted."
::= { lpEngArcCqcRowStatusEntry 1 }

lpEngArcCqcComponentName OBJECT-TYPE
   SYNTAX     DisplayString 
   ACCESS     read-only
   STATUS     mandatory
   DESCRIPTION
     "This variable provides the component's string name for
      use with the ASCII Console Interface"
::= { lpEngArcCqcRowStatusEntry 2 }

lpEngArcCqcStorageType OBJECT-TYPE
   SYNTAX     StorageType 
   ACCESS     read-only
   STATUS     mandatory
   DESCRIPTION
     "This variable represents the storage type value for the
      lpEngArcCqc tables."
::= { lpEngArcCqcRowStatusEntry 4 }

lpEngArcCqcIndex OBJECT-TYPE
   SYNTAX     NonReplicated 
   ACCESS     not-accessible
   STATUS     mandatory
   DESCRIPTION
     "This variable represents the index for the lpEngArcCqc tables."
::= { lpEngArcCqcRowStatusEntry 10 }

lpEngArcCqcOperTable OBJECT-TYPE
   SYNTAX     SEQUENCE OF LpEngArcCqcOperEntry
   ACCESS     not-accessible
   STATUS     mandatory
   DESCRIPTION
     "This group describes the usage of ATM-specific resources on a 
      Logical Processor running ATM services on a CQC based card."
::= { lpEngArcCqc 10 }

lpEngArcCqcOperEntry OBJECT-TYPE
   SYNTAX     LpEngArcCqcOperEntry
   ACCESS     not-accessible
   STATUS     mandatory
   DESCRIPTION
     "An entry in the lpEngArcCqcOperTable."
   INDEX {
      lpIndex,
      lpEngIndex,
      lpEngArcIndex,
      lpEngArcCqcIndex }
::= { lpEngArcCqcOperTable 1 }

LpEngArcCqcOperEntry ::= SEQUENCE {
   lpEngArcCqcCdvReduction
      INTEGER }

lpEngArcCqcCdvReduction OBJECT-TYPE
   SYNTAX     INTEGER  {
                 disabled(0),
                 enabled(1),
                 cardDependent(2) }
   ACCESS     read-only
   STATUS     mandatory
   DESCRIPTION
     "This attribute indicates if the reduction of the maximum Cell Delay 
      Variation (CDV) of shaped transmit traffic is applicable.
      
      When the value of this attribute is disabled, the CDV value can be 
      determined by the following equation:
      
      CDV <= 2/ASR + 1/LS
      
      where ASR is the Actual Shaping Rate of the connection and LS is 
      the Link Speed of the interface.
      
      When the value of this attribute is enabled, the CDV relationship 
      changes to the following equation:
      
      CDV <= 1/ASR + 1/LS"
::= { lpEngArcCqcOperEntry 1 }


-- Lp/n Eng Arc Cqc Override
-- This component is used to configure the usage of ATM-specific 
-- resources on a Logical Processor running ATM services on CQC 
-- based cards. (This component is only permitted under Logical 
-- Processors which are linked to ATM card types.)

lpEngArcCqcOv OBJECT IDENTIFIER ::= { lpEngArcCqc 2 }



lpEngArcCqcOvRowStatusTable OBJECT-TYPE
   SYNTAX     SEQUENCE OF LpEngArcCqcOvRowStatusEntry
   ACCESS     not-accessible
   STATUS     mandatory
   DESCRIPTION
     "This entry controls the addition and deletion of 
      lpEngArcCqcOv components."
::= { lpEngArcCqcOv 1 }

lpEngArcCqcOvRowStatusEntry OBJECT-TYPE
   SYNTAX     LpEngArcCqcOvRowStatusEntry
   ACCESS     not-accessible
   STATUS     mandatory
   DESCRIPTION
     "A single entry in the table represents a single 
      lpEngArcCqcOv component."
   INDEX {
      lpIndex,
      lpEngIndex,
      lpEngArcIndex,
      lpEngArcCqcIndex,
      lpEngArcCqcOvIndex }
::= { lpEngArcCqcOvRowStatusTable 1 }

LpEngArcCqcOvRowStatusEntry ::= SEQUENCE {
   lpEngArcCqcOvRowStatus
      RowStatus,
   lpEngArcCqcOvComponentName
      DisplayString,
   lpEngArcCqcOvStorageType
      StorageType,
   lpEngArcCqcOvIndex
      NonReplicated }

lpEngArcCqcOvRowStatus OBJECT-TYPE
   SYNTAX     RowStatus 
   ACCESS     read-only
   STATUS     mandatory
   DESCRIPTION
     "This variable is used as the basis for SNMP naming of
      lpEngArcCqcOv components.
      These components cannot be added nor deleted."
::= { lpEngArcCqcOvRowStatusEntry 1 }

lpEngArcCqcOvComponentName OBJECT-TYPE
   SYNTAX     DisplayString 
   ACCESS     read-only
   STATUS     mandatory
   DESCRIPTION
     "This variable provides the component's string name for
      use with the ASCII Console Interface"
::= { lpEngArcCqcOvRowStatusEntry 2 }

lpEngArcCqcOvStorageType OBJECT-TYPE
   SYNTAX     StorageType 
   ACCESS     read-only
   STATUS     mandatory
   DESCRIPTION
     "This variable represents the storage type value for the
      lpEngArcCqcOv tables."
::= { lpEngArcCqcOvRowStatusEntry 4 }

lpEngArcCqcOvIndex OBJECT-TYPE
   SYNTAX     NonReplicated 
   ACCESS     not-accessible
   STATUS     mandatory
   DESCRIPTION
     "This variable represents the index for the lpEngArcCqcOv tables."
::= { lpEngArcCqcOvRowStatusEntry 10 }

lpEngArcCqcOvProvTable OBJECT-TYPE
   SYNTAX     SEQUENCE OF LpEngArcCqcOvProvEntry
   ACCESS     not-accessible
   STATUS     mandatory
   DESCRIPTION
     "This group specifies the configuration of processor-wide ATM-
      specific resources on a Logical Processor running ATM services. 
      Note that altering any of these parameters will result in a card 
      reboot."
::= { lpEngArcCqcOv 10 }

lpEngArcCqcOvProvEntry OBJECT-TYPE
   SYNTAX     LpEngArcCqcOvProvEntry
   ACCESS     not-accessible
   STATUS     mandatory
   DESCRIPTION
     "An entry in the lpEngArcCqcOvProvTable."
   INDEX {
      lpIndex,
      lpEngIndex,
      lpEngArcIndex,
      lpEngArcCqcIndex,
      lpEngArcCqcOvIndex }
::= { lpEngArcCqcOvProvTable 1 }

LpEngArcCqcOvProvEntry ::= SEQUENCE {
   lpEngArcCqcOvPerVcQueueInterfaces
      Unsigned32,
   lpEngArcCqcOvShapingScalingFactor
      FixedPoint1,
   lpEngArcCqcOvCdvReduction
      INTEGER,
   lpEngArcCqcOvPortCongestionPolicy
      INTEGER }

lpEngArcCqcOvPerVcQueueInterfaces OBJECT-TYPE
   SYNTAX     Unsigned32 (0..4)
   ACCESS     read-write
   STATUS     mandatory
   DESCRIPTION
     "This attribute specifies the number of independent ports or IMA 
      components which support shaping and per-VC queueing on this 
      FP. 
      
      When this attribute is not zero, at most 4 independent ports or 4 Ima 
      virtual links are supported, regardless of whether or not traffic 
      shaping is enabled on the associated AtmIf components. In this case 
      only independent port instances 0-3 or Ima instances 0-3 can be 
      supported on an associated AtmIf component.
      
      For 2 ports cards, the valid values for this attribute are 0, 1, or 2.
      For 3 ports cards, the valid values for this attribute are 0, 1, 2 or 3.
      For 8 ports cards, the valid values for this attribute are 0, 1, 2, or 4."
   DEFVAL     { 0 }
::= { lpEngArcCqcOvProvEntry 1 }

lpEngArcCqcOvShapingScalingFactor OBJECT-TYPE
   SYNTAX     FixedPoint1 (10 | 14 | 20 | 28 | 40 | 56)
   ACCESS     read-write
   STATUS     mandatory
   DESCRIPTION
     "This attribute specifies the scaling factor which is to be applied to 
      all shaping rates for this FP. The scaling factor is an inverse factor 
      which is applied to the chosen shaping rate to produce an actual 
      shaping rate. For example, if a shaping rate of 25 Mbit/s is used 
      with a scaling factor of 2, the actual shaping rate is 12.5 Mbit/s."
   DEFVAL     { 10 }
::= { lpEngArcCqcOvProvEntry 2 }

lpEngArcCqcOvCdvReduction OBJECT-TYPE
   SYNTAX     INTEGER  {
                 disabled(0),
                 enabled(1),
                 cardDependent(2) }
   ACCESS     read-write
   STATUS     mandatory
   DESCRIPTION
     "This attribute specifies the reduction of the maximum Cell Delay 
      Variation (CDV) of shaped transmit traffic.
      
      When the value of this attribute is set to disabled, the CDV value 
      can be determined by the following equation:
      
      CDV <= 2/ASR + 1/LS
      
      where ASR is the Actual Shaping Rate of the connection and LS is 
      the Link Speed of the interface.
      
      When the value of this attribute is set to enabled, the CDV 
      relationship changes to the following equation:
      
      CDV <= 1/ASR + 1/LS
      
      As can be noted from the equations above, setting this attribute to 
      enabled can reduce the CDV significantly. CDV reduction may be 
      used to conform to policers which have strict Cell Delay Variance 
      Tolerance (CDVT). However using this function reduces the 
      transmit bandwidth utilization of the following cards: 3pDS3Atm, 
      3pOC3Atm, 2pJ6MAtm.
      
      When the value is cardDependent, CDV reduction is disabled for 
      cardtypes 3pDS3Atm, 3pOC3Atm, 2pJ6MAtm, 4pDS1Aal1, 
      4pE1Aal1 and enabled for all other cards."
   DEFVAL     { cardDependent }
::= { lpEngArcCqcOvProvEntry 3 }

lpEngArcCqcOvPortCongestionPolicy OBJECT-TYPE
   SYNTAX     INTEGER  {
                 aggregate(0),
                 individualQueue(1) }
   ACCESS     read-write
   STATUS     mandatory
   DESCRIPTION
     "This attribute specifies the congestion behavior of all ports on 
      this FP. It applies only to transmit traffic served on the 
      common queues and does not apply to per-VC queues.
      
      When the value is aggregate, the enqueue decision of cells or 
      frames to a common queue is based upon the congestion state 
      of the entire port to which the queue belongs. A port is 
      defined to be as congested as the most congested queue 
      amongst all its common queues: the low, medium and high 
      emission priority queues. Thus, for example, if the low 
      priority queue is congested, the high priority queue also 
      experiences discards even though the high priority queue may 
      itself not be congested. Setting this attribute to aggregate 
      assures that the low priority queues are also serviced in the 
      event of congestion.
      
      When the value of this attribute is set to individualQueue, 
      the enqueue decision of cells or frames to a common queue is 
      based solely upon the congestion state of that queue, not the 
      port. This setting assures that the absolute priority of the traffic is 
      taken into account, regardless of whether the lower priority queues 
      are being served."
   DEFVAL     { aggregate }
::= { lpEngArcCqcOvProvEntry 4 }

lpEngArcCqcOvConnCapTable OBJECT-TYPE
   SYNTAX     SEQUENCE OF LpEngArcCqcOvConnCapEntry
   ACCESS     not-accessible
   STATUS     mandatory
   DESCRIPTION
     "This attribute is provided for backward compatibility and can only 
      be used if the LogicalProcessor is associated with a card of one of 
      the following cardType: 3pE3Atm, 3pDS3Atm, 3pOC3MmAtm, 
      3pOC3SmAtm, 3pE1Atm, 3pDS1Atm, 2pJ6MAtm. This attribute 
      can be used when the desired distribution of connections across 
      ports cannot be achieved using the totalConnectionPoolCapacity 
      attribute.
      
      This attribute defines the maximum number of connections (VCC, 
      VPC, and VPT) that are available on each port. A basic Vpt uses 2 
      connections. The entries are indexed by port number. This number 
      limits the range of the ConnMap entries. If the Connmap 
      component does not exist, its default settings are used for this 
      check. Note that the value of this attribute must be evenly divisible 
      by 256, and that port 2 supports at most 2560 connections, not the 
      full 4096.
      
      The connection pool for each port must be set to 0 if the 
      totalConnectionPoolCapacity attribute is set to a non-zero value."
::= { lpEngArcCqcOv 450 }

lpEngArcCqcOvConnCapEntry OBJECT-TYPE
   SYNTAX     LpEngArcCqcOvConnCapEntry
   ACCESS     not-accessible
   STATUS     mandatory
   DESCRIPTION
     "An entry in the lpEngArcCqcOvConnCapTable."
   INDEX {
      lpIndex,
      lpEngIndex,
      lpEngArcIndex,
      lpEngArcCqcIndex,
      lpEngArcCqcOvIndex,
      lpEngArcCqcOvConnCapIndex }
::= { lpEngArcCqcOvConnCapTable 1 }

LpEngArcCqcOvConnCapEntry ::= SEQUENCE {
   lpEngArcCqcOvConnCapIndex
      Integer32,
   lpEngArcCqcOvConnCapValue
      Unsigned32 }

lpEngArcCqcOvConnCapIndex OBJECT-TYPE
   SYNTAX     Integer32 (0..2)
   ACCESS     not-accessible
   STATUS     mandatory
   DESCRIPTION
     "This variable represents the lpEngArcCqcOvConnCapTable
      specific index for the lpEngArcCqcOvConnCapTable."
::= { lpEngArcCqcOvConnCapEntry 1 }

lpEngArcCqcOvConnCapValue OBJECT-TYPE
   SYNTAX     Unsigned32 (0 | 512..4096)
   ACCESS     read-write
   STATUS     mandatory
   DESCRIPTION
     "This variable represents an individual value for the
      lpEngArcCqcOvConnCapTable."
::= { lpEngArcCqcOvConnCapEntry 2 }


-- Lp/n Eng Arc Aqm/n
-- The Aqm component describes the usage of ATM-specific resources 
-- on a LogicalProcessor running ATM services for a specific ATM 
-- Queue Manager. This component is always dynamically created 
-- under any LP Eng which supports an SGAF FP. The number of 
-- instances depends upon the type of card.

lpEngArcAqm OBJECT IDENTIFIER ::= { lpEngArc 4 }



lpEngArcAqmRowStatusTable OBJECT-TYPE
   SYNTAX     SEQUENCE OF LpEngArcAqmRowStatusEntry
   ACCESS     not-accessible
   STATUS     mandatory
   DESCRIPTION
     "This entry controls the addition and deletion of 
      lpEngArcAqm components."
::= { lpEngArcAqm 1 }

lpEngArcAqmRowStatusEntry OBJECT-TYPE
   SYNTAX     LpEngArcAqmRowStatusEntry
   ACCESS     not-accessible
   STATUS     mandatory
   DESCRIPTION
     "A single entry in the table represents a single 
      lpEngArcAqm component."
   INDEX {
      lpIndex,
      lpEngIndex,
      lpEngArcIndex,
      lpEngArcAqmIndex }
::= { lpEngArcAqmRowStatusTable 1 }

LpEngArcAqmRowStatusEntry ::= SEQUENCE {
   lpEngArcAqmRowStatus
      RowStatus,
   lpEngArcAqmComponentName
      DisplayString,
   lpEngArcAqmStorageType
      StorageType,
   lpEngArcAqmIndex
      Integer32 }

lpEngArcAqmRowStatus OBJECT-TYPE
   SYNTAX     RowStatus 
   ACCESS     read-write
   STATUS     mandatory
   DESCRIPTION
     "This variable is used as the basis for SNMP naming of
      lpEngArcAqm components.
      These components can be added and deleted."
::= { lpEngArcAqmRowStatusEntry 1 }

lpEngArcAqmComponentName OBJECT-TYPE
   SYNTAX     DisplayString 
   ACCESS     read-only
   STATUS     mandatory
   DESCRIPTION
     "This variable provides the component's string name for
      use with the ASCII Console Interface"
::= { lpEngArcAqmRowStatusEntry 2 }

lpEngArcAqmStorageType OBJECT-TYPE
   SYNTAX     StorageType 
   ACCESS     read-only
   STATUS     mandatory
   DESCRIPTION
     "This variable represents the storage type value for the
      lpEngArcAqm tables."
::= { lpEngArcAqmRowStatusEntry 4 }

lpEngArcAqmIndex OBJECT-TYPE
   SYNTAX     Integer32 (0..1)
   ACCESS     not-accessible
   STATUS     mandatory
   DESCRIPTION
     "This variable represents the index for the lpEngArcAqm tables."
::= { lpEngArcAqmRowStatusEntry 10 }

lpEngArcAqmOperTable OBJECT-TYPE
   SYNTAX     SEQUENCE OF LpEngArcAqmOperEntry
   ACCESS     not-accessible
   STATUS     mandatory
   DESCRIPTION
     "This group describes the usage of ATM-specific resources for a 
      specific AQM on a Logical Processor running ATM services."
::= { lpEngArcAqm 10 }

lpEngArcAqmOperEntry OBJECT-TYPE
   SYNTAX     LpEngArcAqmOperEntry
   ACCESS     not-accessible
   STATUS     mandatory
   DESCRIPTION
     "An entry in the lpEngArcAqmOperTable."
   INDEX {
      lpIndex,
      lpEngIndex,
      lpEngArcIndex,
      lpEngArcAqmIndex }
::= { lpEngArcAqmOperTable 1 }

LpEngArcAqmOperEntry ::= SEQUENCE {
   lpEngArcAqmConnectionPoolAvailable
      Unsigned32,
   lpEngArcAqmConnectionPoolUsage
      Unsigned32,
   lpEngArcAqmTxCellMemoryAvailable
      Gauge32,
   lpEngArcAqmTxCellMemoryMinAvailable
      Gauge32,
   lpEngArcAqmTxCellMemoryCongestionState
      Gauge32,
   lpEngArcAqmTxCellMemoryMaxUsage
      Gauge32,
   lpEngArcAqmTxCellMemoryUsage
      Gauge32,
   lpEngArcAqmMaxVirtualLinks
      Unsigned32,
   lpEngArcAqmVirtualLinkUsage
      Unsigned32,
   lpEngArcAqmVirtualLinkGranularity
      Unsigned32 }

lpEngArcAqmConnectionPoolAvailable OBJECT-TYPE
   SYNTAX     Unsigned32 (0..16000)
   ACCESS     read-only
   STATUS     mandatory
   DESCRIPTION
     "This attribute indicates the number of connection resources 
      available (VCC, VPC, and VPT) that can be configured on the 
      AQM instance of the LogicalProcessor.
      
      A standard Vpt uses 3 connection resources and a basic Vpt uses 2."
::= { lpEngArcAqmOperEntry 1 }

lpEngArcAqmConnectionPoolUsage OBJECT-TYPE
   SYNTAX     Unsigned32 (0..16000)
   ACCESS     read-only
   STATUS     mandatory
   DESCRIPTION
     "This attribute indicates the total number of connections for 
      configured VCCs, VPCs, and VPTs in AtmIfs associated with the 
      AQM instance of the LogicalProcessor. 
      
      A standard Vpt uses 3 connection resources and a basic Vpt uses 2."
::= { lpEngArcAqmOperEntry 2 }

lpEngArcAqmTxCellMemoryAvailable OBJECT-TYPE
   SYNTAX     Gauge32 (0..163839)
   ACCESS     read-only
   STATUS     obsolete
   DESCRIPTION
     "This attribute indicates the current availability of the transmit 
      cell memory. 
      
      The transmit cell memory is the memory available for storing ATM 
      cells to be transmitted by the Lp."
::= { lpEngArcAqmOperEntry 5 }

lpEngArcAqmTxCellMemoryMinAvailable OBJECT-TYPE
   SYNTAX     Gauge32 (0..163839)
   ACCESS     read-only
   STATUS     obsolete
   DESCRIPTION
     "This attribute indicates the lowest availability of the transmit 
      cell memory. 
      
      The transmit cell memory is the memory available for storing ATM 
      cells to be transmitted by the Lp.
      
      This attribute is reset to the current availability every 15 minutes 
      and when the card is reset."
::= { lpEngArcAqmOperEntry 6 }

lpEngArcAqmTxCellMemoryCongestionState OBJECT-TYPE
   SYNTAX     Gauge32 (0..3)
   ACCESS     read-only
   STATUS     mandatory
   DESCRIPTION
     "This attribute indicates the congestion state of the transmit cell 
      memory for the ATM Queue Manager (AQM) ASIC on this FP. 
      
      This attribute indicates which txCellMemoryThresholds corresponds 
      to the current value of txCellMemoryUsage. The congestion state is 
      used to determine if cells of a particular discard priority (DP) are 
      discarded before being queued for transmit. 
      
      The congestion state of transmit cell memory is indicated by a 
      numeric value ranging from 3 to 0. When transmit cell memory is in 
      congestion state 'x', traffic with DP > 'x' is discarded before 
      transmit. Traffic with DP < 'x' may be queued for transmit, 
      depending on the congestion level of the connection transmit queue. 
      Traffic with DP = 'x' may be either queued or discarded depending 
      on how close the value of txCellMemoryUsage is to the next 
      threshold as displayed in txCellMemoryThresholds. For example, 
      CLP1 traffic is queued until the value indicated by 
      txCellMemoryUsage equals the value indicated in 
      txCellMemoryThresholds 3. At that point, CLP1 traffic is discarded."
::= { lpEngArcAqmOperEntry 7 }

lpEngArcAqmTxCellMemoryMaxUsage OBJECT-TYPE
   SYNTAX     Gauge32 (0..163839)
   ACCESS     read-only
   STATUS     mandatory
   DESCRIPTION
     "This attribute indicates the maximum number which has recently 
      occurred for the txCellMemoryUsage attribute. 
      
      Transmit cell memory is used for storing ATM cells to be 
      transmitted by connections for the ATM Queue Manager (AQM) 
      ASIC on this FP. It includes all cells in all connections at all service 
      categories. 
      
      This attribute is reset to the current usage every 15 minutes and 
      when the card is reset."
::= { lpEngArcAqmOperEntry 8 }

lpEngArcAqmTxCellMemoryUsage OBJECT-TYPE
   SYNTAX     Gauge32 (0..163839)
   ACCESS     read-only
   STATUS     mandatory
   DESCRIPTION
     "This attribute indicates the current number of transmit 
      cells which are in use on this FP. 
      
      Transmit cell memory is used for storing ATM cells to be 
      transmitted by connections for the ATM Queue Manager (AQM) 
      ASIC on this FP. It includes all cells in all connections at all service 
      categories."
::= { lpEngArcAqmOperEntry 9 }

lpEngArcAqmMaxVirtualLinks OBJECT-TYPE
   SYNTAX     Unsigned32 (0 | 6 | 14 | 29)
   ACCESS     read-only
   STATUS     mandatory
   DESCRIPTION
     "This attribute indicates the maximum number of virtual links (VLs) 
      that can exist on this AQM. Normally a virtual link contains all 
      VCCs and VPCs provisioned for a port (OC-3, DS3, E3, etc), 
      making a virtual link equivalent to a port. However, if an AtmIf 
      linked to a port has provisioned virtual path terminations (VPTs) 
      with a vptType of virtualLink, then there is one virtual link per VL 
      VPT, and one virtual link for all remaining VCCs and VPCs not 
      part of a VL VPT.
      
      Unless this attribute is overridden in the optional Override 
      subcomponent, its value will be sameNumberAsPorts, indicating 
      that there is one virtual link per port using the AQM.
      
      The value of maxVirtualLinks may restrict the maximum bandwidth 
      allowed per virtual link. If the value of this attribute is 
      sameNumberAsPorts there is no restriction on a virtual link's 
      bandwidth; it may be any cell rate up to the port's link rate. If 
      maxVirtualLinks is set to some other value, then all virtual links on 
      the AQM are subject to a maximum cell rate, listed in the table 
      below, which may be less than the port cell rate.
      
      maxVirtualLinks : cell rate
      6: 163840 cell/s
      14 : 81920 cell/s
      29: 40960 cell/s
      
      On 2pOC3MmAtm2 and 2pOC3SmAtm2 cards, there is one 
      AQM per port. Since one link is required for connections not part of 
      a VL VPT, if maxVirtualLinks is 6 (for example), then up to fiveVL 
      VPTs may be provisioned on the port. Continuing this example, 
      each VPT's provisioned bandwidth can be no larger than 163840 
      cells/s (46% of the total OC-3 rate) and the total bandwidth 
      available to independent VCCs and non VL VPTs will be no greater 
      than 163840 cell/s.
      
      On 3pDS3Atm2 and 3pE3Atm2 cards, there is one AQM for the 
      card. Since three links are required for connections not part of a VL 
      VPT (one per port), if maxVirtualLinks is 6 (for example), then up 
      to threeVL VPTs may be provisioned on the card. In this case, since 
      the maximum cell rate per virtual link is 163840 cell/s, which is 
      greater than the port cell rate for both DS3 and E3, there is no 
      restriction on the bandwidth assigned to VL VPTs or available to 
      independent VCC and non VL VPT connections.

      VALUES (

      0 = sameNumberAsPorts

      )"
::= { lpEngArcAqmOperEntry 10 }

lpEngArcAqmVirtualLinkUsage OBJECT-TYPE
   SYNTAX     Unsigned32 (0..31)
   ACCESS     read-only
   STATUS     mandatory
   DESCRIPTION
     "This attribute indicates the number of virtual links in use on this 
      AQM. Its maximum value is the value of operational attribute 
      maxVirtualLinks. Since each port uses one virtual link, if 
      maxVirtualLinks has value sameNumberAsPorts then 
      virtualLinkUsage will be 1 for 2pOC3MmAtm2 and 
      2pOC3SmAtm2 cards, and 3 for 3pDS3Atm2 and 3pE3Atm2 
      cards."
::= { lpEngArcAqmOperEntry 11 }

lpEngArcAqmVirtualLinkGranularity OBJECT-TYPE
   SYNTAX     Unsigned32 (0..4294967295)
   ACCESS     read-only
   STATUS     mandatory
   DESCRIPTION
     "This attribute indicates the granularity on which virtual link 
      bandwidths are allocated. It is affected by the Override 
      subcomponent's provisionable virtualLinkGranularity attribute, and 
      will vary between 562 cell/s (minimum granularity for an E3 G.751 
      PLCP link) and 353207 cell/s (maximum granularity for an OC-3 
      link)."
::= { lpEngArcAqmOperEntry 12 }

lpEngArcAqmTxCellThreshTable OBJECT-TYPE
   SYNTAX     SEQUENCE OF LpEngArcAqmTxCellThreshEntry
   ACCESS     not-accessible
   STATUS     mandatory
   DESCRIPTION
     "This attribute is a vector which indicates the size and three discard 
      thresholds for transmit cell memory for the ATM Queue Manager 
      (AQM) ASIC on this FP. Transmit cell memory is used for storing 
      ATM cells to be transmitted by connections. It includes all cells in 
      all connections at all service categories. 
      
      The first value indicates the transmit cell memory size. It is the 
      amount of transmit memory which is available for cell queueing, 
      after the amount of memory specified by connectionPoolCapacity. 
      
      The current value of txCellMemoryUsage together with the vector 
      of values in txCellMemoryThresholds determines the 
      txCellMemoryCongestionState. The congestion state determines 
      whether cells of a given discard priority (DP) are discarded or 
      queued for transmit. 
      
      When the txCellMemoryUsage attribute is between threshold 0 and 
      threshold 1, the txCellMemoryCongestionState indicates the value 
      0. In congestion state 0, traffic with DP > 0 is discarded. Threshold 
      1 is set approximately at 90 percent of threshold 0, the total transmit 
      cell memory size. 
      
      When the txCellMemoryUsage attribute is between threshold 1 and 
      threshold 2, the txCellMemoryCongestionState indicates the value 
      1. In congestion state 1, traffic with DP > 1 is discarded. Threshold 
      2 is set approximately at 85 percent of threshold 0, the total transmit 
      cell memory size. 
      
      When the txCellMemoryUsage attribute is between threshold 2 and 
      threshold 3, the txCellMemoryCongestionState indicates the value 
      2. In congestion state 2, traffic with DP > 2 is discarded. Threshold 
      3 is set approximately at 75 percent of threshold 0, the total transmit 
      cell memory size. 
      
      When the txCellMemoryUsage attribute is below threshold 3, the 
      txCellMemoryCongestionState indicates the value 3. In congestion 
      state 3, traffic with DP=3 is queued."
::= { lpEngArcAqm 448 }

lpEngArcAqmTxCellThreshEntry OBJECT-TYPE
   SYNTAX     LpEngArcAqmTxCellThreshEntry
   ACCESS     not-accessible
   STATUS     mandatory
   DESCRIPTION
     "An entry in the lpEngArcAqmTxCellThreshTable."
   INDEX {
      lpIndex,
      lpEngIndex,
      lpEngArcIndex,
      lpEngArcAqmIndex,
      lpEngArcAqmTxCellThreshIndex }
::= { lpEngArcAqmTxCellThreshTable 1 }

LpEngArcAqmTxCellThreshEntry ::= SEQUENCE {
   lpEngArcAqmTxCellThreshIndex
      Integer32,
   lpEngArcAqmTxCellThreshValue
      Unsigned32 }

lpEngArcAqmTxCellThreshIndex OBJECT-TYPE
   SYNTAX     Integer32 (0..3)
   ACCESS     not-accessible
   STATUS     mandatory
   DESCRIPTION
     "This variable represents the lpEngArcAqmTxCellThreshTable
      specific index for the lpEngArcAqmTxCellThreshTable."
::= { lpEngArcAqmTxCellThreshEntry 1 }

lpEngArcAqmTxCellThreshValue OBJECT-TYPE
   SYNTAX     Unsigned32 (0..163839)
   ACCESS     read-only
   STATUS     mandatory
   DESCRIPTION
     "This variable represents an individual value for the
      lpEngArcAqmTxCellThreshTable."
::= { lpEngArcAqmTxCellThreshEntry 2 }


-- Lp/n Eng Arc Aqm/n Override
-- The Aqm Override component is used to configure the usage of 
-- ATM-specific resources for a specific AQM on a Logical Processor 
-- running ATM services. (This component is only permitted under 
-- Logical Processors which are linked to ATM card types.)

lpEngArcAqmOv OBJECT IDENTIFIER ::= { lpEngArcAqm 2 }



lpEngArcAqmOvRowStatusTable OBJECT-TYPE
   SYNTAX     SEQUENCE OF LpEngArcAqmOvRowStatusEntry
   ACCESS     not-accessible
   STATUS     mandatory
   DESCRIPTION
     "This entry controls the addition and deletion of 
      lpEngArcAqmOv components."
::= { lpEngArcAqmOv 1 }

lpEngArcAqmOvRowStatusEntry OBJECT-TYPE
   SYNTAX     LpEngArcAqmOvRowStatusEntry
   ACCESS     not-accessible
   STATUS     mandatory
   DESCRIPTION
     "A single entry in the table represents a single 
      lpEngArcAqmOv component."
   INDEX {
      lpIndex,
      lpEngIndex,
      lpEngArcIndex,
      lpEngArcAqmIndex,
      lpEngArcAqmOvIndex }
::= { lpEngArcAqmOvRowStatusTable 1 }

LpEngArcAqmOvRowStatusEntry ::= SEQUENCE {
   lpEngArcAqmOvRowStatus
      RowStatus,
   lpEngArcAqmOvComponentName
      DisplayString,
   lpEngArcAqmOvStorageType
      StorageType,
   lpEngArcAqmOvIndex
      NonReplicated }

lpEngArcAqmOvRowStatus OBJECT-TYPE
   SYNTAX     RowStatus 
   ACCESS     read-only
   STATUS     mandatory
   DESCRIPTION
     "This variable is used as the basis for SNMP naming of
      lpEngArcAqmOv components.
      These components cannot be added nor deleted."
::= { lpEngArcAqmOvRowStatusEntry 1 }

lpEngArcAqmOvComponentName OBJECT-TYPE
   SYNTAX     DisplayString 
   ACCESS     read-only
   STATUS     mandatory
   DESCRIPTION
     "This variable provides the component's string name for
      use with the ASCII Console Interface"
::= { lpEngArcAqmOvRowStatusEntry 2 }

lpEngArcAqmOvStorageType OBJECT-TYPE
   SYNTAX     StorageType 
   ACCESS     read-only
   STATUS     mandatory
   DESCRIPTION
     "This variable represents the storage type value for the
      lpEngArcAqmOv tables."
::= { lpEngArcAqmOvRowStatusEntry 4 }

lpEngArcAqmOvIndex OBJECT-TYPE
   SYNTAX     NonReplicated 
   ACCESS     not-accessible
   STATUS     mandatory
   DESCRIPTION
     "This variable represents the index for the lpEngArcAqmOv tables."
::= { lpEngArcAqmOvRowStatusEntry 10 }

lpEngArcAqmOvProvTable OBJECT-TYPE
   SYNTAX     SEQUENCE OF LpEngArcAqmOvProvEntry
   ACCESS     not-accessible
   STATUS     mandatory
   DESCRIPTION
     "This group specifies the configuration of processor-wide ATM-
      specific resources on a Logical Processor running ATM services on 
      CQC based cards. Note that altering any of these parameters will 
      result in a card reboot."
::= { lpEngArcAqmOv 10 }

lpEngArcAqmOvProvEntry OBJECT-TYPE
   SYNTAX     LpEngArcAqmOvProvEntry
   ACCESS     not-accessible
   STATUS     mandatory
   DESCRIPTION
     "An entry in the lpEngArcAqmOvProvTable."
   INDEX {
      lpIndex,
      lpEngIndex,
      lpEngArcIndex,
      lpEngArcAqmIndex,
      lpEngArcAqmOvIndex }
::= { lpEngArcAqmOvProvTable 1 }

LpEngArcAqmOvProvEntry ::= SEQUENCE {
   lpEngArcAqmOvConnectionPoolCapacity
      Unsigned32,
   lpEngArcAqmOvHighPriorityEpdOffset
      Unsigned32,
   lpEngArcAqmOvLowPriorityEpdOffset
      Unsigned32,
   lpEngArcAqmOvPortCongestionPolicy
      INTEGER,
   lpEngArcAqmOvMaxVirtualLinks
      Unsigned32,
   lpEngArcAqmOvVirtualLinkGranularity
      INTEGER }

lpEngArcAqmOvConnectionPoolCapacity OBJECT-TYPE
   SYNTAX     Unsigned32 (0 | 1..16000)
   ACCESS     read-write
   STATUS     mandatory
   DESCRIPTION
     "This attribute specifies the maximum number of connections 
      (VCC, VPC, and VPT) that can be configured on the AQM 
      instance of the LogicalProcessor. 
      
      The value of this attribute should be less than or equal to 
      totalConnectionPoolCapacity of the Arc component. Note that 3 
      connections are used for each standard Vpt and 2 for each basic 
      Vpt.
      
      The default value derivedFromArc is obtained using the following 
      equation: 
      
      totalConnectionPoolCapacity / number of AQM component on FP.

      VALUES (

      0 = derivedFromArc

      )"
   DEFVAL     { 0 }
::= { lpEngArcAqmOvProvEntry 1 }

lpEngArcAqmOvHighPriorityEpdOffset OBJECT-TYPE
   SYNTAX     Unsigned32 (5..1024)
   ACCESS     read-write
   STATUS     mandatory
   DESCRIPTION
     "This attribute specifies the high priority Early Packet Discard (EPD) 
      offset for connection queues. On ATM IP FPs a given connection 
      queue is associated with one of eight emission priorities (EP). These 
      include six unshaped EPs, one exclusive VBR shaper EP and one 
      ABR/VBR shaper EP. This attribute specifies the EPD offset for the 
      exclusive VBR shaper EP and the first four (higher priority) 
      unshaped EPs.
      
      This offset is used to derive a connection EPD threshold for a given 
      Congestion Control (CC) level by subtracting the offset from the 
      All Packet Discard (APD) threshold at the same CC level. The APD 
      thresholds are themselves derived from the transmit queue limit.
      
      The EPD threshold only applies to a connection if the 
      txPacketWiseDiscard feature is requested. The 
      txPacketWiseDiscard feature can be enabled only if the transmit 
      queue limit is at least 5.71 times the EPD offset. This ensures that 
      the derived EPD threshold will never be less than 17.5 % of the 
      transmit queue limit. If this condition is not satisfied, 
      txPacketWiseDiscard for the connection will be automatically 
      disabled.
      
      Due to the above constraint, if the operator wishes to decrease the 
      transmit queue limit and still have txPacketWiseDiscard enabled on 
      the connection then this offset must be set to a lower value that 
      meets the above requirement.
      
      Due to hardware granularity the actual value of the EPD offset may 
      not match exactly the value provisioned. The actual value is 
      displayed under the ATM Connection Administrator service 
      category subcomponents on ATM IP FPs.
      
      This attribute does not apply to CQC FPs."
   DEFVAL     { 50 }
::= { lpEngArcAqmOvProvEntry 2 }

lpEngArcAqmOvLowPriorityEpdOffset OBJECT-TYPE
   SYNTAX     Unsigned32 (5..1024)
   ACCESS     read-write
   STATUS     mandatory
   DESCRIPTION
     "This attribute specifies the low priority Early Packet Discard (EPD) 
      offset for connection queues. On ATM IP FPs a given connection 
      queue is associated with one of eight emission priorities (EP). These 
      include six unshaped EPs, one exclusive VBR shaper EP and one 
      ABR/VBR shaper EP. This attribute specifies the EPD offset for the 
      exclusive ABR/VBR shaper EP and the last two (lower priority) 
      unshaped EPs.
      
      This offset is used to derive a connection EPD threshold for a given 
      Congestion Control (CC) level by subtracting the offset from the 
      All Packet Discard (APD) threshold at the same CC level. The APD 
      thresholds are themselves derived from the transmit queue limit.
      
      The EPD threshold only applies to a connection if the 
      txPacketWiseDiscard feature is requested. The 
      txPacketWiseDiscard feature can be enabled only if the transmit 
      queue limit is at least 5.71 times the EPD offset. This ensures that 
      the derived EPD threshold will never be less than 17.5 % of the 
      transmit queue limit. If this condition is not satisfied, 
      txPacketWiseDiscard for the connection will be automatically 
      disabled.
      
      Due to the above constraint, if the operator wishes to decrease the 
      transmit queue limit and still have txPacketWiseDiscard enabled on 
      the connection then this offset must be set to a lower value that 
      meets the above requirement.
      
      Due to hardware granularity the actual value of the EPD offset may 
      not match exactly the value provisioned. The actual value is 
      displayed under the ATM Connection Administrator service 
      category subcomponents on ATM IP FPs.
      
      This attribute does not apply to CQC FPs."
   DEFVAL     { 200 }
::= { lpEngArcAqmOvProvEntry 3 }

lpEngArcAqmOvPortCongestionPolicy OBJECT-TYPE
   SYNTAX     INTEGER  {
                 aggregate(0),
                 individualQueue(1) }
   ACCESS     read-write
   STATUS     mandatory
   DESCRIPTION
     "This attribute specifies the congestion behavior of all ports on this 
      FP. It applies only to transmit traffic and does not apply to the CBR 
      service category. 
      
      When the value is aggregate, the enqueue decision of cells or 
      frames to a queue is based upon the congestion state of the entire 
      port to which the queue belongs. A port is defined to be as 
      congested as the most congested queue amongst all its queues. 
      Thus, for example, if a nrtVBR queue is congested, the rtVBR 
      queue also experiences discards even though the rtVBR queue may 
      itself not be congested. Setting this attribute to aggregate assures 
      that the low priority queues are also serviced in the event of 
      congestion. If this attribute is set to aggregate then rtVBR must not 
      be configured to do common queueing and its emissionPriority 
      should be set to a number numerically smaller than or equal to 3. 
      Another impact of setting this attribute to aggregate is that the per 
      connection queue limits for nrtVBR and UBR connections will be 
      increased to the link pool size and their discard thresholds will be 
      modified to be aligned with the free list discard thresholds.
      
      When the value of this attribute is set to individualQueue, 
      the enqueue decision of cells or frames to a queue is based solely 
      upon the congestion state of that queue, not the port. This setting 
      assures that the absolute priority of the traffic is taken into account, 
      regardless of whether the lower priority queues are being served. On 
      3pOC3SmAtm2 and 3pOC3MmAtm2 cards, if more than one 
      override component exists, they must have the same setting for this 
      attribute. Otherwise, setting the attribute under one override 
      component applies to the entire card."
   DEFVAL     { individualQueue }
::= { lpEngArcAqmOvProvEntry 4 }

lpEngArcAqmOvMaxVirtualLinks OBJECT-TYPE
   SYNTAX     Unsigned32 (0 | 6 | 14 | 29)
   ACCESS     read-write
   STATUS     mandatory
   DESCRIPTION
     "This attribute specifies the maximum number of virtual links that 
      can use this AQM. Refer to the description of the operational 
      attribute maxVirtualLinks under component Lp/n Eng Arc Aqm/n 
      for a complete description of the effects of setting this attribute.
      
      On all card types except 3pE3Atm2, this attribute may be set to any 
      of the valid values. On 3pE3Atm2 cards this attribute may only be 
      set to sameNumberAsPorts, 14, or 29, since, due to hardware 
      considerations, there is no advantage to setting the value to 6, and 
      there are advantages to not doing so.

      VALUES (

      0 = sameNumberAsPorts

      )"
   DEFVAL     { 0 }
::= { lpEngArcAqmOvProvEntry 5 }

lpEngArcAqmOvVirtualLinkGranularity OBJECT-TYPE
   SYNTAX     INTEGER  {
                 minimum(0),
                 ds1(1),
                 e1(2),
                 jt2(3) }
   ACCESS     read-write
   STATUS     mandatory
   DESCRIPTION
     "This attribute specifies the granularity on which virtual link 
      bandwidths are allocated. A value of minimum indicates the 
      granularity is as small as possible for the specific card on which the 
      Aqm component resides. A value of DS1, E1, or JT2 indicates that 
      the VL bandwidths should be allocated in multiples of the DS1, E1, 
      or JT2 cell rates (nominally 3622 cell/s, 4528 cell/s, and 14490 cell/
      s respectively)."
   DEFVAL     { minimum }
::= { lpEngArcAqmOvProvEntry 6 }


-- Lp/n Eng FrameCoreResourceControl
-- This component is used to view the usage of frame specific 
-- resources on a LogicalProcessor running Frame based services.

lpEngFcrc OBJECT IDENTIFIER ::= { lpEng 6 }



lpEngFcrcRowStatusTable OBJECT-TYPE
   SYNTAX     SEQUENCE OF LpEngFcrcRowStatusEntry
   ACCESS     not-accessible
   STATUS     mandatory
   DESCRIPTION
     "This entry controls the addition and deletion of 
      lpEngFcrc components."
::= { lpEngFcrc 1 }

lpEngFcrcRowStatusEntry OBJECT-TYPE
   SYNTAX     LpEngFcrcRowStatusEntry
   ACCESS     not-accessible
   STATUS     mandatory
   DESCRIPTION
     "A single entry in the table represents a single 
      lpEngFcrc component."
   INDEX {
      lpIndex,
      lpEngIndex,
      lpEngFcrcIndex }
::= { lpEngFcrcRowStatusTable 1 }

LpEngFcrcRowStatusEntry ::= SEQUENCE {
   lpEngFcrcRowStatus
      RowStatus,
   lpEngFcrcComponentName
      DisplayString,
   lpEngFcrcStorageType
      StorageType,
   lpEngFcrcIndex
      NonReplicated }

lpEngFcrcRowStatus OBJECT-TYPE
   SYNTAX     RowStatus 
   ACCESS     read-write
   STATUS     mandatory
   DESCRIPTION
     "This variable is used as the basis for SNMP naming of
      lpEngFcrc components.
      These components can be added and deleted."
::= { lpEngFcrcRowStatusEntry 1 }

lpEngFcrcComponentName OBJECT-TYPE
   SYNTAX     DisplayString 
   ACCESS     read-only
   STATUS     mandatory
   DESCRIPTION
     "This variable provides the component's string name for
      use with the ASCII Console Interface"
::= { lpEngFcrcRowStatusEntry 2 }

lpEngFcrcStorageType OBJECT-TYPE
   SYNTAX     StorageType 
   ACCESS     read-only
   STATUS     mandatory
   DESCRIPTION
     "This variable represents the storage type value for the
      lpEngFcrc tables."
::= { lpEngFcrcRowStatusEntry 4 }

lpEngFcrcIndex OBJECT-TYPE
   SYNTAX     NonReplicated 
   ACCESS     not-accessible
   STATUS     mandatory
   DESCRIPTION
     "This variable represents the index for the lpEngFcrc tables."
::= { lpEngFcrcRowStatusEntry 10 }

lpEngFcrcOperTable OBJECT-TYPE
   SYNTAX     SEQUENCE OF LpEngFcrcOperEntry
   ACCESS     not-accessible
   STATUS     mandatory
   DESCRIPTION
     "This group indicates the configuration of processor-wide frame 
      specific resources on a LogicalProcessor."
::= { lpEngFcrc 10 }

lpEngFcrcOperEntry OBJECT-TYPE
   SYNTAX     LpEngFcrcOperEntry
   ACCESS     not-accessible
   STATUS     mandatory
   DESCRIPTION
     "An entry in the lpEngFcrcOperTable."
   INDEX {
      lpIndex,
      lpEngIndex,
      lpEngFcrcIndex }
::= { lpEngFcrcOperTable 1 }

LpEngFcrcOperEntry ::= SEQUENCE {
   lpEngFcrcSubConnectionPoolAvailable
      Unsigned32,
   lpEngFcrcSubConnectionPoolUsage
      Unsigned32,
   lpEngFcrcLnnConnectionPoolAvailable
      Unsigned32,
   lpEngFcrcLnnConnectionPoolUsage
      Unsigned32,
   lpEngFcrcTxFrameMemoryAvailable
      Gauge32,
   lpEngFcrcTxFrameMemoryMinAvailable
      Gauge32,
   lpEngFcrcTxFrameMemoryCongestionState
      Gauge32,
   lpEngFcrcRxFrameMemoryAvailable
      Gauge32,
   lpEngFcrcRxFrameMemoryMinAvailable
      Gauge32,
   lpEngFcrcRxFrameMemoryCongestionState
      Gauge32,
   lpEngFcrcTxFrameMemoryMaxUsage
      Gauge32,
   lpEngFcrcTxFrameMemoryUsage
      Gauge32,
   lpEngFcrcRxFrameMemoryMaxUsage
      Gauge32,
   lpEngFcrcRxFrameMemoryUsage
      Gauge32 }

lpEngFcrcSubConnectionPoolAvailable OBJECT-TYPE
   SYNTAX     Unsigned32 (0..49152)
   ACCESS     read-only
   STATUS     mandatory
   DESCRIPTION
     "This attribute indicates the number of sub-connections available for 
      the LogicalProcessor. 
      
      A sub-connection is used for interworking the ATM services with 
      the frame oriented services such as Frame Relay and Path Oriented 
      Routing System (PORS). When a frame is received at a sub-
      connection, the frame header is modified to be compatible with the 
      service it is to be forwarded to. 
      
      This pool is used for connection oriented services only. Each of the 
      following components uses one sub-connection from this pool: 
      FrAtm/n Dlci/n Siwf
      McsMgr Frf5EpG/n Frf5Ep/n Lmi
      McsMgr Frf5EpG/n Frf5Ep/n Dlci/n
      
      Note: When the value of this attribute reaches zero, no more 
      connections are accepted for any of the services which utilize this 
      pool. To increase the size of this pool, use the Lp Eng Fcrc Ov 
      subConnectionPoolCapacity attribute."
::= { lpEngFcrcOperEntry 1 }

lpEngFcrcSubConnectionPoolUsage OBJECT-TYPE
   SYNTAX     Unsigned32 (0..49152)
   ACCESS     read-only
   STATUS     mandatory
   DESCRIPTION
     "This attribute indicates the number of sub-connections being 
      utilized by the LogicalProcessor.
      
      A sub-connection is used for interworking the ATM services with 
      the frame oriented services such as Frame Relay and Path Oriented 
      Routing System (PORS). When a frame is received at a sub-
      connection, the frame header is modified to be compatible with the 
      service it is to be forwarded to.
      
      This pool is used for connection oriented services only. Each of the 
      following components uses one sub-connection from this pool: 
      FrAtm/n Dlci/n Siwf
      McsMgr Frf5EpG/n Frf5Ep/n Lmi
      McsMgr Frf5EpG/n Frf5Ep/n Dlci/n"
::= { lpEngFcrcOperEntry 2 }

lpEngFcrcLnnConnectionPoolAvailable OBJECT-TYPE
   SYNTAX     Unsigned32 (0..2048)
   ACCESS     read-only
   STATUS     mandatory
   DESCRIPTION
     "This attribute indicates the number of resource records available for 
      the connections which utilize Logical Network Number (LNN) on 
      the LogicalProcessor.
      
      A logical network is a subset of Passport modules together with a 
      subset of trunks that interconnect those modules. It carries the 
      traffic for a defined set of network protocols. An LNN is used to 
      identify a logical network. The connectionless services which 
      utilize the logical networks require some processing at the 
      intermediate nodes. This pool is allocated at the intermediate nodes 
      to sustain these connectionless services.
      
      If the McsMgr DprsMcsEpG/n Ep/n EpD 
      transportConnectionPreference attribute is set to atmOnly, each 
      instance of the McsMgr DprsMcsEpG/n Ep/n component uses one 
      resource record from this pool, otherwise it does not use this pool.
      
      When the value of this attribute reaches zero, no more connections 
      are accepted for any of the services which utilize this pool. To 
      increase the size of this pool, use the Fcrc Ov 
      lnnConnectionPoolCapacity attribute."
::= { lpEngFcrcOperEntry 3 }

lpEngFcrcLnnConnectionPoolUsage OBJECT-TYPE
   SYNTAX     Unsigned32 (0..2048)
   ACCESS     read-only
   STATUS     mandatory
   DESCRIPTION
     "This attribute indicates the number of resource records being 
      utilized for the connections which use Logical Network Number 
      (LNN) on the LogicalProcessor.
      
      A logical network is a subset of Passport modules together with a 
      subset of trunks that interconnect those modules. It carries the 
      traffic for a defined set of network protocols. An LNN is used to 
      identify a logical network. The connectionless services which 
      utilize the logical networks require some processing at the 
      intermediate nodes. This pool is applied at the intermediate nodes to 
      sustain these connectionless services.
      
      If the McsMgr DprsMcsEpG/n Ep/n EpD 
      transportConnectionPreference attribute is set to atmOnly, each 
      instance of the McsMgr DprsMcsEpG/n Ep/n component uses one 
      resource record from this pool, otherwise it does not use this pool."
::= { lpEngFcrcOperEntry 4 }

lpEngFcrcTxFrameMemoryAvailable OBJECT-TYPE
   SYNTAX     Gauge32 (0..32767)
   ACCESS     read-only
   STATUS     obsolete
   DESCRIPTION
     "This attribute indicates the current availability of the transmit frame 
      memory (in units of frames). 
      
      The transmit frame memory is the memory available for storing 
      frames to be transmitted by this FP."
::= { lpEngFcrcOperEntry 5 }

lpEngFcrcTxFrameMemoryMinAvailable OBJECT-TYPE
   SYNTAX     Gauge32 (0..32767)
   ACCESS     read-only
   STATUS     obsolete
   DESCRIPTION
     "This attribute indicates the lowest availability of the transmit PQC/
      CQC frame memory (in units of frames). 
      
      The transmit frame memory is the memory available for storing 
      frames to be transmitted by this FP.
      
      This value is reset every 15 minutes and when the card is reset."
::= { lpEngFcrcOperEntry 6 }

lpEngFcrcTxFrameMemoryCongestionState OBJECT-TYPE
   SYNTAX     Gauge32 (0..3)
   ACCESS     read-only
   STATUS     mandatory
   DESCRIPTION
     "This attribute indicates the congestion state of the transmit frame 
      memory for this FP. 
      
      This attribute indicates which txFrameMemoryThresholds 
      corresponds to the current value of txFrameMemoryUsage. The 
      congestion state is used to determine if frames of a particular 
      discard priority (DP) are discarded before being queued for 
      transmit. 
      
      The congestion state of transmit frame memory is indicated by a 
      numeric value ranging from 3 to 0. When transmit frame memory is 
      in congestion state 'x', traffic with DP > 'x' is discarded before 
      transmit. Traffic with DP < 'x' may be queued for transmit, 
      depending on the congestion level of the transmit queue. Traffic 
      with DP = 'x' may be either queued or discarded depending on 
      how close the value of txFrameMemoryUsage is to the next 
      threshold as displayed in txFrameMemoryThresholds. For example, 
      DP=3 traffic is queued until the value indicated by 
      txFrameMemoryUsage equals the value indicated in 
      txFrameMemoryThresholds 3. At that point, DP=3 traffic is 
      discarded."
::= { lpEngFcrcOperEntry 7 }

lpEngFcrcRxFrameMemoryAvailable OBJECT-TYPE
   SYNTAX     Gauge32 (0..32767)
   ACCESS     read-only
   STATUS     obsolete
   DESCRIPTION
     "This attribute indicates the current availability of the receive frame 
      memory (in units of frames). 
      
      The receive frame memory is the memory available for storing 
      frames received by this FP."
::= { lpEngFcrcOperEntry 8 }

lpEngFcrcRxFrameMemoryMinAvailable OBJECT-TYPE
   SYNTAX     Gauge32 (0..32767)
   ACCESS     read-only
   STATUS     obsolete
   DESCRIPTION
     "This attribute indicates the lowest availability of the receive frame 
      memory (in units of frames).
      
      The receive frame memory is the memory available for storing 
      frames received by this FP.
      
      This value is reset every 15 minutes and when the card is reset."
::= { lpEngFcrcOperEntry 9 }

lpEngFcrcRxFrameMemoryCongestionState OBJECT-TYPE
   SYNTAX     Gauge32 (0..3)
   ACCESS     read-only
   STATUS     mandatory
   DESCRIPTION
     "This attribute indicates the congestion state of the receive frame 
      memory for this FP. 
      
      This attribute indicates which rxFrameMemoryThresholds 
      corresponds to the current value of rxFrameMemoryUsage. The 
      congestion state is used to determine if frames of a particular 
      discard priority (DP) are discarded before being queued for 
      processing on this FP. 
      
      The congestion state of receive frame memory is indicated by a 
      numeric value ranging from 3 to 0. When receive frame memory is 
      in congestion state 'x', traffic with DP > 'x' is discarded before 
      processing. Traffic with DP < 'x' may be queued for processing, 
      depending on the congestion level of the processor or bus queue. 
      Traffic with DP = 'x' may be either queued or discarded depending 
      on how close the value of rxFrameMemoryUsage is to the next 
      threshold as displayed in rxFrameMemoryThresholds. For example, 
      DP=3 traffic is queued until the value indicated by 
      rxFrameMemoryUsage equals the value indicated in 
      rxFrameMemoryThresholds 3. At that point, DP=3 traffic is 
      discarded."
::= { lpEngFcrcOperEntry 10 }

lpEngFcrcTxFrameMemoryMaxUsage OBJECT-TYPE
   SYNTAX     Gauge32 (0..32767)
   ACCESS     read-only
   STATUS     mandatory
   DESCRIPTION
     "This attribute indicates the maximum number which has recently 
      occurred for the txFrameMemoryUsage attribute. 
      
      On CQC-based ATM FPs, this number indicates the maximum 
      usage of transmit frames for all ports on this FP. 
      
      On ATM IP FPs, this number indicates the maximum usage of 
      transmit frames in the Passport Queue Controller (PQC) ASIC. 
      Queuing of frames for transmit only occurs in the PQC. 
      
      This value is reset to the current usage every 15 minutes and when 
      the card is reset."
::= { lpEngFcrcOperEntry 11 }

lpEngFcrcTxFrameMemoryUsage OBJECT-TYPE
   SYNTAX     Gauge32 (0..32767)
   ACCESS     read-only
   STATUS     mandatory
   DESCRIPTION
     "This attribute indicates the current number of transmit frames which 
      are in use for this FP. 
      
      On CQC-based ATM FPs, this number indicates the total transmit 
      frames which are in use for all ports on this FP. 
      
      On ATM IP FPs, this number indicates the number of transmit 
      frames which are in use in the Passport Queue Controller (PQC) 
      ASIC. Queuing of frames for transmit only occurs in the PQC."
::= { lpEngFcrcOperEntry 12 }

lpEngFcrcRxFrameMemoryMaxUsage OBJECT-TYPE
   SYNTAX     Gauge32 (0..32767)
   ACCESS     read-only
   STATUS     mandatory
   DESCRIPTION
     "This attribute indicates the maximum number which has recently 
      occurred for the rxFrameMemorySize attribute. 
      
      On CQC-based ATM FPs, this number indicates the maximum 
      usage of receive frames for all ports on this FP. 
      
      On ATM IP FPs, this number indicates the maximum usage of 
      received frames in the Passport Queue Controller (PQC) ASIC. 
      Queuing of received frames only occurs in the PQC. 
      
      This value is reset to the current usage every 15 minutes and when 
      the card is reset."
::= { lpEngFcrcOperEntry 13 }

lpEngFcrcRxFrameMemoryUsage OBJECT-TYPE
   SYNTAX     Gauge32 (0..32767)
   ACCESS     read-only
   STATUS     mandatory
   DESCRIPTION
     "This attribute indicates the current number of receive frames which 
      are in use for this FP. 
      
      On CQC-based ATM FPs, this number indicates the total receive 
      frames which are in use for all ports on this FP. 
      
      On ATM IP FPs, this number indicates the number of receive 
      frames which are in use in the Passport Queue Controller (PQC) 
      ASIC. Queuing of received frames only occurs in the PQC."
::= { lpEngFcrcOperEntry 14 }

lpEngFcrcTxFrThreshTable OBJECT-TYPE
   SYNTAX     SEQUENCE OF LpEngFcrcTxFrThreshEntry
   ACCESS     not-accessible
   STATUS     mandatory
   DESCRIPTION
     "This attribute is a vector which indicates the size and three discard 
      thresholds for transmit frame memory for this FP. The transmit 
      frame memory is used for storing frames to be transmitted by this 
      FP.
      
      The first value indicates the transmit frame memory size. This is 
      derived based on the total transmit memory capacity of this FP, and 
      the number of connections specified. 
      
      The current value of txFrameMemoryUsage together with the 
      vector of values in txFrameMemoryThresholds determines the 
      txFrameMemoryCongestionState. The congestion state determines 
      whether frames of a given discard priority (DP) are discarded or 
      queued for transmit. 
      
      When the txFrameMemoryUsage attribute is between threshold 0 
      and threshold 1, the txFrameMemoryCongestionState indicates the 
      value 0. In congestion state 0, traffic with DP > 0 is discarded. 
      Threshold 1 is set approximately at 90 percent of threshold 0, the 
      total transmit frame memory size. 
      
      When the txFrameMemoryUsage attribute is between threshold 1 
      and threshold 2, the txFrameMemoryCongestionState indicates the 
      value 1. In congestion state 1, traffic with DP > 1 is discarded. 
      Threshold 2 is set approximately at 85 percent of threshold 0, the 
      total transmit frame memory size. 
      
      When the txFrameMemoryUsage attribute is between threshold 2 
      and threshold 3, the txFrameMemoryCongestionState indicates the 
      value 2. In congestion state 2, traffic with DP > 2 is discarded. 
      Threshold 3 is set approximately at 75 percent of threshold 0, the 
      total transmit frame memory size. 
      
      When the txFrameMemoryUsage attribute is below threshold 3, the 
      txFrameMemoryCongestionState indicates the value 3. In 
      congestion state 3, traffic with DP=3 is queued."
::= { lpEngFcrc 442 }

lpEngFcrcTxFrThreshEntry OBJECT-TYPE
   SYNTAX     LpEngFcrcTxFrThreshEntry
   ACCESS     not-accessible
   STATUS     mandatory
   DESCRIPTION
     "An entry in the lpEngFcrcTxFrThreshTable."
   INDEX {
      lpIndex,
      lpEngIndex,
      lpEngFcrcIndex,
      lpEngFcrcTxFrThreshIndex }
::= { lpEngFcrcTxFrThreshTable 1 }

LpEngFcrcTxFrThreshEntry ::= SEQUENCE {
   lpEngFcrcTxFrThreshIndex
      Integer32,
   lpEngFcrcTxFrThreshValue
      Unsigned32 }

lpEngFcrcTxFrThreshIndex OBJECT-TYPE
   SYNTAX     Integer32 (0..3)
   ACCESS     not-accessible
   STATUS     mandatory
   DESCRIPTION
     "This variable represents the lpEngFcrcTxFrThreshTable
      specific index for the lpEngFcrcTxFrThreshTable."
::= { lpEngFcrcTxFrThreshEntry 1 }

lpEngFcrcTxFrThreshValue OBJECT-TYPE
   SYNTAX     Unsigned32 (0..32767)
   ACCESS     read-only
   STATUS     mandatory
   DESCRIPTION
     "This variable represents an individual value for the
      lpEngFcrcTxFrThreshTable."
::= { lpEngFcrcTxFrThreshEntry 2 }

lpEngFcrcRxFrThreshTable OBJECT-TYPE
   SYNTAX     SEQUENCE OF LpEngFcrcRxFrThreshEntry
   ACCESS     not-accessible
   STATUS     mandatory
   DESCRIPTION
     "This attribute is a vector which indicates the size and three discard 
      thresholds for receive frame memory for this FP. The receive frame 
      memory is used for storing frames received by this FP.
      
      The first value indicates the total receive frame memory size. This is 
      derived based on the total receive memory capacity of this FP, and 
      the number of connections specified. 
      
      The current value of rxFrameMemoryUsage together with the 
      vector of values in rxFrameMemoryThresholds determines the 
      rxFrameMemoryCongestionState. The congestion state determines 
      whether frames of a given discard priority (DP) are discarded or 
      queued for processing. 
      
      When the rxFrameMemoryUsage attribute is between threshold 0 
      and threshold 1, the rxFrameMemoryCongestionState indicates the 
      value 0. In congestion state 0, traffic with DP > 0 is discarded. 
      Threshold 1 is set approximately at 90 percent of threshold 0, the 
      total receive frame memory size. 
      
      When the rxFrameMemoryUsage attribute is between threshold 1 
      and threshold 2, the rxFrameMemoryCongestionState indicates the 
      value 1. In congestion state 1, traffic with DP > 1 is discarded. 
      Threshold 2 is set approximately at 85 percent of threshold 0, the 
      total receive frame memory size. 
      
      When the rxFrameMemoryUsage attribute is between threshold 2 
      and threshold 3, the rxFrameMemoryCongestionState indicates the 
      value 2. In congestion state 2, traffic with DP > 2 is discarded. 
      Threshold 3 is set approximately at 75 percent of threshold 0, the 
      total receive frame memory size. 
      
      When the rxFrameMemoryUsage attribute is below threshold 3, the 
      rxFrameMemoryCongestionState indicates the value 3. In 
      congestion state 3, traffic with DP=3 is queued."
::= { lpEngFcrc 446 }

lpEngFcrcRxFrThreshEntry OBJECT-TYPE
   SYNTAX     LpEngFcrcRxFrThreshEntry
   ACCESS     not-accessible
   STATUS     mandatory
   DESCRIPTION
     "An entry in the lpEngFcrcRxFrThreshTable."
   INDEX {
      lpIndex,
      lpEngIndex,
      lpEngFcrcIndex,
      lpEngFcrcRxFrThreshIndex }
::= { lpEngFcrcRxFrThreshTable 1 }

LpEngFcrcRxFrThreshEntry ::= SEQUENCE {
   lpEngFcrcRxFrThreshIndex
      Integer32,
   lpEngFcrcRxFrThreshValue
      Unsigned32 }

lpEngFcrcRxFrThreshIndex OBJECT-TYPE
   SYNTAX     Integer32 (0..3)
   ACCESS     not-accessible
   STATUS     mandatory
   DESCRIPTION
     "This variable represents the lpEngFcrcRxFrThreshTable
      specific index for the lpEngFcrcRxFrThreshTable."
::= { lpEngFcrcRxFrThreshEntry 1 }

lpEngFcrcRxFrThreshValue OBJECT-TYPE
   SYNTAX     Unsigned32 (0..32767)
   ACCESS     read-only
   STATUS     mandatory
   DESCRIPTION
     "This variable represents an individual value for the
      lpEngFcrcRxFrThreshTable."
::= { lpEngFcrcRxFrThreshEntry 2 }


-- Lp Eng Fcrc Override
-- This component holds provisionable engineering parameters used 
-- by frame services on this LogicalProcessor.

lpEngFcrcOv OBJECT IDENTIFIER ::= { lpEngFcrc 2 }



lpEngFcrcOvRowStatusTable OBJECT-TYPE
   SYNTAX     SEQUENCE OF LpEngFcrcOvRowStatusEntry
   ACCESS     not-accessible
   STATUS     mandatory
   DESCRIPTION
     "This entry controls the addition and deletion of 
      lpEngFcrcOv components."
::= { lpEngFcrcOv 1 }

lpEngFcrcOvRowStatusEntry OBJECT-TYPE
   SYNTAX     LpEngFcrcOvRowStatusEntry
   ACCESS     not-accessible
   STATUS     mandatory
   DESCRIPTION
     "A single entry in the table represents a single 
      lpEngFcrcOv component."
   INDEX {
      lpIndex,
      lpEngIndex,
      lpEngFcrcIndex,
      lpEngFcrcOvIndex }
::= { lpEngFcrcOvRowStatusTable 1 }

LpEngFcrcOvRowStatusEntry ::= SEQUENCE {
   lpEngFcrcOvRowStatus
      RowStatus,
   lpEngFcrcOvComponentName
      DisplayString,
   lpEngFcrcOvStorageType
      StorageType,
   lpEngFcrcOvIndex
      NonReplicated }

lpEngFcrcOvRowStatus OBJECT-TYPE
   SYNTAX     RowStatus 
   ACCESS     read-write
   STATUS     mandatory
   DESCRIPTION
     "This variable is used as the basis for SNMP naming of
      lpEngFcrcOv components.
      These components can be added and deleted."
::= { lpEngFcrcOvRowStatusEntry 1 }

lpEngFcrcOvComponentName OBJECT-TYPE
   SYNTAX     DisplayString 
   ACCESS     read-only
   STATUS     mandatory
   DESCRIPTION
     "This variable provides the component's string name for
      use with the ASCII Console Interface"
::= { lpEngFcrcOvRowStatusEntry 2 }

lpEngFcrcOvStorageType OBJECT-TYPE
   SYNTAX     StorageType 
   ACCESS     read-only
   STATUS     mandatory
   DESCRIPTION
     "This variable represents the storage type value for the
      lpEngFcrcOv tables."
::= { lpEngFcrcOvRowStatusEntry 4 }

lpEngFcrcOvIndex OBJECT-TYPE
   SYNTAX     NonReplicated 
   ACCESS     not-accessible
   STATUS     mandatory
   DESCRIPTION
     "This variable represents the index for the lpEngFcrcOv tables."
::= { lpEngFcrcOvRowStatusEntry 10 }

lpEngFcrcOvProvTable OBJECT-TYPE
   SYNTAX     SEQUENCE OF LpEngFcrcOvProvEntry
   ACCESS     not-accessible
   STATUS     mandatory
   DESCRIPTION
     "This group contains frame services provisionable engineering 
      parameters for this LogicalProcessor. Note that altering any of 
      these parameters will result in a card reset."
::= { lpEngFcrcOv 10 }

lpEngFcrcOvProvEntry OBJECT-TYPE
   SYNTAX     LpEngFcrcOvProvEntry
   ACCESS     not-accessible
   STATUS     mandatory
   DESCRIPTION
     "An entry in the lpEngFcrcOvProvTable."
   INDEX {
      lpIndex,
      lpEngIndex,
      lpEngFcrcIndex,
      lpEngFcrcOvIndex }
::= { lpEngFcrcOvProvTable 1 }

LpEngFcrcOvProvEntry ::= SEQUENCE {
   lpEngFcrcOvSubConnectionPoolCapacity
      Unsigned32,
   lpEngFcrcOvLnnConnectionPoolCapacity
      Unsigned32 }

lpEngFcrcOvSubConnectionPoolCapacity OBJECT-TYPE
   SYNTAX     Unsigned32 (0..49152 | 65535)
   ACCESS     read-write
   STATUS     mandatory
   DESCRIPTION
     "This attribute indicates the maximum number of sub-connections 
      for the LogicalProcessor. 
      
      A sub-connection is used for interworking the ATM services with 
      the frame oriented services such as Frame Relay and Path Oriented 
      Routing System (PORS). When a frame is received at a sub-
      connection, the frame header is modified to be compatible with the 
      service it is to be forwarded to.
      
      Due to limited resources, not all of the sub-connections requested 
      by this attribute may be allocated. The desired number of sub-
      connections allocated is indicated by the sum of fcrc 
      subConnectionPoolAvailable and fcrc subConnectionPoolUsage 
      attributes. 
      
      This pool is used for connection oriented services only. Each of the 
      following components uses one sub-connection from this pool: 
      FrAtm/n Dlci/n Siwf
      McsMgr Frf5EpG/n Frf5Ep/n Lmi
      McsMgr Frf5EpG/n Frf5Ep/n Dlci/n
      
      When the sub-connection pool is exhausted, no more connections 
      are accepted from the services which utilize this pool.
      
      Note: Ip Routing entries also compete for this memory.
      
      The maximum size of this pool is 8192 for CQC based cards. The 
      default cardDependent has the effect of setting 
      subConnectionPoolCapacity to 1024 for both CQC cards and 
      SGAF cards.

      VALUES (

      65535 = cardDependent

      )"
   DEFVAL     { 65535 }
::= { lpEngFcrcOvProvEntry 1 }

lpEngFcrcOvLnnConnectionPoolCapacity OBJECT-TYPE
   SYNTAX     Unsigned32 (0 | 1..2048)
   ACCESS     read-write
   STATUS     mandatory
   DESCRIPTION
     "This attribute indicates the maximum number of resource records 
      for the connections which utilize Logical Network Number (LNN) 
      on the LogicalProcessor.
      
      A logical network is a subset of passport modules together with a 
      subset of trunks that interconnect those modules. It carries the 
      traffic for a defined set of network protocols. An LNN is used to 
      identify a logical network. The connectionless services which 
      utilize the logical networks require some processing at the 
      intermediate nodes. This pool is allocated at the intermediate nodes 
      to sustain these connectionless services.
      
      If the McsMgr DprsMcsEpG/n Ep/n EpD 
      transportConnectionPreference attribute is set to atmOnly, each 
      instance of the McsMgr DprsMcsEpG/n Ep/n component uses one 
      resource record from this pool, otherwise it does not use this pool.
      
      Note: Frame and Cell queues also compete for this memory.
      
      Each DPRS instance requires two resource records and each VNS 
      instance requires one resource records from this pool. (A VNS 
      instance is an lnn combined with a trunk).
      
      The maximum size of this pool is 256 for CQC based cards. The 
      default cardDependent has the effect of setting 
      lnnConnectionPoolCapacity to 128 for CQC cards and 256 for 
      SGAF cards.

      VALUES (

      0 = cardDependent

      )"
   DEFVAL     { 0 }
::= { lpEngFcrcOvProvEntry 2 }


-- Lp Eng Fcrc Pqc
-- This component is used to view the usage of resources specific to 
-- frame services on a PQC based FP.

lpEngFcrcPqc OBJECT IDENTIFIER ::= { lpEngFcrc 3 }



lpEngFcrcPqcRowStatusTable OBJECT-TYPE
   SYNTAX     SEQUENCE OF LpEngFcrcPqcRowStatusEntry
   ACCESS     not-accessible
   STATUS     mandatory
   DESCRIPTION
     "This entry controls the addition and deletion of 
      lpEngFcrcPqc components."
::= { lpEngFcrcPqc 1 }

lpEngFcrcPqcRowStatusEntry OBJECT-TYPE
   SYNTAX     LpEngFcrcPqcRowStatusEntry
   ACCESS     not-accessible
   STATUS     mandatory
   DESCRIPTION
     "A single entry in the table represents a single 
      lpEngFcrcPqc component."
   INDEX {
      lpIndex,
      lpEngIndex,
      lpEngFcrcIndex,
      lpEngFcrcPqcIndex }
::= { lpEngFcrcPqcRowStatusTable 1 }

LpEngFcrcPqcRowStatusEntry ::= SEQUENCE {
   lpEngFcrcPqcRowStatus
      RowStatus,
   lpEngFcrcPqcComponentName
      DisplayString,
   lpEngFcrcPqcStorageType
      StorageType,
   lpEngFcrcPqcIndex
      NonReplicated }

lpEngFcrcPqcRowStatus OBJECT-TYPE
   SYNTAX     RowStatus 
   ACCESS     read-write
   STATUS     mandatory
   DESCRIPTION
     "This variable is used as the basis for SNMP naming of
      lpEngFcrcPqc components.
      These components can be added and deleted."
::= { lpEngFcrcPqcRowStatusEntry 1 }

lpEngFcrcPqcComponentName OBJECT-TYPE
   SYNTAX     DisplayString 
   ACCESS     read-only
   STATUS     mandatory
   DESCRIPTION
     "This variable provides the component's string name for
      use with the ASCII Console Interface"
::= { lpEngFcrcPqcRowStatusEntry 2 }

lpEngFcrcPqcStorageType OBJECT-TYPE
   SYNTAX     StorageType 
   ACCESS     read-only
   STATUS     mandatory
   DESCRIPTION
     "This variable represents the storage type value for the
      lpEngFcrcPqc tables."
::= { lpEngFcrcPqcRowStatusEntry 4 }

lpEngFcrcPqcIndex OBJECT-TYPE
   SYNTAX     NonReplicated 
   ACCESS     not-accessible
   STATUS     mandatory
   DESCRIPTION
     "This variable represents the index for the lpEngFcrcPqc tables."
::= { lpEngFcrcPqcRowStatusEntry 10 }

lpEngFcrcPqcOperTable OBJECT-TYPE
   SYNTAX     SEQUENCE OF LpEngFcrcPqcOperEntry
   ACCESS     not-accessible
   STATUS     mandatory
   DESCRIPTION
     "This group describes the usage of resources specific to frame 
      services on a PQC based FP."
::= { lpEngFcrcPqc 10 }

lpEngFcrcPqcOperEntry OBJECT-TYPE
   SYNTAX     LpEngFcrcPqcOperEntry
   ACCESS     not-accessible
   STATUS     mandatory
   DESCRIPTION
     "An entry in the lpEngFcrcPqcOperTable."
   INDEX {
      lpIndex,
      lpEngIndex,
      lpEngFcrcIndex,
      lpEngFcrcPqcIndex }
::= { lpEngFcrcPqcOperTable 1 }

LpEngFcrcPqcOperEntry ::= SEQUENCE {
   lpEngFcrcPqcIpRoutesPoolSize
      Gauge32,
   lpEngFcrcPqcIpRoutesPoolUsage
      Gauge32,
   lpEngFcrcPqcIpRoutesPoolAvailableEst
      Gauge32 }

lpEngFcrcPqcIpRoutesPoolSize OBJECT-TYPE
   SYNTAX     Gauge32 (0..100000)
   ACCESS     read-only
   STATUS     mandatory
   DESCRIPTION
     "This attribute indicates the number of IP routing entries permitted 
      on the Logical Processor. If there are enough resources on the card, 
      this value is equal to the provisioned attribute (in Fcrc Pqc Ov) 
      ipRoutesPoolCapacity."
::= { lpEngFcrcPqcOperEntry 1 }

lpEngFcrcPqcIpRoutesPoolUsage OBJECT-TYPE
   SYNTAX     Gauge32 (0..100000)
   ACCESS     read-only
   STATUS     mandatory
   DESCRIPTION
     "This attribute represents the current number of IP routing entries 
      that are in use."
::= { lpEngFcrcPqcOperEntry 2 }

lpEngFcrcPqcIpRoutesPoolAvailableEst OBJECT-TYPE
   SYNTAX     Gauge32 (0..100000)
   ACCESS     read-only
   STATUS     mandatory
   DESCRIPTION
     "Each IP routing resource can hold between one and three IP 
      routing entries. Therefore, it is not possible to know exactly 
      how many more IP routing entries can be added to the IP 
      routing table. This attribute specifies the estimated number of 
      IP routing entries that are available on the Logical Processor. 
      It is an approximation based on the current average number 
      of IP routing entries per IP routing resource."
::= { lpEngFcrcPqcOperEntry 3 }


-- Lp Eng Fcrc Pqc Ov
-- This component is used to configure resources specific to frame 
-- services on a PQC based Logical Processor.

lpEngFcrcPqcOv OBJECT IDENTIFIER ::= { lpEngFcrcPqc 2 }



lpEngFcrcPqcOvRowStatusTable OBJECT-TYPE
   SYNTAX     SEQUENCE OF LpEngFcrcPqcOvRowStatusEntry
   ACCESS     not-accessible
   STATUS     mandatory
   DESCRIPTION
     "This entry controls the addition and deletion of 
      lpEngFcrcPqcOv components."
::= { lpEngFcrcPqcOv 1 }

lpEngFcrcPqcOvRowStatusEntry OBJECT-TYPE
   SYNTAX     LpEngFcrcPqcOvRowStatusEntry
   ACCESS     not-accessible
   STATUS     mandatory
   DESCRIPTION
     "A single entry in the table represents a single 
      lpEngFcrcPqcOv component."
   INDEX {
      lpIndex,
      lpEngIndex,
      lpEngFcrcIndex,
      lpEngFcrcPqcIndex,
      lpEngFcrcPqcOvIndex }
::= { lpEngFcrcPqcOvRowStatusTable 1 }

LpEngFcrcPqcOvRowStatusEntry ::= SEQUENCE {
   lpEngFcrcPqcOvRowStatus
      RowStatus,
   lpEngFcrcPqcOvComponentName
      DisplayString,
   lpEngFcrcPqcOvStorageType
      StorageType,
   lpEngFcrcPqcOvIndex
      NonReplicated }

lpEngFcrcPqcOvRowStatus OBJECT-TYPE
   SYNTAX     RowStatus 
   ACCESS     read-only
   STATUS     mandatory
   DESCRIPTION
     "This variable is used as the basis for SNMP naming of
      lpEngFcrcPqcOv components.
      These components cannot be added nor deleted."
::= { lpEngFcrcPqcOvRowStatusEntry 1 }

lpEngFcrcPqcOvComponentName OBJECT-TYPE
   SYNTAX     DisplayString 
   ACCESS     read-only
   STATUS     mandatory
   DESCRIPTION
     "This variable provides the component's string name for
      use with the ASCII Console Interface"
::= { lpEngFcrcPqcOvRowStatusEntry 2 }

lpEngFcrcPqcOvStorageType OBJECT-TYPE
   SYNTAX     StorageType 
   ACCESS     read-only
   STATUS     mandatory
   DESCRIPTION
     "This variable represents the storage type value for the
      lpEngFcrcPqcOv tables."
::= { lpEngFcrcPqcOvRowStatusEntry 4 }

lpEngFcrcPqcOvIndex OBJECT-TYPE
   SYNTAX     NonReplicated 
   ACCESS     not-accessible
   STATUS     mandatory
   DESCRIPTION
     "This variable represents the index for the lpEngFcrcPqcOv tables."
::= { lpEngFcrcPqcOvRowStatusEntry 10 }

lpEngFcrcPqcOvProvTable OBJECT-TYPE
   SYNTAX     SEQUENCE OF LpEngFcrcPqcOvProvEntry
   ACCESS     not-accessible
   STATUS     mandatory
   DESCRIPTION
     "This group is used for fine tuning resource configuration of frame 
      services on a PQC based Logical Processor."
::= { lpEngFcrcPqcOv 10 }

lpEngFcrcPqcOvProvEntry OBJECT-TYPE
   SYNTAX     LpEngFcrcPqcOvProvEntry
   ACCESS     not-accessible
   STATUS     mandatory
   DESCRIPTION
     "An entry in the lpEngFcrcPqcOvProvTable."
   INDEX {
      lpIndex,
      lpEngIndex,
      lpEngFcrcIndex,
      lpEngFcrcPqcIndex,
      lpEngFcrcPqcOvIndex }
::= { lpEngFcrcPqcOvProvTable 1 }

LpEngFcrcPqcOvProvEntry ::= SEQUENCE {
   lpEngFcrcPqcOvIpRoutesPoolCapacity
      Unsigned32 }

lpEngFcrcPqcOvIpRoutesPoolCapacity OBJECT-TYPE
   SYNTAX     Unsigned32 (0..100000)
   ACCESS     read-write
   STATUS     mandatory
   DESCRIPTION
     "This attribute indicates the number of desired IP routing entries for 
      the Logical Processor. It is used to determine the number of IP 
      routing resources to be allocated on the card. 
      
      Each IP routing resource can hold between one and three IP routing 
      entries. To calculate the number of IP routing resources required, an 
      average of 2 IP routing entries per IP routing resource is used.
      
      If there are not enough resources on the card, a smaller pool is 
      allocated. Operational attribute (in Fcrc Pqc) ipRoutesPoolSize 
      indicates the actual size of the pool."
   DEFVAL     { 4096 }
::= { lpEngFcrcPqcOvProvEntry 1 }




-- 
-- Version and Compliance statements
-- 



-- Object-Group Statement:
-- A list of all current accessible leaf objects.

-- OBJECTS { lpEngArcAqmOvMaxVirtualLinks,
--           lpEngArcCqcOvCdvReduction,
--           lpEngArcRxCellMemoryMaxUsage,
--           lpEngFcrcTxFrameMemoryUsage,
--           lpEngArcAqmOvPortCongestionPolicy,
--           lpEngFcrcPqcIpRoutesPoolSize,
--           lpEngArcRowStatus,
--           lpEngFcrcRxFrameMemoryUsage,
--           lpEngArcTxCellMemoryAllocation,
--           lpEngFcrcRxFrThreshValue,
--           lpEngFcrcPqcOvRowStatus,
--           lpEngArcTxCellMemoryCongestionState,
--           lpEngFcrcOvSubConnectionPoolCapacity,
--           lpEngArcAqmComponentName,
--           lpEngArcRxCellMemoryUsage,
--           lpEngArcMulticastBranchesAvailable,
--           lpEngFcrcRxFrameMemoryMaxUsage,
--           lpEngArcAqmTxCellThreshValue,
--           lpEngArcAqmOvStorageType,
--           lpEngArcAqmConnectionPoolUsage,
--           lpEngFcrcLnnConnectionPoolAvailable,
--           lpEngArcCqcOvPortCongestionPolicy,
--           lpEngArcOvMulticastBranchesCapacity,
--           lpEngArcComponentName,
--           lpEngFcrcPqcOvIpRoutesPoolCapacity,
--           lpEngFcrcTxFrThreshValue,
--           lpEngFcrcOvLnnConnectionPoolCapacity,
--           lpEngArcAqmOvHighPriorityEpdOffset,
--           lpEngArcTxCellThreshValue,
--           lpEngArcOvStorageType,
--           lpEngArcCqcCdvReduction,
--           lpEngArcCqcOvShapingScalingFactor,
--           lpEngArcCqcComponentName,
--           lpEngFcrcPqcStorageType,
--           lpEngArcAqmTxCellMemoryCongestionState,
--           lpEngFcrcRowStatus,
--           lpEngArcRxCellMemoryAllocation,
--           lpEngFcrcStorageType,
--           lpEngArcCqcOvStorageType,
--           lpEngArcRxCellMemoryCongestionState,
--           lpEngArcAqmOvConnectionPoolCapacity,
--           lpEngArcAqmOvVirtualLinkGranularity,
--           lpEngArcCqcOvConnCapValue,
--           lpEngArcAqmOvRowStatus,
--           lpEngFcrcOvComponentName,
--           lpEngArcTotalConnectionPoolUsage,
--           lpEngFcrcPqcRowStatus,
--           lpEngArcAqmMaxVirtualLinks,
--           lpEngFcrcTxFrameMemoryCongestionState,
--           lpEngFcrcComponentName,
--           lpEngArcOvRowStatus,
--           lpEngFcrcPqcOvComponentName,
--           lpEngFcrcPqcIpRoutesPoolAvailableEst,
--           lpEngArcOvTxCellMemoryAllocation,
--           lpEngArcRxCellThreshValue,
--           lpEngArcAqmTxCellMemoryMaxUsage,
--           lpEngFcrcOvStorageType,
--           lpEngArcAqmVirtualLinkUsage,
--           lpEngArcCqcOvRowStatus,
--           lpEngFcrcSubConnectionPoolUsage,
--           lpEngArcAqmStorageType,
--           lpEngArcOvRxCellMemoryAllocation,
--           lpEngArcTxCellMemoryMaxUsage,
--           lpEngArcCqcOvPerVcQueueInterfaces,
--           lpEngArcTotalConnectionPoolAvailable,
--           lpEngArcAqmTxCellMemoryUsage,
--           lpEngArcOvComponentName,
--           lpEngFcrcPqcOvStorageType,
--           lpEngArcStorageType,
--           lpEngArcOvTotalConnectionPoolCapacity,
--           lpEngArcAqmVirtualLinkGranularity,
--           lpEngArcCqcOvComponentName,
--           lpEngFcrcRxFrameMemoryCongestionState,
--           lpEngArcTxCellMemoryUsage,
--           lpEngFcrcPqcComponentName,
--           lpEngArcAqmOvLowPriorityEpdOffset,
--           lpEngFcrcOvRowStatus,
--           lpEngArcCqcStorageType,
--           lpEngFcrcTxFrameMemoryMaxUsage,
--           lpEngFcrcSubConnectionPoolAvailable,
--           lpEngArcCqcRowStatus,
--           lpEngArcAqmOvComponentName,
--           lpEngArcMulticastBranchesUsage,
--           lpEngFcrcPqcIpRoutesPoolUsage,
--           lpEngArcAqmRowStatus,
--           lpEngArcAqmConnectionPoolAvailable,
--           lpEngFcrcLnnConnectionPoolUsage }
-- STATUS  mandatory
-- DESCRIPTION
--   "A list of all current accessible leaf objects."

atmBaseGroup OBJECT IDENTIFIER ::= { atmBaseMIB 1 }
atmBaseGroupBE OBJECT IDENTIFIER ::= { atmBaseGroup 5 }
atmBaseGroupBE00 OBJECT IDENTIFIER ::= { atmBaseGroupBE 1 }
atmBaseGroupBE00A OBJECT IDENTIFIER ::= { atmBaseGroupBE00 2 }



-- Agent-Capabilities Statement:

-- PRODUCT-RELEASE "Passport Release 7.0 AtmBase."
-- STATUS          mandatory
-- DESCRIPTION     "AtmBase MIB: MIB Version BE00A,
--                  Software Version BG00S4C."
-- SUPPORTS        Nortel-Magellan-Passport-AtmBaseMIB
--    INCLUDES     { atmBaseGroupBE00A }

atmBaseCapabilities OBJECT IDENTIFIER ::= { atmBaseMIB 3 }
atmBaseCapabilitiesBE OBJECT IDENTIFIER ::= { atmBaseCapabilities 5 }
atmBaseCapabilitiesBE00 OBJECT IDENTIFIER ::= { atmBaseCapabilitiesBE 1 }
atmBaseCapabilitiesBE00A OBJECT IDENTIFIER ::= { atmBaseCapabilitiesBE00 2 }





END
