-- *****************************************************************
-- CISCO-BRIDGE-CAPABILITY.my:
-- Cisco BRIDGE-MIB AGENT-CAPABILITIES
--
-- August 1994, Jeffrey T. Johnso
--
-- Copyright (c) 1994, 2006, 2007 by Cisco Systems, Inc.
-- All rights reserved.
-- *****************************************************************

CISCO-BRIDGE-CAPABILITY DEFINITIONS ::= BEGIN

IMPORTS
        MODULE-IDENTITY
                FROM SNMPv2-SMI
        AGENT-CAPABILITIES
                FROM SNMPv2-CONF
        ciscoAgentCapability
                FROM CISCO-SMI;

ciscoBridgeCapability MODULE-IDENTITY
        LAST-UPDATED        "200703280000Z"
        ORGANIZATION        "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of BRIDGE-MIB."

        REVISION        "200703280000Z"
        DESCRIPTION
                "Added VARIATION clause of dot1dStaticStatus for
                capability statement ciscoBridgeCapCatOSV08R0601."

        REVISION        "200606120000Z"
        DESCRIPTION
                "Added capability statement
                 ciscoBridgeCapCatOSV08R0601.
                 Commented out ciscoBridgeCapabilityV10R02."

        REVISION        "9408180000Z"
        DESCRIPTION
                "Initial version of this MIB module."
        ::= { ciscoAgentCapability 106 }

-- ciscoBridgeCapabilityV10R02 AGENT-CAPABILITIES
--     PRODUCT-RELEASE     "Cisco IOS 10.2"
--     STATUS              current
--     DESCRIPTION         "IOS 10.2 Bridge MIB capabilities"
-- 
--     SUPPORTS            BRIDGE-MIB
--         INCLUDES        { dot1dBaseGroup, dot1dStpGroup,
--                           dot1dSrGroup, dot1dTpGroup }
-- 
--         VARIATION       dot1dBasePortDelayExceededDiscards
--             SYNTAX      INTEGER (0..0)
--             DESCRIPTION "Hardcoded to 0"
-- 
--         VARIATION       dot1dTpFdbStatus
--             SYNTAX      INTEGER { other(1), learned(3),
--                                   self(4), mgmt(5) }
--             DESCRIPTION "Unable to detect all states"
-- 
--         VARIATION       dot1dTpPortInDiscards
--             SYNTAX      INTEGER (0..0)
--             DESCRIPTION "Hardcoded to 0"
-- 
--         VARIATION       dot1dBaseType
--             SYNTAX      INTEGER { srt(4) }
--             DESCRIPTION "Unable to detect all states"
-- 
--         ::= { ciscoBridgeCapability 1 }

ciscoBridgeCapCatOSV08R0601 AGENT-CAPABILITIES
    PRODUCT-RELEASE     "Cisco CatOS 8.6(1) on Catalyst 6000/6500
                         and Cisco 7600 series devices."
    STATUS              current
    DESCRIPTION         "BRIDGE-MIB capabilities."

    SUPPORTS            BRIDGE-MIB
        INCLUDES        {
                          dot1dBaseBridgeGroup,
                          dot1dBasePortGroup,
                          dot1dStpBridgeGroup,
                          dot1dStpPortGroup2,
                          dot1dStpPortGroup3,
                          dot1dTpBridgeGroup,
                          dot1dTpFdbGroup,
                          dot1dStaticGroup,
                          dot1dNotificationGroup
                        }

        VARIATION       newRoot -- NOTIFICATION-TYPE
            DESCRIPTION
                "Additional VarBinds are appended to notification
                 newRoot depends on the value of stpxSpanningTreeType.

                 'pvstPlus',
                 'rapidPvstPlus' - vtpVlanIndex
                 'mistp',
                 'mistpPvstPlus' - stpxMISTPInstanceIndex
                 'mst' - stpxMSTInstanceIndex
                 "

        VARIATION       topologyChange -- NOTIFICATION-TYPE
            DESCRIPTION
                "Additional VarBinds are appended to notification
                 topologyChange depends on the value of
                 stpxSpanningTreeType.

                 'pvstPlus',
                 'rapidPvstPlus' - vtpVlanIndex, ifName
                 'mistp',
                 'mistpPvstPlus' - stpxMISTPInstanceIndex, ifName
                 'mst' - stpxMSTInstanceIndex, ifName
                 "
        VARIATION       dot1dStaticStatus
            DESCRIPTION 
                "The default value is deleteOnReset(4)."

    ::= { ciscoBridgeCapability 2 }

END
