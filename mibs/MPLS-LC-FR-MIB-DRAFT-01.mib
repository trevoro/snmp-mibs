-- extracted from draft-ietf-mpls-lc-if-mib-01.txt
-- at Tue Feb  3 06:16:36 2004

MPLS-LC-FR-MIB-DRAFT-01 DEFINITIONS ::= BEGIN
IMPORTS
   MODULE-IDENTITY, OBJECT-TYPE
      FROM SNMPv2-SMI
   MODULE-COMPLIANCE, OBJECT-GROUP
      FROM SNMPv2-CONF
   RowStatus, StorageType
      FROM SNMPv2-TC
   mplsInterfaceIndex
      FROM MPLS-LSR-STD-MIB
   DLCI
      FROM FRAME-RELAY-DTE-MIB
   mplsStdMIB
      FROM MPLS-TC-STD-MIB
   ;

mplsLcFrMIB MODULE-IDENTITY
   LAST-UPDATED "200401301200Z"  -- 30 January 2004 12:00:00 GMT
   ORGANIZATION "Multiprotocol Label Switching (MPLS) Working Group"
   CONTACT-INFO
       "        Thomas D. Nadeau
        Postal: Cisco Systems, Inc.
                250 Apollo Drive
                Chelmsford, MA 01824
        Tel:    +1-978-244-3051
        Email:  tnadeau@cisco.com
                Subrahmanya Hegde                
        Postal: Cisco Systems, Inc.
                225 East Tazman Drive
        Tel:    +1-408-525-6562
        Email:  subrah@cisco.com      
        General comments should be sent to mpls@uu.net
       "
   DESCRIPTION
       "This MIB contains managed object definitions for
        MPLS Label Controlled Frame-Relay interfaces as defined 
        in RFC3034."
   
   -- Revision history.
   REVISION
        "200401301200Z"  -- 30 January 2004 12:00:00 GMT
   DESCRIPTION
       "Initial draft revision."
   ::= { mplsStdMIB 1 } -- To Be Assigned by IANA, maybe 7

-- Top level components of this MIB.
-- Tables, Scalars, Notifications, Conformance

mplsLcFrNotifications OBJECT IDENTIFIER ::= { mplsLcFrMIB 0 }
mplsLcFrObjects       OBJECT IDENTIFIER ::= { mplsLcFrMIB 1 }
mplsLcFrConformance   OBJECT IDENTIFIER ::= { mplsLcFrMIB 2 }

-- MPLS LC-FR Interface Configuration Table.
mplsLcFrIfConfTable  OBJECT-TYPE
   SYNTAX        SEQUENCE OF MplsLcFrIfConfEntry
   MAX-ACCESS    not-accessible
   STATUS        current
   DESCRIPTION
       "This table specifies per-interface MPLS LC-FR 
        capability and associated information. In particular,
        this table extends the MPLS-LSR MIB's 
        mplsInterfaceConfTable."
   ::= { mplsLcFrObjects 1 }

mplsLcFrIfConfEntry OBJECT-TYPE
   SYNTAX        MplsLcFrIfConfEntry
   MAX-ACCESS    not-accessible
   STATUS        current
   DESCRIPTION
       "An entry in this table is created by an LSR for
        every interface capable of supporting MPLS LC-FR. 
        Each entry in this table will exist only if a
        corresponding entry in ifTable and mplsInterfaceConfTable
        exist. If the associated entries in ifTable and 
        mplsInterfaceConfTable are deleted, the corresponding 
        entry in this table must also be deleted shortly 
        thereafter. "
   INDEX       { mplsInterfaceIndex }
      ::= { mplsLcFrIfConfTable 1 }

MplsLcFrIfConfEntry ::= SEQUENCE {
   mplsLcFrTrafficMinDlci   DLCI,
   mplsLcFrTrafficMaxDlci   DLCI,
   mplsLcFrCtrlMinDlci      DLCI,
   mplsLcFrCtrlMaxDlci      DLCI,
   mplsLcFrIfConfRowStatus  RowStatus,
   mplsLcFrIfConfStoreType  StorageType
}

mplsLcFrTrafficMinDlci OBJECT-TYPE
   SYNTAX        DLCI
   MAX-ACCESS    read-create
   STATUS        current
   DESCRIPTION
       "This is the minimum DLCI value over which this
        LSR is willing to accept traffic on this 
        interface."
   ::= { mplsLcFrIfConfEntry 1 }

mplsLcFrTrafficMaxDlci OBJECT-TYPE
   SYNTAX        DLCI
   MAX-ACCESS    read-create
   STATUS        current
   DESCRIPTION
       "This is the max DLCI value over which this
        LSR is willing to accept traffic on this 
        interface."
   ::= { mplsLcFrIfConfEntry 2 }

mplsLcFrCtrlMinDlci OBJECT-TYPE
   SYNTAX        DLCI
   MAX-ACCESS    read-create
   STATUS        current
   DESCRIPTION
       "This is the min DLCI value over which this
        LSR is willing to accept control traffic 
        on this interface."
   ::= { mplsLcFrIfConfEntry 3 }

mplsLcFrCtrlMaxDlci OBJECT-TYPE
   SYNTAX        DLCI
   MAX-ACCESS    read-create
   STATUS        current
   DESCRIPTION
       "This is the max DLCI value over which this
        LSR is willing to accept control traffic 
        on this interface."
   ::= { mplsLcFrIfConfEntry 4 }

mplsLcFrIfConfRowStatus OBJECT-TYPE
   SYNTAX        RowStatus
   MAX-ACCESS    read-create
   STATUS        current
   DESCRIPTION
       "This is object is used to create and 
        delete entries in this table. When configuring
        entries in this table, the corresponding
        corresponding ifEntry and mplsInterfaceConfEntry
        MUST exist before hand. If an entry is attempted
        to be created by a manager for a corresponding
        mplsInterfaceConfEntry that does not support LC-FR,
        the agent MUST return an inconsistentValue error.
        If this table is implemented read-only, then the
        agent must set this object to active(1) when this
        row is made active. If this table is implemented
        writable, then an agent MUST not allow modification
        to its objects once this value is set to active(1)."
   ::= { mplsLcFrIfConfEntry 5 }

 mplsLcFrIfConfStoreType OBJECT-TYPE
   SYNTAX        StorageType
   MAX-ACCESS    read-create
   STATUS        current
   DESCRIPTION
       "This SNMP storage type for this entry. All objects
        are writable for permanent entries."
   ::= { mplsLcFrIfConfEntry 6 }

-- End of mplsLcFrIfConfTable

-- Module compliance.

mplsLcFrCompliances
   OBJECT IDENTIFIER ::= { mplsLcFrConformance 1 }

mplsLcFrGroups
   OBJECT IDENTIFIER ::= { mplsLcFrConformance 2 }

mplsLcFrModuleCompliance MODULE-COMPLIANCE
   STATUS current
   DESCRIPTION
       "Compliance statement for agents that support
        MPLS LC-FR Interfaces."

   MODULE -- this module
      -- The mandatory groups have to be implemented
      -- by all LSRs.  However, they may all be supported
      -- as read-only objects in the case where manual
      -- configuration is unsupported.
      MANDATORY-GROUPS {
         mplsLcFrIfGroup
      }

      -- mplsLcFrIfConfTable
          
      OBJECT     mplsLcFrTrafficMinDlci
      MIN-ACCESS  read-only
      DESCRIPTION
          "Write access is not required."

      OBJECT     mplsLcFrTrafficMaxDlci
      MIN-ACCESS  read-only
      DESCRIPTION
          "Write access is not required."

      OBJECT      mplsLcFrCtrlMinDlci   
      MIN-ACCESS  read-only
      DESCRIPTION
          "Write access is not required."

      OBJECT      mplsLcFrCtrlMaxDlci   
      MIN-ACCESS  read-only
      DESCRIPTION
          "Write access is not required."

      OBJECT      mplsLcFrIfConfRowStatus
      MIN-ACCESS  read-only
      DESCRIPTION
          "Write access is not required."

      OBJECT      mplsLcFrIfConfStoreType
      MIN-ACCESS  read-only
      DESCRIPTION
          "Write access is not required."
   ::= { mplsLcFrCompliances 1 }

-- Units of conformance.

mplsLcFrIfGroup OBJECT-GROUP
   OBJECTS {
        mplsLcFrTrafficMinDlci,
        mplsLcFrTrafficMaxDlci, 
        mplsLcFrCtrlMinDlci,    
        mplsLcFrCtrlMaxDlci,    
        mplsLcFrIfConfRowStatus,
        mplsLcFrIfConfStoreType
    }
   STATUS  current

   DESCRIPTION
          "Collection of objects needed for MPLS LC-FR
           interface configuration."
   ::= { mplsLcFrGroups 1 }
END 

--    
--    Copyright (C) The Internet Society (2001).  All Rights Reserved.
--    
--    This document and translations of it may be copied and furnished
--    to others, and derivative works that comment on or otherwise
--    explain it or assist in its implementation may be prepared,
--    copied, published and distributed, in whole or in part, without
--    restriction of any kind, provided that the above copyright notice
--    and this paragraph are included on all such copies and derivative
--    works.  However, this document itself may not be modified in any
--    way, such as by removing the copyright notice or references to the
--    Internet Society or other Internet organizations, except as needed
--    for the  purpose of developing Internet standards in which case
--    the procedures for copyrights defined in the Internet Standards
--    process must be followed, or as required to translate it into
--    languages other than English.
--    
--    The limited permissions granted above are perpetual and will not
--    be revoked by the Internet Society or its successors or assigns.
--    This document and the information contained herein is provided on
--    an "AS IS" basis and THE INTERNET SOCIETY AND THE INTERNET
--    ENGINEERING TASK FORCE DISCLAIMS ALL WARRANTIES, EXPRESS OR
--    IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
--
