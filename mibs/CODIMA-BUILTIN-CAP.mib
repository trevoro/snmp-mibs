CODIMA-BUILTIN-CAP DEFINITIONS ::= BEGIN

IMPORTS
     AGENT-CAPABILITIES
          FROM SNMPv2-CONF
     MODULE-IDENTITY
          FROM SNMPv2-SMI
     codimaCaps
          FROM CODIMA-GLOBAL-REG;

expressCapMIB MODULE-IDENTITY
     LAST-UPDATED "200306171127Z"
     ORGANIZATION "CODIMA Technologies Ltd"
     CONTACT-INFO
          "support@codimatech.com"
     DESCRIPTION
          "MIB module for CODIMA Express agent built-in capabilities."
     REVISION "200306171127Z"
     DESCRIPTION
          "The initial version"
     ::= { codimaCaps 1 }



expressBuiltInCaps AGENT-CAPABILITIES

     PRODUCT-RELEASE
          "CODIMA Express v2.5"
     STATUS current
     DESCRIPTION
          "CODIMA Express Agent built-in capabilities."


     SUPPORTS SNMPv2-MIB
     INCLUDES {
          systemGroup,
          snmpGroup }

     VARIATION coldStart
       DESCRIPTION
          "A coldStart trap is generated on all
          reboots."

     SUPPORTS SNMP-TARGET-MIB
     INCLUDES {
          snmpTargetBasicGroup,
          snmpTargetResponseGroup }


     SUPPORTS SNMP-NOTIFICATION-MIB
     INCLUDES {
          snmpNotifyGroup,
          snmpNotifyFilterGroup }


     SUPPORTS CODIMA-EXPRESS-MIB
     INCLUDES {
          ctrlTimeGroup,
          slBaseGroup,
          slBroadcastGroup,
          slDerivedGroup,
          slEthernetGroup,
          slIcmpGroup,
          slPortGroup,
          ssBaseGroup,
          ssBroadcastGroup,
          ssDerivedGroup,
          ssEthernetGroup,
          ssIcmpGroup,
          ssPortGroup,
          mlBaseGroup,
          mlDerivedGroup,
          mlDuplexGroup,
          mlEthernetGroup,
          mlIcmpGroup,
          mlProtocolGroup,
          msBaseGroup,
          msDerivedGroup,
          msDuplexGroup,
          msEthernetGroup,
          msIcmpGroup,
          msProtocolGroup,
          mplBaseGroup,
          mplDerivedGroup,
          mplDuplexGroup,
          mplProtocolGroup,
          mpsBaseGroup,
          mpsDerivedGroup,
          mpsDuplexGroup,
          mpsProtocolGroup,
          ilBaseGroup,
          ilDerivedGroup,
          ilIcmpGroup,
          isBaseGroup,
          isDerivedGroup,
          isIcmpGroup,
          iplBaseGroup,
          iplDerivedGroup,
          iplIcmpGroup,
          ipsBaseGroup,
          ipsDerivedGroup,
          ipsIcmpGroup,
          plBaseGroup,
          plDerivedGroup,
          psBaseGroup,
          psDerivedGroup,
          netChannelLongTermGroup,
          netChannelShortTermGroup,
          vlanLongTermGroup,
          vlanShortTermGroup,
          alarmObjectGroup,
          alarmNotifyGroup }

     ::= { expressCapMIB 1 }

END
